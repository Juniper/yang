/*
 * Copyright (c) 2024 Juniper Networks, Inc.
 * All rights reserved.
 */
 module junos-nfx-conf-dynamic-profiles {
   namespace "http://yang.juniper.net/junos-nfx/conf/dynamic-profiles";

   prefix jc-dynamic-profiles;

   import junos-common-types {
     prefix jt;
     revision-date 2023-01-01;
   }

   import junos-nfx-conf-root {
     prefix jc;
     revision-date 2023-01-01;
   }

   organization "Juniper Networks, Inc.";

   contact "yang-support@juniper.net";

   description "Junos dynamic-profiles configuration module";

   revision 2023-01-01 {
     description "Junos: 23.4R2.13";
   }

   augment /jc:configuration {
     uses dynamic-profiles-group;
   }
   augment /jc:configuration/jc:groups {
     uses dynamic-profiles-group;
   }
   grouping dynamic-profiles-group {
     list dynamic-profiles {
       key name;
       ordered-by user;
       description "Dynamic profiles configuration";
       uses juniper-dynamic-profile-object;
     }
   }
   grouping juniper-dynamic-profile-object {
     leaf name {
       description "Name for dynamic profile";
       type string {
         length "1 .. 80";
       }
     }
     uses apply-advanced;
     leaf version-alias {
       description "Dynamic profile version alias, transmitted to RADIUS during authentication";
       type string {
         length "1 .. 63";
       }
     }
     list variables {
       key name;
       ordered-by user;
       description "Dynamic variable configuration";
       uses juniper-dynamic-variable-object;
     }
     container predefined-variable-defaults {
       description "Assign default values to predefined variables";
       uses apply-advanced;
       container aggregation-interface-set-name {
         presence "enable aggregation-interface-set-name";
         description "Default for junos-aggregation-interface-set-name";
         uses apply-advanced;
         choice def-value {
           case case_1 {
             leaf default-value {
               description "Default value for junos-aggregation-interface-set-name";
               type string;
             }
           }
           case case_2 {
             leaf equals {
               description "Computable expression of dynamic profile variables";
               type string;
             }
           }
         }
       }
       container interface-set-name {
         presence "enable interface-set-name";
         description "Default for junos-interface-set-name";
         uses apply-advanced;
         choice def-value {
           case case_1 {
             leaf default-value {
               description "Default value for junos-interface-set-name";
               type string;
             }
           }
           case case_2 {
             leaf equals {
               description "Computable expression of dynamic profile variables";
               type string;
             }
           }
         }
       }
       container default-interface-set-name {
         presence "enable default-interface-set-name";
         description "Default for junos-default-interface-set-name";
         uses apply-advanced;
         leaf equals {
           description "Computable expression of dynamic profile variables";
           type string;
         }
       }
       container phy-ifd-interface-set-name {
         presence "enable phy-ifd-interface-set-name";
         description "Default for junos-phy-ifd-interface-set-name";
         uses apply-advanced;
         choice def-value {
           case case_1 {
             leaf default-value {
               description "Default value for junos-phy-ifd-interface-set-name";
               type string;
             }
           }
           case case_2 {
             leaf equals {
               description "Computable expression of dynamic profile variables";
               type string;
             }
           }
         }
       }
       container phy-ifd-underlying-intf-set-name {
         presence "enable phy-ifd-underlying-intf-set-name";
         description "Default for junos-phy-ifd-underlying-intf-set-name";
         uses apply-advanced;
         choice def-value {
           case case_1 {
             leaf default-value {
               description "Default value for junos-phy-ifd-underlying-intf-set-name";
               type string;
             }
           }
           case case_2 {
             leaf equals {
               description "Computable expression of dynamic profile variables";
               type string;
             }
           }
         }
       }
       container cos-excess-rate {
         description "Default for junos-cos-excess-rate";
         uses apply-advanced;
         leaf proportion {
           description "Excess rate as proportion";
           type union {
             type string {
               pattern "<.*>|$.*";
             }
             type uint32 {
               range "0 .. 1000";
             }
           }
         }
         leaf percent {
           description "Excess rate as percentage";
           type union {
             type string {
               pattern "<.*>|$.*";
             }
             type uint32 {
               range "1 .. 100";
             }
           }
         }
       }
       container cos-excess-rate-high {
         description "Default for junos-cos-excess-rate-high";
         uses apply-advanced;
         leaf proportion {
           description "Excess rate as proportion";
           type union {
             type string {
               pattern "<.*>|$.*";
             }
             type uint32 {
               range "0 .. 1000";
             }
           }
         }
         leaf percent {
           description "Excess rate as percentage";
           type union {
             type string {
               pattern "<.*>|$.*";
             }
             type uint32 {
               range "1 .. 100";
             }
           }
         }
       }
       container cos-excess-rate-low {
         description "Default for junos-cos-excess-rate-low";
         uses apply-advanced;
         leaf proportion {
           description "Excess rate as proportion";
           type union {
             type string {
               pattern "<.*>|$.*";
             }
             type uint32 {
               range "0 .. 1000";
             }
           }
         }
         leaf percent {
           description "Excess rate as percentage";
           type union {
             type string {
               pattern "<.*>|$.*";
             }
             type uint32 {
               range "1 .. 100";
             }
           }
         }
       }
       container cos-scheduler-tx {
         description "Default for junos-cos-scheduler-tx";
         uses apply-advanced;
         leaf rate {
           description "Transmit rate as rate";
           type string;
         }
         leaf percent {
           description "Transmit rate as percentage";
           type union {
             type string {
               pattern "<.*>|$.*";
             }
             type uint32 {
               range "0 .. 100";
             }
           }
         }
       }
       container cos-scheduler-bs {
         description "Default for junos-cos-scheduler-bs";
         uses apply-advanced;
         leaf percent {
           description "Buffer size as percentage";
           type union {
             type string {
               pattern "<.*>|$.*";
             }
             type uint32 {
               range "0 .. 100";
             }
           }
         }
         leaf temporal {
           description "Buffer size as temporal";
           units "microseconds";
           type union {
             type uint32;
             type string {
               pattern "<.*>|$.*";
             }
           }
         }
       }
       container cos-scheduler-shaping-rate {
         description "Default for junos-cos-scheduler-shaping-rate";
         uses apply-advanced;
         leaf rate {
           description "Shaping rate as rate";
           units "bits per second";
           type string;
         }
         leaf percent {
           description "Shaping rate as percentage";
           type union {
             type string {
               pattern "<.*>|$.*";
             }
             type uint32 {
               range "1 .. 100";
             }
           }
         }
       }
       list other-variables {
         key name;
         ordered-by user;
         uses base-default-variable-object;
       }
     }
     container routing-instances {
       description "Routing instance configuration";
       uses apply-advanced;
       list instance {
         key name;
         ordered-by user;
         leaf name {
           type enumeration {
             enum "$junos-routing-instance" {
               description "Dynamic profile routing instance name";
             }
           }
         }
         uses apply-advanced;
         list interface {
           key name;
           description "Interface name for this routing instance";
           leaf name {
             type string;
           }
           uses apply-advanced;
           choice mode {
             case case_1 {
               leaf any {
                 description "Interface used for both unicast and multicast traffic";
                 type empty;
               }
             }
             case case_2 {
               leaf unicast {
                 description "Interface used for unicast traffic only";
                 type empty;
               }
             }
             case case_3 {
               leaf multicast {
                 description "Interface used for multicast traffic only";
                 type empty;
               }
             }
           }
           leaf primary {
             description "Preferred multicast vt interface for the routing-instance";
             type empty;
           }
           leaf protect-interface {
             description "Name of protect interface";
             type union {
               type jt:interface-name;
               type string {
                 pattern "<.*>|$.*";
               }
             }
           }
         }
         container routing-options {
           description "Protocol-independent routing option configuration";
           uses apply-advanced;
           list rib {
             key name;
             description "Routing table options";
             leaf name {
               description "Routing table name";
               type string;
             }
             uses apply-advanced;
             container static {
               description "Static routes";
               uses apply-advanced;
               leaf rib-group {
                 description "Routing table group";
                 type string;
               }
               container defaults {
                 description "Global route options";
                 uses apply-advanced;
                 choice retain-choice {
                   leaf retain {
                     description "Always keep route in forwarding table";
                     type empty;
                   }
                   leaf no-retain {
                     description "Don't always keep route in forwarding table";
                     type empty;
                   }
                 }
                 choice install-choice {
                   leaf install {
                     description "Install route into forwarding table";
                     type empty;
                   }
                   leaf no-install {
                     description "Don't install route into forwarding table";
                     type empty;
                   }
                 }
                 choice readvertise-choice {
                   leaf readvertise {
                     description "Mark route as eligible to be readvertised";
                     type empty;
                   }
                   leaf no-readvertise {
                     description "Don't mark route as eligible to be readvertised";
                     type empty;
                   }
                 }
                 choice resolve-choice {
                   leaf resolve {
                     description "Allow resolution of indirectly connected next hops";
                     type empty;
                   }
                   leaf no-resolve {
                     description "Don't allow resolution of indirectly connected next hops";
                     type empty;
                   }
                 }
                 leaf explicit-null {
                   description "Allows service label to be popped and will lookup nexthop-table inet6.0";
                   type empty;
                 }
                 choice longest-match-choice {
                   leaf longest-match {
                     description "Always use longest prefix match to resolve next hops";
                     type empty;
                   }
                   leaf no-longest-match {
                     description "Don't always use longest prefix match to resolve next hops";
                     type empty;
                   }
                 }
                 choice passive_flag {
                   case case_1 {
                     leaf active {
                       description "Remove inactive route from forwarding table";
                       type empty;
                     }
                   }
                   case case_2 {
                     leaf passive {
                       description "Retain inactive route in forwarding table";
                       type empty;
                     }
                   }
                 }
                 container metric {
                   description "Metric value";
                   presence "enable metric";
                   uses rib_static_metric_type;
                 }
                 container metric2 {
                   description "Metric value 2";
                   presence "enable metric2";
                   uses rib_static_metric_type;
                 }
                 container metric3 {
                   description "Metric value 3";
                   presence "enable metric3";
                   uses rib_static_metric_type;
                 }
                 container metric4 {
                   description "Metric value 4";
                   presence "enable metric4";
                   uses rib_static_metric_type;
                 }
                 container tag {
                   description "Tag string";
                   presence "enable tag";
                   uses rib_static_metric_type;
                 }
                 container tag2 {
                   description "Tag string 2";
                   presence "enable tag2";
                   uses rib_static_metric_type;
                 }
                 container preference {
                   description "Preference value";
                   presence "enable preference";
                   uses rib_static_metric_type;
                 }
                 container preference2 {
                   description "Preference value 2";
                   presence "enable preference2";
                   uses rib_static_metric_type;
                 }
                 container color {
                   description "Color (preference) value";
                   presence "enable color";
                   uses rib_static_metric_type;
                 }
                 container color2 {
                   description "Color (preference) value 2";
                   presence "enable color2";
                   uses rib_static_metric_type;
                 }
                 leaf-list community {
                   ordered-by user;
                   description "BGP community identifier";
                   type jt:community;
                 }
                 container as-path {
                   description "Autonomous system path";
                   uses apply-advanced;
                   leaf path {
                     description "Autonomous system path";
                     type string;
                   }
                   leaf origin {
                     type enumeration {
                       enum "igp" {
                         description "Path originated in the local IGP";
                       }
                       enum "egp" {
                         description "Path originated in another AS";
                       }
                       enum "incomplete" {
                         description "Path was learned by some other means";
                       }
                     }
                   }
                   leaf atomic-aggregate {
                     description "Add ATOMIC_AGGREGATE path attribute to route";
                     type empty;
                   }
                   container aggregator {
                     presence "enable aggregator";
                     description "Add AGGREGATOR path attribute to route";
                   }
                   leaf as-number {
                     description " Autonomous system number in plain number or 'higher 16bits'.'Lower 16 bits' (asdot notation) format";
                     type string {
                     }
                   }
                   leaf address {
                     description "Address of BGP system that formed the route";
                     type jt:ipv4addr;
                   }
                 }
               }
               list route {
                 key name;
                 description "Static route";
                 leaf name {
                   type jt:ipprefix;
                 }
                 uses apply-advanced;
                 leaf priority {
                   description "Static route priority high/medium/low";
                   type enumeration {
                     enum "medium" {
                       description "Static route medium priority";
                     }
                     enum "low" {
                       description "Static route low priority";
                     }
                     enum "high" {
                       description "Static route high priority";
                     }
                   }
                 }
                 choice next_hop {
                   case case_1 {
                     leaf-list next-hop {
                       ordered-by user;
                       description "Next hop to destination";
                       type union {
                         type jt:ipaddr-or-interface;
                         type string {
                           pattern "<.*>|$.*";
                         }
                       }
                     }
                   }
                   case case_2 {
                     leaf reject {
                       description "Drop packets to destination; send ICMP unreachables";
                       type empty;
                     }
                   }
                   case case_3 {
                     leaf discard {
                       description "Drop packets to destination; send no ICMP unreachables";
                       type empty;
                     }
                   }
                   case case_4 {
                     leaf receive {
                       description "Install a receive route for the destination";
                       type empty;
                     }
                   }
                   case case_5 {
                     leaf next-table {
                       description "Next hop to another table";
                       type string {
                       }
                     }
                   }
                 }
                 leaf description {
                   description "Static route description";
                   type string {
                   }
                 }
                 list qualified-next-hop {
                   key name;
                   ordered-by user;
                   description "Next hop with qualifiers";
                   uses qualified_nh_obj;
                 }
                 leaf backup-pe-group {
                   description "Multicast source redundancy group";
                   type string;
                 }
                 container bfd-liveness-detection {
                   description "Bidirectional Forwarding Detection (BFD) options";
                   uses apply-advanced;
                   leaf version {
                     description "BFD protocol version number";
                     default "automatic";
                     type enumeration {
                       enum "0" {
                         description "BFD version 0 (deprecated)";
                       }
                       enum "1" {
                         description "BFD version 1";
                       }
                       enum "automatic" {
                         description "Choose BFD version automatically";
                       }
                     }
                   }
                   leaf minimum-interval {
                     description "Minimum transmit and receive interval";
                     units "milliseconds";
                     type union {
                       type string {
                         pattern "<.*>|$.*";
                       }
                       type uint32 {
                         range "1 .. 255000";
                       }
                     }
                   }
                   leaf minimum-transmit-interval {
                     description "Minimum transmit interval";
                     status deprecated;
                     units "milliseconds";
                     type union {
                       type string {
                         pattern "<.*>|$.*";
                       }
                       type uint32 {
                         range "1 .. 255000";
                       }
                     }
                   }
                   leaf minimum-receive-interval {
                     description "Minimum receive interval";
                     units "milliseconds";
                     type union {
                       type string {
                         pattern "<.*>|$.*";
                       }
                       type uint32 {
                         range "1 .. 255000";
                       }
                     }
                   }
                   leaf multiplier {
                     description "Detection time multiplier";
                     default "3";
                     type union {
                       type string {
                         pattern "<.*>|$.*";
                       }
                       type uint32 {
                         range "1 .. 255";
                       }
                     }
                   }
                   leaf inline-disable {
                     description "Disable inline mode for this BFD session";
                     type empty;
                   }
                   leaf pdu-size {
                     description "BFD transport protocol payload size";
                     default "24";
                     type union {
                       type string {
                         pattern "<.*>|$.*";
                       }
                       type uint32 {
                         range "24 .. 9000";
                       }
                     }
                   }
                   choice adaptation-choice {
                     case case_1 {
                       leaf no-adaptation {
                         description "Disable adaptation";
                         type empty;
                       }
                     }
                   }
                   container transmit-interval {
                     description "Transmit-interval options";
                     uses apply-advanced;
                     leaf minimum-interval {
                       description "Minimum transmit interval";
                       units "milliseconds";
                       type union {
                         type string {
                           pattern "<.*>|$.*";
                         }
                         type uint32 {
                           range "1 .. 255000";
                         }
                       }
                     }
                     leaf threshold {
                       description "High transmit interval triggering a trap";
                       units "milliseconds";
                       type union {
                         type uint32;
                         type string {
                           pattern "<.*>|$.*";
                         }
                       }
                     }
                   }
                   container detection-time {
                     description "Detection-time options";
                     uses apply-advanced;
                     leaf threshold {
                       description "High detection-time triggering a trap";
                       units "milliseconds";
                       type union {
                         type uint32;
                         type string {
                           pattern "<.*>|$.*";
                         }
                       }
                     }
                   }
                   container authentication {
                     description "Authentication options";
                     uses apply-advanced;
                     leaf key-chain {
                       description "Key chain name";
                       type string;
                     }
                     leaf algorithm {
                       description "Algorithm name";
                       type enumeration {
                         enum "simple-password" {
                           description "Simple password";
                         }
                         enum "keyed-md5" {
                           description "Keyed message Digest 5";
                         }
                         enum "meticulous-keyed-md5" {
                           description "Meticulous keyed message Digest 5";
                         }
                         enum "keyed-sha-1" {
                           description "Keyed secure hash algorithm (SHA1) ";
                         }
                         enum "meticulous-keyed-sha-1" {
                           description "Meticulous keyed secure hash algorithm (SHA1) ";
                         }
                       }
                     }
                     leaf loose-check {
                       description "Verify authentication only if authentication is negotiated";
                       type empty;
                     }
                   }
                   container echo {
                     description "Echo mode parameters";
                     uses apply-advanced;
                     leaf minimum-interval {
                       description "Minimum transmit and receive interval";
                       units "milliseconds";
                       type union {
                         type string {
                           pattern "<.*>|$.*";
                         }
                         type uint32 {
                           range "100 .. 255000";
                         }
                       }
                     }
                   }
                   container echo-lite {
                     description "Echo-lite more parameters";
                     uses apply-advanced;
                     leaf minimum-interval {
                       description "Minimum transmit and receive interval";
                       units "milliseconds";
                       type union {
                         type string {
                           pattern "<.*>|$.*";
                         }
                         type uint32 {
                           range "100 .. 255000";
                         }
                       }
                     }
                   }
                   leaf neighbor {
                     description "BFD neighbor address";
                     type jt:ipaddr;
                   }
                   leaf local-address {
                     description "BFD local address (for multihop only)";
                     type jt:ipaddr;
                   }
                   leaf holddown-interval {
                     description "Time to hold the session-UP notification to the client";
                     units "milliseconds";
                     type union {
                       type string {
                         pattern "<.*>|$.*";
                       }
                       type uint32 {
                         range "0 .. 255000";
                       }
                     }
                   }
                   leaf minimum-receive-ttl {
                     description "Minimum receive TTL below which to drop";
                     type union {
                       type string {
                         pattern "<.*>|$.*";
                       }
                       type uint8 {
                         range "1 .. 255";
                       }
                     }
                   }
                 }
                 choice retain-choice {
                   leaf retain {
                     description "Always keep route in forwarding table";
                     type empty;
                   }
                   leaf no-retain {
                     description "Don't always keep route in forwarding table";
                     type empty;
                   }
                 }
                 choice install-choice {
                   leaf install {
                     description "Install route into forwarding table";
                     type empty;
                   }
                   leaf no-install {
                     description "Don't install route into forwarding table";
                     type empty;
                   }
                 }
                 choice readvertise-choice {
                   leaf readvertise {
                     description "Mark route as eligible to be readvertised";
                     type empty;
                   }
                   leaf no-readvertise {
                     description "Don't mark route as eligible to be readvertised";
                     type empty;
                   }
                 }
                 choice resolve-choice {
                   leaf resolve {
                     description "Allow resolution of indirectly connected next hops";
                     type empty;
                   }
                   leaf no-resolve {
                     description "Don't allow resolution of indirectly connected next hops";
                     type empty;
                   }
                 }
                 leaf explicit-null {
                   description "Allows service label to be popped and will lookup nexthop-table inet6.0";
                   type empty;
                 }
                 choice longest-match-choice {
                   leaf longest-match {
                     description "Always use longest prefix match to resolve next hops";
                     type empty;
                   }
                   leaf no-longest-match {
                     description "Don't always use longest prefix match to resolve next hops";
                     type empty;
                   }
                 }
                 choice passive_flag {
                   case case_1 {
                     leaf active {
                       description "Remove inactive route from forwarding table";
                       type empty;
                     }
                   }
                   case case_2 {
                     leaf passive {
                       description "Retain inactive route in forwarding table";
                       type empty;
                     }
                   }
                 }
                 container metric {
                   description "Metric value";
                   presence "enable metric";
                   uses rib_static_metric_type;
                 }
                 container metric2 {
                   description "Metric value 2";
                   presence "enable metric2";
                   uses rib_static_metric_type;
                 }
                 container metric3 {
                   description "Metric value 3";
                   presence "enable metric3";
                   uses rib_static_metric_type;
                 }
                 container metric4 {
                   description "Metric value 4";
                   presence "enable metric4";
                   uses rib_static_metric_type;
                 }
                 container tag {
                   description "Tag string";
                   presence "enable tag";
                   uses rib_static_metric_type;
                 }
                 container tag2 {
                   description "Tag string 2";
                   presence "enable tag2";
                   uses rib_static_metric_type;
                 }
                 container preference {
                   description "Preference value";
                   presence "enable preference";
                   uses rib_static_metric_type;
                 }
                 container preference2 {
                   description "Preference value 2";
                   presence "enable preference2";
                   uses rib_static_metric_type;
                 }
                 container color {
                   description "Color (preference) value";
                   presence "enable color";
                   uses rib_static_metric_type;
                 }
                 container color2 {
                   description "Color (preference) value 2";
                   presence "enable color2";
                   uses rib_static_metric_type;
                 }
                 leaf-list community {
                   ordered-by user;
                   description "BGP community identifier";
                   type jt:community;
                 }
                 container as-path {
                   description "Autonomous system path";
                   uses apply-advanced;
                   leaf path {
                     description "Autonomous system path";
                     type string;
                   }
                   leaf origin {
                     type enumeration {
                       enum "igp" {
                         description "Path originated in the local IGP";
                       }
                       enum "egp" {
                         description "Path originated in another AS";
                       }
                       enum "incomplete" {
                         description "Path was learned by some other means";
                       }
                     }
                   }
                   leaf atomic-aggregate {
                     description "Add ATOMIC_AGGREGATE path attribute to route";
                     type empty;
                   }
                   container aggregator {
                     presence "enable aggregator";
                     description "Add AGGREGATOR path attribute to route";
                   }
                   leaf as-number {
                     description " Autonomous system number in plain number or 'higher 16bits'.'Lower 16 bits' (asdot notation) format";
                     type string {
                     }
                   }
                   leaf address {
                     description "Address of BGP system that formed the route";
                     type jt:ipv4addr;
                   }
                 }
                 list lsp-next-hop {
                   key name;
                   ordered-by user;
                   description "LSP next hop";
                   uses lsp_nh_obj;
                 }
                 list p2mp-lsp-next-hop {
                   key name;
                   ordered-by user;
                   description "Point-to-multipoint LSP next hop";
                   max-elements 1;
                   uses lsp_nh_obj;
                 }
                 container spring-te-lsp-next-hop {
                   description "SPRING-TE LSP next hop";
                   uses springte_lsp_nh_obj;
                 }
                 container p2mp-ldp-next-hop {
                   description "Point-to-multipoint LDP LSP next hop";
                   uses p2mp_ldp_lsp_nh_obj;
                 }
                 list static-lsp-next-hop {
                   key name;
                   ordered-by user;
                   description "Static LSP next hop";
                   uses lsp_nh_obj;
                 }
               }
               leaf protocol-instance-name {
                 description "Name of protocol instance under routing instance";
                 type string;
               }
               container static-route {
                 description "Static route Status";
                 leaf bfd-admin-down {
                   description "Static route State on BFD ADMIN DOWN";
                   type enumeration {
                     enum "active" {
                       description "Static route will be inactive on bfd-admin-down";
                     }
                     enum "passive" {
                       description "Static route will remain active on bfd-admin-down";
                     }
                   }
                 }
               }
               list iso-route {
                 key name;
                 ordered-by user;
                 description "ISO family static route";
                 leaf name {
                   type jt:isoprefix;
                 }
                 uses apply-advanced;
                 leaf priority {
                   description "Static route priority high/medium/low";
                   type enumeration {
                     enum "medium" {
                       description "Static route medium priority";
                     }
                     enum "low" {
                       description "Static route low priority";
                     }
                     enum "high" {
                       description "Static route high priority";
                     }
                   }
                 }
                 choice next_hop {
                   case case_1 {
                     leaf-list next-hop {
                       ordered-by user;
                       description "Next hop to destination";
                       type union {
                         type jt:ipaddr-or-interface;
                         type string {
                           pattern "<.*>|$.*";
                         }
                       }
                     }
                   }
                   case case_2 {
                     leaf reject {
                       description "Drop packets to destination; send ICMP unreachables";
                       type empty;
                     }
                   }
                   case case_3 {
                     leaf discard {
                       description "Drop packets to destination; send no ICMP unreachables";
                       type empty;
                     }
                   }
                   case case_4 {
                     leaf receive {
                       description "Install a receive route for the destination";
                       type empty;
                     }
                   }
                   case case_5 {
                     leaf next-table {
                       description "Next hop to another table";
                       type string {
                       }
                     }
                   }
                 }
                 leaf description {
                   description "Static route description";
                   type string {
                   }
                 }
                 list qualified-next-hop {
                   key name;
                   ordered-by user;
                   description "Next hop with qualifiers";
                   uses qualified_nh_obj;
                 }
                 leaf backup-pe-group {
                   description "Multicast source redundancy group";
                   type string;
                 }
                 container bfd-liveness-detection {
                   description "Bidirectional Forwarding Detection (BFD) options";
                   uses apply-advanced;
                   leaf version {
                     description "BFD protocol version number";
                     default "automatic";
                     type enumeration {
                       enum "0" {
                         description "BFD version 0 (deprecated)";
                       }
                       enum "1" {
                         description "BFD version 1";
                       }
                       enum "automatic" {
                         description "Choose BFD version automatically";
                       }
                     }
                   }
                   leaf minimum-interval {
                     description "Minimum transmit and receive interval";
                     units "milliseconds";
                     type union {
                       type string {
                         pattern "<.*>|$.*";
                       }
                       type uint32 {
                         range "1 .. 255000";
                       }
                     }
                   }
                   leaf minimum-transmit-interval {
                     description "Minimum transmit interval";
                     status deprecated;
                     units "milliseconds";
                     type union {
                       type string {
                         pattern "<.*>|$.*";
                       }
                       type uint32 {
                         range "1 .. 255000";
                       }
                     }
                   }
                   leaf minimum-receive-interval {
                     description "Minimum receive interval";
                     units "milliseconds";
                     type union {
                       type string {
                         pattern "<.*>|$.*";
                       }
                       type uint32 {
                         range "1 .. 255000";
                       }
                     }
                   }
                   leaf multiplier {
                     description "Detection time multiplier";
                     default "3";
                     type union {
                       type string {
                         pattern "<.*>|$.*";
                       }
                       type uint32 {
                         range "1 .. 255";
                       }
                     }
                   }
                   leaf inline-disable {
                     description "Disable inline mode for this BFD session";
                     type empty;
                   }
                   leaf pdu-size {
                     description "BFD transport protocol payload size";
                     default "24";
                     type union {
                       type string {
                         pattern "<.*>|$.*";
                       }
                       type uint32 {
                         range "24 .. 9000";
                       }
                     }
                   }
                   choice adaptation-choice {
                     case case_1 {
                       leaf no-adaptation {
                         description "Disable adaptation";
                         type empty;
                       }
                     }
                   }
                   container transmit-interval {
                     description "Transmit-interval options";
                     uses apply-advanced;
                     leaf minimum-interval {
                       description "Minimum transmit interval";
                       units "milliseconds";
                       type union {
                         type string {
                           pattern "<.*>|$.*";
                         }
                         type uint32 {
                           range "1 .. 255000";
                         }
                       }
                     }
                     leaf threshold {
                       description "High transmit interval triggering a trap";
                       units "milliseconds";
                       type union {
                         type uint32;
                         type string {
                           pattern "<.*>|$.*";
                         }
                       }
                     }
                   }
                   container detection-time {
                     description "Detection-time options";
                     uses apply-advanced;
                     leaf threshold {
                       description "High detection-time triggering a trap";
                       units "milliseconds";
                       type union {
                         type uint32;
                         type string {
                           pattern "<.*>|$.*";
                         }
                       }
                     }
                   }
                   container authentication {
                     description "Authentication options";
                     uses apply-advanced;
                     leaf key-chain {
                       description "Key chain name";
                       type string;
                     }
                     leaf algorithm {
                       description "Algorithm name";
                       type enumeration {
                         enum "simple-password" {
                           description "Simple password";
                         }
                         enum "keyed-md5" {
                           description "Keyed message Digest 5";
                         }
                         enum "meticulous-keyed-md5" {
                           description "Meticulous keyed message Digest 5";
                         }
                         enum "keyed-sha-1" {
                           description "Keyed secure hash algorithm (SHA1) ";
                         }
                         enum "meticulous-keyed-sha-1" {
                           description "Meticulous keyed secure hash algorithm (SHA1) ";
                         }
                       }
                     }
                     leaf loose-check {
                       description "Verify authentication only if authentication is negotiated";
                       type empty;
                     }
                   }
                   container echo {
                     description "Echo mode parameters";
                     uses apply-advanced;
                     leaf minimum-interval {
                       description "Minimum transmit and receive interval";
                       units "milliseconds";
                       type union {
                         type string {
                           pattern "<.*>|$.*";
                         }
                         type uint32 {
                           range "100 .. 255000";
                         }
                       }
                     }
                   }
                   container echo-lite {
                     description "Echo-lite more parameters";
                     uses apply-advanced;
                     leaf minimum-interval {
                       description "Minimum transmit and receive interval";
                       units "milliseconds";
                       type union {
                         type string {
                           pattern "<.*>|$.*";
                         }
                         type uint32 {
                           range "100 .. 255000";
                         }
                       }
                     }
                   }
                   leaf neighbor {
                     description "BFD neighbor address";
                     type jt:ipaddr;
                   }
                   leaf local-address {
                     description "BFD local address (for multihop only)";
                     type jt:ipaddr;
                   }
                   leaf holddown-interval {
                     description "Time to hold the session-UP notification to the client";
                     units "milliseconds";
                     type union {
                       type string {
                         pattern "<.*>|$.*";
                       }
                       type uint32 {
                         range "0 .. 255000";
                       }
                     }
                   }
                   leaf minimum-receive-ttl {
                     description "Minimum receive TTL below which to drop";
                     type union {
                       type string {
                         pattern "<.*>|$.*";
                       }
                       type uint8 {
                         range "1 .. 255";
                       }
                     }
                   }
                 }
                 choice retain-choice {
                   leaf retain {
                     description "Always keep route in forwarding table";
                     type empty;
                   }
                   leaf no-retain {
                     description "Don't always keep route in forwarding table";
                     type empty;
                   }
                 }
                 choice install-choice {
                   leaf install {
                     description "Install route into forwarding table";
                     type empty;
                   }
                   leaf no-install {
                     description "Don't install route into forwarding table";
                     type empty;
                   }
                 }
                 choice readvertise-choice {
                   leaf readvertise {
                     description "Mark route as eligible to be readvertised";
                     type empty;
                   }
                   leaf no-readvertise {
                     description "Don't mark route as eligible to be readvertised";
                     type empty;
                   }
                 }
                 choice resolve-choice {
                   leaf resolve {
                     description "Allow resolution of indirectly connected next hops";
                     type empty;
                   }
                   leaf no-resolve {
                     description "Don't allow resolution of indirectly connected next hops";
                     type empty;
                   }
                 }
                 leaf explicit-null {
                   description "Allows service label to be popped and will lookup nexthop-table inet6.0";
                   type empty;
                 }
                 choice longest-match-choice {
                   leaf longest-match {
                     description "Always use longest prefix match to resolve next hops";
                     type empty;
                   }
                   leaf no-longest-match {
                     description "Don't always use longest prefix match to resolve next hops";
                     type empty;
                   }
                 }
                 choice passive_flag {
                   case case_1 {
                     leaf active {
                       description "Remove inactive route from forwarding table";
                       type empty;
                     }
                   }
                   case case_2 {
                     leaf passive {
                       description "Retain inactive route in forwarding table";
                       type empty;
                     }
                   }
                 }
                 container metric {
                   description "Metric value";
                   presence "enable metric";
                   uses rib_static_metric_type;
                 }
                 container metric2 {
                   description "Metric value 2";
                   presence "enable metric2";
                   uses rib_static_metric_type;
                 }
                 container metric3 {
                   description "Metric value 3";
                   presence "enable metric3";
                   uses rib_static_metric_type;
                 }
                 container metric4 {
                   description "Metric value 4";
                   presence "enable metric4";
                   uses rib_static_metric_type;
                 }
                 container tag {
                   description "Tag string";
                   presence "enable tag";
                   uses rib_static_metric_type;
                 }
                 container tag2 {
                   description "Tag string 2";
                   presence "enable tag2";
                   uses rib_static_metric_type;
                 }
                 container preference {
                   description "Preference value";
                   presence "enable preference";
                   uses rib_static_metric_type;
                 }
                 container preference2 {
                   description "Preference value 2";
                   presence "enable preference2";
                   uses rib_static_metric_type;
                 }
                 container color {
                   description "Color (preference) value";
                   presence "enable color";
                   uses rib_static_metric_type;
                 }
                 container color2 {
                   description "Color (preference) value 2";
                   presence "enable color2";
                   uses rib_static_metric_type;
                 }
                 leaf-list community {
                   ordered-by user;
                   description "BGP community identifier";
                   type jt:community;
                 }
                 container as-path {
                   description "Autonomous system path";
                   uses apply-advanced;
                   leaf path {
                     description "Autonomous system path";
                     type string;
                   }
                   leaf origin {
                     type enumeration {
                       enum "igp" {
                         description "Path originated in the local IGP";
                       }
                       enum "egp" {
                         description "Path originated in another AS";
                       }
                       enum "incomplete" {
                         description "Path was learned by some other means";
                       }
                     }
                   }
                   leaf atomic-aggregate {
                     description "Add ATOMIC_AGGREGATE path attribute to route";
                     type empty;
                   }
                   container aggregator {
                     presence "enable aggregator";
                     description "Add AGGREGATOR path attribute to route";
                   }
                   leaf as-number {
                     description " Autonomous system number in plain number or 'higher 16bits'.'Lower 16 bits' (asdot notation) format";
                     type string {
                     }
                   }
                   leaf address {
                     description "Address of BGP system that formed the route";
                     type jt:ipv4addr;
                   }
                 }
                 list lsp-next-hop {
                   key name;
                   ordered-by user;
                   description "LSP next hop";
                   uses lsp_nh_obj;
                 }
                 list p2mp-lsp-next-hop {
                   key name;
                   ordered-by user;
                   description "Point-to-multipoint LSP next hop";
                   max-elements 1;
                   uses lsp_nh_obj;
                 }
                 container spring-te-lsp-next-hop {
                   description "SPRING-TE LSP next hop";
                   uses springte_lsp_nh_obj;
                 }
                 container p2mp-ldp-next-hop {
                   description "Point-to-multipoint LDP LSP next hop";
                   uses p2mp_ldp_lsp_nh_obj;
                 }
               }
               list route-target-filter {
                 key name;
                 ordered-by user;
                 description "Route-target-filter route";
                 leaf name {
                   type string {
                     length "1 .. 47";
                   }
                 }
                 uses apply-advanced;
                 leaf-list neighbor {
                   ordered-by user;
                   description "BGP peers for filter";
                   type jt:ipaddr-scoped;
                 }
                 leaf-list group {
                   ordered-by user;
                   description "BGP groups for filter";
                   type string;
                 }
                 leaf local {
                   description "Locally originated filter";
                   type empty;
                 }
               }
             }
             list martians {
               key "address choice-ident choice-value";
               ordered-by user;
               description "Invalid routes";
               uses martian_type;
             }
             container aggregate {
               description "Coalesced routes";
               uses rib_aggregate_type;
             }
             container generate {
               description "Route of last resort";
               uses rib_aggregate_type;
             }
             choice maximum-paths-type {
               case case_1 {
                 container maximum-routes {
                   description "Maximum number of routes";
                   status deprecated;
                   leaf limit {
                     description "Maximum number of routes";
                     type union {
                       type string {
                         pattern "<.*>|$.*";
                       }
                       type uint32 {
                         range "1 .. 4294967295";
                       }
                     }
                   }
                   choice log_type {
                     case case_1 {
                       leaf threshold {
                         description "Percentage of limit at which to start generating warnings";
                         type union {
                           type string {
                             pattern "<.*>|$.*";
                           }
                           type uint32 {
                             range "1 .. 100";
                           }
                         }
                       }
                     }
                     case case_2 {
                       leaf log-only {
                         description "Generate warning messages only";
                         type empty;
                       }
                     }
                   }
                   leaf log-interval {
                     description "Minimum interval between log messages";
                     units "seconds";
                     type union {
                       type string {
                         pattern "<.*>|$.*";
                       }
                       type uint32 {
                         range "5 .. 86400";
                       }
                     }
                   }
                 }
               }
               case case_2 {
                 container maximum-paths {
                   description "Maximum number of paths";
                   leaf limit {
                     description "Maximum number of paths";
                     type union {
                       type string {
                         pattern "<.*>|$.*";
                       }
                       type uint32 {
                         range "1 .. 4294967295";
                       }
                     }
                   }
                   choice log_type {
                     case case_1 {
                       leaf threshold {
                         description "Percentage of limit at which to start generating warnings";
                         type union {
                           type string {
                             pattern "<.*>|$.*";
                           }
                           type uint32 {
                             range "1 .. 100";
                           }
                         }
                       }
                     }
                     case case_2 {
                       leaf log-only {
                         description "Generate warning messages only";
                         type empty;
                       }
                     }
                   }
                   leaf log-interval {
                     description "Minimum interval between log messages";
                     units "seconds";
                     type union {
                       type string {
                         pattern "<.*>|$.*";
                       }
                       type uint32 {
                         range "5 .. 86400";
                       }
                     }
                   }
                 }
               }
             }
             container maximum-prefixes {
               description "Maximum number of prefixes";
               leaf limit {
                 description "Maximum number of prefixes";
                 type union {
                   type string {
                     pattern "<.*>|$.*";
                   }
                   type uint32 {
                     range "1 .. 4294967295";
                   }
                 }
               }
               choice log_type {
                 case case_1 {
                   leaf threshold {
                     description "Percentage of limit at which to start generating warnings";
                     type union {
                       type string {
                         pattern "<.*>|$.*";
                       }
                       type uint32 {
                         range "1 .. 100";
                       }
                     }
                   }
                 }
                 case case_2 {
                   leaf log-only {
                     description "Generate warning messages only";
                     type empty;
                   }
                 }
               }
               leaf log-interval {
                 description "Minimum interval between log messages";
                 units "seconds";
                 type union {
                   type string {
                     pattern "<.*>|$.*";
                   }
                   type uint32 {
                     range "5 .. 86400";
                   }
                 }
               }
             }
             container multipath {
               presence "enable multipath";
               description "Protocol-independent load balancing";
               uses apply-advanced;
               container vpn-unequal-cost {
                 presence "enable vpn-unequal-cost";
                 description "Include VPN routes with unequal IGP metrics";
                 leaf equal-external-internal {
                   description "Include external and internal VPN routes";
                   type empty;
                 }
               }
               leaf as-path-compare {
                 description "Compare AS path sequences in addition to AS path length";
                 type empty;
               }
               leaf preserve-nexthop-hierarchy {
                 description "Force multipath to create List nexthop";
                 type empty;
               }
             }
             container policy-multipath {
               description "Policy based multipath";
               uses apply-advanced;
               leaf-list policy {
                 ordered-by user;
                 description "Import policy to create policy based multipath";
                 type jt:policy-algebra;
               }
               container traceoptions {
                 description "Trace options";
                 uses apply-advanced;
                 container file {
                   description "Trace file options";
                   leaf filename {
                     description "Name of file in which to write trace information";
                     type string {
                       length "1 .. 1024";
                     }
                   }
                   leaf replace {
                     description "Replace trace file rather than appending to it";
                     status deprecated;
                     type empty;
                   }
                   leaf size {
                     description "Maximum trace file size";
                     type string;
                   }
                   leaf files {
                     description "Maximum number of trace files";
                     default "10";
                     type union {
                       type string {
                         pattern "<.*>|$.*";
                       }
                       type uint32 {
                         range "2 .. 1000";
                       }
                     }
                   }
                   leaf no-stamp {
                     description "Do not timestamp trace file";
                     status deprecated;
                     type empty;
                   }
                   choice world-readable-choice {
                     leaf world-readable {
                       description "Allow any user to read the log file";
                       type empty;
                     }
                     leaf no-world-readable {
                       description "Don't allow any user to read the log file";
                       type empty;
                     }
                   }
                 }
                 list flag {
                   key name;
                   ordered-by user;
                   description "Tracing parameters";
                   leaf name {
                     type enumeration {
                       enum "route" {
                         description "Policy-multipath route tracing.";
                       }
                     }
                   }
                   leaf send {
                     description "Trace transmitted packets";
                     type empty;
                   }
                   leaf receive {
                     description "Trace received packets";
                     type empty;
                   }
                   leaf detail {
                     description "Trace detailed information";
                     type empty;
                   }
                   leaf disable {
                     description "Disable this trace flag";
                     type empty;
                   }
                 }
               }
               leaf preserve-nexthop-hierarchy {
                 description "Enable preserved nexthop hierarchy";
                 type empty;
               }
             }
             container protect {
               description "Protocol-independent protection";
               leaf core {
                 description "Protect against unreachability to service-edge router";
                 type empty;
               }
             }
             container access {
               description "Access routes";
               uses apply-advanced;
               list route {
                 key name;
                 ordered-by user;
                 description "Access route";
                 leaf name {
                   description "IP address of destination";
                   type jt:ipprefix;
                 }
                 uses apply-advanced;
                 leaf-list next-hop {
                   ordered-by user;
                   description "Next hop to destination";
                   type union {
                     type jt:ipaddr-or-interface;
                     type string {
                       pattern "<.*>|$.*";
                     }
                   }
                 }
                 list qualified-next-hop {
                   key name;
                   ordered-by user;
                   description "Next hop with qualifiers";
                   uses qualified_nh_obj;
                 }
                 leaf metric {
                   description "Metric value";
                   type union {
                     type string {
                       pattern "<.*>|$.*";
                     }
                     type uint32 {
                       range "1 .. 255";
                     }
                   }
                 }
                 leaf preference {
                   description "Preference value";
                   type union {
                     type uint32;
                     type string {
                       pattern "<.*>|$.*";
                     }
                   }
                 }
                 leaf tag {
                   description "Tag string";
                   type union {
                     type uint32;
                     type string {
                       pattern "<.*>|$.*";
                     }
                   }
                 }
                 leaf tag2 {
                   description "Tag2 string";
                   type union {
                     type uint32;
                     type string {
                       pattern "<.*>|$.*";
                     }
                   }
                 }
               }
             }
             container access-internal {
               description "Access-internal routes";
               uses apply-advanced;
               list route {
                 key name;
                 ordered-by user;
                 description "Access-internal route";
                 leaf name {
                   description "IP address and optional prefix length of destination";
                   type jt:ipprefix;
                 }
                 uses apply-advanced;
                 leaf-list next-hop {
                   ordered-by user;
                   description "Next hop to destination";
                   type union {
                     type jt:ipaddr-or-interface;
                     type string {
                       pattern "<.*>|$.*";
                     }
                   }
                 }
                 list qualified-next-hop {
                   key name;
                   ordered-by user;
                   description "Next hop with qualifiers";
                   uses qualified_nh_obj;
                 }
               }
             }
             container bgp-static {
               description "Routes for BGP static advertisements";
               uses apply-advanced;
               list route {
                 key name;
                 ordered-by user;
                 description "BGP-static route";
                 leaf name {
                   description "IP address and optional prefix length of destination";
                   type jt:ipprefix;
                 }
                 uses apply-advanced;
                 container metric {
                   description "Metric value";
                   presence "enable metric";
                   uses rib_static_metric_type;
                 }
                 container metric2 {
                   description "Metric value 2";
                   presence "enable metric2";
                   uses rib_static_metric_type;
                 }
                 container metric3 {
                   description "Metric value 3";
                   presence "enable metric3";
                   uses rib_static_metric_type;
                 }
                 container metric4 {
                   description "Metric value 4";
                   presence "enable metric4";
                   uses rib_static_metric_type;
                 }
                 container tag {
                   description "Tag string";
                   presence "enable tag";
                   uses rib_static_metric_type;
                 }
                 container tag2 {
                   description "Tag string 2";
                   presence "enable tag2";
                   uses rib_static_metric_type;
                 }
                 container preference {
                   description "Preference value";
                   presence "enable preference";
                   uses rib_static_metric_type;
                 }
                 container preference2 {
                   description "Preference value 2";
                   presence "enable preference2";
                   uses rib_static_metric_type;
                 }
                 container color {
                   description "Color (preference) value";
                   presence "enable color";
                   uses rib_static_metric_type;
                 }
                 container color2 {
                   description "Color (preference) value 2";
                   presence "enable color2";
                   uses rib_static_metric_type;
                 }
                 leaf-list community {
                   ordered-by user;
                   description "BGP community identifier";
                   type jt:community;
                 }
                 container as-path {
                   description "Autonomous system path";
                   uses apply-advanced;
                   leaf path {
                     description "Autonomous system path";
                     type string;
                   }
                   leaf origin {
                     type enumeration {
                       enum "igp" {
                         description "Path originated in the local IGP";
                       }
                       enum "egp" {
                         description "Path originated in another AS";
                       }
                       enum "incomplete" {
                         description "Path was learned by some other means";
                       }
                     }
                   }
                   leaf atomic-aggregate {
                     description "Add ATOMIC_AGGREGATE path attribute to route";
                     type empty;
                   }
                   container aggregator {
                     presence "enable aggregator";
                     description "Add AGGREGATOR path attribute to route";
                   }
                   leaf as-number {
                     description " Autonomous system number in plain number or 'higher 16bits'.'Lower 16 bits' (asdot notation) format";
                     type string {
                     }
                   }
                   leaf address {
                     description "Address of BGP system that formed the route";
                     type jt:ipv4addr;
                   }
                 }
               }
             }
             container flow {
               description "Locally defined flow routing information";
               uses apply-advanced;
               container validation {
                 description "Flow route validation options";
                 presence "enable validation";
                 uses flow-validation;
               }
               list route {
                 key name;
                 ordered-by user;
                 description "Flow route";
                 uses flow-route-inet6;
               }
               list security-group {
                 key name;
                 ordered-by user;
                 description "Security groups";
                 leaf name {
                   description "Name of the security group";
                   type string {
                     length "1 .. 16";
                   }
                 }
                 uses apply-advanced;
                 list rule {
                   key name;
                   ordered-by user;
                   description "Flow route";
                   uses flow-rule-inet6;
                 }
               }
               container interface-group {
                 description "Interface-group for applying flow-spec filter";
                 uses flow-interface-group;
               }
               leaf discard-action-for-unresolved-redir-addr {
                 description "For action redirect IP if redirect address is unresolved install discard action filter";
                 type empty;
               }
               choice per-route-accounting-choice {
                 leaf per-route-accounting {
                   description "Enable traffic accounting per flowspec route";
                   type empty;
                 }
                 leaf no-per-route-accounting {
                   description "Don't enable traffic accounting per flowspec route";
                   type empty;
                 }
               }
             }
             container label {
               presence "enable label";
               description "Label processing";
               uses apply-advanced;
               leaf-list allocation {
                 ordered-by user;
                 description "Label allocation policy";
                 type jt:policy-algebra;
               }
               leaf-list substitution {
                 ordered-by user;
                 description "Label substitution policy";
                 type jt:policy-algebra;
               }
             }
           }
           container access {
             description "Access routes";
             uses apply-advanced;
             list route {
               key name;
               ordered-by user;
               description "Access route";
               leaf name {
                 description "IP address of destination";
                 type jt:ipprefix;
               }
               uses apply-advanced;
               leaf-list next-hop {
                 ordered-by user;
                 description "Next hop to destination";
                 type union {
                   type jt:ipaddr-or-interface;
                   type string {
                     pattern "<.*>|$.*";
                   }
                 }
               }
               list qualified-next-hop {
                 key name;
                 ordered-by user;
                 description "Next hop with qualifiers";
                 uses qualified_nh_obj;
               }
               leaf metric {
                 description "Metric value";
                 type union {
                   type string {
                     pattern "<.*>|$.*";
                   }
                   type uint32 {
                     range "1 .. 255";
                   }
                 }
               }
               leaf preference {
                 description "Preference value";
                 type union {
                   type uint32;
                   type string {
                     pattern "<.*>|$.*";
                   }
                 }
               }
               leaf tag {
                 description "Tag string";
                 type union {
                   type uint32;
                   type string {
                     pattern "<.*>|$.*";
                   }
                 }
               }
               leaf tag2 {
                 description "Tag2 string";
                 type union {
                   type uint32;
                   type string {
                     pattern "<.*>|$.*";
                   }
                 }
               }
             }
           }
           container access-internal {
             description "Access-internal routes";
             uses apply-advanced;
             list route {
               key name;
               ordered-by user;
               description "Access-internal route";
               leaf name {
                 description "IP address and optional prefix length of destination";
                 type jt:ipprefix;
               }
               uses apply-advanced;
               leaf-list next-hop {
                 ordered-by user;
                 description "Next hop to destination";
                 type union {
                   type jt:ipaddr-or-interface;
                   type string {
                     pattern "<.*>|$.*";
                   }
                 }
               }
               list qualified-next-hop {
                 key name;
                 ordered-by user;
                 description "Next hop with qualifiers";
                 uses qualified_nh_obj;
               }
             }
           }
           container multicast {
             description "Global multicast options";
             uses apply-advanced;
             container traceoptions {
               description "Global multicast trace options";
               uses apply-advanced;
               container file {
                 description "Trace file options";
                 leaf filename {
                   description "Name of file in which to write trace information";
                   type string {
                     length "1 .. 1024";
                   }
                 }
                 leaf replace {
                   description "Replace trace file rather than appending to it";
                   status deprecated;
                   type empty;
                 }
                 leaf size {
                   description "Maximum trace file size";
                   type string;
                 }
                 leaf files {
                   description "Maximum number of trace files";
                   default "10";
                   type union {
                     type string {
                       pattern "<.*>|$.*";
                     }
                     type uint32 {
                       range "2 .. 1000";
                     }
                   }
                 }
                 leaf no-stamp {
                   description "Do not timestamp trace file";
                   status deprecated;
                   type empty;
                 }
                 choice world-readable-choice {
                   leaf world-readable {
                     description "Allow any user to read the log file";
                     type empty;
                   }
                   leaf no-world-readable {
                     description "Don't allow any user to read the log file";
                     type empty;
                   }
                 }
               }
               list flag {
                 key name;
                 ordered-by user;
                 description "Tracing parameters";
                 leaf name {
                   type enumeration {
                     enum "parse" {
                       description "Trace configuration parsing";
                     }
                     enum "config-internal" {
                       description "Trace configuration internals";
                     }
                     enum "route" {
                       description "Trace routing information";
                     }
                     enum "normal" {
                       description "Trace normal events";
                     }
                     enum "general" {
                       description "Trace general events";
                     }
                     enum "state" {
                       description "Trace state transitions";
                     }
                     enum "policy" {
                       description "Trace policy processing";
                     }
                     enum "task" {
                       description "Trace routing protocol task processing";
                     }
                     enum "timer" {
                       description "Trace routing protocol timer processing";
                     }
                     enum "all" {
                       description "Trace everything";
                     }
                   }
                 }
                 leaf disable {
                   description "Disable this trace flag";
                   type empty;
                 }
               }
             }
             leaf rpf {
               status deprecated;
               type string;
             }
             list scope {
               key name;
               ordered-by user;
               description "Multicast address scope";
               leaf name {
                 description "Name to identify multicast address scope";
                 type string;
               }
               uses apply-advanced;
               leaf prefix {
                 description "Administratively scoped address";
                 type jt:ipprefix;
               }
               leaf-list interface {
                 ordered-by user;
                 description "Interface on which to configure scoping";
                 type union {
                   type jt:interface-name;
                   type string {
                     pattern "<.*>|$.*";
                   }
                 }
               }
             }
             leaf-list scope-policy {
               ordered-by user;
               description "Scoping policy";
               type jt:policy-algebra;
             }
             list flow-map {
               key name;
               ordered-by user;
               description "Multicast flow map configuration";
               leaf name {
                 description "Name of the flow map";
                 type string;
               }
               uses apply-advanced;
               leaf-list policy {
                 ordered-by user;
                 description "Policy for matched flows";
                 type jt:policy-algebra;
               }
               container bandwidth {
                 presence "enable bandwidth";
                 description "Bandwidth properties for matched flows";
                 leaf bandwidth-value {
                   description "Static or default bandwidth for the matched flows";
                   units "bps";
                   type string;
                 }
                 leaf adaptive {
                   description "Auto-sense bandwidth for matched flows";
                   type empty;
                 }
               }
               leaf-list redundant-sources {
                 ordered-by user;
                 description "Redundant source addresses";
                 type jt:ipaddr;
               }
               container forwarding-cache {
                 description "Forwarding cache properties for matched flows";
                 uses apply-advanced;
                 container timeout {
                   description "Timeout properties for matched flows";
                   choice timeout_choice {
                     case case_1 {
                       leaf timeout-value {
                         description "Timeout for forwarding cache entry";
                         units "minutes";
                         type union {
                           type string {
                             pattern "<.*>|$.*";
                           }
                           type uint32 {
                             range "1 .. 720";
                           }
                         }
                       }
                     }
                     case case_2 {
                       container never {
                         presence "enable never";
                         description "Forwarding cache entries never time out";
                         uses apply-advanced;
                         leaf non-discard-entry-only {
                           description "Apply only to non-discard entries";
                           type empty;
                         }
                       }
                     }
                   }
                 }
               }
             }
             leaf-list resolve-filter {
               ordered-by user;
               description "Multicast resolve policy filter";
               status deprecated;
               type jt:policy-algebra;
             }
             leaf-list ssm-groups {
               ordered-by user;
               description "Source-specific multicast group ranges";
               type jt:ipprefix;
             }
             leaf cont-stats-collection-interval {
               description "IGMP/MLD continuous statistics collection interval";
               default "300";
               type union {
                 type string {
                   pattern "<.*>|$.*";
                 }
                 type uint16 {
                   range "60 .. 3600";
                 }
               }
             }
             leaf asm-override-ssm {
               description "Allow ASM state for SSM group ranges";
               type empty;
             }
             leaf-list rpf-check-policy {
               ordered-by user;
               description "Disable RPF check for a source group pair";
               type jt:policy-algebra;
             }
             container pim-to-igmp-proxy {
               description "PIM-to-IGMP proxy";
               uses apply-advanced;
               leaf-list upstream-interface {
                 ordered-by user;
                 description "Upstream interface list";
                 type union {
                   type jt:interface-name;
                   type string {
                     pattern "<.*>|$.*";
                   }
                 }
                 max-elements 2;
               }
             }
             container pim-to-mld-proxy {
               description "PIM-to-MLD proxy";
               uses apply-advanced;
               leaf-list upstream-interface {
                 ordered-by user;
                 description "Upstream interface list";
                 type union {
                   type jt:interface-name;
                   type string {
                     pattern "<.*>|$.*";
                   }
                 }
                 max-elements 2;
               }
             }
             container forwarding-cache {
               description "Multicast forwarding cache";
               uses apply-advanced;
               leaf allow-maximum {
                 description "Allow maximum of global and family level threshold values for suppress and reuse";
                 type empty;
               }
               list family {
                 key name;
                 ordered-by user;
                 description "Protocol family";
                 leaf name {
                   description "Protocol family";
                   type enumeration {
                     enum "inet" {
                       description "IPv4 family";
                     }
                     enum "inet6" {
                       description "IPv6 family";
                     }
                   }
                 }
                 uses apply-advanced;
                 container threshold {
                   presence "enable threshold";
                   description "Multicast forwarding cache suppress threshold";
                   uses apply-advanced;
                   leaf suppress {
                     description "Suppress threshold";
                     type union {
                       type string {
                         pattern "<.*>|$.*";
                       }
                       type uint32 {
                         range "1 .. 200000";
                       }
                     }
                   }
                   leaf reuse {
                     description "Reuse threshold";
                     type union {
                       type string {
                         pattern "<.*>|$.*";
                       }
                       type uint32 {
                         range "1 .. 200000";
                       }
                     }
                   }
                   leaf mvpn-rpt-suppress {
                     description "MVPN RP tree entry suppress threshold";
                     type union {
                       type string {
                         pattern "<.*>|$.*";
                       }
                       type uint32 {
                         range "1 .. 200000";
                       }
                     }
                   }
                   leaf mvpn-rpt-reuse {
                     description "MVPN RP tree entry reuse threshold";
                     type union {
                       type string {
                         pattern "<.*>|$.*";
                       }
                       type uint32 {
                         range "1 .. 200000";
                       }
                     }
                   }
                   leaf log-warning {
                     description "Percentage at which to start generating warnings";
                     type union {
                       type string {
                         pattern "<.*>|$.*";
                       }
                       type uint32 {
                         range "1 .. 100";
                       }
                     }
                   }
                 }
               }
               container threshold {
                 description "Threshold";
                 uses apply-advanced;
                 leaf suppress {
                   description "Suppress threshold";
                   type union {
                     type string {
                       pattern "<.*>|$.*";
                     }
                     type uint32 {
                       range "1 .. 200000";
                     }
                   }
                 }
                 leaf reuse {
                   description "Reuse threshold";
                   type union {
                     type string {
                       pattern "<.*>|$.*";
                     }
                     type uint32 {
                       range "1 .. 200000";
                     }
                   }
                 }
                 leaf mvpn-rpt-suppress {
                   description "MVPN RP tree entry suppress threshold";
                   type union {
                     type string {
                       pattern "<.*>|$.*";
                     }
                     type uint32 {
                       range "1 .. 200000";
                     }
                   }
                 }
                 leaf mvpn-rpt-reuse {
                   description "MVPN RP tree entry reuse threshold";
                   type union {
                     type string {
                       pattern "<.*>|$.*";
                     }
                     type uint32 {
                       range "1 .. 200000";
                     }
                   }
                 }
                 leaf log-warning {
                   description "Percentage at which to start generating warnings";
                   type union {
                     type string {
                       pattern "<.*>|$.*";
                     }
                     type uint32 {
                       range "1 .. 100";
                     }
                   }
                 }
               }
               leaf timeout {
                 description "Forwarding cache entry timeout in minutes";
                 type union {
                   type string {
                     pattern "<.*>|$.*";
                   }
                   type uint32 {
                     range "1 .. 720";
                   }
                 }
               }
             }
             list interface {
               key name;
               ordered-by user;
               description "Multicast interface options";
               uses multicast_interface_options_type;
             }
             list ssm-map {
               key name;
               ordered-by user;
               description "SSM map definitions";
               leaf name {
                 description "SSM map name";
                 type string;
               }
               uses apply-advanced;
               leaf-list policy {
                 ordered-by user;
                 description "Policy for matching group";
                 type jt:policy-algebra;
               }
               leaf-list source {
                 ordered-by user;
                 description "One or more source addresses";
                 type jt:ipaddr;
               }
             }
             container stream-protection {
               presence "enable stream-protection";
               description "Multicast only Fast Re-Route";
               uses apply-advanced;
               leaf mofrr-primary-path-selection-by-routing {
                 description "Multicast only Fast Re-Route primary path by Routing";
                 type empty;
               }
               leaf mofrr-disjoint-upstream-only {
                 description "Multicast only Fast Re-Route disjoint upstream only";
                 type empty;
               }
               leaf mofrr-no-backup-join {
                 description "Multicast only Fast Re-Route no backup join";
                 type empty;
               }
               leaf mofrr-asm-starg {
                 description "Multicast only Fast Re-Route asm (*,G)";
                 type empty;
               }
               leaf-list policy {
                 ordered-by user;
                 description "MoFRR Policy";
                 type jt:policy-algebra;
               }
             }
             list backup-pe-group {
               key name;
               ordered-by user;
               description "Backup PE group definitions";
               leaf name {
                 description "PE group name";
                 type string;
               }
               uses apply-advanced;
               leaf-list backups {
                 ordered-by user;
                 description "One or more IP addresses";
                 type jt:ipaddr;
                 max-elements 8;
               }
               leaf local-address {
                 description "Address to be used as local-address for this group";
                 type jt:ipaddr;
               }
             }
             leaf omit-wildcard-address {
               description "Omit wildcard source/group fields in SPMSI AD NLRI";
               type empty;
             }
             leaf local-address {
               description "Local address for PIM and MVPN sessions";
               type jt:ipv4addr;
             }
           }
         }
       }
     }
     container telemetry {
       description "Telemetry configuration";
       uses apply-advanced;
       container service-statistics {
         presence "enable service-statistics";
         description "Subscriber Service-statistics configuration";
       }
       container subscriber-statistics {
         presence "enable subscriber-statistics";
         description "Subscriber statistics configuration";
       }
       container queue-statistics {
         description "Telemetry Queue-Statistics configuration";
         uses apply-advanced;
         list interface {
           key name;
           ordered-by user;
           description "Interface name for this telemetry configuration";
           leaf name {
             type enumeration {
               enum "$junos-interface-name" {
                 description "Dynamic profile interface";
               }
             }
           }
           uses apply-advanced;
           leaf refresh {
             description "Refresh interval range 300-86400";
             type union {
               type string {
                 pattern "<.*>|$.*";
               }
               type uint32 {
                 range "300 .. 86400";
               }
             }
           }
           leaf queues {
             description "Queues to be exported 0-7 separated by ,";
             type string {
             }
           }
         }
         list interface-set {
           key name;
           ordered-by user;
           description "Logical interface set configuration";
           leaf name {
             type enumeration {
               enum "$junos-interface-set-name" {
                 description "Dynamic profile Interface set name";
               }
             }
           }
           uses apply-advanced;
           leaf refresh {
             description "Refresh interval range 300-86400";
             type union {
               type string {
                 pattern "<.*>|$.*";
               }
               type uint32 {
                 range "300 .. 86400";
               }
             }
           }
           leaf queues {
             description "Queues to be exported 0-7 separated by ,";
             type string {
             }
           }
         }
       }
     }
     container interfaces {
       description "Interface configuration";
       uses apply-advanced;
       list pic-set {
         key name;
         ordered-by user;
         description "NP bundling configuration";
         leaf name {
           description "Pic set name";
           type string {
             length "1 .. 127";
           }
         }
         uses apply-advanced;
         list interface {
           key name;
           ordered-by user;
           description "One or more interfaces that use this picset";
           leaf name {
             description "Interface name";
             type string {
               length "1 .. 127";
             }
           }
           uses apply-advanced;
         }
         list fpc {
           key name;
           ordered-by user;
           leaf name {
             description "FPC slot number";
             type union {
               type string {
                 pattern "<.*>|$.*";
               }
               type uint32;
             }
           }
           uses apply-advanced;
           list pic {
             key name;
             ordered-by user;
             description "Physical Interface Card number";
             leaf name {
               description "PIC slot number";
               type union {
                 type string {
                   pattern "<.*>|$.*";
                 }
                 type uint32;
               }
             }
             uses apply-advanced;
           }
         }
       }
       list interface-set {
         key name;
         description "Logical interface set configuration";
         leaf name {
           type string;
         }
         uses apply-advanced;
         container load-balance {
           description "Load-balance weight per subscriber interface-set";
           uses apply-advanced;
           leaf weight {
             description "Load-balance weight";
             type union {
               type string {
                 pattern "<.*>|$.*";
               }
               type uint32 {
                 range "1 .. 1000";
               }
             }
           }
         }
         leaf targeted-distribution {
           description "Interface participates in targeted-distribution";
           type empty;
         }
         container targeted-options {
           presence "enable targeted-options";
           description "Targeting specific options";
           uses apply-advanced;
           leaf weight {
             description "Targeting weight for interface set";
             type string;
           }
         }
         list interface {
           key name;
           description "One or more interfaces that belong to interface set";
           leaf name {
             description "Interface name";
             type union {
               type jt:interface-device;
               type string {
                 pattern "<.*>|$.*";
               }
             }
           }
           uses apply-advanced;
           list unit {
             key name;
             description "One or more logical interface unit numbers";
             leaf name {
               description "Unit number";
               type union {
                 type string {
                   pattern "<.*>|$.*";
                 }
                 type uint32 {
                   range "0 .. 1073741823";
                 }
               }
             }
             uses apply-advanced;
           }
           list vlan-tags-outer {
             key name;
             description "One or more outer VLAN tags";
             leaf name {
               description "VLAN tag ID";
               type union {
                 type string {
                   pattern "<.*>|$.*";
                 }
                 type uint32 {
                   range "0 .. 4094";
                 }
               }
             }
             uses apply-advanced;
           }
         }
         container pppoe-underlying-options {
           description "PPP over Ethernet underlying interface-specific options";
           uses pppoe_underlying_options_type;
         }
       }
       container stacked-interface-set {
         presence "enable stacked-interface-set";
         description "Stacked interface set configuration";
         uses apply-advanced;
         list interface-set {
           key name;
           ordered-by user;
           description "Stacked parent interface set configuration";
           leaf name {
             type string;
           }
           uses apply-advanced;
           list interface-set {
             key name;
             ordered-by user;
             description "Stacked child interface set configuration";
             leaf name {
               type string;
             }
             uses apply-advanced;
           }
         }
       }
       container traceoptions {
         description "Interface trace options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           description "Tracing parameters";
           leaf name {
             type enumeration {
               enum "all" {
                 description "Enable all configuration logging";
               }
               enum "kernel" {
                 description "Log configuration IPC messages to kernel";
               }
               enum "change-events" {
                 description "Log changes that produce configuration events";
               }
               enum "kernel-detail" {
                 description "Log details of configuration messages to kernel";
               }
               enum "config-states" {
                 description "Log the configuration state machine changes";
               }
               enum "resource-usage" {
                 description "Log the resource usage for different states";
               }
               enum "gres-events" {
                 description "Log the events related to GRES ";
               }
               enum "select-events" {
                 description "Log the events on select state machine ";
               }
               enum "bfd-events" {
                 description "Log BFD related events";
               }
               enum "lib-events" {
                 description "Log DCD library related events";
               }
               enum "reserved" {
                 description "Reserved DCD logs";
               }
               enum "emergency" {
                 description "Log DCD emergency events";
               }
               enum "alert" {
                 description "Log DCD alert events";
               }
               enum "critical" {
                 description "Log DCD critical events";
               }
               enum "error" {
                 description "Log DCD error events";
               }
               enum "warning" {
                 description "Log DCD warning events";
               }
               enum "notice" {
                 description "Log DCD notification events";
               }
               enum "informational" {
                 description "Log DCD informations";
               }
               enum "debugging" {
                 description "Log DCD debug events";
               }
               enum "verbose" {
                 description "Log DCD debug all events";
               }
               enum "japi" {
                 description "Log DCD JAPI events";
               }
             }
           }
           leaf disable {
             description "Disable this trace flag";
             type empty;
           }
         }
       }
       list interface-range {
         key name;
         ordered-by user;
         description "Interface ranges configuration";
         leaf name {
           description "Interface-range name";
           type string {
             length "1 .. 128";
           }
         }
         list member {
           key name;
           ordered-by user;
           description "Interfaces belonging to the interface range";
           leaf name {
             description "Member interface name";
             type union {
               type jt:interface-range-wild;
               type string {
                 pattern "<.*>|$.*";
               }
             }
           }
           uses apply-advanced;
         }
         list member-range {
           key name;
           ordered-by user;
           description "Interfaces range in <start-range> to <end-range> format";
           leaf name {
             type union {
               type jt:interface-device;
               type string {
                 pattern "<.*>|$.*";
               }
             }
           }
           leaf end-range {
             type union {
               type jt:interface-device;
               type string {
                 pattern "<.*>|$.*";
               }
             }
           }
         }
         uses apply-advanced;
         leaf description {
           description "Text description of interface";
           type string;
         }
         leaf external-model-name {
           description "Name for interface as configured using 3rd-party model";
           type string;
         }
         container management-ethernet-redundancy {
           presence "enable management-ethernet-redundancy";
           description "Management Interface Redundancy";
           uses apply-advanced;
           choice enable_choice {
             case case_1 {
               leaf redundancy-enable {
                 description "Enable Managment Ethernet Redundancy";
                 type empty;
               }
             }
             case case_2 {
               leaf redundancy-disable {
                 description "Disable  Managment Ethernet Redundancy";
                 type empty;
               }
             }
           }
           leaf connectivity-test-interval {
             description "Connectivity test interval";
             default "5";
             units "seconds";
             type union {
               type string {
                 pattern "<.*>|$.*";
               }
               type uint32 {
                 range "1 .. 10";
               }
             }
           }
           leaf connectivity-test-response-interval {
             description "Connectivity test response wait time";
             default "5";
             units "seconds";
             type union {
               type string {
                 pattern "<.*>|$.*";
               }
               type uint32 {
                 range "1 .. 10";
               }
             }
           }
           leaf remote-ipv4-address {
             description "Destination IPV4 address to reach remote ";
             default "nil";
             type jt:ipv4addr;
           }
           leaf remote-ipv6-address {
             description "Destination IPV6 address to reach remote";
             default "nil";
             type jt:ipv6addr;
           }
           leaf number-of-connectivity-retries {
             description "Number of Connectivity retries ";
             default "2";
             type union {
               type string {
                 pattern "<.*>|$.*";
               }
               type uint32 {
                 range "1 .. 8";
               }
             }
           }
         }
         leaf metadata {
           description "Text metadata attached to interface";
           type string;
         }
         choice enable-disable {
           case case_1 {
             leaf disable {
               description "Disable this interface";
               type empty;
             }
           }
         }
         leaf promiscuous-mode {
           description "Enable promiscuous mode for L3 interface";
           type empty;
         }
         leaf port-mirror-instance {
           description "Port-mirror the packet to specified instance";
           type string {
             length "1 .. 64";
           }
         }
         leaf multicast-statistics {
           description "Enable multicast statistics";
           type empty;
         }
         leaf oam-on-svlan {
           description "Propagate SVLAN OAM state to CVLANs";
           type empty;
         }
         container fabric-options {
           description "Fabric interface specific options";
           uses apply-advanced;
           list member-interfaces {
             key name;
             description "Member interface for the fabric interface";
             leaf name {
               description "Interface name of member";
               type union {
                 type jt:interface-device;
                 type string {
                   pattern "<.*>|$.*";
                 }
               }
             }
             uses apply-advanced;
           }
           container remote-chassis {
             presence "enable remote-chassis";
             description "Remote chassis reachability";
             uses apply-advanced;
             leaf destination {
               description "Destination IP address to reach remote chassis";
               type jt:ipv4addr;
             }
           }
         }
         container traceoptions {
           presence "enable traceoptions";
           description "Interface trace options";
           uses apply-advanced;
           list flag {
             key name;
             ordered-by user;
             description "Tracing parameters";
             leaf name {
               type enumeration {
                 enum "ipc" {
                   description "Trace interface IPC messages";
                 }
                 enum "event" {
                   description "Trace interface events";
                 }
                 enum "media" {
                   description "Trace interface media changes";
                 }
                 enum "all" {
                   description "Enable all interface trace flags";
                 }
                 enum "q921" {
                   description "Trace ISDN Q.921 frames";
                 }
                 enum "q931" {
                   description "Trace ISDN Q.931 frames";
                 }
               }
             }
           }
           container file {
             presence "enable file";
             description "Trace file information for ISDN decoded frames";
             uses apply-advanced;
             leaf filename {
               description "Name of file in which to write trace information";
               type string {
                 length "1 .. 1024";
               }
             }
             leaf size {
               description "Maximum trace file size";
               default "128k";
               type string;
             }
             leaf files {
               description "Maximum number of trace files";
               default "10";
               type union {
                 type uint32;
                 type string {
                   pattern "<.*>|$.*";
                 }
               }
             }
             choice world-readable-choice {
               leaf world-readable {
                 description "Allow any user to read the log file";
                 type empty;
               }
               leaf no-world-readable {
                 description "Don't allow any user to read the log file";
                 type empty;
               }
             }
           }
         }
         leaf passive-monitor-mode {
           description "Use interface to tap packets from another router";
           type empty;
         }
         choice keepalive_choices {
           case case_1 {
             container keepalives {
               description "Send or demand keepalive messages";
               presence "enable keepalives";
               uses keepalives_type;
             }
           }
           case case_2 {
             leaf no-keepalives {
               description "Do not send keepalive messages";
               type empty;
             }
           }
         }
         choice traps-choice {
           leaf traps {
             description "Enable SNMP notifications on state changes";
             type empty;
           }
           leaf no-traps {
             description "Don't enable SNMP notifications on state changes";
             type empty;
           }
         }
         choice interface-mib-choice {
           leaf interface-mib {
             description "Enable interface-related MIBs";
             type empty;
           }
           leaf no-interface-mib {
             description "Don't enable interface-related MIBs";
             type empty;
           }
         }
         leaf accounting-profile {
           description "Accounting profile name";
           type string;
         }
         container anchor-point {
           description "Anchor point";
           uses apply-advanced;
           leaf interface-name {
             description "Interface name";
             type union {
               type jt:interface-device;
               type string {
                 pattern "<.*>|$.*";
               }
             }
           }
         }
         container targeted-options {
           description "Targeting specific options for PS/RLT active-active mode";
           uses apply-advanced;
           leaf type {
             description "Targeting type of PS";
             type enumeration {
               enum "manual" {
                 description "Targeting type is Manual";
               }
             }
           }
           choice redundancy_choice {
             case case_1 {
               leaf logical-interface-fpc-redundancy {
                 description "Enable FPC redundancy for logical interfaces";
                 type empty;
               }
             }
             case case_2 {
               leaf logical-interface-chassis-redundancy {
                 description "Enable CHASSIS redundancy for logical interfaces";
                 type empty;
               }
             }
           }
           container rebalance-periodic {
             presence "enable rebalance-periodic";
             uses apply-advanced;
             leaf start-time {
               description "Start time of the rebalance operation ( Wall clock time )";
               type jt:time-of-day;
             }
             leaf interval {
               description "Interval of the rebalance operation in hrs";
               type union {
                 type string {
                   pattern "<.*>|$.*";
                 }
                 type uint32 {
                   range "1 .. 24";
                 }
               }
             }
           }
           leaf rebalance-subscriber-granularity {
             description "Max subscriber aggregate weight";
             type union {
               type string {
                 pattern "<.*>|$.*";
               }
               type uint32 {
                 range "1 .. 65535";
               }
             }
           }
         }
         choice bypass-queueing-chip-choice {
           leaf bypass-queueing-chip {
             description "Enable to bypass queueing chip";
             type empty;
           }
           leaf no-bypass-queueing-chip {
             description "Don't enable to bypass queueing chip";
             type empty;
           }
         }
         choice scheduler_type {
           case case_1 {
             choice per-unit-scheduler-choice {
               leaf per-unit-scheduler {
                 description "Enable subunit queuing on Frame Relay or VLAN IQ interface";
                 type empty;
               }
               leaf no-per-unit-scheduler {
                 description "Don't enable subunit queuing on Frame Relay or VLAN IQ interface";
                 type empty;
               }
             }
           }
           case case_2 {
             leaf shared-scheduler {
               description "Enabled shared queuing on an IQ2 interface";
               type empty;
             }
           }
           case case_3 {
             container hierarchical-scheduler {
               presence "enable hierarchical-scheduler";
               description "Enable hierarchical scheduling";
               leaf maximum-hierarchy-levels {
                 description "Maximum hierarchy levels";
                 type union {
                   type string {
                     pattern "<.*>|$.*";
                   }
                   type uint32;
                 }
               }
               leaf maximum-l2-nodes {
                 description "Maximum l2 nodes, allowed numbers are power of 2 between 1 and 16k (needs FPC reboot)";
                 default "1";
                 type union {
                   type string {
                     pattern "<.*>|$.*";
                   }
                   type uint32 {
                     range "1 .. 16384";
                   }
                 }
               }
               leaf maximum-l3-nodes {
                 description "Maximum l3 nodes, allowed numbers are power of 2 between 2 and 32k (needs FPC reboot)";
                 default "16384";
                 type union {
                   type string {
                     pattern "<.*>|$.*";
                   }
                   type uint32 {
                     range "2 .. 32768";
                   }
                 }
               }
               leaf implicit-hierarchy {
                 description "Implicit hierarchy (follows interface hierarchy)";
                 type empty;
               }
             }
           }
         }
         leaf l2tp-maximum-session {
           description "Maximum L2TP session";
           type union {
             type string {
               pattern "<.*>|$.*";
             }
             type uint32 {
               range "0 .. 64000";
             }
           }
         }
         leaf schedulers {
           description "Number of schedulers to allocate for interface";
           type union {
             type uint32;
             type string {
               pattern "<.*>|$.*";
             }
           }
         }
         leaf interface-transmit-statistics {
           description "Interface statistics based on the transmitted packets";
           type empty;
         }
         leaf cascade-port {
           description "Cascade port";
           type empty;
         }
         leaf dce {
           description "Respond to Frame Relay status enquiry messages";
           type empty;
         }
         choice vlan_tag_mode {
           case case_1 {
             leaf vlan-tagging {
               description "802.1q VLAN tagging support";
               type empty;
             }
           }
           case case_2 {
             leaf stacked-vlan-tagging {
               description "Stacked 802.1q VLAN tagging support";
               type empty;
             }
           }
           case case_3 {
             leaf flexible-vlan-tagging {
               description "Support for no tagging, or single and double 802.1q VLAN tagging";
               type empty;
             }
           }
           case case_4 {
             leaf vlan-vci-tagging {
               description "CCC for VLAN Q-in-Q and ATM VPI/VCI interworking";
               type empty;
             }
           }
         }
         leaf native-vlan-id {
           description "Virtual LAN identifier for untagged frames";
           type union {
             type string {
               pattern "<.*>|$.*";
             }
             type uint32 {
               range "0 .. 4094";
             }
           }
         }
         leaf no-native-vlan-insert {
           description "Disable native-vlan-id insertion to untagged frames";
           type empty;
         }
         leaf vlan-offload {
           description "Offload VLAN filtering to NIC HW";
           type empty;
         }
         leaf input-native-vlan-push {
           description "Control native-vlan-id insertion to untagged frames when input-vlan-map push is configured";
           type enumeration {
             enum "disable" {
               description "Disable input-native-vlan-push";
             }
             enum "enable" {
               description "Enable input-native-vlan-push";
             }
           }
         }
         leaf no-pseudowire-down-on-core-isolation {
           description "Do not bring the pseudowire down in the event of EVPN Core isolation";
           type empty;
         }
         leaf number-of-sub-ports {
           description "Number of channels to create for a port";
           type union {
             type string {
               pattern "<.*>|$.*";
             }
             type uint32 {
               range "1 .. 8";
             }
           }
         }
         leaf unused {
           description "Disable physical port";
           type empty;
         }
         leaf speed {
           description "Link speed";
           type enumeration {
             enum "auto" {
               description "Enable auto negotiation of interface speed";
             }
             enum "auto-10m-100m" {
               description "Enable auto negotiation of limiting interface speed to 10m/100m";
             }
             enum "10m" {
             }
             enum "100m" {
             }
             enum "1g" {
             }
             enum "2.5g" {
             }
             enum "5g" {
             }
             enum "10g" {
             }
             enum "25g" {
             }
             enum "40g" {
             }
             enum "50g" {
             }
             enum "100g" {
             }
             enum "200g" {
             }
             enum "400g" {
             }
             enum "800g" {
             }
             enum "oc3" {
             }
             enum "oc12" {
             }
             enum "oc48" {
             }
           }
         }
         container forwarding-class-accounting {
           presence "enable forwarding-class-accounting";
           description "Configure Forwarding-class-accounting parameters";
           uses apply-advanced;
           leaf direction {
             description "Direction of the traffic to be accounted for IFD";
             type enumeration {
               enum "ingress" {
                 description "Enable forwarding-class-accounting for ingress traffic";
               }
               enum "egress" {
                 description "Enable forwarding-class-accounting for egress traffic";
               }
               enum "both" {
                 description "Enable forwarding-class-accounting for both directions";
               }
             }
           }
           container enhanced {
             presence "enable enhanced";
             uses apply-advanced;
             leaf traffic-type {
               description "Traffic-type to be accounted for forwarding-class-accounting";
               type enumeration {
                 enum "unicast-statistics" {
                   description "Count only unicast traffic for forwarding-class-accounting";
                 }
                 enum "multicast-statistics" {
                   description "Count only multicast traffic for forwarding-class-accounting";
                 }
               }
             }
             leaf family {
               description "Protocol traffic to be accounted for forwarding-class-accounting";
               type enumeration {
                 enum "inet" {
                   description "Enable forwarding-class-accounting for IPv4 family only";
                 }
                 enum "inet6" {
                   description "Enable forwarding-class-accounting for IPv6 family only";
                 }
                 enum "both" {
                   description "Enable forwarding-class-accounting for both IPv4 and IPv6 family only";
                 }
               }
             }
             leaf direction {
               description "Direction of the traffic to be accounted for forwarding-class-accounting";
               type enumeration {
                 enum "ingress" {
                   description "Enable forwarding-class-accounting for ingress traffic";
                 }
                 enum "egress" {
                   description "Enable forwarding-class-accounting for egress traffic";
                 }
                 enum "both" {
                   description "Enable forwarding-class-accounting for both ingress and egress traffic";
                 }
               }
             }
             leaf overhead-bytes {
               description "Per octet overhead bytes to be accounted for forwarding-class-accounting";
               default "0";
               type union {
                 type string {
                   pattern "<.*>|$.*";
                 }
                 type uint32 {
                   range "0 .. 255";
                 }
               }
             }
           }
         }
         container auto-configure {
           description "Auto configuration";
           uses auto_configure_vlan_type;
         }
         leaf mtu {
           description "Maximum transmit packet size";
           type union {
             type string {
               pattern "<.*>|$.*";
             }
             type uint32;
           }
         }
         container hold-time {
           description "Hold time for link up and link down";
           leaf up {
             description "Link up hold time";
             units "milliseconds";
             type union {
               type uint32;
               type string {
                 pattern "<.*>|$.*";
               }
             }
           }
           leaf down {
             description "Link down hold time";
             units "milliseconds";
             type union {
               type uint32;
               type string {
                 pattern "<.*>|$.*";
               }
             }
           }
         }
         container damping {
           description "Interface damping parameters";
           uses apply-advanced;
           leaf half-life {
             description "Damping half life time";
             default "5";
             units "seconds";
             type union {
               type string {
                 pattern "<.*>|$.*";
               }
               type uint32 {
                 range "1 .. 30";
               }
             }
           }
           leaf max-suppress {
             description "Maximum suppress time";
             default "20";
             units "seconds";
             type union {
               type string {
                 pattern "<.*>|$.*";
               }
               type uint32 {
                 range "1 .. 20000";
               }
             }
           }
           leaf reuse {
             description "Reuse threshold";
             default "1000";
             type union {
               type string {
                 pattern "<.*>|$.*";
               }
               type uint32 {
                 range "1 .. 20000";
               }
             }
           }
           leaf suppress {
             description "Suppress threshold";
             default "2000";
             type union {
               type string {
                 pattern "<.*>|$.*";
               }
               type uint32 {
                 range "1 .. 20000";
               }
             }
           }
           leaf enable {
             description "Enable interface damping";
             type empty;
           }
         }
         container link-degrade-monitor {
           presence "enable link-degrade-monitor";
           description "Enable link degrade monitoring";
           uses apply-advanced;
           choice enable_choice {
             case case_1 {
               leaf link-degrade-monitor-enable {
                 description "Enable Link Degrade Monitoring";
                 type empty;
               }
             }
             case case_2 {
               leaf no-link-degrade-monitor-enable {
                 description "Disable Link Degrade Monitoring";
                 type empty;
               }
             }
           }
           container actions {
             description "Action upon link degrade event";
             uses apply-advanced;
             choice action_choice {
               case case_1 {
                 leaf media-based {
                   description "Media based";
                   type empty;
                 }
               }
             }
           }
           container recovery {
             description "Link degrade recovery mechanism";
             uses apply-advanced;
             leaf timer {
               description "Auto recovery timer in seconds";
               default "1800";
               type union {
                 type uint32;
                 type string {
                   pattern "<.*>|$.*";
                 }
               }
             }
             choice receovery_choice {
               case case_1 {
                 leaf auto {
                   description "Automatic recovery";
                   type empty;
                 }
               }
               case case_2 {
                 leaf manual {
                   description "Manual recovery";
                   type empty;
                 }
               }
             }
           }
           container thresholds {
             description "Link degrade threshold parameters";
             uses apply-advanced;
             leaf set {
               description "BER at which link considered degraded(1..16)";
               default "1e-7";
               type string {
               }
             }
             leaf clear {
               description "BER at which link considered improved(1..16)";
               default "1e-12";
               type string {
               }
             }
             leaf warning-set {
               description "BER at which link degrade warning raised(1..16)";
               default "1e-9";
               type string {
               }
             }
             leaf warning-clear {
               description "BER at which link degrade warning cleared(1..16)";
               default "1e-11";
               type string {
               }
             }
             leaf interval {
               description "Consecutive link degrade events";
               default "10";
               type union {
                 type string {
                   pattern "<.*>|$.*";
                 }
                 type uint32 {
                   range "1 .. 256";
                 }
               }
             }
           }
         }
         container satop-options {
           description "Structure-Agnostic TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf payload-size {
             description "Number of payload bytes per packet";
             type union {
               type string {
                 pattern "<.*>|$.*";
               }
               type uint32 {
                 range "64 .. 1024";
               }
             }
           }
           container excessive-packet-loss-rate {
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         container cesopsn-options {
           description "Structure-Aware TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf packetization-latency {
             description "Number of microseconds to create packets";
             units "microseconds";
             type union {
               type string {
                 pattern "<.*>|$.*";
               }
               type uint32 {
                 range "1000 .. 8000";
               }
             }
           }
           leaf payload-size {
             description "Number of payload bytes per packet";
             type union {
               type string {
                 pattern "<.*>|$.*";
               }
               type uint32 {
                 range "64 .. 1024";
               }
             }
           }
           container excessive-packet-loss-rate {
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         container ima-group-options {
           description "IMA group options";
           uses apply-advanced;
           leaf frame-length {
             description "Frame length (cells)";
             type enumeration {
               enum "32" {
               }
               enum "64" {
               }
               enum "128" {
               }
               enum "256" {
               }
             }
           }
           leaf symmetry {
             description "Symmetry of IMA group";
             default "symmetrical-config-and-operation";
             type enumeration {
               enum "symmetrical-config-and-operation" {
               }
               enum "symmetrical-config-asymmetrical-operation" {
               }
             }
           }
           leaf transmit-clock {
             description "Transmit clock";
             type enumeration {
               enum "common" {
                 description "Common transmit clock";
               }
               enum "independent" {
                 description "Independent transmit clock";
               }
             }
           }
           leaf version {
             description "IMA specification version";
             type enumeration {
               enum "1.0" {
                 description "Version 1.0";
               }
               enum "1.1" {
                 description "Version 1.1";
               }
             }
           }
           container minimum-links {
             description "IMA group minimum active links";
             choice minimum_links_type {
               case case_1 {
                 leaf symmetrical {
                   description "Minimum active receive and transmit links";
                   type union {
                     type string {
                       pattern "<.*>|$.*";
                     }
                     type uint32 {
                       range "1 .. 32";
                     }
                   }
                 }
               }
             }
           }
           container frame-synchronization {
             description "IMA group frame synchronization state parameters";
             uses apply-advanced;
             leaf alpha {
               description "Consecutive invalid ICP cells";
               type union {
                 type string {
                   pattern "<.*>|$.*";
                 }
                 type uint32 {
                   range "1 .. 2";
                 }
               }
             }
             leaf beta {
               description "Consecutive errored ICP cells";
               type union {
                 type string {
                   pattern "<.*>|$.*";
                 }
                 type uint32 {
                   range "1 .. 5";
                 }
               }
             }
             leaf gamma {
               description "Consecutive valid ICP cells";
               type union {
                 type string {
                   pattern "<.*>|$.*";
                 }
                 type uint32 {
                   range "1 .. 5";
                 }
               }
             }
           }
           container test-procedure {
             description "IMA group test pattern procedure";
             uses apply-advanced;
             leaf period {
               description "Length of IMA pattern test";
               units "seconds";
               type union {
                 type string {
                   pattern "<.*>|$.*";
                 }
                 type uint32 {
                   range "1 .. 4294967294";
                 }
               }
             }
             leaf interface {
               description "Interface name of the IMA link to test";
               type union {
                 type jt:interface-device;
                 type string {
                   pattern "<.*>|$.*";
                 }
               }
             }
             leaf pattern {
               description "IMA test pattern";
               type union {
                 type string {
                   pattern "<.*>|$.*";
                 }
                 type uint32 {
                   range "1 .. 254";
                 }
               }
             }
           }
           leaf differential-delay {
             description "Maximum differential delay among links in the IMA group";
             units "milliseconds";
             type union {
               type string {
                 pattern "<.*>|$.*";
               }
               type uint32 {
                 range "1 .. 56";
               }
             }
           }
         }
         container ima-link-options {
           description "IMA link options";
           uses apply-advanced;
           leaf group-id {
             description "IMA group ID this IMA link belongs to";
             type union {
               type string {
                 pattern "<.*>|$.*";
               }
               type uint32;
             }
           }
         }
         list multi-chassis-protection {
           key name;
           description "Inter-Chassis protection configuration";
           uses multi-chassis-protection-group;
         }
         container clocking {
           description "Interface clock source";
           choice clocking_choices {
             case case_1 {
               leaf internal {
                 description "Clocking provided by local system";
                 type empty;
               }
             }
             case case_2 {
               container external {
                 presence "enable external";
                 description "Clocking provided by DCE (loop timing)";
                 uses apply-advanced;
                 leaf interface {
                   description "Interface that acts as clock source";
                   type union {
                     type jt:interface-device;
                     type string {
                       pattern "<.*>|$.*";
                     }
                   }
                 }
               }
             }
           }
           uses apply-advanced;
         }
         leaf link-mode {
           description "Link operational mode";
           type enumeration {
             enum "automatic" {
               description "Automatically negotiate duplex";
             }
             enum "half-duplex" {
               description "Half-duplex operation";
             }
             enum "full-duplex" {
               description "Full-duplex operation";
             }
           }
         }
         leaf media-type {
           description "Interface media type (copper or fiber)";
           type enumeration {
             enum "copper" {
               description "Copper as media";
             }
             enum "fiber" {
               description "Fiber as media";
             }
           }
         }
         leaf encapsulation {
           description "Physical link-layer encapsulation";
           type enumeration {
             enum "ethernet" {
               description "Ethernet physical media";
             }
             enum "fddi" {
               description "FDDI physical media";
             }
             enum "token-ring" {
               description "Token Ring physical media";
             }
             enum "ppp" {
               description "Serial PPP device";
             }
             enum "ppp-ccc" {
               description "Serial PPP device for a cross-connect";
             }
             enum "ppp-tcc" {
               description "Serial PPP device for a translational cross-connect";
             }
             enum "ether-vpls-ppp" {
               description "Ethernet VPLS over PPP (bridging) device";
             }
             enum "frame-relay" {
               description "Frame Relay encapsulation";
             }
             enum "frame-relay-ccc" {
               description "Frame Relay for cross-connect";
             }
             enum "frame-relay-tcc" {
               description "Frame Relay for translational cross-connect";
             }
             enum "extended-frame-relay-ccc" {
               description "Any Frame Relay DLCI for cross-connect";
             }
             enum "extended-frame-relay-tcc" {
               description "Any Frame Relay DLCI for translational cross-connect";
             }
             enum "flexible-frame-relay" {
               description "Multiple Frame Relay encapsulations";
             }
             enum "frame-relay-port-ccc" {
               description "Frame Relay port encapsulation for a cross-connect";
             }
             enum "frame-relay-ether-type" {
               description "Cisco-compatible Frame Relay encapsulation";
             }
             enum "frame-relay-ether-type-tcc" {
               description "Cisco-compatible Frame Relay encapsulation for translational cross-connect";
             }
             enum "extended-frame-relay-ether-type-tcc" {
               description "Cisco-compatible Frame Relay encapsulation any DLCI for translational cross-connect";
             }
             enum "cisco-hdlc" {
               description "Cisco-compatible HDLC framing";
             }
             enum "cisco-hdlc-ccc" {
               description "Cisco-compatible HDLC framing for a cross-connect";
             }
             enum "cisco-hdlc-tcc" {
               description "Cisco-compatible HDLC framing for a translational cross-connect";
             }
             enum "vlan-ccc" {
               description "802.1q tagging for a cross-connect";
             }
             enum "extended-vlan-ccc" {
               description "Nonstandard TPID tagging for a cross-connect";
             }
             enum "ethernet-ccc" {
               description "Ethernet cross-connect";
             }
             enum "flexible-ethernet-services" {
               description "Allows per-unit Ethernet encapsulation configuration";
             }
             enum "smds-dxi" {
               description "SMDS DXI framing";
             }
             enum "atm-pvc" {
               description "ATM permanent virtual circuits";
             }
             enum "atm-ccc-cell-relay" {
               description "ATM cell relay encapsulation for cross-connect";
             }
             enum "ethernet-over-atm" {
               description "Ethernet over ATM encapsulation";
             }
             enum "ethernet-tcc" {
               description "Ethernet translational cross-connect";
             }
             enum "extended-vlan-tcc" {
               description "802.1q tagging for a translational cross-connect";
             }
             enum "multilink-frame-relay-uni-nni" {
               description "Multilink Frame Relay UNI NNI (FRF.16) encapsulation";
             }
             enum "satop" {
               description "Structure-Agnostic TDM over Packet encapsulation";
             }
             enum "cesopsn" {
               description "Structure-Agnostic TDM over Packet encapsulation";
             }
             enum "ima" {
               description "Inverse Multiplexing for ATM";
             }
             enum "ethernet-vpls" {
               description "Ethernet virtual private LAN service";
             }
             enum "ethernet-bridge" {
               description "Ethernet layer-2 bridging";
             }
             enum "vlan-vpls" {
               description "VLAN virtual private LAN service";
             }
             enum "vlan-vci-ccc" {
               description "CCC for VLAN Q-in-Q and ATM VPI/VCI interworking";
             }
             enum "extended-vlan-vpls" {
               description "Extended VLAN virtual private LAN service";
             }
             enum "extended-vlan-bridge" {
               description "VLAN layer-2 bridging";
             }
             enum "multilink-ppp" {
               description "Multilink PPP";
             }
             enum "generic-services" {
               description "Generic services";
             }
           }
         }
         leaf network-isolation-profile {
           description "Attach a network isolation profile on this interface";
           type string;
         }
         container esi {
           description "ESI configuration of multi-homed interface";
           uses apply-advanced;
           container auto-derive {
             description "Auto-derive ESI value for the interface";
             uses apply-advanced;
             choice esitype {
               case case_1 {
                 leaf lacp-pe-system-id-and-admin-key {
                   description "Auto-derive ESI from lacp pe system-id and admin key";
                   type empty;
                 }
               }
               case case_2 {
                 leaf type-1-lacp {
                   description "Auto-generate Type1 ESI LACP";
                   type empty;
                 }
               }
               case case_3 {
                 container type-3-system-mac {
                   description "Auto-generate Type3 ESI System-mac";
                   uses apply-advanced;
                   leaf mac {
                     description "System mac";
                     type jt:mac-unicast;
                   }
                   leaf local-discriminator {
                     description "Local-discriminator";
                     type union {
                       type string {
                         pattern "<.*>|$.*";
                       }
                       type int32 {
                         range "0 .. 16777215";
                       }
                     }
                   }
                 }
               }
             }
           }
           leaf identifier {
             description "ESI value for the interface";
             type jt:esi;
           }
           choice mode {
             case case_1 {
               leaf single-active {
                 description "Single-active mode";
                 type empty;
               }
             }
             case case_2 {
               leaf all-active {
                 description "All-active mode";
                 type empty;
               }
             }
           }
           container df-election-granularity {
             presence "enable df-election-granularity";
             description "DF Election Granularity Selection ";
             uses apply-advanced;
             choice mode {
               case case_1 {
                 container per-esi {
                   presence "enable per-esi";
                   description "DF Election Granularity Per Esi";
                   uses apply-advanced;
                   leaf lacp-oos-on-ndf {
                     description "Lacp Oos";
                     type empty;
                   }
                 }
               }
               case case_2 {
                 leaf per-esi-vlan {
                   description "Per Esi Vlan";
                   type empty;
                 }
               }
             }
           }
           container df-election-type {
             presence "enable df-election-type";
             description "DF Election Type";
             uses apply-advanced;
             choice pref_choice {
               case case_1 {
                 container preference {
                   presence "enable preference";
                   description "Preference based DF election";
                   uses apply-advanced;
                   leaf value {
                     description "Preference value for EVPN Multihoming DF election";
                     default "32767";
                     type union {
                       type string {
                         pattern "<.*>|$.*";
                       }
                       type uint32 {
                         range "0 .. 65535";
                       }
                     }
                   }
                 }
               }
             }
             choice mod_choice {
               case case_1 {
                 container mod {
                   presence "enable mod";
                   description "MOD based DF election";
                 }
               }
             }
           }
           leaf source-bmac {
             description "Unicast Source B-MAC address per ESI for PBB-EVPN";
             type jt:mac-unicast;
           }
         }
         container framing {
           description "Frame type";
           uses apply-advanced;
           choice frame {
             case case_1 {
               leaf lan-phy {
                 description "802.3ae 10-Gbps LAN-mode interface";
                 type empty;
               }
             }
             case case_2 {
               leaf wan-phy {
                 description "802.3ae 10-Gbps WAN-mode interface";
                 type empty;
               }
             }
             case case_3 {
               leaf sonet {
                 description "SONET framing";
                 type empty;
               }
             }
             case case_4 {
               leaf sdh {
                 description "SDH framing";
                 type empty;
               }
             }
           }
           leaf precise-bandwidth {
             description "Use precise bandwidth for 10G wan-phy interface";
             type empty;
           }
         }
         leaf unidirectional {
           description "Unidirectional Mode";
           type empty;
         }
         container lmi {
           description "Local Management Interface settings";
           uses apply-advanced;
           leaf n391dte {
             description "DTE full status polling interval";
             type union {
               type string {
                 pattern "<.*>|$.*";
               }
               type uint16 {
                 range "1 .. 255";
               }
             }
           }
           leaf n392dce {
             description "DCE error threshold";
             type union {
               type string {
                 pattern "<.*>|$.*";
               }
               type uint16 {
                 range "1 .. 10";
               }
             }
           }
           leaf n392dte {
             description "DTE error threshold";
             type union {
               type string {
                 pattern "<.*>|$.*";
               }
               type uint16 {
                 range "1 .. 10";
               }
             }
           }
           leaf n393dce {
             description "DCE monitored event count";
             type union {
               type string {
                 pattern "<.*>|$.*";
               }
               type uint16 {
                 range "1 .. 10";
               }
             }
           }
           leaf n393dte {
             description "DTE monitored event count";
             type union {
               type string {
                 pattern "<.*>|$.*";
               }
               type uint16 {
                 range "1 .. 10";
               }
             }
           }
           leaf t391dte {
             description "DTE polling timer";
             units "seconds";
             type union {
               type string {
                 pattern "<.*>|$.*";
               }
               type uint16 {
                 range "5 .. 30";
               }
             }
           }
           leaf t392dce {
             description "DCE polling verification timer";
             units "seconds";
             type union {
               type string {
                 pattern "<.*>|$.*";
               }
               type uint16 {
                 range "5 .. 30";
               }
             }
           }
           leaf lmi-type {
             description "Specify the Frame Relay LMI type";
             type enumeration {
               enum "ansi" {
                 description "Use ANSI Annex D LMI";
               }
               enum "itu" {
                 description "Use ITU Q933a Annex A LMI";
               }
               enum "c-lmi" {
                 description "Use Consortium LMI";
               }
             }
           }
         }
         container mlfr-uni-nni-bundle-options {
           description "Multilink Frame Relay UNI NNI (FRF.16) management settings";
           uses apply-advanced;
           container cisco-interoperability {
             description "FRF.16 Cisco interoperability settings";
             uses apply-advanced;
             leaf send-lip-remove-link-for-link-reject {
               description "Send Link Integrity Protocol remove link on receiving add-link rejection";
               type empty;
             }
           }
           leaf mrru {
             description "Maximum received reconstructed unit";
             units "bytes";
             type union {
               type string {
                 pattern "<.*>|$.*";
               }
               type uint16 {
                 range "1500 .. 4500";
               }
             }
           }
           leaf yellow-differential-delay {
             description "Yellow differential delay among bundle links to give warning";
             units "milliseconds";
             type union {
               type string {
                 pattern "<.*>|$.*";
               }
               type uint16 {
                 range "3 .. 2000";
               }
             }
           }
           leaf red-differential-delay {
             description "Red differential delay among bundle links to take action";
             units "milliseconds";
             type union {
               type string {
                 pattern "<.*>|$.*";
               }
               type uint16 {
                 range "5 .. 2000";
               }
             }
           }
           leaf action-red-differential-delay {
             description "Type of actions when differential delay exceeds red limit";
             type enumeration {
               enum "remove-link" {
                 description "Remove bundle link from service when exceeding red limit";
               }
               enum "disable-tx" {
                 description "Disable transfer of bundle link when exceeding red limit";
               }
             }
           }
           leaf fragment-threshold {
             description "Fragmentation threshold";
             units "bytes";
             type union {
               type string {
                 pattern "<.*>|$.*";
               }
               type uint32 {
                 range "64 .. 16320";
               }
             }
           }
           leaf drop-timeout {
             description "Drop timeout";
             units "milliseconds";
             type union {
               type string {
                 pattern "<.*>|$.*";
               }
               type uint16 {
                 range "0 .. 2000";
               }
             }
           }
           leaf link-layer-overhead {
             description "Link layer bit stuffing overhead (0.0 .. 50.0 percent)";
             type jt:unsigned-float;
           }
           leaf lmi-type {
             description "Specify the multilink Frame Relay UNI NNI LMI type";
             type enumeration {
               enum "ansi" {
                 description "Use ANSI Annex D LMI";
               }
               enum "itu" {
                 description "Use ITU Q933a Annex A LMI";
               }
               enum "c-lmi" {
                 description "Use Consortium LMI";
               }
             }
           }
           leaf minimum-links {
             description "Minimum number of links to sustain the bundle";
             type union {
               type string {
                 pattern "<.*>|$.*";
               }
               type uint16 {
                 range "1 .. 8";
               }
             }
           }
           leaf hello-timer {
             description "LIP hello timer";
             type union {
               type string {
                 pattern "<.*>|$.*";
               }
               type uint16 {
                 range "5 .. 180";
               }
             }
           }
           leaf acknowledge-timer {
             description "LIP ack timer";
             type union {
               type string {
                 pattern "<.*>|$.*";
               }
               type uint16 {
                 range "1 .. 10";
               }
             }
           }
           leaf acknowledge-retries {
             description "LIP ack retry times";
             type union {
               type string {
                 pattern "<.*>|$.*";
               }
               type uint16 {
                 range "1 .. 5";
               }
             }
           }
           leaf n391 {
             description "Multilink Frame Relay UNI NNI full status polling counter";
             type union {
               type string {
                 pattern "<.*>|$.*";
               }
               type uint16 {
                 range "1 .. 255";
               }
             }
           }
           leaf n392 {
             description "Multilink Frame Relay UNI NNI LMI error threshold";
             type union {
               type string {
                 pattern "<.*>|$.*";
               }
               type uint16 {
                 range "1 .. 10";
               }
             }
           }
           leaf n393 {
             description "Multilink Frame Relay UNI NNI LMI monitored event count";
             type union {
               type string {
                 pattern "<.*>|$.*";
               }
               type uint16 {
                 range "1 .. 10";
               }
             }
           }
           leaf t391 {
             description "Multilink Frame Relay UNI NNI link integrity verify polling timer";
             type union {
               type string {
                 pattern "<.*>|$.*";
               }
               type uint16 {
                 range "5 .. 30";
               }
             }
           }
           leaf t392 {
             description "Multilink Frame Relay UNI NNI polling verification timer";
             type union {
               type string {
                 pattern "<.*>|$.*";
               }
               type uint16 {
                 range "5 .. 30";
               }
             }
           }
         }
         leaf mac {
           description "Hardware MAC address";
           type jt:mac-unicast;
         }
         leaf no-forwarding-viable {
           description "Disable forwarding";
           type empty;
         }
         container p4rt {
           description "P4-runtime interfaces";
           uses apply-advanced;
           leaf id {
             description "Port number";
             type union {
               type string {
                 pattern "<.*>|$.*";
               }
               type uint64 {
                 range "1 .. 4294967296";
               }
             }
           }
           leaf node-id {
             description "Device Id";
             type union {
               type string {
                 pattern "<.*>|$.*";
               }
               type uint64 {
                 range "1 .. 18446744073709551615";
               }
             }
           }
         }
         container receive-bucket {
           description "Set receive bucket parameters";
           uses dcd_rx_bucket_config;
         }
         container transmit-bucket {
           description "Set transmit bucket parameters";
           uses dcd_tx_bucket_config;
         }
         leaf shared-interface {
           description "Enable shared interface on the interface";
           type empty;
         }
         container sonet-options {
           description "SONET interface-specific options";
           uses sonet_options_type;
         }
         container logical-tunnel-options {
           description "Logical Tunnel interface-specific options";
           uses apply-advanced;
           container link-protection {
             presence "enable link-protection";
             description "Enable link protection mode";
             uses apply-advanced;
             leaf revertive {
               description "Revert back (Default mode) from active backup link to primary, if primary is UP";
               type empty;
             }
             leaf non-revertive {
               description "Do not revert back from active backup link to primary, if primary is UP";
               type empty;
             }
           }
           leaf per-unit-mac-disable {
             description "Disable the creation of per unit mac address on LT IFLs for VPLS/CCC encaps";
             type empty;
           }
           container load-balance {
             uses aggregate-load-balance;
           }
           leaf distribution-list {
             description "Distribution list to which interface belongs";
             type string {
               length "1 .. 20";
             }
           }
         }
         container aggregated-sonet-options {
           description "Aggregated SONET interface-specific options";
           uses apply-advanced;
           leaf minimum-links {
             description "Minimum number of aggregated links";
             type union {
               type string {
                 pattern "<.*>|$.*";
               }
               type uint16;
             }
           }
           leaf link-speed {
             description "Aggregated links speed";
             type enumeration {
               enum "oc3" {
                 description "Links are OC-3c or STM-1c";
               }
               enum "oc12" {
                 description "Links are OC-12c or STM-4c";
               }
               enum "oc48" {
                 description "Links are OC-48c or STM-16c";
               }
               enum "oc192" {
                 description "Links are OC-192c or STM-64c";
               }
               enum "oc768" {
                 description "Links are OC-768c or STM-256c";
               }
               enum "mixed" {
                 description "Links are various speeds";
               }
             }
           }
           leaf minimum-bandwidth {
             description "Minimum bandwidth necessary to sustain bundle";
             units "bps";
             type union {
               type string {
                 pattern "<.*>|$.*";
               }
               type uint64 {
                 range "0 .. 159232000000";
               }
             }
           }
         }
         container atm-options {
           description "ATM interface-specific options";
           uses apply-advanced;
           leaf pic-type {
             description "Type of ATM PIC (ATM I, ATM II or ATM CE)";
             type enumeration {
               enum "atm-ce" {
                 description "CE PIC";
               }
               enum "atm2" {
                 description "ATM II IQ PIC";
               }
               enum "atm1" {
                 description "ATM I PIC";
               }
             }
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf use-null-cw {
             description "Always insert/strip null control words with cell-relay";
             type empty;
           }
           container promiscuous-mode {
             presence "enable promiscuous-mode";
             description "Set ATM interface to promiscuous mode";
             uses apply-advanced;
             list vpi {
               key name;
               ordered-by user;
               description "Open this VPI in promiscuous mode";
               leaf name {
                 description "Virtual path index";
                 type union {
                   type string {
                     pattern "<.*>|$.*";
                   }
                   type uint32 {
                     range "0 .. 255";
                   }
                 }
               }
             }
           }
           list vpi {
             key name;
             ordered-by user;
             description "Define a virtual path";
             leaf name {
               description "Virtual path index";
               type union {
                 type string {
                   pattern "<.*>|$.*";
                 }
                 type uint32 {
                   range "0 .. 255";
                 }
               }
             }
             uses apply-advanced;
             leaf maximum-vcs {
               description "Maximum number of virtual circuits on this VP";
               type union {
                 type uint32;
                 type string {
                   pattern "<.*>|$.*";
                 }
               }
             }
             container shaping {
               description "Virtual path traffic-shaping options";
               uses dcd_shaping_config;
             }
             container oam-period {
               description "F4 OAM cell period";
               choice oam_period_choices {
                 case case_1 {
                   leaf oam-period {
                     description "F4 OAM cell period";
                     units "seconds";
                     type union {
                       type string {
                         pattern "<.*>|$.*";
                       }
                       type uint32 {
                         range "1 .. 900";
                       }
                     }
                   }
                 }
                 case case_2 {
                   container disable {
                     presence "enable disable";
                     description "Disable F4 OAM loopback";
                   }
                 }
               }
             }
             container oam-liveness {
               description "F4 OAM virtual path liveness parameters";
               uses apply-advanced;
               leaf up-count {
                 description "Number of F4 OAM cells to consider VP up";
                 type union {
                   type string {
                     pattern "<.*>|$.*";
                   }
                   type uint32 {
                     range "1 .. 255";
                   }
                 }
               }
               leaf down-count {
                 description "Number of F4 OAM cells to consider VP down";
                 type union {
                   type string {
                     pattern "<.*>|$.*";
                   }
                   type uint32 {
                     range "1 .. 255";
                   }
                 }
               }
             }
           }
           container ilmi {
             presence "enable ilmi";
             description "Enable Interim Local Management Interface";
             uses apply-advanced;
           }
           list linear-red-profiles {
             key name;
             ordered-by user;
             description "ATM2 CoS virtual circuit drop profiles";
             leaf name {
               description "Linear RED profile name";
               type string {
               }
             }
             leaf queue-depth {
               description "Maximum queue depth";
               units "cells";
               type string;
             }
             leaf high-plp-threshold {
               description "Fill level percentage when linear RED is applied for high PLP";
               type union {
                 type string {
                   pattern "<.*>|$.*";
                 }
                 type uint32 {
                   range "0 .. 100";
                 }
               }
             }
             leaf low-plp-threshold {
               description "Fill level percentage when linear RED is applied for low PLP";
               type union {
                 type string {
                   pattern "<.*>|$.*";
                 }
                 type uint32 {
                   range "0 .. 100";
                 }
               }
             }
             leaf high-plp-max-threshold {
               description "Fill level percentage with 100 percent packet drop for high PLP";
               type union {
                 type string {
                   pattern "<.*>|$.*";
                 }
                 type uint32 {
                   range "0 .. 100";
                 }
               }
             }
             leaf low-plp-max-threshold {
               description "Fill level percentage with 100 percent packet drop for low PLP";
               type union {
                 type string {
                   pattern "<.*>|$.*";
                 }
                 type uint32 {
                   range "0 .. 100";
                 }
               }
             }
           }
           list scheduler-maps {
             key name;
             ordered-by user;
             description "ATM2 CoS parameters assigned to forwarding classes";
             leaf name {
               description "ATM2 CoS scheduler map name";
               type string {
               }
             }
             uses apply-advanced;
             leaf vc-cos-mode {
               description "ATM2 virtual circuit CoS mode";
               type enumeration {
                 enum "strict" {
                   description "Always schedule high priority queue first";
                 }
                 enum "alternate" {
                   description "Every other packet from high priority queue (default)";
                 }
               }
             }
             list forwarding-class {
               key name;
               ordered-by user;
               description "Scheduling parameters associated with forwarding class";
               leaf name {
                 description "Forwarding class name";
                 type string {
                 }
               }
               uses apply-advanced;
               leaf priority {
                 description "Queuing priority assigned to forwarding class";
                 type enumeration {
                   enum "low" {
                     description "Low priority queuing";
                   }
                   enum "high" {
                     description "High priority queuing";
                   }
                 }
               }
               container transmit-weight {
                 description "Transmit weight";
                 choice weight-method {
                   case case_1 {
                     leaf percent {
                       description "Transmit weight as percentage";
                       type union {
                         type string {
                           pattern "<.*>|$.*";
                         }
                         type uint32 {
                           range "5 .. 100";
                         }
                       }
                     }
                   }
                   case case_2 {
                     leaf cells {
                       description "Transmit weight by cells count";
                       type string;
                     }
                   }
                 }
               }
               choice drop-profile-method {
                 case case_1 {
                   container epd-threshold {
                     description "Early packet discard threshold for ATM2";
                     uses epd_threshold_config;
                   }
                 }
                 case case_2 {
                   leaf linear-red-profile {
                     description "Linear RED profile profile name";
                     type string;
                   }
                 }
               }
             }
           }
           container mpls {
             description "MPLS options";
             uses mpls_ifd_options;
           }
           choice payload-scrambler-choice {
             leaf payload-scrambler {
               description "Enable payload scrambling";
               type empty;
             }
             leaf no-payload-scrambler {
               description "Don't enable payload scrambling";
               type empty;
             }
           }
         }
         container multiservice-options {
           description "Multiservice interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
           choice dump-on-flow-control-choice {
             leaf dump-on-flow-control {
               description "Enable dumping for this interface on prolonged flow-control";
               status deprecated;
               type empty;
             }
             leaf no-dump-on-flow-control {
               description "Don't enable dumping for this interface on prolonged flow-control";
               status deprecated;
               type empty;
             }
           }
           choice reset-on-flow-control-choice {
             leaf reset-on-flow-control {
               description "Enable resetting this interface on prolonged flow-control";
               status deprecated;
               type empty;
             }
             leaf no-reset-on-flow-control {
               description "Don't enable resetting this interface on prolonged flow-control";
               status deprecated;
               type empty;
             }
           }
           container flow-control-options {
             description "Flow control configuration";
             uses apply-advanced;
             leaf dump-on-flow-control {
               description "Cause core dump during prolonged flow-control";
               type empty;
             }
             leaf reset-on-flow-control {
               description "Reset interface during prolonged flow-control";
               type empty;
             }
             leaf down-on-flow-control {
               description "Bring interface down during prolonged flow-control";
               type empty;
             }
             leaf up-on-flow-control {
               description "Keep interface up during prolonged flow-control";
               type empty;
             }
           }
         }
         container ggsn-options {
           description "GGSN interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
         }
         container ppp-options {
           description "Point-to-Point Protocol (PPP) interface-specific options";
           uses ppp_options_type;
         }
         container redundancy-options {
           description "Redundancy options";
           uses apply-advanced;
           leaf primary {
             description "Specify the primary interface";
             type union {
               type jt:interface-device;
               type string {
                 pattern "<.*>|$.*";
               }
             }
           }
           leaf secondary {
             description "Specify the secondary interface";
             type union {
               type jt:interface-device;
               type string {
                 pattern "<.*>|$.*";
               }
             }
           }
           container redundancy-peer {
             description "Specify information for peer";
             uses apply-advanced;
             leaf ipaddress {
               description "Specify the IP address";
               type jt:ipv4addr;
             }
           }
           container redundancy-local {
             description "Specify information for the local peer";
             uses apply-advanced;
             leaf data-address {
               description "Specify the HA local data IP address";
               type jt:ipv4addr;
             }
           }
           leaf routing-instance {
             description "Specify routing-instance for the HA traffic";
             type string;
           }
           leaf replication-threshold {
             description "Duration for which flow should remain active for replication";
             default "180";
             units "seconds";
             type union {
               type string {
                 pattern "<.*>|$.*";
               }
               type uint32 {
                 range "60 .. 3600";
               }
             }
           }
           container replication-options {
             description "Specify state replication attributes";
             uses apply-advanced;
             leaf mtu {
               description "Specify the maximal packet size for replicated data";
               default "1500";
               type union {
                 type string {
                   pattern "<.*>|$.*";
                 }
                 type uint32 {
                   range "1500 .. 8000";
                 }
               }
             }
           }
           container replicate-services {
             description "Replicate services state from active to backup";
             uses apply-advanced;
             leaf pgcp {
               description "Replicate the PGCP service state";
               type empty;
             }
           }
         }
         container load-balancing-options {
           description "Load-balancing on services pics";
           uses apply-advanced;
           list member-interface {
             key name;
             max-elements 36;
             leaf name {
               description "Interface name";
               type union {
                 type jt:interface-device;
                 type string {
                   pattern "<.*>|$.*";
                 }
               }
             }
             uses apply-advanced;
             container redundancy-group {
               description "Group id to represent a pair of active-backup mams";
               leaf description {
                 description "Text description mapping the redundancy group id";
                 type string;
               }
               leaf group-id {
                 description "Value for Redundancy-group";
                 type union {
                   type string {
                     pattern "<.*>|$.*";
                   }
                   type uint32 {
                     range "1 .. 18";
                   }
                 }
               }
             }
           }
           container member-failure-options {
             description "Load balancing member failure handling options";
             uses apply-advanced;
             choice member-failure {
               case case_1 {
                 container redistribute-all-traffic {
                   presence "enable redistribute-all-traffic";
                   description "On a member failure, redistribute traffic to ams";
                   uses apply-advanced;
                   leaf enable-rejoin {
                     description "Failed member can rejoin after recovery";
                     type empty;
                   }
                 }
               }
               case case_2 {
                 container drop-member-traffic {
                   presence "enable drop-member-traffic";
                   description "On a member failure, drop its traffic";
                   uses apply-advanced;
                   leaf rejoin-timeout {
                     description "Wait time(in seconds) for failed member to rejoin";
                     default "120";
                     type union {
                       type string {
                         pattern "<.*>|$.*";
                       }
                       type uint32 {
                         range "0 .. 1000";
                       }
                     }
                   }
                   leaf enable-rejoin {
                     description "Failed member can join after recovery";
                     type empty;
                   }
                 }
               }
             }
           }
           leaf no-bundle-flap {
             description "No bundle flap on member addition - recommended only with IPSec services";
             type empty;
           }
           container high-availability-options {
             description "High Availability options for Load-balancing";
             uses apply-advanced;
             choice ha-type {
               case case_1 {
                 container many-to-one {
                   description "N:1 High Availability model";
                   uses apply-advanced;
                   leaf preferred-backup {
                     description "Preferred backup Interface name";
                     type union {
                       type jt:interface-device;
                       type string {
                         pattern "<.*>|$.*";
                       }
                     }
                   }
                 }
               }
               case case_2 {
                 container one-to-one {
                   description "1:1 High Availability model";
                   uses apply-advanced;
                   list redundancy-group {
                     key name;
                     ordered-by user;
                     description "Group number for linking HA member for intra-chassis";
                     leaf name {
                       description "Value for HA Redundancy-group";
                       type union {
                         type string {
                           pattern "<.*>|$.*";
                         }
                         type uint32 {
                           range "1 .. 18";
                         }
                       }
                     }
                     leaf preferred-backup {
                       description "Preferred backup Interface name for Redundancy group";
                       type union {
                         type jt:interface-device;
                         type string {
                           pattern "<.*>|$.*";
                         }
                       }
                     }
                   }
                   leaf preferred-backup {
                     description "Preferred backup Interface name";
                     type union {
                       type jt:interface-device;
                       type string {
                         pattern "<.*>|$.*";
                       }
                     }
                   }
                 }
               }
             }
           }
         }
         container aggregated-inline-services-options {
           description "Aggregated Inline Service interface specific options";
           uses apply-advanced;
           leaf primary-interface {
             description "Specify the primary interface";
             type union {
               type jt:interface-device;
               type string {
                 pattern "<.*>|$.*";
               }
             }
           }
           leaf secondary-interface {
             description "Specify the secondary interface";
             type union {
               type jt:interface-device;
               type string {
                 pattern "<.*>|$.*";
               }
             }
           }
         }
         container anchoring-options {
           description "Groups anchoring PFEs or FPCs together.";
           uses apply-advanced;
           leaf apfe-group-set {
             description "Ties up different anchoring groups to share similar fate";
             type string {
               length "1 .. 32";
             }
           }
           list primary-list {
             key name;
             description "Primary anchoring PFE name.";
             leaf name {
               description "Anchoring PFE name.";
               type string {
               }
             }
             uses apply-advanced;
           }
           container secondary {
             presence "enable secondary";
             description "Secondary anchoring PFE name.";
             uses apply-advanced;
             leaf anchoring-device-name {
               description "Anchoring PFE name.";
               type string {
               }
             }
           }
           choice mode {
             case case_1 {
               leaf warm-standby {
                 description "Delayed failover to secondary when primary fails";
                 type empty;
               }
             }
           }
         }
         container lsq-failure-options {
           description "Link services queuing failure options";
           uses apply-advanced;
           list trigger-link-failure {
             key name;
             ordered-by user;
             description "Link on which to trigger failure";
             leaf name {
               description "Interface name";
               type union {
                 type jt:interface-device;
                 type string {
                   pattern "<.*>|$.*";
                 }
               }
             }
             uses apply-advanced;
           }
           choice no-termination-request-choice {
             leaf no-termination-request {
               description "Do not send PPP termination requests";
               type empty;
             }
             leaf no-no-termination-request {
               description "Don't do not send PPP termination requests";
               type empty;
             }
           }
         }
         container redundancy-group {
           description "Redundancy group configuration";
           uses apply-advanced;
           list member-interface {
             key name;
             description "Member interface for the redundancy group";
             leaf name {
               description "Interface name of member";
               type union {
                 type jt:interface-device;
                 type string {
                   pattern "<.*>|$.*";
                 }
               }
             }
             uses apply-advanced;
             choice redundancy {
               case case_1 {
                 leaf active {
                   description "Active interface";
                   type empty;
                 }
               }
               case case_2 {
                 leaf backup {
                   description "Backup interface";
                   type empty;
                 }
               }
             }
           }
           leaf maximum-links {
             type union {
               type string {
                 pattern "<.*>|$.*";
               }
               type uint32 {
                 range "2 .. 32";
               }
             }
           }
         }
         container services-options {
           description "Services interface-specific options";
           uses apply-advanced;
           container syslog {
             description "Define system log parameters";
             uses log-object;
           }
           container jflow-log {
             description "Define Jflow-log parameters.";
             uses apply-advanced;
             leaf message-rate-limit {
               description "Maximum jflow-log NAT error events allowed per second from this interface";
               units "messages per second";
               type union {
                 type string {
                   pattern "<.*>|$.*";
                 }
                 type uint32 {
                   range "1 .. 2147483647";
                 }
               }
             }
           }
           container deterministic-nat-configuration-log-interval {
             presence "enable deterministic-nat-configuration-log-interval";
             description "Define Deterministic NAT parameters";
             uses apply-advanced;
             leaf interval {
               description "Interval in which deterministic NAT logs are generated";
               units "seconds";
               type union {
                 type string {
                   pattern "<.*>|$.*";
                 }
                 type uint32 {
                   range "1800 .. 86400";
                 }
               }
             }
           }
           leaf open-timeout {
             description "Timeout period for TCP session establishment";
             units "seconds";
             type union {
               type string {
                 pattern "<.*>|$.*";
               }
               type uint32 {
                 range "4 .. 300";
               }
             }
           }
           leaf close-timeout {
             description "Timeout period for TCP session tear-down";
             units "seconds";
             type union {
               type string {
                 pattern "<.*>|$.*";
               }
               type uint32 {
                 range "2 .. 300";
               }
             }
           }
           leaf inactivity-timeout {
             description "Inactivity timeout period for established sessions (4..86400)";
             units "seconds";
             type union {
               type uint32;
               type string {
                 pattern "<.*>|$.*";
               }
             }
           }
           leaf inactivity-tcp-timeout {
             description "Inactivity timeout period for TCP established sessions";
             units "seconds";
             type union {
               type string {
                 pattern "<.*>|$.*";
               }
               type uint32 {
                 range "4 .. 86400";
               }
             }
           }
           leaf inactivity-asymm-tcp-timeout {
             description "Inactivity timeout period for asymmetric TCP established sessions";
             units "seconds";
             type union {
               type string {
                 pattern "<.*>|$.*";
               }
               type uint32 {
                 range "4 .. 86400";
               }
             }
           }
           leaf inactivity-non-tcp-timeout {
             description "Inactivity timeout period for non-TCP established sessions";
             units "seconds";
             type union {
               type string {
                 pattern "<.*>|$.*";
               }
               type uint32 {
                 range "4 .. 86400";
               }
             }
           }
           leaf session-timeout {
             description "Session timeout period for established sessions";
             units "seconds";
             type union {
               type string {
                 pattern "<.*>|$.*";
               }
               type uint32 {
                 range "4 .. 86400";
               }
             }
           }
           leaf disable-global-timeout-override {
             description "Disallow overriding  global inactivity or session timeout";
             type empty;
           }
           leaf tcp-tickles {
             description "Number of TCP keep-alive packets to be sent for bi-directional TCP flows";
             default "4";
             type union {
               type string {
                 pattern "<.*>|$.*";
               }
               type uint8 {
                 range "0 .. 30";
               }
             }
           }
           container trio-flow-offload {
             presence "enable trio-flow-offload";
             description "Allow PIC to offload flows to Trio-based PFE";
             uses apply-advanced;
             leaf minimum-bytes {
               description "Attempt flow offload after minimum bytes are seen on the flow";
               type union {
                 type uint32;
                 type string {
                   pattern "<.*>|$.*";
                 }
               }
             }
           }
           leaf fragment-limit {
             description "Maximum number of fragments allowed for a packet";
             default "64";
             type union {
               type string {
                 pattern "<.*>|$.*";
               }
               type uint8 {
                 range "1 .. 250";
               }
             }
           }
           leaf reassembly-timeout {
             description "Re-assembly timeout (seconds) for fragments of a packet";
             default "4";
             units "seconds";
             type union {
               type string {
                 pattern "<.*>|$.*";
               }
               type uint8 {
                 range "1 .. 60";
               }
             }
           }
           leaf cgn-pic {
             description "PIC will be used for Carrier Grade NAT configuration only";
             type empty;
           }
           leaf pba-interim-logging-interval {
             description "Interim logging interval in seconds";
             default "0";
             units "seconds";
             type union {
               type string {
                 pattern "<.*>|$.*";
               }
               type uint32 {
                 range "0 .. 86400";
               }
             }
           }
           container session-limit {
             presence "enable session-limit";
             description "Session limit";
             uses apply-advanced;
             leaf maximum {
               description "Maximum number of sessions allowed simultaneously";
               type string;
             }
             leaf rate {
               description "Maximum number of new sessions allowed per second";
               type string;
             }
             leaf cpu-load-threshold {
               description "CPU limit in percentage for auto-tuning of session rate";
               units "percent";
               type union {
                 type string {
                   pattern "<.*>|$.*";
                 }
                 type uint8 {
                   range "1 .. 100";
                 }
               }
             }
           }
           leaf enable-subscriber-analysis {
             description "Enable subscriber analysis on the interface";
             type empty;
           }
           leaf disable-subscriber-analysis {
             description "Disable subscriber analysis on the interface";
             type empty;
           }
           leaf disable-usp-tracing {
             description "Disable usp tracing on this pic";
             type empty;
           }
           leaf disable-drop-flows {
             description "Disable drop flows on this pic";
             type empty;
           }
           container ignore-errors {
             presence "enable ignore-errors";
             description "Ignore anomalies or errors";
             leaf tcp {
               description "TCP protocol errors";
               type empty;
             }
             leaf alg {
               description "ALG anomalies or errors";
               type empty;
             }
           }
           container capture {
             description "Packet capture for SFW and NAT on the Services PIC";
             uses apply-advanced;
             leaf capture-size {
               description "The number of packets to store";
               type union {
                 type string {
                   pattern "<.*>|$.*";
                 }
                 type uint32 {
                   range "1 .. 344000";
                 }
               }
             }
             leaf pkt-size {
               description "Number of bytes to be saved from each packet";
               type union {
                 type string {
                   pattern "<.*>|$.*";
                 }
                 type uint16 {
                   range "64 .. 15000";
                 }
               }
             }
             leaf logs-per-packet {
               description "The number of trace messages stored for each packet";
               type union {
                 type string {
                   pattern "<.*>|$.*";
                 }
                 type uint16 {
                   range "0 .. 500";
                 }
               }
             }
             leaf max-log-line-size {
               description "The maximum length of a stored trace message";
               type union {
                 type uint8;
                 type string {
                   pattern "<.*>|$.*";
                 }
               }
             }
             container filter {
               presence "enable filter";
               description "Filtering options for the packet capture";
               uses apply-advanced;
               container source-ip {
                 description "Filter based on source-ip (and wildcard)";
                 leaf ip {
                   description "Source IP";
                   type jt:ipaddr;
                 }
                 leaf wildcard {
                   description "Source IP wildcard";
                   type jt:ipaddr;
                 }
               }
               container dest-ip {
                 description "Filter based on dest-ip (and wildcard)";
                 leaf ip {
                   description "Dest IP";
                   type jt:ipaddr;
                 }
                 leaf wildcard {
                   description "Dest IP wildcard";
                   type jt:ipaddr;
                 }
               }
               container sw-sip {
                 description "Filter based on source softwire ip (and wildcard)";
                 leaf ip {
                   description "Source softwire IP";
                   type jt:ipv6addr;
                 }
                 leaf wildcard {
                   description "Source IP wildcard";
                   type jt:ipv6addr;
                 }
               }
               container sw-dip {
                 description "Filter based on destination softwire ip (and wildcard)";
                 leaf ip {
                   description "Destination softwire IP";
                   type jt:ipaddr;
                 }
                 leaf wildcard {
                   description "Destination IP wildcard";
                   type jt:ipaddr;
                 }
               }
               container sport-range {
                 description "Filter based on source port";
                 leaf low {
                   description "Source port range start";
                   type union {
                     type uint16;
                     type string {
                       pattern "<.*>|$.*";
                     }
                   }
                 }
                 leaf high {
                   description "Source port range end";
                   type union {
                     type uint16;
                     type string {
                       pattern "<.*>|$.*";
                     }
                   }
                 }
               }
               container dport-range {
                 description "Filter based on destination port";
                 leaf low {
                   description "Destination port range start";
                   type union {
                     type uint16;
                     type string {
                       pattern "<.*>|$.*";
                     }
                   }
                 }
                 leaf high {
                   description "Destination port range end";
                   type union {
                     type uint16;
                     type string {
                       pattern "<.*>|$.*";
                     }
                   }
                 }
               }
               leaf proto {
                 description "Filter based on L4 protocol";
                 type enumeration {
                   enum "icmp" {
                   }
                   enum "tcp" {
                   }
                   enum "udp" {
                   }
                 }
               }
             }
           }
           container flow {
             description "Define flow parameters";
             uses apply-advanced;
             container traceoptions {
               description "Trace options for flow services";
               uses flow-traceoptions-object;
             }
           }
           leaf fpc-pic-information {
             description "Include FPC and PIC slot number in the syslogs";
             type empty;
           }
           leaf utc-timestamp {
             description "Use UTC time for security log timestamps";
             type empty;
           }
           leaf syslog-local-system-timestamp {
             description "Use local system time for services syslog timestamp";
             type empty;
           }
         }
         container t3-options {
           description "T3 interface-specific options";
           uses apply-advanced;
           leaf loopback {
             description "Loopback mode";
             type enumeration {
               enum "local" {
                 description "Local loopback";
               }
               enum "remote" {
                 description "Remote loopback";
               }
               enum "payload" {
                 description "Payload loopback";
               }
             }
           }
           choice long-buildout-choice {
             leaf long-buildout {
               description "Set hardware to drive line longer than 255 feet";
               type empty;
             }
             leaf no-long-buildout {
               description "Don't set hardware to drive line longer than 255 feet";
               type empty;
             }
           }
           choice loop-timing-choice {
             leaf loop-timing {
               description "Set loop timing for T3";
               type empty;
             }
             leaf no-loop-timing {
               description "Don't set loop timing for T3";
               type empty;
             }
           }
           choice unframed-choice {
             leaf unframed {
               description "Enable unframed mode";
               type empty;
             }
             leaf no-unframed {
               description "Don't enable unframed mode";
               type empty;
             }
           }
           container compatibility-mode {
             description "Set CSU compatibility mode";
             choice vendor {
               case case_1 {
                 container larscom {
                   presence "enable larscom";
                   description "Compatible with Larscom CSU";
                   leaf subrate {
                     description "Set subrate value";
                     type union {
                       type string {
                         pattern "<.*>|$.*";
                       }
                       type uint32 {
                         range "1 .. 14";
                       }
                     }
                   }
                 }
               }
               case case_2 {
                 container verilink {
                   presence "enable verilink";
                   description "Compatible with Verilink CSU (not on 2/4-port T3 PIC)";
                   leaf subrate {
                     description "Set subrate value";
                     type union {
                       type string {
                         pattern "<.*>|$.*";
                       }
                       type uint32 {
                         range "1 .. 28";
                       }
                     }
                   }
                 }
               }
               case case_3 {
                 container adtran {
                   presence "enable adtran";
                   description "Compatible with Adtran CSU (not on 2/4-port T3 PIC)";
                   leaf subrate {
                     description "Set subrate value";
                     type union {
                       type string {
                         pattern "<.*>|$.*";
                       }
                       type uint32 {
                         range "1 .. 588";
                       }
                     }
                   }
                 }
               }
               case case_4 {
                 container kentrox {
                   presence "enable kentrox";
                   description "Compatible with Kentrox CSU";
                   leaf subrate {
                     description "Set subrate value (not on 2/4-port T3 PIC)";
                     type union {
                       type string {
                         pattern "<.*>|$.*";
                       }
                       type uint32 {
                         range "1 .. 69";
                       }
                     }
                   }
                 }
               }
               case case_5 {
                 container digital-link {
                   presence "enable digital-link";
                   description "Compatible with Digital Link CSU";
                   leaf subrate {
                     description "Set subrate value";
                     type enumeration {
                       enum "301Kb" {
                         description "301 Kbps";
                       }
                       enum "601Kb" {
                         description "601 Kbps";
                       }
                       enum "902Kb" {
                         description "902 Kbps";
                       }
                       enum "1.2Mb" {
                         description "1.2 Mbps";
                       }
                       enum "1.5Mb" {
                         description "1.5 Mbps";
                       }
                       enum "1.8Mb" {
                         description "1.8 Mbps";
                       }
                       enum "2.1Mb" {
                         description "2.1 Mbps";
                       }
                       enum "2.4Mb" {
                         description "2.4 Mbps";
                       }
                       enum "2.7Mb" {
                         description "2.7 Mbps";
                       }
                       enum "3.0Mb" {
                         description "3.0 Mbps";
                       }
                       enum "3.3Mb" {
                         description "3.3 Mbps";
                       }
                       enum "3.6Mb" {
                         description "3.6 Mbps";
                       }
                       enum "3.9Mb" {
                         description "3.9 Mbps";
                       }
                       enum "4.2Mb" {
                         description "4.2 Mbps";
                       }
                       enum "4.5Mb" {
                         description "4.5 Mbps";
                       }
                       enum "4.8Mb" {
                         description "4.8 Mbps";
                       }
                       enum "5.1Mb" {
                         description "5.1 Mbps";
                       }
                       enum "5.4Mb" {
                         description "5.4 Mbps";
                       }
                       enum "5.7Mb" {
                         description "5.7 Mbps";
                       }
                       enum "6.0Mb" {
                         description "6.0 Mbps";
                       }
                       enum "6.3Mb" {
                         description "6.3 Mbps";
                       }
                       enum "6.6Mb" {
                         description "6.6 Mbps";
                       }
                       enum "6.9Mb" {
                         description "6.9 Mbps";
                       }
                       enum "7.2Mb" {
                         description "7.2 Mbps";
                       }
                       enum "7.5Mb" {
                         description "7.5 Mbps";
                       }
                       enum "7.8Mb" {
                         description "7.8 Mbps";
                       }
                       enum "8.1Mb" {
                         description "8.1 Mbps";
                       }
                       enum "8.4Mb" {
                         description "8.4 Mbps";
                       }
                       enum "8.7Mb" {
                         description "8.7 Mbps";
                       }
                       enum "9.0Mb" {
                         description "9.0 Mbps";
                       }
                       enum "9.3Mb" {
                         description "9.3 Mbps";
                       }
                       enum "9.6Mb" {
                         description "9.6 Mbps";
                       }
                       enum "9.9Mb" {
                         description "9.9 Mbps";
                       }
                       enum "10.2Mb" {
                         description "10.2 Mbps";
                       }
                       enum "10.5Mb" {
                         description "10.5 Mbps";
                       }
                       enum "10.8Mb" {
                         description "10.8 Mbps";
                       }
                       enum "11.1Mb" {
                         description "11.1 Mbps";
                       }
                       enum "11.4Mb" {
                         description "11.4 Mbps";
                       }
                       enum "11.7Mb" {
                         description "11.7 Mbps";
                       }
                       enum "12.0Mb" {
                         description "12.0 Mbps";
                       }
                       enum "12.3Mb" {
                         description "12.3 Mbps";
                       }
                       enum "12.6Mb" {
                         description "12.6 Mbps";
                       }
                       enum "12.9Mb" {
                         description "12.9 Mbps";
                       }
                       enum "13.2Mb" {
                         description "13.2 Mbps";
                       }
                       enum "13.5Mb" {
                         description "13.5 Mbps";
                       }
                       enum "13.8Mb" {
                         description "13.8 Mbps";
                       }
                       enum "14.1Mb" {
                         description "14.1 Mbps";
                       }
                       enum "14.4Mb" {
                         description "14.4 Mbps";
                       }
                       enum "14.7Mb" {
                         description "14.7 Mbps";
                       }
                       enum "15.0Mb" {
                         description "15.0 Mbps";
                       }
                       enum "15.3Mb" {
                         description "15.3 Mbps";
                       }
                       enum "15.6Mb" {
                         description "15.6 Mbps";
                       }
                       enum "15.9Mb" {
                         description "15.9 Mbps";
                       }
                       enum "16.2Mb" {
                         description "16.2 Mbps";
                       }
                       enum "16.5Mb" {
                         description "16.5 Mbps";
                       }
                       enum "16.8Mb" {
                         description "16.8 Mbps";
                       }
                       enum "17.1Mb" {
                         description "17.1 Mbps";
                       }
                       enum "17.4Mb" {
                         description "17.4 Mbps";
                       }
                       enum "17.7Mb" {
                         description "17.7 Mbps";
                       }
                       enum "18.0Mb" {
                         description "18.0 Mbps";
                       }
                       enum "18.3Mb" {
                         description "18.3 Mbps";
                       }
                       enum "18.6Mb" {
                         description "18.6 Mbps";
                       }
                       enum "18.9Mb" {
                         description "18.9 Mbps";
                       }
                       enum "19.2Mb" {
                         description "19.2 Mbps";
                       }
                       enum "19.5Mb" {
                         description "19.5 Mbps";
                       }
                       enum "19.8Mb" {
                         description "19.8 Mbps";
                       }
                       enum "20.1Mb" {
                         description "20.1 Mbps";
                       }
                       enum "20.5Mb" {
                         description "20.5 Mbps";
                       }
                       enum "20.8Mb" {
                         description "20.8 Mbps";
                       }
                       enum "21.1Mb" {
                         description "21.1 Mbps";
                       }
                       enum "21.4Mb" {
                         description "21.4 Mbps";
                       }
                       enum "21.7Mb" {
                         description "21.7 Mbps";
                       }
                       enum "22.0Mb" {
                         description "22.0 Mbps";
                       }
                       enum "22.3Mb" {
                         description "22.3 Mbps";
                       }
                       enum "22.6Mb" {
                         description "22.6 Mbps";
                       }
                       enum "22.9Mb" {
                         description "22.9 Mbps";
                       }
                       enum "23.2Mb" {
                         description "23.2 Mbps";
                       }
                       enum "23.5Mb" {
                         description "23.5 Mbps";
                       }
                       enum "23.8Mb" {
                         description "23.8 Mbps";
                       }
                       enum "24.1Mb" {
                         description "24.1 Mbps";
                       }
                       enum "24.4Mb" {
                         description "24.4 Mbps";
                       }
                       enum "24.7Mb" {
                         description "24.7 Mbps";
                       }
                       enum "25.0Mb" {
                         description "25.0 Mbps";
                       }
                       enum "25.3Mb" {
                         description "25.3 Mbps";
                       }
                       enum "25.6Mb" {
                         description "25.6 Mbps";
                       }
                       enum "25.9Mb" {
                         description "25.9 Mbps";
                       }
                       enum "26.2Mb" {
                         description "26.2 Mbps";
                       }
                       enum "26.5Mb" {
                         description "26.5 Mbps";
                       }
                       enum "26.8Mb" {
                         description "26.8 Mbps";
                       }
                       enum "27.1Mb" {
                         description "27.1 Mbps";
                       }
                       enum "27.4Mb" {
                         description "27.4 Mbps";
                       }
                       enum "27.7Mb" {
                         description "27.7 Mbps";
                       }
                       enum "28.0Mb" {
                         description "28.0 Mbps";
                       }
                       enum "28.3Mb" {
                         description "28.3 Mbps";
                       }
                       enum "28.6Mb" {
                         description "28.6 Mbps";
                       }
                       enum "28.9Mb" {
                         description "28.9 Mbps";
                       }
                       enum "29.2Mb" {
                         description "29.2 Mbps";
                       }
                       enum "29.5Mb" {
                         description "29.5 Mbps";
                       }
                       enum "29.8Mb" {
                         description "29.8 Mbps";
                       }
                       enum "30.1Mb" {
                         description "30.1 Mbps";
                       }
                       enum "30.4Mb" {
                         description "30.4 Mbps";
                       }
                       enum "30.7Mb" {
                         description "30.7 Mbps";
                       }
                       enum "31.0Mb" {
                         description "31.0 Mbps";
                       }
                       enum "31.3Mb" {
                         description "31.3 Mbps";
                       }
                       enum "31.6Mb" {
                         description "31.6 Mbps";
                       }
                       enum "31.9Mb" {
                         description "31.9 Mbps";
                       }
                       enum "32.2Mb" {
                         description "32.2 Mbps";
                       }
                       enum "32.5Mb" {
                         description "32.5 Mbps";
                       }
                       enum "32.8Mb" {
                         description "32.8 Mbps";
                       }
                       enum "33.1Mb" {
                         description "33.1 Mbps";
                       }
                       enum "33.4Mb" {
                         description "33.4 Mbps";
                       }
                       enum "33.7Mb" {
                         description "33.7 Mbps";
                       }
                       enum "34.0Mb" {
                         description "34.0 Mbps";
                       }
                       enum "34.3Mb" {
                         description "34.3 Mbps";
                       }
                       enum "34.6Mb" {
                         description "34.6 Mbps";
                       }
                       enum "34.9Mb" {
                         description "34.9 Mbps";
                       }
                       enum "35.2Mb" {
                         description "35.2 Mbps";
                       }
                       enum "35.5Mb" {
                         description "35.5 Mbps";
                       }
                       enum "35.8Mb" {
                         description "35.8 Mbps";
                       }
                       enum "36.1Mb" {
                         description "36.1 Mbps";
                       }
                       enum "36.4Mb" {
                         description "36.4 Mbps";
                       }
                       enum "36.7Mb" {
                         description "36.7 Mbps";
                       }
                       enum "37.0Mb" {
                         description "37.0 Mbps";
                       }
                       enum "37.3Mb" {
                         description "37.3 Mbps";
                       }
                       enum "37.6Mb" {
                         description "37.6 Mbps";
                       }
                       enum "37.9Mb" {
                         description "37.9 Mbps";
                       }
                       enum "38.2Mb" {
                         description "38.2 Mbps";
                       }
                       enum "38.5Mb" {
                         description "38.5 Mbps";
                       }
                       enum "38.8Mb" {
                         description "38.8 Mbps";
                       }
                       enum "39.1Mb" {
                         description "39.1 Mbps";
                       }
                       enum "39.4Mb" {
                         description "39.4 Mbps";
                       }
                       enum "39.7Mb" {
                         description "39.7 Mbps";
                       }
                       enum "40.0Mb" {
                         description "40.0 Mbps";
                       }
                       enum "40.3Mb" {
                         description "40.3 Mbps";
                       }
                       enum "40.6Mb" {
                         description "40.6 Mbps";
                       }
                       enum "40.9Mb" {
                         description "40.9 Mbps";
                       }
                       enum "41.2Mb" {
                         description "41.2 Mbps";
                       }
                       enum "41.5Mb" {
                         description "41.5 Mbps";
                       }
                       enum "41.8Mb" {
                         description "41.8 Mbps";
                       }
                       enum "42.1Mb" {
                         description "42.1 Mbps";
                       }
                       enum "42.4Mb" {
                         description "42.4 Mbps";
                       }
                       enum "42.7Mb" {
                         description "42.7 Mbps";
                       }
                       enum "43.0Mb" {
                         description "43.0 Mbps";
                       }
                       enum "43.3Mb" {
                         description "43.3 Mbps";
                       }
                       enum "43.6Mb" {
                         description "43.6 Mbps";
                       }
                       enum "43.9Mb" {
                         description "43.9 Mbps";
                       }
                       enum "44.2Mb" {
                         description "44.2 Mbps";
                       }
                     }
                   }
                 }
               }
             }
           }
           choice payload-scrambler-choice {
             leaf payload-scrambler {
               description "Enable payload scrambling";
               type empty;
             }
             leaf no-payload-scrambler {
               description "Don't enable payload scrambling";
               type empty;
             }
           }
           choice cbit-parity-choice {
             leaf cbit-parity {
               description "Enable C-bit parity mode";
               type empty;
             }
             leaf no-cbit-parity {
               description "Don't enable C-bit parity mode";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           choice feac-loop-respond-choice {
             leaf feac-loop-respond {
               description "Respond to FEAC loop requests";
               type empty;
             }
             leaf no-feac-loop-respond {
               description "Don't respond to FEAC loop requests";
               type empty;
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "DS-3 interface encapsulation";
             type enumeration {
               enum "plcp" {
                 description "PLCP encapsulation";
               }
               enum "direct" {
                 description "ATM direct mapping";
               }
             }
           }
         }
         container e3-options {
           description "E3 interface-specific options";
           uses apply-advanced;
           leaf loopback {
             description "Loopback mode";
             type enumeration {
               enum "local" {
                 description "Local loopback";
               }
               enum "remote" {
                 description "Remote loopback";
               }
             }
           }
           choice unframed-choice {
             leaf unframed {
               description "Enable unframed mode";
               type empty;
             }
             leaf no-unframed {
               description "Don't enable unframed mode";
               type empty;
             }
           }
           container compatibility-mode {
             description "Set CSU compatibility mode";
             choice vendor {
               case case_1 {
                 leaf larscom {
                   description "Compatible with Larscom CSU (only non IQ E3 interfaces)";
                   type empty;
                 }
               }
               case case_2 {
                 container digital-link {
                   presence "enable digital-link";
                   description "Compatible with Digital Link CSU";
                   leaf subrate {
                     description "Set subrate value";
                     type enumeration {
                       enum "358Kb" {
                         description "358 Kbps";
                       }
                       enum "716Kb" {
                         description "716 Kbps";
                       }
                       enum "1.1Mb" {
                         description "1.1 Mbps";
                       }
                       enum "1.4Mb" {
                         description "1.4 Mbps";
                       }
                       enum "1.8Mb" {
                         description "1.8 Mbps";
                       }
                       enum "2.1Mb" {
                         description "2.1 Mbps";
                       }
                       enum "2.5Mb" {
                         description "2.5 Mbps";
                       }
                       enum "2.9Mb" {
                         description "2.9 Mbps";
                       }
                       enum "3.2Mb" {
                         description "3.2 Mbps";
                       }
                       enum "3.6Mb" {
                         description "3.6 Mbps";
                       }
                       enum "3.9Mb" {
                         description "3.9 Mbps";
                       }
                       enum "4.3Mb" {
                         description "4.3 Mbps";
                       }
                       enum "4.7Mb" {
                         description "4.7 Mbps";
                       }
                       enum "5.0Mb" {
                         description "5.0 Mbps";
                       }
                       enum "5.4Mb" {
                         description "5.4 Mbps";
                       }
                       enum "5.7Mb" {
                         description "5.7 Mbps";
                       }
                       enum "6.1Mb" {
                         description "6.1 Mbps";
                       }
                       enum "6.4Mb" {
                         description "6.4 Mbps";
                       }
                       enum "6.8Mb" {
                         description "6.8 Mbps";
                       }
                       enum "7.2Mb" {
                         description "7.2 Mbps";
                       }
                       enum "7.5Mb" {
                         description "7.5 Mbps";
                       }
                       enum "7.9Mb" {
                         description "7.9 Mbps";
                       }
                       enum "8.2Mb" {
                         description "8.2 Mbps";
                       }
                       enum "8.6Mb" {
                         description "8.6 Mbps";
                       }
                       enum "9.0Mb" {
                         description "9.0 Mbps";
                       }
                       enum "9.3Mb" {
                         description "9.3 Mbps";
                       }
                       enum "9.7Mb" {
                         description "9.7 Mbps";
                       }
                       enum "10.0Mb" {
                         description "10.0 Mbps";
                       }
                       enum "10.4Mb" {
                         description "10.4 Mbps";
                       }
                       enum "10.7Mb" {
                         description "10.7 Mbps";
                       }
                       enum "11.1Mb" {
                         description "11.1 Mbps";
                       }
                       enum "11.5Mb" {
                         description "11.5 Mbps";
                       }
                       enum "11.8Mb" {
                         description "11.8 Mbps";
                       }
                       enum "12.2Mb" {
                         description "12.2 Mbps";
                       }
                       enum "12.5Mb" {
                         description "12.5 Mbps";
                       }
                       enum "12.9Mb" {
                         description "12.9 Mbps";
                       }
                       enum "13.2Mb" {
                         description "13.2 Mbps";
                       }
                       enum "13.6Mb" {
                         description "13.6 Mbps";
                       }
                       enum "14.0Mb" {
                         description "14.0 Mbps";
                       }
                       enum "14.3Mb" {
                         description "14.3 Mbps";
                       }
                       enum "14.7Mb" {
                         description "14.7 Mbps";
                       }
                       enum "15.0Mb" {
                         description "15.0 Mbps";
                       }
                       enum "15.4Mb" {
                         description "15.4 Mbps";
                       }
                       enum "15.8Mb" {
                         description "15.8 Mbps";
                       }
                       enum "16.1Mb" {
                         description "16.1 Mbps";
                       }
                       enum "16.5Mb" {
                         description "16.5 Mbps";
                       }
                       enum "16.8Mb" {
                         description "16.8 Mbps";
                       }
                       enum "17.2Mb" {
                         description "17.2 Mbps";
                       }
                       enum "17.5Mb" {
                         description "17.5 Mbps";
                       }
                       enum "17.9Mb" {
                         description "17.9 Mbps";
                       }
                       enum "18.3Mb" {
                         description "18.3 Mbps";
                       }
                       enum "18.6Mb" {
                         description "18.6 Mbps";
                       }
                       enum "19.0Mb" {
                         description "19.0 Mbps";
                       }
                       enum "19.3Mb" {
                         description "19.3 Mbps";
                       }
                       enum "19.7Mb" {
                         description "19.7 Mbps";
                       }
                       enum "20.0Mb" {
                         description "20.0 Mbps";
                       }
                       enum "20.4Mb" {
                         description "20.4 Mbps";
                       }
                       enum "20.8Mb" {
                         description "20.8 Mbps";
                       }
                       enum "21.1Mb" {
                         description "21.1 Mbps";
                       }
                       enum "21.5Mb" {
                         description "21.5 Mbps";
                       }
                       enum "21.8Mb" {
                         description "21.8 Mbps";
                       }
                       enum "22.2Mb" {
                         description "22.2 Mbps";
                       }
                       enum "22.6Mb" {
                         description "22.6 Mbps";
                       }
                       enum "22.9Mb" {
                         description "22.9 Mbps";
                       }
                       enum "23.3Mb" {
                         description "23.3 Mbps";
                       }
                       enum "23.6Mb" {
                         description "23.6 Mbps";
                       }
                       enum "24.0Mb" {
                         description "24.0 Mbps";
                       }
                       enum "24.3Mb" {
                         description "24.3 Mbps";
                       }
                       enum "24.7Mb" {
                         description "24.7 Mbps";
                       }
                       enum "25.1Mb" {
                         description "25.1 Mbps";
                       }
                       enum "25.4Mb" {
                         description "25.4 Mbps";
                       }
                       enum "25.8Mb" {
                         description "25.8 Mbps";
                       }
                       enum "26.1Mb" {
                         description "26.1 Mbps";
                       }
                       enum "26.5Mb" {
                         description "26.5 Mbps";
                       }
                       enum "26.9Mb" {
                         description "26.9 Mbps";
                       }
                       enum "27.2Mb" {
                         description "27.2 Mbps";
                       }
                       enum "27.6Mb" {
                         description "27.6 Mbps";
                       }
                       enum "27.9Mb" {
                         description "27.9 Mbps";
                       }
                       enum "28.3Mb" {
                         description "28.3 Mbps";
                       }
                       enum "28.6Mb" {
                         description "28.6 Mbps";
                       }
                       enum "29.0Mb" {
                         description "29.0 Mbps";
                       }
                       enum "29.4Mb" {
                         description "29.4 Mbps";
                       }
                       enum "29.7Mb" {
                         description "29.7 Mbps";
                       }
                       enum "30.1Mb" {
                         description "30.1 Mbps";
                       }
                       enum "30.4Mb" {
                         description "30.4 Mbps";
                       }
                       enum "30.8Mb" {
                         description "30.8 Mbps";
                       }
                       enum "31.1Mb" {
                         description "31.1 Mbps";
                       }
                       enum "31.5Mb" {
                         description "31.5 Mbps";
                       }
                       enum "31.9Mb" {
                         description "31.9 Mbps";
                       }
                       enum "32.2Mb" {
                         description "32.2 Mbps";
                       }
                       enum "32.6Mb" {
                         description "32.6 Mbps";
                       }
                       enum "32.9Mb" {
                         description "32.9 Mbps";
                       }
                       enum "33.3Mb" {
                         description "33.3 Mbps";
                       }
                       enum "33.7Mb" {
                         description "33.7 Mbps";
                       }
                       enum "34.0Mb" {
                         description "34.0 Mbps";
                       }
                     }
                   }
                 }
               }
               case case_3 {
                 container kentrox {
                   presence "enable kentrox";
                   description "Compatible with Kentrox CSU";
                   leaf subrate {
                     description "Set subrate value (only for E3 IQ interfaces)";
                     type union {
                       type string {
                         pattern "<.*>|$.*";
                       }
                       type uint32 {
                         range "1 .. 48";
                       }
                     }
                   }
                 }
               }
             }
           }
           choice payload-scrambler-choice {
             leaf payload-scrambler {
               description "Enable payload scrambling";
               type empty;
             }
             leaf no-payload-scrambler {
               description "Don't enable payload scrambling";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf invert-data {
             description "Invert data";
             type empty;
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "E3 interface encapsulation";
             type enumeration {
               enum "plcp" {
                 description "PLCP encapsulation";
               }
               enum "direct" {
                 description "ATM direct mapping";
               }
             }
           }
           leaf framing {
             description "E3 line format";
             type enumeration {
               enum "g.751" {
                 description "G.751 format";
               }
               enum "g.832" {
                 description "G.832 format";
               }
             }
           }
         }
         container e1-options {
           description "E1 interface-specific options";
           uses apply-advanced;
           leaf timeslots {
             description "Timeslots (1..32); for example, 1-4,6,9-11,32 (no space)";
             type string;
           }
           leaf loopback {
             description "Loopback mode";
             type enumeration {
               enum "local" {
                 description "Local loopback";
               }
               enum "remote" {
                 description "Remote loopback";
               }
             }
           }
           leaf framing {
             description "Framing mode";
             type enumeration {
               enum "g704" {
                 description "G704 mode with CRC4";
               }
               enum "unframed" {
                 description "Unframed mode";
               }
               enum "g704-no-crc4" {
                 description "G704 mode without CRC4";
               }
             }
           }
           leaf fcs {
             description "Frame checksum";
             type enumeration {
               enum "32" {
                 description "32-bit mode";
               }
               enum "16" {
                 description "16-bit mode";
               }
             }
           }
           leaf invert-data {
             description "Invert data";
             type empty;
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
         }
         container t1-options {
           description "T1 interface-specific options";
           uses apply-advanced;
           leaf timeslots {
             description "Timeslots (1..24; for example, 1-3,4,9,22-24 (no space)";
             type string;
           }
           leaf voice-timeslots {
             description "Voice timeslots (1..24),for example, 1-3,4,9,22-24 (no space)";
             type string;
           }
           leaf disable-remote-alarm-detection {
             description "Disable detection of a remote alarm";
             type enumeration {
               enum "yellow" {
                 description "Disable yellow alarm detection";
               }
             }
           }
           leaf loopback {
             description "Loopback mode";
             type enumeration {
               enum "local" {
                 description "Local loopback";
               }
               enum "remote" {
                 description "Remote loopback";
               }
               enum "payload" {
                 description "Payload loopback";
               }
             }
           }
           leaf buildout {
             description "Line buildout";
             type enumeration {
               enum "0-132" {
                 description "Line buildout is between 0-132 feet";
               }
               enum "133-265" {
                 description "Line buildout is between 133-265 feet";
               }
               enum "266-398" {
                 description "Line buildout is between 266-398 feet";
               }
               enum "399-531" {
                 description "Line buildout is between 399-531 feet";
               }
               enum "532-655" {
                 description "Line buildout is between 532-655 feet";
               }
               enum "long-0db" {
                 description "Long buildout with 0 dB transmit attenuation";
               }
               enum "long-7.5db" {
                 description "Long buildout with 7.5 dB transmit attenuation";
               }
               enum "long-15db" {
                 description "Long buildout with 15 dB transmit attenuation";
               }
               enum "long-22.5db" {
                 description "Long buildout with 22.5 dB transmit attenuation";
               }
             }
           }
           leaf byte-encoding {
             description "Byte encoding";
             type enumeration {
               enum "nx64" {
                 description "8 bits per byte";
               }
               enum "nx56" {
                 description "7 bits per byte";
               }
             }
           }
           leaf line-encoding {
             description "Line encoding";
             type enumeration {
               enum "ami" {
                 description "Automatic mark inversion";
               }
               enum "b8zs" {
                 description "8-bit zero suppression";
               }
             }
           }
           leaf invert-data {
             description "Invert data";
             type empty;
           }
           leaf framing {
             description "Framing mode";
             type enumeration {
               enum "sf" {
                 description "Super frame";
               }
               enum "esf" {
                 description "Extended super frame";
               }
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
           leaf remote-loopback-respond {
             description "Respond to loop requests from remote end";
             type empty;
           }
           leaf crc-major-alarm-threshold {
             description "CRC Major alarm threshold value";
             default "5e-5";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
             }
           }
           leaf crc-minor-alarm-threshold {
             description "CRC Minor alarm threshold value";
             default "5e-6";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
               enum "5e-6" {
                 description "5 crc errors in 10^6 bits";
               }
               enum "1e-6" {
                 description "1 crc error in 10^6 bits";
               }
             }
           }
           leaf alarm-compliance {
             description "Enforce standard for alarm reporting";
             type enumeration {
               enum "accunet-t1-5-service" {
                 description "T1.5 interface specification";
               }
             }
           }
         }
         container ds0-options {
           description "DS-0 interface-specific options";
           uses apply-advanced;
           leaf loopback {
             description "Loopback mode";
             type enumeration {
               enum "payload" {
                 description "Payload loopback";
               }
             }
           }
           leaf byte-encoding {
             description "Byte encoding";
             type enumeration {
               enum "nx64" {
                 description "8 bits per byte";
               }
               enum "nx56" {
                 description "7 bits per byte";
               }
             }
           }
           leaf invert-data {
             description "Invert data";
             type empty;
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e11-o152" {
                 description "Pattern is 2^11 -1 (per O.152 standard)";
               }
               enum "pseudo-2e15-o151" {
                 description "Pattern is 2^15 - 1 (per O.151 standard)";
               }
               enum "pseudo-2e20-o153" {
                 description "Pattern is 2^20 - 1 (per O.153 standard)";
               }
               enum "pseudo-2e20-o151" {
                 description "Pattern is 2^20 - 1 (per O.151 standard)";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
               enum "repeating-1-in-16" {
                 description "1 bit in 16 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
         }
         container serial-options {
           description "Serial interface-specific options";
           uses apply-advanced;
           leaf line-protocol {
             description "Line protocol to be used";
             default "eia530";
             type enumeration {
               enum "eia530" {
                 description "Line protocol EIA530";
               }
               enum "v.35" {
                 description "Line protocol V.35";
               }
               enum "x.21" {
                 description "Line protocol X.21";
               }
             }
           }
           choice control_leads_choice {
             case case_1 {
               container dte-options {
                 description "DTE options/control leads";
                 uses apply-advanced;
                 leaf ignore-all {
                   description "Ignore all control leads";
                   type empty;
                 }
                 container dtr {
                   description "Data Transmit Ready signal handling";
                   choice dtr_choices {
                     case case_1 {
                       leaf assert {
                         description "Assert DTR signal";
                         type empty;
                       }
                     }
                     case case_2 {
                       leaf de-assert {
                         description "Deassert DTR signal";
                         type empty;
                       }
                     }
                     case case_3 {
                       leaf normal {
                         description "Normal DTR signal";
                         type empty;
                       }
                     }
                     case case_4 {
                       container auto-synchronize {
                         presence "enable auto-synchronize";
                         description "Normal DTR signal, with autoresynchronization";
                         uses apply-advanced;
                         leaf duration {
                           description "Duration of autoresynchronization";
                           units "milliseconds";
                           type union {
                             type string {
                               pattern "<.*>|$.*";
                             }
                             type uint16 {
                               range "1 .. 1000";
                             }
                           }
                         }
                         leaf interval {
                           description "Interval for autoresynchronization";
                           units "seconds";
                           type union {
                             type string {
                               pattern "<.*>|$.*";
                             }
                             type uint16 {
                               range "1 .. 31";
                             }
                           }
                         }
                       }
                     }
                   }
                 }
                 leaf control-signal {
                   description "X.21 control signal handling";
                   type enumeration {
                     enum "assert" {
                       description "Assert control signal";
                     }
                     enum "de-assert" {
                       description "Deassert control signal";
                     }
                     enum "normal" {
                       description "Normal control signal";
                     }
                   }
                 }
                 leaf rts {
                   description "Request To Send signal handling";
                   type enumeration {
                     enum "assert" {
                       description "Assert RTS signal";
                     }
                     enum "de-assert" {
                       description "Deassert RTS signal";
                     }
                     enum "normal" {
                       description "Normal RTS signal";
                     }
                   }
                 }
                 leaf dcd {
                   description "Data Carrier Detect signal handling";
                   type enumeration {
                     enum "require" {
                       description "Require DCD signal";
                     }
                     enum "ignore" {
                       description "Ignore DCD signal";
                     }
                     enum "normal" {
                       description "Normal DCD signal";
                     }
                   }
                 }
                 leaf dsr {
                   description "Data Set Ready signal handling";
                   type enumeration {
                     enum "require" {
                       description "Require DSR signal";
                     }
                     enum "ignore" {
                       description "Ignore DSR signal";
                     }
                     enum "normal" {
                       description "Normal DSR signal";
                     }
                   }
                 }
                 leaf cts {
                   description "Clear To Send signal handling";
                   type enumeration {
                     enum "require" {
                       description "Require CTS signal";
                     }
                     enum "ignore" {
                       description "Ignore CTS signal";
                     }
                     enum "normal" {
                       description "Normal CTS signal";
                     }
                   }
                 }
                 leaf indication {
                   description "X.21 Indication signal handling";
                   type enumeration {
                     enum "require" {
                       description "Require Indication signal";
                     }
                     enum "ignore" {
                       description "Ignore Indication signal";
                     }
                     enum "normal" {
                       description "Normal Indication signal";
                     }
                   }
                 }
                 leaf tm {
                   description "Test Mode signal handling";
                   type enumeration {
                     enum "require" {
                       description "Require TM signal";
                     }
                     enum "ignore" {
                       description "Ignore TM signal";
                     }
                     enum "normal" {
                       description "Normal TM signal";
                     }
                   }
                 }
               }
             }
             case case_2 {
               container dce-options {
                 description "DCE options";
                 uses apply-advanced;
                 leaf ignore-all {
                   description "Ignore all control leads";
                   type empty;
                 }
                 leaf dtr {
                   description "Data Transmit Ready signal handling";
                   type enumeration {
                     enum "require" {
                       description "Require Data Carrier Detect (DCD) signal";
                     }
                     enum "ignore" {
                       description "Ignore Data Carrier Detect (DCD) signal";
                     }
                     enum "normal" {
                       description "Normal Data Carrier Detect (DCD) signal";
                     }
                   }
                 }
                 leaf rts {
                   description "Request To Send signal handling";
                   type enumeration {
                     enum "require" {
                       description "Require Data Carrier Detect (DCD) signal";
                     }
                     enum "ignore" {
                       description "Ignore Data Carrier Detect (DCD) signal";
                     }
                     enum "normal" {
                       description "Normal Data Carrier Detect (DCD) signal";
                     }
                   }
                 }
                 leaf dcd {
                   description "Data Carrier Detect signal handling";
                   type enumeration {
                     enum "assert" {
                       description "Assert Request To Send (RTS) signal";
                     }
                     enum "de-assert" {
                       description "Deassert Request To Send (RTS) signal";
                     }
                     enum "normal" {
                       description "Normal Request To Send (RTS) signal";
                     }
                   }
                 }
                 leaf dsr {
                   description "Data Set Ready signal handling";
                   type enumeration {
                     enum "assert" {
                       description "Assert Request To Send (RTS) signal";
                     }
                     enum "de-assert" {
                       description "Deassert Request To Send (RTS) signal";
                     }
                     enum "normal" {
                       description "Normal Request To Send (RTS) signal";
                     }
                   }
                 }
                 leaf cts {
                   description "Clear To Send signal handling";
                   type enumeration {
                     enum "assert" {
                       description "Assert Request To Send (RTS) signal";
                     }
                     enum "de-assert" {
                       description "Deassert Request To Send (RTS) signal";
                     }
                     enum "normal" {
                       description "Normal Request To Send (RTS) signal";
                     }
                   }
                 }
                 leaf tm {
                   description "Test Mode signal handling";
                   type enumeration {
                     enum "require" {
                       description "Require TM signal";
                     }
                     enum "ignore" {
                       description "Ignore TM signal";
                     }
                     enum "normal" {
                       description "Normal TM signal";
                     }
                   }
                 }
                 leaf dce-loopback-override {
                   description "DCE loopback override";
                   type empty;
                 }
               }
             }
           }
           leaf dtr-circuit {
             description "Data Transmit Ready circuit mode";
             type enumeration {
               enum "balanced" {
                 description "Balanced signal";
               }
               enum "unbalanced" {
                 description "Unbalanced signal";
               }
             }
           }
           leaf dtr-polarity {
             description "Data Transmit Ready signal polarity";
             type enumeration {
               enum "positive" {
                 description "Positive polarity";
               }
               enum "negative" {
                 description "Negative polarity";
               }
             }
           }
           leaf rts-polarity {
             description "Request To Send signal polarity";
             type enumeration {
               enum "positive" {
                 description "Positive polarity";
               }
               enum "negative" {
                 description "Negative polarity";
               }
             }
           }
           leaf control-polarity {
             description "X.21 Control signal polarity";
             type enumeration {
               enum "positive" {
                 description "Positive polarity";
               }
               enum "negative" {
                 description "Negative polarity";
               }
             }
           }
           leaf dcd-polarity {
             description "Data Carrier Detect signal polarity";
             type enumeration {
               enum "positive" {
                 description "Positive polarity";
               }
               enum "negative" {
                 description "Negative polarity";
               }
             }
           }
           leaf dsr-polarity {
             description "Data Set Ready signal polarity";
             type enumeration {
               enum "positive" {
                 description "Positive polarity";
               }
               enum "negative" {
                 description "Negative polarity";
               }
             }
           }
           leaf cts-polarity {
             description "Clear To Send signal polarity";
             type enumeration {
               enum "positive" {
                 description "Positive polarity";
               }
               enum "negative" {
                 description "Negative polarity";
               }
             }
           }
           leaf indication-polarity {
             description "X.21 Indication signal polarity";
             type enumeration {
               enum "positive" {
                 description "Positive polarity";
               }
               enum "negative" {
                 description "Negative polarity";
               }
             }
           }
           leaf tm-polarity {
             description "Test Mode signal polarity";
             type enumeration {
               enum "positive" {
                 description "Positive polarity";
               }
               enum "negative" {
                 description "Negative polarity";
               }
             }
           }
           leaf clocking-mode {
             description "Clock mode";
             type enumeration {
               enum "dce" {
                 description "DCE timing (DTE mode only, not valid for X.21)";
               }
               enum "internal" {
                 description "Internal baud timing";
               }
               enum "loop" {
                 description "Loop timing";
               }
             }
           }
           leaf transmit-clock {
             description "Transmit clock phase";
             type enumeration {
               enum "invert" {
                 description "Shift clock phase 180 degrees";
               }
             }
           }
           leaf clock-rate {
             description "Interface clock rate";
             type enumeration {
               enum "2.048mhz" {
                 description "2.048 MHz";
               }
               enum "2.341mhz" {
                 description "2.341 MHz";
               }
               enum "2.731mhz" {
                 description "2.731 MHz";
               }
               enum "3.277mhz" {
                 description "3.277 MHz";
               }
               enum "4.096mhz" {
                 description "4.096 MHz";
               }
               enum "5.461mhz" {
                 description "5.461 MHz";
               }
               enum "8.192mhz" {
                 description "8.192 MHz";
               }
               enum "16.384mhz" {
                 description "16.384 MHz";
               }
               enum "1.2khz" {
                 description "1.2 KHz";
               }
               enum "2.4khz" {
                 description "2.4 KHz";
               }
               enum "9.6khz" {
                 description "9.6 KHz";
               }
               enum "19.2khz" {
                 description "19.2 KHz";
               }
               enum "38.4khz" {
                 description "38.4 KHz";
               }
               enum "56.0khz" {
                 description "56.0 KHz";
               }
               enum "64.0khz" {
                 description "64.0 KHz";
               }
               enum "72.0khz" {
                 description "72.0 KHz";
               }
               enum "125.0khz" {
                 description "125.0 KHz";
               }
               enum "148.0khz" {
                 description "148.0 KHz";
               }
               enum "250.0khz" {
                 description "250.0 KHz";
               }
               enum "500.0khz" {
                 description "500.0 KHz";
               }
               enum "800.0khz" {
                 description "800.0 KHz";
               }
               enum "1.0mhz" {
                 description "1.0 MHz";
               }
               enum "1.3mhz" {
                 description "1.3 MHz";
               }
               enum "2.0mhz" {
                 description "2.0 MHz";
               }
               enum "4.0mhz" {
                 description "4.0 MHz";
               }
               enum "8.0mhz" {
                 description "8.0 MHz";
               }
             }
           }
           leaf loopback {
             description "Loopback mode";
             type enumeration {
               enum "local" {
                 description "Local loopback";
               }
               enum "remote" {
                 description "Remote/LIU loopback";
               }
               enum "dce-local" {
                 description "DCE local loopback (DTE mode only)";
               }
               enum "dce-remote" {
                 description "DCE remote loopback";
               }
             }
           }
           leaf encoding {
             description "Line encoding";
             type enumeration {
               enum "nrz" {
                 description "Non-Return-To-Zero";
               }
               enum "nrzi" {
                 description "Non-Return-To-Zero-Invertible";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
         }
         choice gratuitous-arp-reply-choice {
           leaf gratuitous-arp-reply {
             description "Enable gratuitous ARP reply";
             type empty;
           }
           leaf no-gratuitous-arp-reply {
             description "Don't enable gratuitous ARP reply";
             type empty;
           }
         }
         choice no-gratuitous-arp-request-choice {
           leaf no-gratuitous-arp-request {
             description "Ignore gratuitous ARP request";
             type empty;
           }
           leaf no-no-gratuitous-arp-request {
             description "Don't ignore gratuitous ARP request";
             type empty;
           }
         }
         leaf arp-l2-validate {
           description "Validate ARP against L2";
           type empty;
         }
         container ether-options {
           description "Ethernet interface-specific options";
           uses apply-advanced;
           choice loopback-choice {
             leaf loopback {
               description "Enable loopback";
               type empty;
             }
             leaf no-loopback {
               description "Don't enable loopback";
               type empty;
             }
           }
           leaf loopback-remote {
             description "Enable remote loopback";
             type empty;
           }
           choice source-filtering-choice {
             leaf source-filtering {
               description "Enable source address filtering";
               type empty;
             }
             leaf no-source-filtering {
               description "Don't enable source address filtering";
               type empty;
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             container ethernet-policer-profile {
               description "Ethernet level CoS-based policer configuration";
               uses apply-advanced;
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container storm-control {
               description "Storm control profile name to bind";
               uses apply-advanced;
               leaf profile-name {
                 description "Profile name";
                 type string;
               }
             }
             container recovery-timeout {
               description "Recovery timeout for this interface";
               leaf time-in-seconds {
                 units "seconds";
                 type union {
                   type string {
                     pattern "<.*>|$.*";
                   }
                   type uint32 {
                     range "10 .. 3600";
                   }
                 }
               }
             }
             choice mac-learn-enable-choice {
               leaf mac-learn-enable {
                 description "Learn MAC addresses dynamically";
                 type empty;
               }
               leaf no-mac-learn-enable {
                 description "Don't learn MAC addresses dynamically";
                 type empty;
               }
             }
           }
           leaf asynchronous-notification {
             description "Enable sending asynchronous notification to peer on CCC-down";
             type empty;
           }
           list source-address-filter {
             key name;
             description "Source address filters";
             leaf name {
               description "Remote MAC address";
               type jt:mac-addr;
             }
           }
           choice auto-negotiation-choice {
             leaf auto-negotiation {
               description "Enable auto-negotiation";
               type empty;
             }
             leaf no-auto-negotiation {
               description "Don't enable auto-negotiation";
               type empty;
             }
           }
           choice flow-control-choice {
             leaf flow-control {
               description "Enable flow control";
               type empty;
             }
             leaf no-flow-control {
               description "Don't enable flow control";
               type empty;
             }
           }
           container configured-flow-control {
             presence "enable configured-flow-control";
             description "Enable flow control";
             uses apply-advanced;
             leaf rx-buffers {
               description "Enable/Disable Rx buffers";
               type enumeration {
                 enum "on" {
                   description "Enable Rx buffers";
                 }
                 enum "off" {
                   description "Disable Rx buffers";
                 }
               }
             }
             leaf tx-buffers {
               description "Enable/Disable Tx buffers";
               type enumeration {
                 enum "on" {
                   description "Enable Tx buffers";
                 }
                 enum "off" {
                   description "Disable Tx buffers";
                 }
               }
             }
           }
           leaf link-mode {
             description "Link duplex";
             type enumeration {
               enum "automatic" {
                 description "Automatic negotiate duplex ";
               }
               enum "half-duplex" {
                 description "Half-duplex operation";
               }
               enum "full-duplex" {
                 description "Full-duplex operation";
               }
             }
           }
           container mpls {
             description "MPLS options";
             uses mpls_ifd_options;
           }
           leaf ignore-l3-incompletes {
             description "Ignore L3 incomplete errors";
             type empty;
           }
           leaf no-auto-mdix {
             description "Disable auto MDI/MDIX";
             type empty;
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
             }
           }
           container speed {
             description "Specify speed";
             choice automatic {
               case case_1 {
                 container auto-negotiation {
                   presence "enable auto-negotiation";
                   description "Enable auto-negotiation";
                   leaf auto-negotiate-10-100 {
                     description "Limits the auto-negotiation to 10m/100m only";
                     type empty;
                   }
                 }
               }
               case case_2 {
                 leaf ethernet-10m {
                   description "10Mbps";
                   type empty;
                 }
               }
               case case_3 {
                 leaf ethernet-100m {
                   description "100Mbps";
                   type empty;
                 }
               }
               case case_4 {
                 leaf ethernet-1g {
                   description "1Gbps";
                   type empty;
                 }
               }
               case case_5 {
                 leaf ethernet-10g {
                   description "10Gbps";
                   type empty;
                 }
               }
             }
           }
           container ieee-802.3ad {
             description "IEEE 802.3ad";
             uses apply-advanced;
             container lacp {
               description "Link Aggregation Control Protocol configuration";
               uses apply-advanced;
               leaf force-up {
                 description "Keep the port up in absence of received LACPDU";
                 type empty;
               }
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
             container link-protection-sub-group {
               description "Link Protection subgroup configuration";
               uses apply-advanced;
               leaf subgroup-name {
                 description "Name of the subgroup";
                 type string {
                   length "2 .. 64";
                 }
               }
             }
             leaf port-priority {
               description "Link protection Priority of the port (0 ... 65535)";
               type union {
                 type uint16;
                 type string {
                   pattern "<.*>|$.*";
                 }
               }
             }
           }
           leaf ieee-802-3az-eee {
             description "IEEE 802.3az Energy Efficient Ethernet(EEE)";
             type empty;
           }
           leaf mdi-mode {
             description "Cable cross-over mode";
             type enumeration {
               enum "auto" {
                 description "Automatic mdi/mdi-x mode";
               }
               enum "force" {
                 description "Enable auto-MDIX always";
               }
               enum "mdi" {
                 description "MDI(straight through) mode";
               }
               enum "mdix" {
                 description "MDI Cross-over mode";
               }
             }
           }
           container redundant-parent {
             description " Parent of this interface";
             uses apply-advanced;
             leaf parent {
               description "Join a redundant ethernet interface";
               type union {
                 type jt:interface-device;
                 type string {
                   pattern "<.*>|$.*";
                 }
               }
             }
           }
           leaf autostate-exclude {
             description "Interface will not contribute to IRB state";
             type empty;
           }
         }
         container fibrechannel-options {
           description "Fibre Channel interface-specific options";
           uses apply-advanced;
           choice loopback-choice {
             leaf loopback {
               description "Enable loopback";
               type empty;
             }
             leaf no-loopback {
               description "Don't enable loopback";
               type empty;
             }
           }
           leaf bb-sc-n {
             description "B2B state change number";
             type union {
               type string {
                 pattern "<.*>|$.*";
               }
               type uint16 {
                 range "0 .. 15";
               }
             }
           }
           leaf speed {
             description "Specify speed";
             type enumeration {
               enum "auto-negotiation" {
                 description "Enable auto-negotiation";
               }
               enum "1g" {
                 description "1Gbps";
               }
               enum "2g" {
                 description "2Gbps";
               }
               enum "4g" {
                 description "4Gbps";
               }
               enum "8g" {
                 description "8Gbps";
               }
             }
           }
         }
         container gigether-options {
           description "Gigabit Ethernet interface-specific options";
           uses apply-advanced;
           choice loopback-choice {
             leaf loopback {
               description "Enable loopback";
               type empty;
             }
             leaf no-loopback {
               description "Don't enable loopback";
               type empty;
             }
           }
           leaf loopback-remote {
             description "Enable remote loopback";
             type empty;
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           choice auto_negotiation_option {
             case case_1 {
               leaf no-auto-negotiation {
                 description "Disable auto-negotiation";
                 type empty;
               }
             }
             case case_2 {
               container auto-negotiation {
                 presence "enable auto-negotiation";
                 description "Enable auto-negotiation";
                 leaf remote-fault {
                   type enumeration {
                     enum "local-interface-offline" {
                       description "Disable local interface";
                     }
                     enum "local-interface-online" {
                       description "Enable local interface";
                     }
                   }
                 }
               }
             }
           }
           leaf mac-mode {
             description "Physical layer protocol of MAC's SERDES interface";
             type enumeration {
               enum "sgmii" {
                 description "Serial Gigabit Media Independent Interface (10/100/1000 Mbps)";
               }
               enum "mac-mode-1000base-x" {
                 description "1000Base-X (1000 Mbps)";
               }
             }
           }
           leaf asynchronous-notification {
             description "Enable sending asynchronous notification to peer on CCC-down";
             type empty;
           }
           list source-address-filter {
             key name;
             description "Source address filters";
             leaf name {
               description "Remote MAC address";
               type jt:mac-addr;
             }
           }
           leaf pad-to-minimum-frame-size {
             description "Pad Tx vlan tagged frame to minimum of 68 bytes";
             type empty;
           }
           container redundant-parent {
             description "Parent of this interface";
             uses apply-advanced;
             leaf parent {
               description "Join a redundant-ethernet interface";
               type union {
                 type jt:interface-device;
                 type string {
                   pattern "<.*>|$.*";
                 }
               }
             }
           }
           container ieee-802.3ad {
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             leaf link-index {
               description "Desired child link index within the Aggregated Interface";
               type union {
                 type string {
                   pattern "<.*>|$.*";
                 }
                 type uint16 {
                   range "0 .. 63";
                 }
               }
             }
             choice type {
               case case_1 {
                 leaf primary {
                   description "Primary interface for link-protection mode";
                   type empty;
                 }
               }
               case case_2 {
                 leaf backup {
                   description "Backup interface for link-protection mode";
                   type empty;
                 }
               }
             }
             leaf distribution-list {
               description "Distribution list to which interface belongs";
               type string {
                 length "1 .. 20";
               }
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             container ethernet-policer-profile {
               description "Ethernet level CoS-based policer configuration";
               uses apply-advanced;
               container ieee802.1-priority-map {
                 presence "enable ieee802.1-priority-map";
                 description "Premium priority values for IEEE 802.1p bits";
                 status deprecated;
                 uses apply-advanced;
                 leaf-list premium {
                   ordered-by user;
                   description "Premium policer priority map";
                   type union {
                     type string {
                       pattern "<.*>|$.*";
                     }
                     type uint32 {
                       range "0 .. 7";
                     }
                   }
                 }
               }
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container accept-from {
               description "Accept traffic from or to specified remote MAC";
               status deprecated;
               uses apply-advanced;
               list mac-address {
                 key name;
                 description "Remote MAC";
                 uses mac_list;
               }
             }
             choice reject-the-rest-choice {
               leaf reject-the-rest {
                 description "Accept traffic from only the specified MAC addresses";
                 status deprecated;
                 type empty;
               }
               leaf no-reject-the-rest {
                 description "Don't accept traffic from only the specified MAC addresses";
                 status deprecated;
                 type empty;
               }
             }
             leaf mac-learn-enable {
               description "Learn MAC addresses dynamically";
               type empty;
             }
           }
           container mpls {
             description "MPLS options";
             uses mpls_ifd_options;
           }
           leaf ignore-l3-incompletes {
             description "Ignore L3 incomplete errors";
             type empty;
           }
           leaf no-auto-mdix {
             description "Disable auto MDI/MDIX";
             type empty;
           }
           leaf ieee-802-3az-eee {
             description "IEEE 802.3az Energy Efficient Ethernet(EEE)";
             type empty;
           }
           leaf mru {
             description "Maximum receive packet size";
             type union {
               type string {
                 pattern "<.*>|$.*";
               }
               type uint32;
             }
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
             }
           }
           leaf speed {
             description "Speed mode";
             type enumeration {
               enum "1g" {
                 description "Speed 1g";
               }
               enum "10g" {
                 description "Speed 10g";
               }
             }
           }
         }
         container optics-options {
           description "Optics options";
           uses apply-advanced;
           leaf wavelength {
             description "Wavelength of the optics (nanometers) for 50Ghz/100Ghz spacing";
             type enumeration {
               enum "1568.77" {
                 description "1568.77 nm/191.1003 THz 50/100Ghz spacing";
               }
               enum "1568.36" {
                 description "1568.36 nm/191.15000 THz 6.25/12.5/50GHz spacing";
               }
               enum "1568.31" {
                 description "1568.31 nm/191.15625 THz 6.25GHz spacing";
               }
               enum "1568.26" {
                 description "1568.26 nm/191.16250 THz 6.25/12.5GHz spacing";
               }
               enum "1568.21" {
                 description "1568.21 nm/191.16875 THz 6.25GHz spacing";
               }
               enum "1568.16" {
                 description "1568.16 nm/191.17500 THz 6.25/12.5GHz spacing";
               }
               enum "1568.11" {
                 description "1568.11 nm/191.18125 THz 6.25GHz spacing";
               }
               enum "1568.05" {
                 description "1568.05 nm/191.18750 THz 6.25/12.5GHz spacing";
               }
               enum "1568.00" {
                 description "1568.00 nm/191.19375 THz 6.25GHz spacing";
               }
               enum "1567.95" {
                 description "1567.95 nm/191.20000 THz 6.25/12.5/50/100GHz spacing";
               }
               enum "1567.90" {
                 description "1567.90 nm/191.20625 THz 6.25GHz spacing";
               }
               enum "1567.85" {
                 description "1567.85 nm/191.21250 THz 6.25/12.5GHz spacing";
               }
               enum "1567.80" {
                 description "1567.80 nm/191.21875 THz 6.25GHz spacing";
               }
               enum "1567.75" {
                 description "1567.75 nm/191.22500 THz 6.25/12.5GHz spacing";
               }
               enum "1567.70" {
                 description "1567.70 nm/191.23125 THz 6.25GHz spacing";
               }
               enum "1567.64" {
                 description "1567.64 nm/191.23750 THz 6.25/12.5GHz spacing";
               }
               enum "1567.59" {
                 description "1567.59 nm/191.24375 THz 6.25GHz spacing";
               }
               enum "1567.54" {
                 description "1567.54 nm/191.25000 THz 6.25/12.5/50GHz spacing";
               }
               enum "1567.49" {
                 description "1567.49 nm/191.25625 THz 6.25GHz spacing";
               }
               enum "1567.44" {
                 description "1567.44 nm/191.26250 THz 6.25/12.5GHz spacing";
               }
               enum "1567.39" {
                 description "1567.39 nm/191.26875 THz 6.25GHz spacing";
               }
               enum "1567.34" {
                 description "1567.34 nm/191.27500 THz 6.25/12.5GHz spacing";
               }
               enum "1567.29" {
                 description "1567.29 nm/191.28125 THz 6.25GHz spacing";
               }
               enum "1567.23" {
                 description "1567.23 nm/191.28750 THz 6.25/12.5GHz spacing";
               }
               enum "1567.18" {
                 description "1567.18 nm/191.29375 THz 6.25GHz spacing";
               }
               enum "1567.13" {
                 description "1567.13 nm/191.30000 THz 6.25/12.5/50/100GHz spacing";
               }
               enum "1567.08" {
                 description "1567.08 nm/191.30625 THz 6.25GHz spacing";
               }
               enum "1567.03" {
                 description "1567.03 nm/191.31250 THz 6.25/12.5GHz spacing";
               }
               enum "1566.98" {
                 description "1566.98 nm/191.31875 THz 6.25GHz spacing";
               }
               enum "1566.93" {
                 description "1566.93 nm/191.32500 THz 6.25/12.5GHz spacing";
               }
               enum "1566.88" {
                 description "1566.88 nm/191.33125 THz 6.25GHz spacing";
               }
               enum "1566.83" {
                 description "1566.83 nm/191.33750 THz 6.25/12.5GHz spacing";
               }
               enum "1566.77" {
                 description "1566.77 nm/191.34375 THz 6.25GHz spacing";
               }
               enum "1566.72" {
                 description "1566.72 nm/191.35000 THz 6.25/12.5/50GHz spacing";
               }
               enum "1566.67" {
                 description "1566.67 nm/191.35625 THz 6.25GHz spacing";
               }
               enum "1566.62" {
                 description "1566.62 nm/191.36250 THz 6.25/12.5GHz spacing";
               }
               enum "1566.57" {
                 description "1566.57 nm/191.36875 THz 6.25GHz spacing";
               }
               enum "1566.52" {
                 description "1566.52 nm/191.37500 THz 6.25/12.5/75GHz spacing";
               }
               enum "1566.47" {
                 description "1566.47 nm/191.38125 THz 6.25GHz spacing";
               }
               enum "1566.42" {
                 description "1566.42 nm/191.38750 THz 6.25/12.5GHz spacing";
               }
               enum "1566.36" {
                 description "1566.36 nm/191.39375 THz 6.25GHz spacing";
               }
               enum "1566.31" {
                 description "1566.31 nm/191.40000 THz 6.25/12.5/50/100GHz spacing";
               }
               enum "1566.26" {
                 description "1566.26 nm/191.40625 THz 6.25GHz spacing";
               }
               enum "1566.21" {
                 description "1566.21 nm/191.41250 THz 6.25/12.5GHz spacing";
               }
               enum "1566.16" {
                 description "1566.16 nm/191.41875 THz 6.25GHz spacing";
               }
               enum "1566.11" {
                 description "1566.11 nm/191.42500 THz 6.25/12.5GHz spacing";
               }
               enum "1566.06" {
                 description "1566.06 nm/191.43125 THz 6.25GHz spacing";
               }
               enum "1566.01" {
                 description "1566.01 nm/191.43750 THz 6.25/12.5GHz spacing";
               }
               enum "1565.96" {
                 description "1565.96 nm/191.44375 THz 6.25GHz spacing";
               }
               enum "1565.90" {
                 description "1565.90 nm/191.45000 THz 6.25/12.5/50/75GHz spacing";
               }
               enum "1565.85" {
                 description "1565.85 nm/191.45625 THz 6.25GHz spacing";
               }
               enum "1565.80" {
                 description "1565.80 nm/191.46250 THz 6.25/12.5GHz spacing";
               }
               enum "1565.75" {
                 description "1565.75 nm/191.46875 THz 6.25GHz spacing";
               }
               enum "1565.70" {
                 description "1565.70 nm/191.47500 THz 6.25/12.5GHz spacing";
               }
               enum "1565.65" {
                 description "1565.65 nm/191.48125 THz 6.25GHz spacing";
               }
               enum "1565.60" {
                 description "1565.60 nm/191.48750 THz 6.25/12.5GHz spacing";
               }
               enum "1565.55" {
                 description "1565.55 nm/191.49375 THz 6.25GHz spacing";
               }
               enum "1565.50" {
                 description "1565.50 nm/191.50000 THz 6.25/12.5/50/100GHz spacing";
               }
               enum "1565.44" {
                 description "1565.44 nm/191.50625 THz 6.25GHz spacing";
               }
               enum "1565.39" {
                 description "1565.39 nm/191.51250 THz 6.25/12.5GHz spacing";
               }
               enum "1565.34" {
                 description "1565.34 nm/191.51875 THz 6.25GHz spacing";
               }
               enum "1565.29" {
                 description "1565.29 nm/191.52500 THz 6.25/12.5/75GHz spacing";
               }
               enum "1565.24" {
                 description "1565.24 nm/191.53125 THz 6.25GHz spacing";
               }
               enum "1565.19" {
                 description "1565.19 nm/191.53750 THz 6.25/12.5GHz spacing";
               }
               enum "1565.14" {
                 description "1565.14 nm/191.54375 THz 6.25GHz spacing";
               }
               enum "1565.09" {
                 description "1565.09 nm/191.55000 THz 6.25/12.5/50GHz spacing";
               }
               enum "1565.04" {
                 description "1565.04 nm/191.55625 THz 6.25GHz spacing";
               }
               enum "1564.99" {
                 description "1564.99 nm/191.56250 THz 6.25/12.5GHz spacing";
               }
               enum "1564.93" {
                 description "1564.93 nm/191.56875 THz 6.25GHz spacing";
               }
               enum "1564.88" {
                 description "1564.88 nm/191.57500 THz 6.25/12.5GHz spacing";
               }
               enum "1564.83" {
                 description "1564.83 nm/191.58125 THz 6.25GHz spacing";
               }
               enum "1564.78" {
                 description "1564.78 nm/191.58750 THz 6.25/12.5GHz spacing";
               }
               enum "1564.73" {
                 description "1564.73 nm/191.59375 THz 6.25GHz spacing";
               }
               enum "1564.68" {
                 description "1564.68 nm/191.60000 THz 6.25/12.5/50/75/100GHz spacing";
               }
               enum "1564.63" {
                 description "1564.63 nm/191.60625 THz 6.25GHz spacing";
               }
               enum "1564.58" {
                 description "1564.58 nm/191.61250 THz 6.25/12.5GHz spacing";
               }
               enum "1564.53" {
                 description "1564.53 nm/191.61875 THz 6.25GHz spacing";
               }
               enum "1564.47" {
                 description "1564.47 nm/191.62500 THz 6.25/12.5GHz spacing";
               }
               enum "1564.42" {
                 description "1564.42 nm/191.63125 THz 6.25GHz spacing";
               }
               enum "1564.37" {
                 description "1564.37 nm/191.63750 THz 6.25/12.5GHz spacing";
               }
               enum "1564.32" {
                 description "1564.32 nm/191.64375 THz 6.25GHz spacing";
               }
               enum "1564.27" {
                 description "1564.27 nm/191.65000 THz 6.25/12.5/50GHz spacing";
               }
               enum "1564.22" {
                 description "1564.22 nm/191.65625 THz 6.25GHz spacing";
               }
               enum "1564.17" {
                 description "1564.17 nm/191.66250 THz 6.25/12.5GHz spacing";
               }
               enum "1564.12" {
                 description "1564.12 nm/191.66875 THz 6.25GHz spacing";
               }
               enum "1564.07" {
                 description "1564.07 nm/191.67500 THz 6.25/12.5/75GHz spacing";
               }
               enum "1564.02" {
                 description "1564.02 nm/191.68125 THz 6.25GHz spacing";
               }
               enum "1563.96" {
                 description "1563.96 nm/191.68750 THz 6.25/12.5GHz spacing";
               }
               enum "1563.91" {
                 description "1563.91 nm/191.69375 THz 6.25GHz spacing";
               }
               enum "1563.86" {
                 description "1563.86 nm/191.70000 THz 6.25/12.5/50/100GHz spacing";
               }
               enum "1563.81" {
                 description "1563.81 nm/191.70625 THz 6.25GHz spacing";
               }
               enum "1563.76" {
                 description "1563.76 nm/191.71250 THz 6.25/12.5GHz spacing";
               }
               enum "1563.71" {
                 description "1563.71 nm/191.71875 THz 6.25GHz spacing";
               }
               enum "1563.66" {
                 description "1563.66 nm/191.72500 THz 6.25/12.5GHz spacing";
               }
               enum "1563.61" {
                 description "1563.61 nm/191.73125 THz 6.25GHz spacing";
               }
               enum "1563.56" {
                 description "1563.56 nm/191.73750 THz 6.25/12.5GHz spacing";
               }
               enum "1563.51" {
                 description "1563.51 nm/191.74375 THz 6.25GHz spacing";
               }
               enum "1563.45" {
                 description "1563.45 nm/191.75000 THz 6.25/12.5/50/75GHz spacing";
               }
               enum "1563.40" {
                 description "1563.40 nm/191.75625 THz 6.25GHz spacing";
               }
               enum "1563.35" {
                 description "1563.35 nm/191.76250 THz 6.25/12.5GHz spacing";
               }
               enum "1563.30" {
                 description "1563.30 nm/191.76875 THz 6.25GHz spacing";
               }
               enum "1563.25" {
                 description "1563.25 nm/191.77500 THz 6.25/12.5GHz spacing";
               }
               enum "1563.20" {
                 description "1563.20 nm/191.78125 THz 6.25GHz spacing";
               }
               enum "1563.15" {
                 description "1563.15 nm/191.78750 THz 6.25/12.5GHz spacing";
               }
               enum "1563.10" {
                 description "1563.10 nm/191.79375 THz 6.25GHz spacing";
               }
               enum "1563.05" {
                 description "1563.05 nm/191.80000 THz 6.25/12.5/50/100GHz spacing";
               }
               enum "1563.00" {
                 description "1563.00 nm/191.80625 THz 6.25GHz spacing";
               }
               enum "1562.95" {
                 description "1562.95 nm/191.81250 THz 6.25/12.5GHz spacing";
               }
               enum "1562.89" {
                 description "1562.89 nm/191.81875 THz 6.25GHz spacing";
               }
               enum "1562.84" {
                 description "1562.84 nm/191.82500 THz 6.25/12.5/75GHz spacing";
               }
               enum "1562.79" {
                 description "1562.79 nm/191.83125 THz 6.25GHz spacing";
               }
               enum "1562.74" {
                 description "1562.74 nm/191.83750 THz 6.25/12.5GHz spacing";
               }
               enum "1562.69" {
                 description "1562.69 nm/191.84375 THz 6.25GHz spacing";
               }
               enum "1562.64" {
                 description "1562.64 nm/191.85000 THz 6.25/12.5/50GHz spacing";
               }
               enum "1562.59" {
                 description "1562.59 nm/191.85625 THz 6.25GHz spacing";
               }
               enum "1562.54" {
                 description "1562.54 nm/191.86250 THz 6.25/12.5GHz spacing";
               }
               enum "1562.49" {
                 description "1562.49 nm/191.86875 THz 6.25GHz spacing";
               }
               enum "1562.44" {
                 description "1562.44 nm/191.87500 THz 6.25/12.5GHz spacing";
               }
               enum "1562.39" {
                 description "1562.39 nm/191.88125 THz 6.25GHz spacing";
               }
               enum "1562.33" {
                 description "1562.33 nm/191.88750 THz 6.25/12.5GHz spacing";
               }
               enum "1562.28" {
                 description "1562.28 nm/191.89375 THz 6.25GHz spacing";
               }
               enum "1562.23" {
                 description "1562.23 nm/191.90000 THz 6.25/12.5/50/75/100GHz spacing";
               }
               enum "1562.18" {
                 description "1562.18 nm/191.90625 THz 6.25GHz spacing";
               }
               enum "1562.13" {
                 description "1562.13 nm/191.91250 THz 6.25/12.5GHz spacing";
               }
               enum "1562.08" {
                 description "1562.08 nm/191.91875 THz 6.25GHz spacing";
               }
               enum "1562.03" {
                 description "1562.03 nm/191.92500 THz 6.25/12.5GHz spacing";
               }
               enum "1561.98" {
                 description "1561.98 nm/191.93125 THz 6.25GHz spacing";
               }
               enum "1561.93" {
                 description "1561.93 nm/191.93750 THz 6.25/12.5GHz spacing";
               }
               enum "1561.88" {
                 description "1561.88 nm/191.94375 THz 6.25GHz spacing";
               }
               enum "1561.83" {
                 description "1561.83 nm/191.95000 THz 6.25/12.5/50GHz spacing";
               }
               enum "1561.77" {
                 description "1561.77 nm/191.95625 THz 6.25GHz spacing";
               }
               enum "1561.72" {
                 description "1561.72 nm/191.96250 THz 6.25/12.5GHz spacing";
               }
               enum "1561.67" {
                 description "1561.67 nm/191.96875 THz 6.25GHz spacing";
               }
               enum "1561.62" {
                 description "1561.62 nm/191.97500 THz 6.25/12.5/75GHz spacing";
               }
               enum "1561.57" {
                 description "1561.57 nm/191.98125 THz 6.25GHz spacing";
               }
               enum "1561.52" {
                 description "1561.52 nm/191.98750 THz 6.25/12.5GHz spacing";
               }
               enum "1561.47" {
                 description "1561.47 nm/191.99375 THz 6.25GHz spacing";
               }
               enum "1561.42" {
                 description "1561.42 nm/192.00000 THz 6.25/12.5/50/100GHz spacing";
               }
               enum "1561.37" {
                 description "1561.37 nm/192.00625 THz 6.25GHz spacing";
               }
               enum "1561.32" {
                 description "1561.32 nm/192.01250 THz 6.25/12.5GHz spacing";
               }
               enum "1561.27" {
                 description "1561.27 nm/192.01875 THz 6.25GHz spacing";
               }
               enum "1561.22" {
                 description "1561.22 nm/192.02500 THz 6.25/12.5GHz spacing";
               }
               enum "1561.16" {
                 description "1561.16 nm/192.03125 THz 6.25GHz spacing";
               }
               enum "1561.11" {
                 description "1561.11 nm/192.03750 THz 6.25/12.5GHz spacing";
               }
               enum "1561.06" {
                 description "1561.06 nm/192.04375 THz 6.25GHz spacing";
               }
               enum "1561.01" {
                 description "1561.01 nm/192.05000 THz 6.25/12.5/50G/75Hz spacing";
               }
               enum "1560.96" {
                 description "1560.96 nm/192.05625 THz 6.25GHz spacing";
               }
               enum "1560.91" {
                 description "1560.91 nm/192.06250 THz 6.25/12.5GHz spacing";
               }
               enum "1560.86" {
                 description "1560.86 nm/192.06875 THz 6.25GHz spacing";
               }
               enum "1560.81" {
                 description "1560.81 nm/192.07500 THz 6.25/12.5GHz spacing";
               }
               enum "1560.76" {
                 description "1560.76 nm/192.08125 THz 6.25GHz spacing";
               }
               enum "1560.71" {
                 description "1560.71 nm/192.08750 THz 6.25/12.5GHz spacing";
               }
               enum "1560.66" {
                 description "1560.66 nm/192.09375 THz 6.25GHz spacing";
               }
               enum "1560.61" {
                 description "1560.61 nm/192.10000 THz 6.25/12.5/50/100GHz spacing";
               }
               enum "1560.56" {
                 description "1560.56 nm/192.10625 THz 6.25GHz spacing";
               }
               enum "1560.50" {
                 description "1560.50 nm/192.11250 THz 6.25/12.5GHz spacing";
               }
               enum "1560.45" {
                 description "1560.45 nm/192.11875 THz 6.25GHz spacing";
               }
               enum "1560.40" {
                 description "1560.40 nm/192.12500 THz 6.25/12.5/75GHz spacing";
               }
               enum "1560.35" {
                 description "1560.35 nm/192.13125 THz 6.25GHz spacing";
               }
               enum "1560.30" {
                 description "1560.30 nm/192.13750 THz 6.25/12.5GHz spacing";
               }
               enum "1560.25" {
                 description "1560.25 nm/192.14375 THz 6.25GHz spacing";
               }
               enum "1560.20" {
                 description "1560.20 nm/192.15000 THz 6.25/12.5/50GHz spacing";
               }
               enum "1560.15" {
                 description "1560.15 nm/192.15625 THz 6.25GHz spacing";
               }
               enum "1560.10" {
                 description "1560.10 nm/192.16250 THz 6.25/12.5GHz spacing";
               }
               enum "1560.05" {
                 description "1560.05 nm/192.16875 THz 6.25GHz spacing";
               }
               enum "1560.00" {
                 description "1560.00 nm/192.17500 THz 6.25/12.5GHz spacing";
               }
               enum "1559.95" {
                 description "1559.95 nm/192.18125 THz 6.25GHz spacing";
               }
               enum "1559.90" {
                 description "1559.90 nm/192.18750 THz 6.25/12.5GHz spacing";
               }
               enum "1559.84" {
                 description "1559.84 nm/192.19375 THz 6.25GHz spacing";
               }
               enum "1559.79" {
                 description "1559.79 nm/192.20000 THz 6.25/12.5/50/75/100GHz spacing";
               }
               enum "1559.74" {
                 description "1559.74 nm/192.20625 THz 6.25GHz spacing";
               }
               enum "1559.69" {
                 description "1559.69 nm/192.21250 THz 6.25/12.5GHz spacing";
               }
               enum "1559.64" {
                 description "1559.64 nm/192.21875 THz 6.25GHz spacing";
               }
               enum "1559.59" {
                 description "1559.59 nm/192.22500 THz 6.25/12.5GHz spacing";
               }
               enum "1559.54" {
                 description "1559.54 nm/192.23125 THz 6.25GHz spacing";
               }
               enum "1559.49" {
                 description "1559.49 nm/192.23750 THz 6.25/12.5GHz spacing";
               }
               enum "1559.44" {
                 description "1559.44 nm/192.24375 THz 6.25GHz spacing";
               }
               enum "1559.39" {
                 description "1559.39 nm/192.25000 THz 6.25/12.5/50GHz spacing";
               }
               enum "1559.34" {
                 description "1559.34 nm/192.25625 THz 6.25GHz spacing";
               }
               enum "1559.29" {
                 description "1559.29 nm/192.26250 THz 6.25/12.5GHz spacing";
               }
               enum "1559.24" {
                 description "1559.24 nm/192.26875 THz 6.25GHz spacing";
               }
               enum "1559.19" {
                 description "1559.19 nm/192.27500 THz 6.25/12.5/75GHz spacing";
               }
               enum "1559.14" {
                 description "1559.14 nm/192.28125 THz 6.25GHz spacing";
               }
               enum "1559.08" {
                 description "1559.08 nm/192.28750 THz 6.25/12.5GHz spacing";
               }
               enum "1559.03" {
                 description "1559.03 nm/192.29375 THz 6.25GHz spacing";
               }
               enum "1558.98" {
                 description "1558.98 nm/192.30000 THz 6.25/12.5/50/100GHz spacing";
               }
               enum "1558.93" {
                 description "1558.93 nm/192.30625 THz 6.25GHz spacing";
               }
               enum "1558.88" {
                 description "1558.88 nm/192.31250 THz 6.25/12.5GHz spacing";
               }
               enum "1558.83" {
                 description "1558.83 nm/192.31875 THz 6.25GHz spacing";
               }
               enum "1558.78" {
                 description "1558.78 nm/192.32500 THz 6.25/12.5GHz spacing";
               }
               enum "1558.73" {
                 description "1558.73 nm/192.33125 THz 6.25GHz spacing";
               }
               enum "1558.68" {
                 description "1558.68 nm/192.33750 THz 6.25/12.5GHz spacing";
               }
               enum "1558.63" {
                 description "1558.63 nm/192.34375 THz 6.25GHz spacing";
               }
               enum "1558.58" {
                 description "1558.58 nm/192.35000 THz 6.25/12.5/50/75GHz spacing";
               }
               enum "1558.53" {
                 description "1558.53 nm/192.35625 THz 6.25GHz spacing";
               }
               enum "1558.48" {
                 description "1558.48 nm/192.36250 THz 6.25/12.5GHz spacing";
               }
               enum "1558.43" {
                 description "1558.43 nm/192.36875 THz 6.25GHz spacing";
               }
               enum "1558.38" {
                 description "1558.38 nm/192.37500 THz 6.25/12.5GHz spacing";
               }
               enum "1558.32" {
                 description "1558.32 nm/192.38125 THz 6.25GHz spacing";
               }
               enum "1558.27" {
                 description "1558.27 nm/192.38750 THz 6.25/12.5GHz spacing";
               }
               enum "1558.22" {
                 description "1558.22 nm/192.39375 THz 6.25GHz spacing";
               }
               enum "1558.17" {
                 description "1558.17 nm/192.40000 THz 6.25/12.5/50/100GHz spacing";
               }
               enum "1558.12" {
                 description "1558.12 nm/192.40625 THz 6.25GHz spacing";
               }
               enum "1558.07" {
                 description "1558.07 nm/192.41250 THz 6.25/12.5GHz spacing";
               }
               enum "1558.02" {
                 description "1558.02 nm/192.41875 THz 6.25GHz spacing";
               }
               enum "1557.97" {
                 description "1557.97 nm/192.42500 THz 6.25/12.5/75GHz spacing";
               }
               enum "1557.92" {
                 description "1557.92 nm/192.43125 THz 6.25GHz spacing";
               }
               enum "1557.87" {
                 description "1557.87 nm/192.43750 THz 6.25/12.5GHz spacing";
               }
               enum "1557.82" {
                 description "1557.82 nm/192.44375 THz 6.25GHz spacing";
               }
               enum "1557.77" {
                 description "1557.77 nm/192.45000 THz 6.25/12.5/50GHz spacing";
               }
               enum "1557.72" {
                 description "1557.72 nm/192.45625 THz 6.25GHz spacing";
               }
               enum "1557.67" {
                 description "1557.67 nm/192.46250 THz 6.25/12.5GHz spacing";
               }
               enum "1557.62" {
                 description "1557.62 nm/192.46875 THz 6.25GHz spacing";
               }
               enum "1557.57" {
                 description "1557.57 nm/192.47500 THz 6.25/12.5GHz spacing";
               }
               enum "1557.52" {
                 description "1557.52 nm/192.48125 THz 6.25GHz spacing";
               }
               enum "1557.46" {
                 description "1557.46 nm/192.48750 THz 6.25/12.5GHz spacing";
               }
               enum "1557.41" {
                 description "1557.41 nm/192.49375 THz 6.25GHz spacing";
               }
               enum "1557.36" {
                 description "1557.36 nm/192.50000 THz 6.25/12.5/50/75/100GHz spacing";
               }
               enum "1557.31" {
                 description "1557.31 nm/192.50625 THz 6.25GHz spacing";
               }
               enum "1557.26" {
                 description "1557.26 nm/192.51250 THz 6.25/12.5GHz spacing";
               }
               enum "1557.21" {
                 description "1557.21 nm/192.51875 THz 6.25GHz spacing";
               }
               enum "1557.16" {
                 description "1557.16 nm/192.52500 THz 6.25/12.5GHz spacing";
               }
               enum "1557.11" {
                 description "1557.11 nm/192.53125 THz 6.25GHz spacing";
               }
               enum "1557.06" {
                 description "1557.06 nm/192.53750 THz 6.25/12.5GHz spacing";
               }
               enum "1557.01" {
                 description "1557.01 nm/192.54375 THz 6.25GHz spacing";
               }
               enum "1556.96" {
                 description "1556.96 nm/192.55000 THz 6.25/12.5/50GHz spacing";
               }
               enum "1556.91" {
                 description "1556.91 nm/192.55625 THz 6.25GHz spacing";
               }
               enum "1556.86" {
                 description "1556.86 nm/192.56250 THz 6.25/12.5GHz spacing";
               }
               enum "1556.81" {
                 description "1556.81 nm/192.56875 THz 6.25GHz spacing";
               }
               enum "1556.76" {
                 description "1556.76 nm/192.57500 THz 6.25/12.5/75GHz spacing";
               }
               enum "1556.71" {
                 description "1556.71 nm/192.58125 THz 6.25GHz spacing";
               }
               enum "1556.66" {
                 description "1556.66 nm/192.58750 THz 6.25/12.5GHz spacing";
               }
               enum "1556.61" {
                 description "1556.61 nm/192.59375 THz 6.25GHz spacing";
               }
               enum "1556.55" {
                 description "1556.55 nm/192.60000 THz 6.25/12.5/50/100GHz spacing";
               }
               enum "1556.50" {
                 description "1556.50 nm/192.60625 THz 6.25GHz spacing";
               }
               enum "1556.45" {
                 description "1556.45 nm/192.61250 THz 6.25/12.5GHz spacing";
               }
               enum "1556.40" {
                 description "1556.40 nm/192.61875 THz 6.25GHz spacing";
               }
               enum "1556.35" {
                 description "1556.35 nm/192.62500 THz 6.25/12.5GHz spacing";
               }
               enum "1556.30" {
                 description "1556.30 nm/192.63125 THz 6.25GHz spacing";
               }
               enum "1556.25" {
                 description "1556.25 nm/192.63750 THz 6.25/12.5GHz spacing";
               }
               enum "1556.20" {
                 description "1556.20 nm/192.64375 THz 6.25GHz spacing";
               }
               enum "1556.15" {
                 description "1556.15 nm/192.65000 THz 6.25/12.5/50/75GHz spacing";
               }
               enum "1556.10" {
                 description "1556.10 nm/192.65625 THz 6.25GHz spacing";
               }
               enum "1556.05" {
                 description "1556.05 nm/192.66250 THz 6.25/12.5GHz spacing";
               }
               enum "1556.00" {
                 description "1556.00 nm/192.66875 THz 6.25GHz spacing";
               }
               enum "1555.95" {
                 description "1555.95 nm/192.67500 THz 6.25/12.5GHz spacing";
               }
               enum "1555.90" {
                 description "1555.90 nm/192.68125 THz 6.25GHz spacing";
               }
               enum "1555.85" {
                 description "1555.85 nm/192.68750 THz 6.25/12.5GHz spacing";
               }
               enum "1555.80" {
                 description "1555.80 nm/192.69375 THz 6.25GHz spacing";
               }
               enum "1555.75" {
                 description "1555.75 nm/192.70000 THz 6.25/12.5/50/100GHz spacing";
               }
               enum "1555.70" {
                 description "1555.70 nm/192.70625 THz 6.25GHz spacing";
               }
               enum "1555.65" {
                 description "1555.65 nm/192.71250 THz 6.25/12.5GHz spacing";
               }
               enum "1555.60" {
                 description "1555.60 nm/192.71875 THz 6.25GHz spacing";
               }
               enum "1555.55" {
                 description "1555.55 nm/192.72500 THz 6.25/12.5/75GHz spacing";
               }
               enum "1555.49" {
                 description "1555.49 nm/192.73125 THz 6.25GHz spacing";
               }
               enum "1555.44" {
                 description "1555.44 nm/192.73750 THz 6.25/12.5GHz spacing";
               }
               enum "1555.39" {
                 description "1555.39 nm/192.74375 THz 6.25GHz spacing";
               }
               enum "1555.34" {
                 description "1555.34 nm/192.75000 THz 6.25/12.5/50GHz spacing";
               }
               enum "1555.29" {
                 description "1555.29 nm/192.75625 THz 6.25GHz spacing";
               }
               enum "1555.24" {
                 description "1555.24 nm/192.76250 THz 6.25/12.5GHz spacing";
               }
               enum "1555.19" {
                 description "1555.19 nm/192.76875 THz 6.25GHz spacing";
               }
               enum "1555.14" {
                 description "1555.14 nm/192.77500 THz 6.25/12.5GHz spacing";
               }
               enum "1555.09" {
                 description "1555.09 nm/192.78125 THz 6.25GHz spacing";
               }
               enum "1555.04" {
                 description "1555.04 nm/192.78750 THz 6.25/12.5GHz spacing";
               }
               enum "1554.99" {
                 description "1554.99 nm/192.79375 THz 6.25GHz spacing";
               }
               enum "1554.94" {
                 description "1554.94 nm/192.80000 THz 6.25/12.5/50/75/100GHz spacing";
               }
               enum "1554.89" {
                 description "1554.89 nm/192.80625 THz 6.25GHz spacing";
               }
               enum "1554.84" {
                 description "1554.84 nm/192.81250 THz 6.25/12.5GHz spacing";
               }
               enum "1554.79" {
                 description "1554.79 nm/192.81875 THz 6.25GHz spacing";
               }
               enum "1554.74" {
                 description "1554.74 nm/192.82500 THz 6.25/12.5GHz spacing";
               }
               enum "1554.69" {
                 description "1554.69 nm/192.83125 THz 6.25GHz spacing";
               }
               enum "1554.64" {
                 description "1554.64 nm/192.83750 THz 6.25/12.5GHz spacing";
               }
               enum "1554.59" {
                 description "1554.59 nm/192.84375 THz 6.25GHz spacing";
               }
               enum "1554.54" {
                 description "1554.54 nm/192.85000 THz 6.25/12.5/50GHz spacing";
               }
               enum "1554.49" {
                 description "1554.49 nm/192.85625 THz 6.25GHz spacing";
               }
               enum "1554.44" {
                 description "1554.44 nm/192.86250 THz 6.25/12.5GHz spacing";
               }
               enum "1554.39" {
                 description "1554.39 nm/192.86875 THz 6.25GHz spacing";
               }
               enum "1554.34" {
                 description "1554.34 nm/192.87500 THz 6.25/12.5/75GHz spacing";
               }
               enum "1554.29" {
                 description "1554.29 nm/192.88125 THz 6.25GHz spacing";
               }
               enum "1554.23" {
                 description "1554.23 nm/192.88750 THz 6.25/12.5GHz spacing";
               }
               enum "1554.18" {
                 description "1554.18 nm/192.89375 THz 6.25GHz spacing";
               }
               enum "1554.13" {
                 description "1554.13 nm/192.90000 THz 6.25/12.5/50/100GHz spacing";
               }
               enum "1554.08" {
                 description "1554.08 nm/192.90625 THz 6.25GHz spacing";
               }
               enum "1554.03" {
                 description "1554.03 nm/192.91250 THz 6.25/12.5GHz spacing";
               }
               enum "1553.98" {
                 description "1553.98 nm/192.91875 THz 6.25GHz spacing";
               }
               enum "1553.93" {
                 description "1553.93 nm/192.92500 THz 6.25/12.5GHz spacing";
               }
               enum "1553.88" {
                 description "1553.88 nm/192.93125 THz 6.25GHz spacing";
               }
               enum "1553.83" {
                 description "1553.83 nm/192.93750 THz 6.25/12.5GHz spacing";
               }
               enum "1553.78" {
                 description "1553.78 nm/192.94375 THz 6.25GHz spacing";
               }
               enum "1553.73" {
                 description "1553.73 nm/192.95000 THz 6.25/12.5/50/75GHz spacing";
               }
               enum "1553.68" {
                 description "1553.68 nm/192.95625 THz 6.25GHz spacing";
               }
               enum "1553.63" {
                 description "1553.63 nm/192.96250 THz 6.25/12.5GHz spacing";
               }
               enum "1553.58" {
                 description "1553.58 nm/192.96875 THz 6.25GHz spacing";
               }
               enum "1553.53" {
                 description "1553.53 nm/192.97500 THz 6.25/12.5GHz spacing";
               }
               enum "1553.48" {
                 description "1553.48 nm/192.98125 THz 6.25GHz spacing";
               }
               enum "1553.43" {
                 description "1553.43 nm/192.98750 THz 6.25/12.5GHz spacing";
               }
               enum "1553.38" {
                 description "1553.38 nm/192.99375 THz 6.25GHz spacing";
               }
               enum "1553.33" {
                 description "1553.33 nm/193.00000 THz 6.25/12.5/50/100GHz spacing";
               }
               enum "1553.28" {
                 description "1553.28 nm/193.00625 THz 6.25GHz spacing";
               }
               enum "1553.23" {
                 description "1553.23 nm/193.01250 THz 6.25/12.5GHz spacing";
               }
               enum "1553.18" {
                 description "1553.18 nm/193.01875 THz 6.25GHz spacing";
               }
               enum "1553.13" {
                 description "1553.13 nm/193.02500 THz 6.25/12.5/75GHz spacing";
               }
               enum "1553.08" {
                 description "1553.08 nm/193.03125 THz 6.25GHz spacing";
               }
               enum "1553.03" {
                 description "1553.03 nm/193.03750 THz 6.25/12.5GHz spacing";
               }
               enum "1552.98" {
                 description "1552.98 nm/193.04375 THz 6.25GHz spacing";
               }
               enum "1552.93" {
                 description "1552.93 nm/193.05000 THz 6.25/12.5/50GHz spacing";
               }
               enum "1552.88" {
                 description "1552.88 nm/193.05625 THz 6.25GHz spacing";
               }
               enum "1552.83" {
                 description "1552.83 nm/193.06250 THz 6.25/12.5GHz spacing";
               }
               enum "1552.78" {
                 description "1552.78 nm/193.06875 THz 6.25GHz spacing";
               }
               enum "1552.73" {
                 description "1552.73 nm/193.07500 THz 6.25/12.5GHz spacing";
               }
               enum "1552.68" {
                 description "1552.68 nm/193.08125 THz 6.25GHz spacing";
               }
               enum "1552.62" {
                 description "1552.62 nm/193.08750 THz 6.25/12.5GHz spacing";
               }
               enum "1552.57" {
                 description "1552.57 nm/193.09375 THz 6.25GHz spacing";
               }
               enum "1552.52" {
                 description "1552.52 nm/193.10000 THz 6.25/12.5/50/75/100GHz spacing";
               }
               enum "1552.47" {
                 description "1552.47 nm/193.10625 THz 6.25GHz spacing";
               }
               enum "1552.42" {
                 description "1552.42 nm/193.11250 THz 6.25/12.5GHz spacing";
               }
               enum "1552.37" {
                 description "1552.37 nm/193.11875 THz 6.25GHz spacing";
               }
               enum "1552.32" {
                 description "1552.32 nm/193.12500 THz 6.25/12.5GHz spacing";
               }
               enum "1552.27" {
                 description "1552.27 nm/193.13125 THz 6.25GHz spacing";
               }
               enum "1552.22" {
                 description "1552.22 nm/193.13750 THz 6.25/12.5GHz spacing";
               }
               enum "1552.17" {
                 description "1552.17 nm/193.14375 THz 6.25GHz spacing";
               }
               enum "1552.12" {
                 description "1552.12 nm/193.15000 THz 6.25/12.5/50GHz spacing";
               }
               enum "1552.07" {
                 description "1552.07 nm/193.15625 THz 6.25GHz spacing";
               }
               enum "1552.02" {
                 description "1552.02 nm/193.16250 THz 6.25/12.5GHz spacing";
               }
               enum "1551.97" {
                 description "1551.97 nm/193.16875 THz 6.25GHz spacing";
               }
               enum "1551.92" {
                 description "1551.92 nm/193.17500 THz 6.25/12.5/75GHz spacing";
               }
               enum "1551.87" {
                 description "1551.87 nm/193.18125 THz 6.25GHz spacing";
               }
               enum "1551.82" {
                 description "1551.82 nm/193.18750 THz 6.25/12.5GHz spacing";
               }
               enum "1551.77" {
                 description "1551.77 nm/193.19375 THz 6.25GHz spacing";
               }
               enum "1551.72" {
                 description "1551.72 nm/193.20000 THz 6.25/12.5/50/100GHz spacing";
               }
               enum "1551.67" {
                 description "1551.67 nm/193.20625 THz 6.25GHz spacing";
               }
               enum "1551.62" {
                 description "1551.62 nm/193.21250 THz 6.25/12.5GHz spacing";
               }
               enum "1551.57" {
                 description "1551.57 nm/193.21875 THz 6.25GHz spacing";
               }
               enum "1551.52" {
                 description "1551.52 nm/193.22500 THz 6.25/12.5GHz spacing";
               }
               enum "1551.47" {
                 description "1551.47 nm/193.23125 THz 6.25GHz spacing";
               }
               enum "1551.42" {
                 description "1551.42 nm/193.23750 THz 6.25/12.5GHz spacing";
               }
               enum "1551.37" {
                 description "1551.37 nm/193.24375 THz 6.25GHz spacing";
               }
               enum "1551.32" {
                 description "1551.32 nm/193.25000 THz 6.25/12.5/50/75GHz spacing";
               }
               enum "1551.27" {
                 description "1551.27 nm/193.25625 THz 6.25GHz spacing";
               }
               enum "1551.22" {
                 description "1551.22 nm/193.26250 THz 6.25/12.5GHz spacing";
               }
               enum "1551.17" {
                 description "1551.17 nm/193.26875 THz 6.25GHz spacing";
               }
               enum "1551.12" {
                 description "1551.12 nm/193.27500 THz 6.25/12.5GHz spacing";
               }
               enum "1551.07" {
                 description "1551.07 nm/193.28125 THz 6.25GHz spacing";
               }
               enum "1551.02" {
                 description "1551.02 nm/193.28750 THz 6.25/12.5GHz spacing";
               }
               enum "1550.97" {
                 description "1550.97 nm/193.29375 THz 6.25GHz spacing";
               }
               enum "1550.92" {
                 description "1550.92 nm/193.30000 THz 6.25/12.5/50/100GHz spacing";
               }
               enum "1550.87" {
                 description "1550.87 nm/193.30625 THz 6.25GHz spacing";
               }
               enum "1550.82" {
                 description "1550.82 nm/193.31250 THz 6.25/12.5GHz spacing";
               }
               enum "1550.77" {
                 description "1550.77 nm/193.31875 THz 6.25GHz spacing";
               }
               enum "1550.72" {
                 description "1550.72 nm/193.32500 THz 6.25/12.5/75GHz spacing";
               }
               enum "1550.67" {
                 description "1550.67 nm/193.33125 THz 6.25GHz spacing";
               }
               enum "1550.62" {
                 description "1550.62 nm/193.33750 THz 6.25/12.5GHz spacing";
               }
               enum "1550.57" {
                 description "1550.57 nm/193.34375 THz 6.25GHz spacing";
               }
               enum "1550.52" {
                 description "1550.52 nm/193.35000 THz 6.25/12.5/50GHz spacing";
               }
               enum "1550.47" {
                 description "1550.47 nm/193.35625 THz 6.25GHz spacing";
               }
               enum "1550.42" {
                 description "1550.42 nm/193.36250 THz 6.25/12.5GHz spacing";
               }
               enum "1550.37" {
                 description "1550.37 nm/193.36875 THz 6.25GHz spacing";
               }
               enum "1550.32" {
                 description "1550.32 nm/193.37500 THz 6.25/12.5GHz spacing";
               }
               enum "1550.27" {
                 description "1550.27 nm/193.38125 THz 6.25GHz spacing";
               }
               enum "1550.22" {
                 description "1550.22 nm/193.38750 THz 6.25/12.5GHz spacing";
               }
               enum "1550.17" {
                 description "1550.17 nm/193.39375 THz 6.25GHz spacing";
               }
               enum "1550.12" {
                 description "1550.12 nm/193.40000 THz 6.25/12.5/50/75/100GHz spacing";
               }
               enum "1550.07" {
                 description "1550.07 nm/193.40625 THz 6.25GHz spacing";
               }
               enum "1550.02" {
                 description "1550.02 nm/193.41250 THz 6.25/12.5GHz spacing";
               }
               enum "1549.97" {
                 description "1549.97 nm/193.41875 THz 6.25GHz spacing";
               }
               enum "1549.92" {
                 description "1549.92 nm/193.42500 THz 6.25/12.5GHz spacing";
               }
               enum "1549.87" {
                 description "1549.87 nm/193.43125 THz 6.25GHz spacing";
               }
               enum "1549.82" {
                 description "1549.82 nm/193.43750 THz 6.25/12.5GHz spacing";
               }
               enum "1549.77" {
                 description "1549.77 nm/193.44375 THz 6.25GHz spacing";
               }
               enum "1549.72" {
                 description "1549.72 nm/193.45000 THz 6.25/12.5/50GHz spacing";
               }
               enum "1549.67" {
                 description "1549.67 nm/193.45625 THz 6.25GHz spacing";
               }
               enum "1549.62" {
                 description "1549.62 nm/193.46250 THz 6.25/12.5GHz spacing";
               }
               enum "1549.57" {
                 description "1549.57 nm/193.46875 THz 6.25GHz spacing";
               }
               enum "1549.52" {
                 description "1549.52 nm/193.47500 THz 6.25/12.5/75GHz spacing";
               }
               enum "1549.47" {
                 description "1549.47 nm/193.48125 THz 6.25GHz spacing";
               }
               enum "1549.42" {
                 description "1549.42 nm/193.48750 THz 6.25/12.5GHz spacing";
               }
               enum "1549.37" {
                 description "1549.37 nm/193.49375 THz 6.25GHz spacing";
               }
               enum "1549.32" {
                 description "1549.32 nm/193.50000 THz 6.25/12.5/50/100GHz spacing";
               }
               enum "1549.26" {
                 description "1549.26 nm/193.50625 THz 6.25GHz spacing";
               }
               enum "1549.21" {
                 description "1549.21 nm/193.51250 THz 6.25/12.5GHz spacing";
               }
               enum "1549.16" {
                 description "1549.16 nm/193.51875 THz 6.25GHz spacing";
               }
               enum "1549.11" {
                 description "1549.11 nm/193.52500 THz 6.25/12.5GHz spacing";
               }
               enum "1549.06" {
                 description "1549.06 nm/193.53125 THz 6.25GHz spacing";
               }
               enum "1549.01" {
                 description "1549.01 nm/193.53750 THz 6.25/12.5GHz spacing";
               }
               enum "1548.96" {
                 description "1548.96 nm/193.54375 THz 6.25GHz spacing";
               }
               enum "1548.91" {
                 description "1548.91 nm/193.55000 THz 6.25/12.5/50G/75Hz spacing";
               }
               enum "1548.86" {
                 description "1548.86 nm/193.55625 THz 6.25GHz spacing";
               }
               enum "1548.81" {
                 description "1548.81 nm/193.56250 THz 6.25/12.5GHz spacing";
               }
               enum "1548.76" {
                 description "1548.76 nm/193.56875 THz 6.25GHz spacing";
               }
               enum "1548.71" {
                 description "1548.71 nm/193.57500 THz 6.25/12.5GHz spacing";
               }
               enum "1548.66" {
                 description "1548.66 nm/193.58125 THz 6.25GHz spacing";
               }
               enum "1548.61" {
                 description "1548.61 nm/193.58750 THz 6.25/12.5GHz spacing";
               }
               enum "1548.56" {
                 description "1548.56 nm/193.59375 THz 6.25GHz spacing";
               }
               enum "1548.51" {
                 description "1548.51 nm/193.60000 THz 6.25/12.5/50/100GHz spacing";
               }
               enum "1548.46" {
                 description "1548.46 nm/193.60625 THz 6.25GHz spacing";
               }
               enum "1548.41" {
                 description "1548.41 nm/193.61250 THz 6.25/12.5GHz spacing";
               }
               enum "1548.36" {
                 description "1548.36 nm/193.61875 THz 6.25GHz spacing";
               }
               enum "1548.31" {
                 description "1548.31 nm/193.62500 THz 6.25/12.5/75GHz spacing";
               }
               enum "1548.26" {
                 description "1548.26 nm/193.63125 THz 6.25GHz spacing";
               }
               enum "1548.21" {
                 description "1548.21 nm/193.63750 THz 6.25/12.5GHz spacing";
               }
               enum "1548.16" {
                 description "1548.16 nm/193.64375 THz 6.25GHz spacing";
               }
               enum "1548.11" {
                 description "1548.11 nm/193.65000 THz 6.25/12.5/50GHz spacing";
               }
               enum "1548.06" {
                 description "1548.06 nm/193.65625 THz 6.25GHz spacing";
               }
               enum "1548.02" {
                 description "1548.02 nm/193.66250 THz 6.25/12.5GHz spacing";
               }
               enum "1547.97" {
                 description "1547.97 nm/193.66875 THz 6.25GHz spacing";
               }
               enum "1547.92" {
                 description "1547.92 nm/193.67500 THz 6.25/12.5GHz spacing";
               }
               enum "1547.87" {
                 description "1547.87 nm/193.68125 THz 6.25GHz spacing";
               }
               enum "1547.82" {
                 description "1547.82 nm/193.68750 THz 6.25/12.5GHz spacing";
               }
               enum "1547.77" {
                 description "1547.77 nm/193.69375 THz 6.25GHz spacing";
               }
               enum "1547.72" {
                 description "1547.72 nm/193.70000 THz 6.25/12.5/50/75/100GHz spacing";
               }
               enum "1547.67" {
                 description "1547.67 nm/193.70625 THz 6.25GHz spacing";
               }
               enum "1547.62" {
                 description "1547.62 nm/193.71250 THz 6.25/12.5GHz spacing";
               }
               enum "1547.57" {
                 description "1547.57 nm/193.71875 THz 6.25GHz spacing";
               }
               enum "1547.52" {
                 description "1547.52 nm/193.72500 THz 6.25/12.5GHz spacing";
               }
               enum "1547.47" {
                 description "1547.47 nm/193.73125 THz 6.25GHz spacing";
               }
               enum "1547.42" {
                 description "1547.42 nm/193.73750 THz 6.25/12.5GHz spacing";
               }
               enum "1547.37" {
                 description "1547.37 nm/193.74375 THz 6.25GHz spacing";
               }
               enum "1547.32" {
                 description "1547.32 nm/193.75000 THz 6.25/12.5/50GHz spacing";
               }
               enum "1547.27" {
                 description "1547.27 nm/193.75625 THz 6.25GHz spacing";
               }
               enum "1547.22" {
                 description "1547.22 nm/193.76250 THz 6.25/12.5GHz spacing";
               }
               enum "1547.17" {
                 description "1547.17 nm/193.76875 THz 6.25GHz spacing";
               }
               enum "1547.12" {
                 description "1547.12 nm/193.77500 THz 6.25/12.5/75GHz spacing";
               }
               enum "1547.07" {
                 description "1547.07 nm/193.78125 THz 6.25GHz spacing";
               }
               enum "1547.02" {
                 description "1547.02 nm/193.78750 THz 6.25/12.5GHz spacing";
               }
               enum "1546.97" {
                 description "1546.97 nm/193.79375 THz 6.25GHz spacing";
               }
               enum "1546.92" {
                 description "1546.92 nm/193.80000 THz 6.25/12.5/50/100GHz spacing";
               }
               enum "1546.87" {
                 description "1546.87 nm/193.80625 THz 6.25GHz spacing";
               }
               enum "1546.82" {
                 description "1546.82 nm/193.81250 THz 6.25/12.5GHz spacing";
               }
               enum "1546.77" {
                 description "1546.77 nm/193.81875 THz 6.25GHz spacing";
               }
               enum "1546.72" {
                 description "1546.72 nm/193.82500 THz 6.25/12.5GHz spacing";
               }
               enum "1546.67" {
                 description "1546.67 nm/193.83125 THz 6.25GHz spacing";
               }
               enum "1546.62" {
                 description "1546.62 nm/193.83750 THz 6.25/12.5GHz spacing";
               }
               enum "1546.57" {
                 description "1546.57 nm/193.84375 THz 6.25GHz spacing";
               }
               enum "1546.52" {
                 description "1546.52 nm/193.85000 THz 6.25/12.5/50/75GHz spacing";
               }
               enum "1546.47" {
                 description "1546.47 nm/193.85625 THz 6.25GHz spacing";
               }
               enum "1546.42" {
                 description "1546.42 nm/193.86250 THz 6.25/12.5GHz spacing";
               }
               enum "1546.37" {
                 description "1546.37 nm/193.86875 THz 6.25GHz spacing";
               }
               enum "1546.32" {
                 description "1546.32 nm/193.87500 THz 6.25/12.5GHz spacing";
               }
               enum "1546.27" {
                 description "1546.27 nm/193.88125 THz 6.25GHz spacing";
               }
               enum "1546.22" {
                 description "1546.22 nm/193.88750 THz 6.25/12.5GHz spacing";
               }
               enum "1546.17" {
                 description "1546.17 nm/193.89375 THz 6.25GHz spacing";
               }
               enum "1546.12" {
                 description "1546.12 nm/193.90000 THz 6.25/12.5/50/100GHz spacing";
               }
               enum "1546.07" {
                 description "1546.07 nm/193.90625 THz 6.25GHz spacing";
               }
               enum "1546.02" {
                 description "1546.02 nm/193.91250 THz 6.25/12.5GHz spacing";
               }
               enum "1545.97" {
                 description "1545.97 nm/193.91875 THz 6.25GHz spacing";
               }
               enum "1545.92" {
                 description "1545.92 nm/193.92500 THz 6.25/12.5/75GHz spacing";
               }
               enum "1545.87" {
                 description "1545.87 nm/193.93125 THz 6.25GHz spacing";
               }
               enum "1545.82" {
                 description "1545.82 nm/193.93750 THz 6.25/12.5GHz spacing";
               }
               enum "1545.77" {
                 description "1545.77 nm/193.94375 THz 6.25GHz spacing";
               }
               enum "1545.72" {
                 description "1545.72 nm/193.95000 THz 6.25/12.5/50GHz spacing";
               }
               enum "1545.67" {
                 description "1545.67 nm/193.95625 THz 6.25GHz spacing";
               }
               enum "1545.62" {
                 description "1545.62 nm/193.96250 THz 6.25/12.5GHz spacing";
               }
               enum "1545.57" {
                 description "1545.57 nm/193.96875 THz 6.25GHz spacing";
               }
               enum "1545.52" {
                 description "1545.52 nm/193.97500 THz 6.25/12.5GHz spacing";
               }
               enum "1545.47" {
                 description "1545.47 nm/193.98125 THz 6.25GHz spacing";
               }
               enum "1545.42" {
                 description "1545.42 nm/193.98750 THz 6.25/12.5GHz spacing";
               }
               enum "1545.37" {
                 description "1545.37 nm/193.99375 THz 6.25GHz spacing";
               }
               enum "1545.32" {
                 description "1545.32 nm/194.00000 THz 6.25/12.5/50/75/100GHz spacing";
               }
               enum "1545.27" {
                 description "1545.27 nm/194.00625 THz 6.25GHz spacing";
               }
               enum "1545.22" {
                 description "1545.22 nm/194.01250 THz 6.25/12.5GHz spacing";
               }
               enum "1545.17" {
                 description "1545.17 nm/194.01875 THz 6.25GHz spacing";
               }
               enum "1545.12" {
                 description "1545.12 nm/194.02500 THz 6.25/12.5GHz spacing";
               }
               enum "1545.07" {
                 description "1545.07 nm/194.03125 THz 6.25GHz spacing";
               }
               enum "1545.02" {
                 description "1545.02 nm/194.03750 THz 6.25/12.5GHz spacing";
               }
               enum "1544.97" {
                 description "1544.97 nm/194.04375 THz 6.25GHz spacing";
               }
               enum "1544.92" {
                 description "1544.92 nm/194.05000 THz 6.25/12.5/50GHz spacing";
               }
               enum "1544.87" {
                 description "1544.87 nm/194.05625 THz 6.25GHz spacing";
               }
               enum "1544.82" {
                 description "1544.82 nm/194.06250 THz 6.25/12.5GHz spacing";
               }
               enum "1544.77" {
                 description "1544.77 nm/194.06875 THz 6.25GHz spacing";
               }
               enum "1544.72" {
                 description "1544.72 nm/194.07500 THz 6.25/12.5/75GHz spacing";
               }
               enum "1544.68" {
                 description "1544.68 nm/194.08125 THz 6.25GHz spacing";
               }
               enum "1544.63" {
                 description "1544.63 nm/194.08750 THz 6.25/12.5GHz spacing";
               }
               enum "1544.58" {
                 description "1544.58 nm/194.09375 THz 6.25GHz spacing";
               }
               enum "1544.53" {
                 description "1544.53 nm/194.10000 THz 6.25/12.5/50/100GHz spacing";
               }
               enum "1544.48" {
                 description "1544.48 nm/194.10625 THz 6.25GHz spacing";
               }
               enum "1544.43" {
                 description "1544.43 nm/194.11250 THz 6.25/12.5GHz spacing";
               }
               enum "1544.38" {
                 description "1544.38 nm/194.11875 THz 6.25GHz spacing";
               }
               enum "1544.33" {
                 description "1544.33 nm/194.12500 THz 6.25/12.5GHz spacing";
               }
               enum "1544.28" {
                 description "1544.28 nm/194.13125 THz 6.25GHz spacing";
               }
               enum "1544.23" {
                 description "1544.23 nm/194.13750 THz 6.25/12.5GHz spacing";
               }
               enum "1544.18" {
                 description "1544.18 nm/194.14375 THz 6.25GHz spacing";
               }
               enum "1544.13" {
                 description "1544.13 nm/194.15000 THz 6.25/12.5/50/75GHz spacing";
               }
               enum "1544.08" {
                 description "1544.08 nm/194.15625 THz 6.25GHz spacing";
               }
               enum "1544.03" {
                 description "1544.03 nm/194.16250 THz 6.25/12.5GHz spacing";
               }
               enum "1543.98" {
                 description "1543.98 nm/194.16875 THz 6.25GHz spacing";
               }
               enum "1543.93" {
                 description "1543.93 nm/194.17500 THz 6.25/12.5GHz spacing";
               }
               enum "1543.88" {
                 description "1543.88 nm/194.18125 THz 6.25GHz spacing";
               }
               enum "1543.83" {
                 description "1543.83 nm/194.18750 THz 6.25/12.5GHz spacing";
               }
               enum "1543.78" {
                 description "1543.78 nm/194.19375 THz 6.25GHz spacing";
               }
               enum "1543.73" {
                 description "1543.73 nm/194.20000 THz 6.25/12.5/50/100GHz spacing";
               }
               enum "1543.68" {
                 description "1543.68 nm/194.20625 THz 6.25GHz spacing";
               }
               enum "1543.63" {
                 description "1543.63 nm/194.21250 THz 6.25/12.5GHz spacing";
               }
               enum "1543.58" {
                 description "1543.58 nm/194.21875 THz 6.25GHz spacing";
               }
               enum "1543.53" {
                 description "1543.53 nm/194.22500 THz 6.25/12.5/75GHz spacing";
               }
               enum "1543.48" {
                 description "1543.48 nm/194.23125 THz 6.25GHz spacing";
               }
               enum "1543.43" {
                 description "1543.43 nm/194.23750 THz 6.25/12.5GHz spacing";
               }
               enum "1543.38" {
                 description "1543.38 nm/194.24375 THz 6.25GHz spacing";
               }
               enum "1543.33" {
                 description "1543.33 nm/194.25000 THz 6.25/12.5/50GHz spacing";
               }
               enum "1543.28" {
                 description "1543.28 nm/194.25625 THz 6.25GHz spacing";
               }
               enum "1543.23" {
                 description "1543.23 nm/194.26250 THz 6.25/12.5GHz spacing";
               }
               enum "1543.18" {
                 description "1543.18 nm/194.26875 THz 6.25GHz spacing";
               }
               enum "1543.13" {
                 description "1543.13 nm/194.27500 THz 6.25/12.5GHz spacing";
               }
               enum "1543.08" {
                 description "1543.08 nm/194.28125 THz 6.25GHz spacing";
               }
               enum "1543.04" {
                 description "1543.04 nm/194.28750 THz 6.25/12.5GHz spacing";
               }
               enum "1542.99" {
                 description "1542.99 nm/194.29375 THz 6.25GHz spacing";
               }
               enum "1542.94" {
                 description "1542.94 nm/194.30000 THz 6.25/12.5/50/75/100GHz spacing";
               }
               enum "1542.89" {
                 description "1542.89 nm/194.30625 THz 6.25GHz spacing";
               }
               enum "1542.84" {
                 description "1542.84 nm/194.31250 THz 6.25/12.5GHz spacing";
               }
               enum "1542.79" {
                 description "1542.79 nm/194.31875 THz 6.25GHz spacing";
               }
               enum "1542.74" {
                 description "1542.74 nm/194.32500 THz 6.25/12.5GHz spacing";
               }
               enum "1542.69" {
                 description "1542.69 nm/194.33125 THz 6.25GHz spacing";
               }
               enum "1542.64" {
                 description "1542.64 nm/194.33750 THz 6.25/12.5GHz spacing";
               }
               enum "1542.59" {
                 description "1542.59 nm/194.34375 THz 6.25GHz spacing";
               }
               enum "1542.54" {
                 description "1542.54 nm/194.35000 THz 6.25/12.5/50GHz spacing";
               }
               enum "1542.49" {
                 description "1542.49 nm/194.35625 THz 6.25GHz spacing";
               }
               enum "1542.44" {
                 description "1542.44 nm/194.36250 THz 6.25/12.5GHz spacing";
               }
               enum "1542.39" {
                 description "1542.39 nm/194.36875 THz 6.25GHz spacing";
               }
               enum "1542.34" {
                 description "1542.34 nm/194.37500 THz 6.25/12.5/75GHz spacing";
               }
               enum "1542.29" {
                 description "1542.29 nm/194.38125 THz 6.25GHz spacing";
               }
               enum "1542.24" {
                 description "1542.24 nm/194.38750 THz 6.25/12.5GHz spacing";
               }
               enum "1542.19" {
                 description "1542.19 nm/194.39375 THz 6.25GHz spacing";
               }
               enum "1542.14" {
                 description "1542.14 nm/194.40000 THz 6.25/12.5/50/100GHz spacing";
               }
               enum "1542.09" {
                 description "1542.09 nm/194.40625 THz 6.25GHz spacing";
               }
               enum "1542.04" {
                 description "1542.04 nm/194.41250 THz 6.25/12.5GHz spacing";
               }
               enum "1541.99" {
                 description "1541.99 nm/194.41875 THz 6.25GHz spacing";
               }
               enum "1541.94" {
                 description "1541.94 nm/194.42500 THz 6.25/12.5GHz spacing";
               }
               enum "1541.89" {
                 description "1541.89 nm/194.43125 THz 6.25GHz spacing";
               }
               enum "1541.84" {
                 description "1541.84 nm/194.43750 THz 6.25/12.5GHz spacing";
               }
               enum "1541.80" {
                 description "1541.80 nm/194.44375 THz 6.25GHz spacing";
               }
               enum "1541.75" {
                 description "1541.75 nm/194.45000 THz 6.25/12.5/50/75GHz spacing";
               }
               enum "1541.70" {
                 description "1541.70 nm/194.45625 THz 6.25GHz spacing";
               }
               enum "1541.65" {
                 description "1541.65 nm/194.46250 THz 6.25/12.5GHz spacing";
               }
               enum "1541.60" {
                 description "1541.60 nm/194.46875 THz 6.25GHz spacing";
               }
               enum "1541.55" {
                 description "1541.55 nm/194.47500 THz 6.25/12.5GHz spacing";
               }
               enum "1541.50" {
                 description "1541.50 nm/194.48125 THz 6.25GHz spacing";
               }
               enum "1541.45" {
                 description "1541.45 nm/194.48750 THz 6.25/12.5GHz spacing";
               }
               enum "1541.40" {
                 description "1541.40 nm/194.49375 THz 6.25GHz spacing";
               }
               enum "1541.35" {
                 description "1541.35 nm/194.50000 THz 6.25/12.5/50/100GHz spacing";
               }
               enum "1541.30" {
                 description "1541.30 nm/194.50625 THz 6.25GHz spacing";
               }
               enum "1541.25" {
                 description "1541.25 nm/194.51250 THz 6.25/12.5GHz spacing";
               }
               enum "1541.20" {
                 description "1541.20 nm/194.51875 THz 6.25GHz spacing";
               }
               enum "1541.15" {
                 description "1541.15 nm/194.52500 THz 6.25/12.5/75GHz spacing";
               }
               enum "1541.10" {
                 description "1541.10 nm/194.53125 THz 6.25GHz spacing";
               }
               enum "1541.05" {
                 description "1541.05 nm/194.53750 THz 6.25/12.5GHz spacing";
               }
               enum "1541.00" {
                 description "1541.00 nm/194.54375 THz 6.25GHz spacing";
               }
               enum "1540.95" {
                 description "1540.95 nm/194.55000 THz 6.25/12.5/50GHz spacing";
               }
               enum "1540.90" {
                 description "1540.90 nm/194.55625 THz 6.25GHz spacing";
               }
               enum "1540.85" {
                 description "1540.85 nm/194.56250 THz 6.25/12.5GHz spacing";
               }
               enum "1540.80" {
                 description "1540.80 nm/194.56875 THz 6.25GHz spacing";
               }
               enum "1540.76" {
                 description "1540.76 nm/194.57500 THz 6.25/12.5GHz spacing";
               }
               enum "1540.71" {
                 description "1540.71 nm/194.58125 THz 6.25GHz spacing";
               }
               enum "1540.66" {
                 description "1540.66 nm/194.58750 THz 6.25/12.5GHz spacing";
               }
               enum "1540.61" {
                 description "1540.61 nm/194.59375 THz 6.25GHz spacing";
               }
               enum "1540.56" {
                 description "1540.56 nm/194.60000 THz 6.25/12.5/50/75/100GHz spacing";
               }
               enum "1540.51" {
                 description "1540.51 nm/194.60625 THz 6.25GHz spacing";
               }
               enum "1540.46" {
                 description "1540.46 nm/194.61250 THz 6.25/12.5GHz spacing";
               }
               enum "1540.41" {
                 description "1540.41 nm/194.61875 THz 6.25GHz spacing";
               }
               enum "1540.36" {
                 description "1540.36 nm/194.62500 THz 6.25/12.5GHz spacing";
               }
               enum "1540.31" {
                 description "1540.31 nm/194.63125 THz 6.25GHz spacing";
               }
               enum "1540.26" {
                 description "1540.26 nm/194.63750 THz 6.25/12.5GHz spacing";
               }
               enum "1540.21" {
                 description "1540.21 nm/194.64375 THz 6.25GHz spacing";
               }
               enum "1540.16" {
                 description "1540.16 nm/194.65000 THz 6.25/12.5/50GHz spacing";
               }
               enum "1540.11" {
                 description "1540.11 nm/194.65625 THz 6.25GHz spacing";
               }
               enum "1540.06" {
                 description "1540.06 nm/194.66250 THz 6.25/12.5GHz spacing";
               }
               enum "1540.01" {
                 description "1540.01 nm/194.66875 THz 6.25GHz spacing";
               }
               enum "1539.96" {
                 description "1539.96 nm/194.67500 THz 6.25/12.5/50/75GHz spacing";
               }
               enum "1539.91" {
                 description "1539.91 nm/194.68125 THz 6.25GHz spacing";
               }
               enum "1539.86" {
                 description "1539.86 nm/194.68750 THz 6.25/12.5GHz spacing";
               }
               enum "1539.82" {
                 description "1539.82 nm/194.69375 THz 6.25GHz spacing";
               }
               enum "1539.77" {
                 description "1539.77 nm/194.70000 THz 6.25/12.5/50/100GHz spacing";
               }
               enum "1539.72" {
                 description "1539.72 nm/194.70625 THz 6.25GHz spacing";
               }
               enum "1539.67" {
                 description "1539.67 nm/194.71250 THz 6.25/12.5GHz spacing";
               }
               enum "1539.62" {
                 description "1539.62 nm/194.71875 THz 6.25GHz spacing";
               }
               enum "1539.57" {
                 description "1539.57 nm/194.72500 THz 6.25/12.5GHz spacing";
               }
               enum "1539.52" {
                 description "1539.52 nm/194.73125 THz 6.25GHz spacing";
               }
               enum "1539.47" {
                 description "1539.47 nm/194.73750 THz 6.25/12.5GHz spacing";
               }
               enum "1539.42" {
                 description "1539.42 nm/194.74375 THz 6.25GHz spacing";
               }
               enum "1539.37" {
                 description "1539.37 nm/194.75000 THz 6.25/12.5/50/75GHz spacing";
               }
               enum "1539.32" {
                 description "1539.32 nm/194.75625 THz 6.25GHz spacing";
               }
               enum "1539.27" {
                 description "1539.27 nm/194.76250 THz 6.25/12.5GHz spacing";
               }
               enum "1539.22" {
                 description "1539.22 nm/194.76875 THz 6.25GHz spacing";
               }
               enum "1539.17" {
                 description "1539.17 nm/194.77500 THz 6.25/12.5GHz spacing";
               }
               enum "1539.12" {
                 description "1539.12 nm/194.78125 THz 6.25GHz spacing";
               }
               enum "1539.07" {
                 description "1539.07 nm/194.78750 THz 6.25/12.5GHz spacing";
               }
               enum "1539.03" {
                 description "1539.03 nm/194.79375 THz 6.25GHz spacing";
               }
               enum "1538.98" {
                 description "1538.98 nm/194.80000 THz 6.25/12.5/50/100GHz spacing";
               }
               enum "1538.93" {
                 description "1538.93 nm/194.80625 THz 6.25GHz spacing";
               }
               enum "1538.88" {
                 description "1538.88 nm/194.81250 THz 6.25/12.5GHz spacing";
               }
               enum "1538.83" {
                 description "1538.83 nm/194.81875 THz 6.25GHz spacing";
               }
               enum "1538.78" {
                 description "1538.78 nm/194.82500 THz 6.25/12.5/75GHz spacing";
               }
               enum "1538.73" {
                 description "1538.73 nm/194.83125 THz 6.25GHz spacing";
               }
               enum "1538.68" {
                 description "1538.68 nm/194.83750 THz 6.25/12.5GHz spacing";
               }
               enum "1538.63" {
                 description "1538.63 nm/194.84375 THz 6.25GHz spacing";
               }
               enum "1538.58" {
                 description "1538.58 nm/194.85000 THz 6.25/12.5/50GHz spacing";
               }
               enum "1538.53" {
                 description "1538.53 nm/194.85625 THz 6.25GHz spacing";
               }
               enum "1538.48" {
                 description "1538.48 nm/194.86250 THz 6.25/12.5GHz spacing";
               }
               enum "1538.43" {
                 description "1538.43 nm/194.86875 THz 6.25GHz spacing";
               }
               enum "1538.38" {
                 description "1538.38 nm/194.87500 THz 6.25/12.5/75GHz spacing";
               }
               enum "1538.33" {
                 description "1538.33 nm/194.88125 THz 6.25GHz spacing";
               }
               enum "1538.28" {
                 description "1538.28 nm/194.88750 THz 6.25/12.5GHz spacing";
               }
               enum "1538.24" {
                 description "1538.24 nm/194.89375 THz 6.25GHz spacing";
               }
               enum "1538.19" {
                 description "1538.19 nm/194.90000 THz 6.25/12.5/50/75/100GHz spacing";
               }
               enum "1538.14" {
                 description "1538.14 nm/194.90625 THz 6.25GHz spacing";
               }
               enum "1538.09" {
                 description "1538.09 nm/194.91250 THz 6.25/12.5GHz spacing";
               }
               enum "1538.04" {
                 description "1538.04 nm/194.91875 THz 6.25GHz spacing";
               }
               enum "1537.99" {
                 description "1537.99 nm/194.92500 THz 6.25/12.5GHz spacing";
               }
               enum "1537.94" {
                 description "1537.94 nm/194.93125 THz 6.25GHz spacing";
               }
               enum "1537.89" {
                 description "1537.89 nm/194.93750 THz 6.25/12.5GHz spacing";
               }
               enum "1537.84" {
                 description "1537.84 nm/194.94375 THz 6.25GHz spacing";
               }
               enum "1537.79" {
                 description "1537.79 nm/194.95000 THz 6.25/12.5/50GHz spacing";
               }
               enum "1537.74" {
                 description "1537.74 nm/194.95625 THz 6.25GHz spacing";
               }
               enum "1537.69" {
                 description "1537.69 nm/194.96250 THz 6.25/12.5GHz spacing";
               }
               enum "1537.64" {
                 description "1537.64 nm/194.96875 THz 6.25GHz spacing";
               }
               enum "1537.59" {
                 description "1537.59 nm/194.97500 THz 6.25/12.5/75GHz spacing";
               }
               enum "1537.55" {
                 description "1537.55 nm/194.98125 THz 6.25GHz spacing";
               }
               enum "1537.50" {
                 description "1537.50 nm/194.98750 THz 6.25/12.5GHz spacing";
               }
               enum "1537.45" {
                 description "1537.45 nm/194.99375 THz 6.25GHz spacing";
               }
               enum "1537.40" {
                 description "1537.40 nm/195.00000 THz 6.25/12.5/50/100GHz spacing";
               }
               enum "1537.35" {
                 description "1537.35 nm/195.00625 THz 6.25GHz spacing";
               }
               enum "1537.30" {
                 description "1537.30 nm/195.01250 THz 6.25/12.5GHz spacing";
               }
               enum "1537.25" {
                 description "1537.25 nm/195.01875 THz 6.25GHz spacing";
               }
               enum "1537.20" {
                 description "1537.20 nm/195.02500 THz 6.25/12.5GHz spacing";
               }
               enum "1537.15" {
                 description "1537.15 nm/195.03125 THz 6.25GHz spacing";
               }
               enum "1537.10" {
                 description "1537.10 nm/195.03750 THz 6.25/12.5GHz spacing";
               }
               enum "1537.05" {
                 description "1537.05 nm/195.04375 THz 6.25GHz spacing";
               }
               enum "1537.00" {
                 description "1537.00 nm/195.05000 THz 6.25/12.5/50/75GHz spacing";
               }
               enum "1536.95" {
                 description "1536.95 nm/195.05625 THz 6.25GHz spacing";
               }
               enum "1536.90" {
                 description "1536.90 nm/195.06250 THz 6.25/12.5GHz spacing";
               }
               enum "1536.86" {
                 description "1536.86 nm/195.06875 THz 6.25GHz spacing";
               }
               enum "1536.81" {
                 description "1536.81 nm/195.07500 THz 6.25/12.5GHz spacing";
               }
               enum "1536.76" {
                 description "1536.76 nm/195.08125 THz 6.25GHz spacing";
               }
               enum "1536.71" {
                 description "1536.71 nm/195.08750 THz 6.25/12.5GHz spacing";
               }
               enum "1536.66" {
                 description "1536.66 nm/195.09375 THz 6.25GHz spacing";
               }
               enum "1536.61" {
                 description "1536.61 nm/195.10000 THz 6.25/12.5/50/100GHz spacing";
               }
               enum "1536.56" {
                 description "1536.56 nm/195.10625 THz 6.25GHz spacing";
               }
               enum "1536.51" {
                 description "1536.51 nm/195.11250 THz 6.25/12.5GHz spacing";
               }
               enum "1536.46" {
                 description "1536.46 nm/195.11875 THz 6.25GHz spacing";
               }
               enum "1536.41" {
                 description "1536.41 nm/195.12500 THz 6.25/12.5/75GHz spacing";
               }
               enum "1536.36" {
                 description "1536.36 nm/195.13125 THz 6.25GHz spacing";
               }
               enum "1536.31" {
                 description "1536.31 nm/195.13750 THz 6.25/12.5GHz spacing";
               }
               enum "1536.26" {
                 description "1536.26 nm/195.14375 THz 6.25GHz spacing";
               }
               enum "1536.22" {
                 description "1536.22 nm/195.15000 THz 6.25/12.5/50GHz spacing";
               }
               enum "1536.17" {
                 description "1536.17 nm/195.15625 THz 6.25GHz spacing";
               }
               enum "1536.12" {
                 description "1536.12 nm/195.16250 THz 6.25/12.5GHz spacing";
               }
               enum "1536.07" {
                 description "1536.07 nm/195.16875 THz 6.25GHz spacing";
               }
               enum "1536.02" {
                 description "1536.02 nm/195.17500 THz 6.25/12.5GHz spacing";
               }
               enum "1535.97" {
                 description "1535.97 nm/195.18125 THz 6.25GHz spacing";
               }
               enum "1535.92" {
                 description "1535.92 nm/195.18750 THz 6.25/12.5GHz spacing";
               }
               enum "1535.87" {
                 description "1535.87 nm/195.19375 THz 6.25GHz spacing";
               }
               enum "1535.82" {
                 description "1535.82 nm/195.20000 THz 6.25/12.5/50/75/100GHz spacing";
               }
               enum "1535.77" {
                 description "1535.77 nm/195.20625 THz 6.25GHz spacing";
               }
               enum "1535.72" {
                 description "1535.72 nm/195.21250 THz 6.25/12.5GHz spacing";
               }
               enum "1535.67" {
                 description "1535.67 nm/195.21875 THz 6.25GHz spacing";
               }
               enum "1535.63" {
                 description "1535.63 nm/195.22500 THz 6.25/12.5GHz spacing";
               }
               enum "1535.58" {
                 description "1535.58 nm/195.23125 THz 6.25GHz spacing";
               }
               enum "1535.53" {
                 description "1535.53 nm/195.23750 THz 6.25/12.5GHz spacing";
               }
               enum "1535.48" {
                 description "1535.48 nm/195.24375 THz 6.25GHz spacing";
               }
               enum "1535.43" {
                 description "1535.43 nm/195.25000 THz 6.25/12.5/50GHz spacing";
               }
               enum "1535.38" {
                 description "1535.38 nm/195.25625 THz 6.25GHz spacing";
               }
               enum "1535.33" {
                 description "1535.33 nm/195.26250 THz 6.25/12.5GHz spacing";
               }
               enum "1535.28" {
                 description "1535.28 nm/195.26875 THz 6.25GHz spacing";
               }
               enum "1535.23" {
                 description "1535.23 nm/195.27500 THz 6.25/12.5/75GHz spacing";
               }
               enum "1535.18" {
                 description "1535.18 nm/195.28125 THz 6.25GHz spacing";
               }
               enum "1535.13" {
                 description "1535.13 nm/195.28750 THz 6.25/12.5GHz spacing";
               }
               enum "1535.08" {
                 description "1535.08 nm/195.29375 THz 6.25GHz spacing";
               }
               enum "1535.04" {
                 description "1535.04 nm/195.30000 THz 6.25/12.5/50/100GHz spacing";
               }
               enum "1534.99" {
                 description "1534.99 nm/195.30625 THz 6.25GHz spacing";
               }
               enum "1534.94" {
                 description "1534.94 nm/195.31250 THz 6.25/12.5GHz spacing";
               }
               enum "1534.89" {
                 description "1534.89 nm/195.31875 THz 6.25GHz spacing";
               }
               enum "1534.84" {
                 description "1534.84 nm/195.32500 THz 6.25/12.5GHz spacing";
               }
               enum "1534.79" {
                 description "1534.79 nm/195.33125 THz 6.25GHz spacing";
               }
               enum "1534.74" {
                 description "1534.74 nm/195.33750 THz 6.25/12.5GHz spacing";
               }
               enum "1534.69" {
                 description "1534.69 nm/195.34375 THz 6.25GHz spacing";
               }
               enum "1534.64" {
                 description "1534.64 nm/195.35000 THz 6.25/12.5/50/75GHz spacing";
               }
               enum "1534.59" {
                 description "1534.59 nm/195.35625 THz 6.25GHz spacing";
               }
               enum "1534.54" {
                 description "1534.54 nm/195.36250 THz 6.25/12.5GHz spacing";
               }
               enum "1534.50" {
                 description "1534.50 nm/195.36875 THz 6.25GHz spacing";
               }
               enum "1534.45" {
                 description "1534.45 nm/195.37500 THz 6.25/12.5GHz spacing";
               }
               enum "1534.40" {
                 description "1534.40 nm/195.38125 THz 6.25GHz spacing";
               }
               enum "1534.35" {
                 description "1534.35 nm/195.38750 THz 6.25/12.5GHz spacing";
               }
               enum "1534.30" {
                 description "1534.30 nm/195.39375 THz 6.25GHz spacing";
               }
               enum "1534.25" {
                 description "1534.25 nm/195.40000 THz 6.25/12.5/50/100GHz spacing";
               }
               enum "1534.20" {
                 description "1534.20 nm/195.40625 THz 6.25GHz spacing";
               }
               enum "1534.15" {
                 description "1534.15 nm/195.41250 THz 6.25/12.5GHz spacing";
               }
               enum "1534.10" {
                 description "1534.10 nm/195.41875 THz 6.25GHz spacing";
               }
               enum "1534.05" {
                 description "1534.05 nm/195.42500 THz 6.25/12.5/75GHz spacing";
               }
               enum "1534.00" {
                 description "1534.00 nm/195.43125 THz 6.25GHz spacing";
               }
               enum "1533.96" {
                 description "1533.96 nm/195.43750 THz 6.25/12.5GHz spacing";
               }
               enum "1533.91" {
                 description "1533.91 nm/195.44375 THz 6.25GHz spacing";
               }
               enum "1533.86" {
                 description "1533.86 nm/195.45000 THz 6.25/12.5/50GHz spacing";
               }
               enum "1533.81" {
                 description "1533.81 nm/195.45625 THz 6.25GHz spacing";
               }
               enum "1533.76" {
                 description "1533.76 nm/195.46250 THz 6.25/12.5GHz spacing";
               }
               enum "1533.71" {
                 description "1533.71 nm/195.46875 THz 6.25GHz spacing";
               }
               enum "1533.66" {
                 description "1533.66 nm/195.47500 THz 6.25/12.5GHz spacing";
               }
               enum "1533.61" {
                 description "1533.61 nm/195.48125 THz 6.25GHz spacing";
               }
               enum "1533.56" {
                 description "1533.56 nm/195.48750 THz 6.25/12.5GHz spacing";
               }
               enum "1533.51" {
                 description "1533.51 nm/195.49375 THz 6.25GHz spacing";
               }
               enum "1533.47" {
                 description "1533.47 nm/195.50000 THz 6.25/12.5/50/75/100GHz spacing";
               }
               enum "1533.42" {
                 description "1533.42 nm/195.50625 THz 6.25GHz spacing";
               }
               enum "1533.37" {
                 description "1533.37 nm/195.51250 THz 6.25/12.5GHz spacing";
               }
               enum "1533.32" {
                 description "1533.32 nm/195.51875 THz 6.25GHz spacing";
               }
               enum "1533.27" {
                 description "1533.27 nm/195.52500 THz 6.25/12.5GHz spacing";
               }
               enum "1533.22" {
                 description "1533.22 nm/195.53125 THz 6.25GHz spacing";
               }
               enum "1533.17" {
                 description "1533.17 nm/195.53750 THz 6.25/12.5GHz spacing";
               }
               enum "1533.12" {
                 description "1533.12 nm/195.54375 THz 6.25GHz spacing";
               }
               enum "1533.07" {
                 description "1533.07 nm/195.55000 THz 6.25/12.5/50GHz spacing";
               }
               enum "1533.02" {
                 description "1533.02 nm/195.55625 THz 6.25GHz spacing";
               }
               enum "1532.98" {
                 description "1532.98 nm/195.56250 THz 6.25/12.5GHz spacing";
               }
               enum "1532.93" {
                 description "1532.93 nm/195.56875 THz 6.25GHz spacing";
               }
               enum "1532.88" {
                 description "1532.88 nm/195.57500 THz 6.25/12.5/75GHz spacing";
               }
               enum "1532.83" {
                 description "1532.83 nm/195.58125 THz 6.25GHz spacing";
               }
               enum "1532.78" {
                 description "1532.78 nm/195.58750 THz 6.25/12.5GHz spacing";
               }
               enum "1532.73" {
                 description "1532.73 nm/195.59375 THz 6.25GHz spacing";
               }
               enum "1532.68" {
                 description "1532.68 nm/195.60000 THz 6.25/12.5/50/100GHz spacing";
               }
               enum "1532.63" {
                 description "1532.63 nm/195.60625 THz 6.25GHz spacing";
               }
               enum "1532.58" {
                 description "1532.58 nm/195.61250 THz 6.25/12.5GHz spacing";
               }
               enum "1532.53" {
                 description "1532.53 nm/195.61875 THz 6.25GHz spacing";
               }
               enum "1532.49" {
                 description "1532.49 nm/195.62500 THz 6.25/12.5GHz spacing";
               }
               enum "1532.44" {
                 description "1532.44 nm/195.63125 THz 6.25GHz spacing";
               }
               enum "1532.39" {
                 description "1532.39 nm/195.63750 THz 6.25/12.5GHz spacing";
               }
               enum "1532.34" {
                 description "1532.34 nm/195.64375 THz 6.25GHz spacing";
               }
               enum "1532.29" {
                 description "1532.29 nm/195.65000 THz 6.25/12.5/50/75GHz spacing";
               }
               enum "1532.24" {
                 description "1532.24 nm/195.65625 THz 6.25GHz spacing";
               }
               enum "1532.19" {
                 description "1532.19 nm/195.66250 THz 6.25/12.5GHz spacing";
               }
               enum "1532.14" {
                 description "1532.14 nm/195.66875 THz 6.25GHz spacing";
               }
               enum "1532.09" {
                 description "1532.09 nm/195.67500 THz 6.25/12.5GHz spacing";
               }
               enum "1532.04" {
                 description "1532.04 nm/195.68125 THz 6.25GHz spacing";
               }
               enum "1532.00" {
                 description "1532.00 nm/195.68750 THz 6.25/12.5GHz spacing";
               }
               enum "1531.95" {
                 description "1531.95 nm/195.69375 THz 6.25GHz spacing";
               }
               enum "1531.90" {
                 description "1531.90 nm/195.70000 THz 6.25/12.5/50/100GHz spacing";
               }
               enum "1531.85" {
                 description "1531.85 nm/195.70625 THz 6.25GHz spacing";
               }
               enum "1531.80" {
                 description "1531.80 nm/195.71250 THz 6.25/12.5GHz spacing";
               }
               enum "1531.75" {
                 description "1531.75 nm/195.71875 THz 6.25GHz spacing";
               }
               enum "1531.70" {
                 description "1531.70 nm/195.72500 THz 6.25/12.5/75GHz spacing";
               }
               enum "1531.65" {
                 description "1531.65 nm/195.73125 THz 6.25GHz spacing";
               }
               enum "1531.60" {
                 description "1531.60 nm/195.73750 THz 6.25/12.5GHz spacing";
               }
               enum "1531.56" {
                 description "1531.56 nm/195.74375 THz 6.25GHz spacing";
               }
               enum "1531.51" {
                 description "1531.51 nm/195.75000 THz 6.25/12.5/50GHz spacing";
               }
               enum "1531.46" {
                 description "1531.46 nm/195.75625 THz 6.25GHz spacing";
               }
               enum "1531.41" {
                 description "1531.41 nm/195.76250 THz 6.25/12.5GHz spacing";
               }
               enum "1531.36" {
                 description "1531.36 nm/195.76875 THz 6.25GHz spacing";
               }
               enum "1531.31" {
                 description "1531.31 nm/195.77500 THz 6.25/12.5GHz spacing";
               }
               enum "1531.26" {
                 description "1531.26 nm/195.78125 THz 6.25GHz spacing";
               }
               enum "1531.21" {
                 description "1531.21 nm/195.78750 THz 6.25/12.5GHz spacing";
               }
               enum "1531.16" {
                 description "1531.16 nm/195.79375 THz 6.25GHz spacing";
               }
               enum "1531.12" {
                 description "1531.12 nm/195.80000 THz 6.25/12.5/50/75/100GHz spacing";
               }
               enum "1531.07" {
                 description "1531.07 nm/195.80625 THz 6.25GHz spacing";
               }
               enum "1531.02" {
                 description "1531.02 nm/195.81250 THz 6.25/12.5GHz spacing";
               }
               enum "1530.97" {
                 description "1530.97 nm/195.81875 THz 6.25GHz spacing";
               }
               enum "1530.92" {
                 description "1530.92 nm/195.82500 THz 6.25/12.5GHz spacing";
               }
               enum "1530.87" {
                 description "1530.87 nm/195.83125 THz 6.25GHz spacing";
               }
               enum "1530.82" {
                 description "1530.82 nm/195.83750 THz 6.25/12.5GHz spacing";
               }
               enum "1530.77" {
                 description "1530.77 nm/195.84375 THz 6.25GHz spacing";
               }
               enum "1530.72" {
                 description "1530.72 nm/195.85000 THz 6.25/12.5/50GHz spacing";
               }
               enum "1530.68" {
                 description "1530.68 nm/195.85625 THz 6.25GHz spacing";
               }
               enum "1530.63" {
                 description "1530.63 nm/195.86250 THz 6.25/12.5GHz spacing";
               }
               enum "1530.58" {
                 description "1530.58 nm/195.86875 THz 6.25GHz spacing";
               }
               enum "1530.53" {
                 description "1530.53 nm/195.87500 THz 6.25/12.5/75GHz spacing";
               }
               enum "1530.48" {
                 description "1530.48 nm/195.88125 THz 6.25GHz spacing";
               }
               enum "1530.43" {
                 description "1530.43 nm/195.88750 THz 6.25/12.5GHz spacing";
               }
               enum "1530.38" {
                 description "1530.38 nm/195.89375 THz 6.25GHz spacing";
               }
               enum "1530.33" {
                 description "1530.33 nm/195.90000 THz 6.25/12.5/50/100GHz spacing";
               }
               enum "1530.29" {
                 description "1530.29 nm/195.90625 THz 6.25GHz spacing";
               }
               enum "1530.24" {
                 description "1530.24 nm/195.91250 THz 6.25/12.5GHz spacing";
               }
               enum "1530.19" {
                 description "1530.19 nm/195.91875 THz 6.25GHz spacing";
               }
               enum "1530.14" {
                 description "1530.14 nm/195.92500 THz 6.25/12.5GHz spacing";
               }
               enum "1530.09" {
                 description "1530.09 nm/195.93125 THz 6.25GHz spacing";
               }
               enum "1530.04" {
                 description "1530.04 nm/195.93750 THz 6.25/12.5GHz spacing";
               }
               enum "1529.99" {
                 description "1529.99 nm/195.94375 THz 6.25GHz spacing";
               }
               enum "1529.94" {
                 description "1529.94 nm/195.95000 THz 6.25/12.5/50/75GHz spacing";
               }
               enum "1529.89" {
                 description "1529.89 nm/195.95625 THz 6.25GHz spacing";
               }
               enum "1529.85" {
                 description "1529.85 nm/195.96250 THz 6.25/12.5GHz spacing";
               }
               enum "1529.80" {
                 description "1529.80 nm/195.96875 THz 6.25GHz spacing";
               }
               enum "1529.75" {
                 description "1529.75 nm/195.97500 THz 6.25/12.5GHz spacing";
               }
               enum "1529.70" {
                 description "1529.70 nm/195.98125 THz 6.25GHz spacing";
               }
               enum "1529.65" {
                 description "1529.65 nm/195.98750 THz 6.25/12.5GHz spacing";
               }
               enum "1529.60" {
                 description "1529.60 nm/195.99375 THz 6.25GHz spacing";
               }
               enum "1529.55" {
                 description "1529.55 nm/196.00000 THz 6.25/12.5/50/100GHz spacing";
               }
               enum "1529.50" {
                 description "1529.50 nm/196.00625 THz 6.25GHz spacing";
               }
               enum "1529.46" {
                 description "1529.46 nm/196.01250 THz 6.25/12.5GHz spacing";
               }
               enum "1529.41" {
                 description "1529.41 nm/196.01875 THz 6.25GHz spacing";
               }
               enum "1529.36" {
                 description "1529.36 nm/196.02500 THz 6.25/12.5/75GHz spacing";
               }
               enum "1529.31" {
                 description "1529.31 nm/196.03125 THz 6.25GHz spacing";
               }
               enum "1529.26" {
                 description "1529.26 nm/196.03750 THz 6.25/12.5GHz spacing";
               }
               enum "1529.21" {
                 description "1529.21 nm/196.04375 THz 6.25GHz spacing";
               }
               enum "1529.16" {
                 description "1529.16 nm/196.05000 THz 6.25/12.5/50GHz spacing";
               }
               enum "1529.11" {
                 description "1529.11 nm/196.05625 THz 6.25GHz spacing";
               }
               enum "1529.07" {
                 description "1529.07 nm/196.06250 THz 6.25/12.5GHz spacing";
               }
               enum "1529.02" {
                 description "1529.02 nm/196.06875 THz 6.25GHz spacing";
               }
               enum "1528.97" {
                 description "1528.97 nm/196.07500 THz 6.25/12.5GHz spacing";
               }
               enum "1528.92" {
                 description "1528.92 nm/196.08125 THz 6.25GHz spacing";
               }
               enum "1528.87" {
                 description "1528.87 nm/196.08750 THz 6.25/12.5GHz spacing";
               }
               enum "1528.82" {
                 description "1528.82 nm/196.09375 THz 6.25GHz spacing";
               }
               enum "1528.77" {
                 description "1528.77 nm/196.10000 THz 6.25/12.5/50/75/100GHz spacing";
               }
               enum "1528.38" {
                 description "1528.38 nm/196.15040 THz 50Ghz spacing";
               }
             }
           }
           leaf tx-power {
             description "Transmit laser output power";
             units "dBm";
             type string {
             }
           }
           container loopback {
             presence "enable loopback";
             description "Put the optics in loopback mode";
             uses apply-advanced;
             leaf loopbacktype {
               description "Set loopback type";
               type enumeration {
                 enum "media-side-out" {
                   description "Loop media side output back to input";
                 }
                 enum "media-side-in" {
                   description "Loop media side input back to output";
                 }
                 enum "host-side-out" {
                   description "Loop host side output back to input";
                 }
                 enum "host-side-in" {
                   description "Loop host side input back to output";
                 }
               }
             }
           }
           leaf los-warning-threshold {
             description "LOS warning threshold";
             units "dBm";
             type string;
           }
           leaf los-alarm-threshold {
             description "LOS alarm threshold";
             units "dBm";
             type string;
           }
           leaf modulation-format {
             description "Type of Modulation Format";
             type enumeration {
               enum "16qam" {
                 description "16-QAM Modulation Format";
               }
               enum "8qam" {
                 description "8-QAM MOdulation Format";
               }
               enum "qpsk" {
                 description "QPSK Modulation Format";
               }
             }
           }
           choice laser-enable-choice {
             leaf laser-enable {
               description "Enable Laser";
               type empty;
             }
             leaf no-laser-enable {
               description "Don't enable Laser";
               type empty;
             }
           }
           choice is-ma-choice {
             leaf is-ma {
               description "Link is enabled with alarms masked";
               type empty;
             }
             leaf no-is-ma {
               description "Don't link is enabled with alarms masked";
               type empty;
             }
           }
           leaf encoding {
             description "Line encoding";
             type enumeration {
               enum "differential" {
                 description "Differential phase line encoding";
               }
               enum "non-differential" {
                 description "Non-differential phase line encoding";
               }
             }
           }
           leaf fec {
             description "Forward Error Correction mode";
             type enumeration {
               enum "sdfec" {
                 description "Sky-Compatible Soft Decision Forward Error Correction";
               }
               enum "sdfec25" {
                 description "Denali-Compatible Soft Decision Forward Error Correction with 25 percent overhead";
               }
               enum "hgfec" {
                 description "High Gain Forward Error Correction";
               }
               enum "sdfec15" {
                 description "Soft Decision Forward Error Correction with 15 percent overhead";
               }
             }
           }
           leaf high-polarization {
             description "High polarization tracking mode";
             type empty;
           }
           container application {
             description "Config Host and Media Code";
             uses apply-advanced;
             leaf hostid {
               description "Enter Host Code";
               type union {
                 type string {
                   pattern "<.*>|$.*";
                 }
                 type uint32 {
                   range "1 .. 300";
                 }
               }
             }
             leaf mediaid {
               description "Enter Media Code";
               type union {
                 type string {
                   pattern "<.*>|$.*";
                 }
                 type uint32 {
                   range "1 .. 300";
                 }
               }
             }
             leaf domainid {
               description "Enter Domain ID";
               type union {
                 type string {
                   pattern "<.*>|$.*";
                 }
                 type uint32 {
                   range "0 .. 300";
                 }
               }
             }
           }
           container signal-degrade {
             description "Signal degrade thresholds";
             uses apply-advanced;
             leaf interval {
               description "Time interval";
               default "10";
               units "milliseconds";
               type union {
                 type string {
                   pattern "<.*>|$.*";
                 }
                 type uint32 {
                   range "1 .. 1000";
                 }
               }
             }
             leaf ber-threshold-clear {
               description "Ber threshold for signal degrade clear (format: xe-n, example: 4.5e-3)";
               type string {
               }
             }
             leaf ber-threshold-signal-degrade {
               description "Ber threshold for signal-degrade (format: xe-n, example: 4.5e-3)";
               type string {
               }
             }
             leaf q-threshold-signal-degrade-clear {
               description "Q threshold for signal-degrade clear (e.g. 14.26)";
               units "dB";
               type string;
             }
             leaf q-threshold-signal-degrade {
               description "Q threshold for signal-degrade (e.g. 9.26)";
               units "dB";
               type string;
             }
           }
           list alarm {
             key name;
             ordered-by user;
             description "Set optic alarms";
             leaf name {
               type enumeration {
                 enum "low-light-alarm" {
                   description "Enable low light alarm";
                 }
               }
             }
             uses apply-advanced;
             choice actiontype {
               case case_1 {
                 leaf syslog {
                   type empty;
                 }
               }
               case case_2 {
                 leaf link-down {
                   type empty;
                 }
               }
             }
           }
           container tca {
             description "Set tca for optic alarms";
             uses apply-advanced;
             container tx-power-high-tca {
               description "Tx power high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute tx power high TCA in dBm";
                 type string {
                 }
               }
               leaf threshold-24hrs {
                 description "Threshold for 24 hour tx power high TCA in dBm";
                 type string {
                 }
               }
             }
             container tx-power-low-tca {
               description "Tx power low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute tx power low TCA in dBm";
                 type string {
                 }
               }
               leaf threshold-24hrs {
                 description "Threshold for 24 hour tx power low TCA in dBm";
                 type string {
                 }
               }
             }
             container rx-power-high-tca {
               description "Rx power high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute rx power high TCA in dBm";
                 type string {
                 }
               }
               leaf threshold-24hrs {
                 description "Threshold for 24 hour rx power high TCA in dBm";
                 type string {
                 }
               }
             }
             container rx-power-low-tca {
               description "Rx power low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute rx power low TCA in dBm";
                 type string {
                 }
               }
               leaf threshold-24hrs {
                 description "Threshold for 24 hour rx power low TCA in dBm";
                 type string {
                 }
               }
             }
             container rx-signal-power-high-tca {
               description "Rx signal power high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute rx signal power high TCA in dBm";
                 type string {
                 }
               }
               leaf threshold-24hrs {
                 description "Threshold for 24 hour rx signal power high TCA in dBm";
                 type string {
                 }
               }
             }
             container rx-signal-power-low-tca {
               description "Rx signal power low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute rx signal power low TCA in dBm";
                 type string {
                 }
               }
               leaf threshold-24hrs {
                 description "Threshold for 24 hour rx signal power low TCA in dBm";
                 type string {
                 }
               }
             }
             container temperature-high-tca {
               description "Temperature high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute high temperature TCA in celsius";
                 type string {
                 }
               }
               leaf threshold-24hrs {
                 description "Threshold for 24 hour high temperature TCA in celsius";
                 type string {
                 }
               }
             }
             container temperature-low-tca {
               description "Temperature low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute low temperature TCA in celsius";
                 type string {
                 }
               }
               leaf threshold-24hrs {
                 description "Threshold for 24 hour low temperature TCA in celsius";
                 type string {
                 }
               }
             }
             container carrier-frequency-offset-high-tca {
               description "Carrier frequency offset high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency offset high TCA in MHz";
                 type string {
                 }
               }
               leaf threshold-24hrs {
                 description "Threshold for 24 hour frequency offset high TCA in MHz";
                 type string {
                 }
               }
             }
             container carrier-frequency-offset-low-tca {
               description "Carrier frequency offset low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency offset low TCA in MHz";
                 type string {
                 }
               }
               leaf threshold-24hrs {
                 description "Threshold for 24 hour frequency offset low TCA in MHz";
                 type string {
                 }
               }
             }
             container fec-ber {
               description "Optics Errored Seconds Threshold crossing defect trigger";
               choice enable-tca-choice {
                 leaf enable-tca {
                   description "Enable the Optics errored seconds threshold crossing alert";
                   type empty;
                 }
                 leaf no-enable-tca {
                   description "Don't enable the Optics errored seconds threshold crossing alert";
                   type empty;
                 }
               }
               leaf threshold {
                 description "TCA threshold for BER value in format: xe-n, x is an integer or decimal number, n = 0..9";
                 default "10e-3";
                 type string {
                 }
               }
               leaf threshold-24hrs {
                 description "TCA threshold for BER value in format: xe-n, x is an integer or decimal number, n = 0..9";
                 default "10e-3";
                 type string {
                 }
               }
             }
             container tec-current-high-tca {
               description "TEC Current high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute TEC Current high TCA in mA";
                 type string {
                 }
               }
               leaf threshold-24hrs {
                 description "Threshold for 24 hour TEC Current high TCA in mA";
                 type string {
                 }
               }
             }
             container tec-current-low-tca {
               description "TEC Current low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute TEC Current low TCA in mA";
                 type string {
                 }
               }
               leaf threshold-24hrs {
                 description "Threshold for 24 hour TEC Current low TCA in mA";
                 type string {
                 }
               }
             }
             container residual-isi-high-tca {
               description "Residual ISI high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute Residual ISI high TCA in ps/nm";
                 type string {
                 }
               }
               leaf threshold-24hrs {
                 description "Threshold for 24 hour Residual ISI high TCA in ps/nm";
                 type string {
                 }
               }
             }
             container residual-isi-low-tca {
               description "Residual ISI low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute Residual ISI low TCA in ps/nm";
                 type string {
                 }
               }
               leaf threshold-24hrs {
                 description "Threshold for 24 hour Residual ISI low TCA in ps/nm";
                 type string {
                 }
               }
             }
             container pam-histogram-high-tca {
               description "PAM Histogram high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute PAM Histogram high TCA";
                 type string {
                 }
               }
               leaf threshold-24hrs {
                 description "Threshold for 24 hour PAM Histogram high TCA";
                 type string {
                 }
               }
             }
             container snr-low-tca {
               description "SNR low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute SNR low TCA in dBm ";
                 type string {
                 }
               }
               leaf threshold-24hrs {
                 description "Threshold for 24 hour SNR low TCA in dBm";
                 type string {
                 }
               }
             }
             container fec-corrected-errors-high-tca {
               description "FEC Corrected Error High Threshold crossing defect trigger";
               uses apply-advanced;
               choice enable-tca-choice {
                 leaf enable-tca {
                   description "Enable the FEC Corrected Errors threshold crossing alert";
                   type empty;
                 }
                 leaf no-enable-tca {
                   description "Don't enable the FEC Corrected Errors threshold crossing alert";
                   type empty;
                 }
               }
               leaf threshold {
                 description "FEC Corrected-Errs value in format: xe-n, x is an integer or decimal number, n = 0..9";
                 default "10e-3";
                 type string {
                 }
               }
               leaf threshold-24hrs {
                 description "FEC Corrected-Errs value in format: xe-n, x is an integer or decimal number, n = 0..9";
                 default "10e-3";
                 type string {
                 }
               }
             }
             container fec-ucorrected-words-high-tca {
               description "FEC UCorrected Words High Threshold crossing defect trigger";
               uses apply-advanced;
               choice enable-tca-choice {
                 leaf enable-tca {
                   description "Enable the FEC UCorrected Words threshold crossing alert";
                   type empty;
                 }
                 leaf no-enable-tca {
                   description "Don't enable the FEC UCorrected Words threshold crossing alert";
                   type empty;
                 }
               }
               leaf threshold {
                 description "FEC UCorrected-Words value in format: xe-n, x is an integer or decimal number, n = 0..9";
                 default "10e-3";
                 type string {
                 }
               }
               leaf threshold-24hrs {
                 description "FEC UCorrected-Words value in format: xe-n, x is an integer or decimal number, n = 0..9";
                 default "10e-3";
                 type string {
                 }
               }
             }
             container laser-frequency-error-high-tca {
               description "Laser frequency error high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency error high TCA in MHz";
                 type string {
                 }
               }
               leaf threshold-24hrs {
                 description "Threshold for 24 hour frequency error high TCA in MHz";
                 type string {
                 }
               }
             }
             container laser-frequency-error-low-tca {
               description "Laser frequency error low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency error low TCA in MHz";
                 type string {
                 }
               }
               leaf threshold-24hrs {
                 description "Threshold for 24 hour frequency error low TCA in MHz";
                 type string {
                 }
               }
             }
           }
           list warning {
             key name;
             ordered-by user;
             description "Set optic warnings";
             leaf name {
               type enumeration {
                 enum "low-light-warning" {
                   description "Enable low light warning";
                 }
               }
             }
             uses apply-advanced;
             choice actiontype {
               case case_1 {
                 leaf syslog {
                   description "Set action as syslog";
                   type empty;
                 }
               }
               case case_2 {
                 leaf link-down {
                   description "Set action as link-down";
                   type empty;
                 }
               }
             }
           }
           leaf low-power-mode {
             description "Force optics to low power mode";
             type empty;
           }
           leaf high-power-mode {
             description "High power optic mode";
             type empty;
           }
           leaf host-side-fec {
             description "Host side optics FEC ON/OFF";
             type enumeration {
               enum "off" {
                 description "Host side FEC OFF for optics";
               }
               enum "on" {
                 description "Host side FEC ON for optics";
               }
             }
           }
           leaf media-side-fec {
             description "Media side FEC ON/OFF";
             type enumeration {
               enum "off" {
                 description "Media side FEC OFF for optics";
               }
               enum "on" {
                 description "Media side FEC ON for optics";
               }
             }
           }
           choice lane-info {
             case case_1 {
               list lane {
                 key name;
                 description "Media lane number";
                 leaf name {
                   description "Lane number";
                   type union {
                     type string {
                       pattern "<.*>|$.*";
                     }
                     type uint32 {
                       range "0 .. 7";
                     }
                   }
                 }
                 uses apply-advanced;
                 leaf tx-laser {
                   description "Transmit Laser ON/OFF";
                   type enumeration {
                     enum "off" {
                       description "Transmit laser OFF for optics";
                     }
                     enum "on" {
                       description "Transmit laser ON for optics";
                     }
                   }
                 }
                 leaf rx-output {
                   description "Receive output ON/OFF";
                   type enumeration {
                     enum "off" {
                       description "Receive output OFF for optics";
                     }
                     enum "on" {
                       description "Receive output ON for optics";
                     }
                   }
                 }
                 leaf tx-cdr {
                   description "Transmit Clock and Data Recovery ON/OFF";
                   type enumeration {
                     enum "off" {
                       description "Transmit Clock and Data Recovery OFF for optics";
                     }
                     enum "on" {
                       description "Transmit Clock and Data Recovery ON for optics";
                     }
                   }
                 }
                 leaf rx-cdr {
                   description "Receive Clock and Data Recovery ON/OFF";
                   type enumeration {
                     enum "off" {
                       description "Receive Clock and Data Recovery OFF for optics";
                     }
                     enum "on" {
                       description "Receive Clock and Data Recovery ON for optics";
                     }
                   }
                 }
                 leaf tx-input-equalization-adaptive {
                   description "Transmit adaptive equalization ON/OFF";
                   type enumeration {
                     enum "off" {
                       description "Transmit adaptive equalization OFF for optics";
                     }
                     enum "on" {
                       description "Transmit adaptive equalization ON for optics";
                     }
                   }
                 }
                 leaf tx-input-equalization-manual {
                   description "Transmit manual equalization for optics";
                   units "dB";
                   type union {
                     type string {
                       pattern "<.*>|$.*";
                     }
                     type int32 {
                       range "0 .. 15";
                     }
                   }
                 }
                 leaf rx-output-emphasis {
                   description "Receive output emphasis for optics";
                   units "dB";
                   type union {
                     type string {
                       pattern "<.*>|$.*";
                     }
                     type int32 {
                       range "0 .. 15";
                     }
                   }
                 }
                 leaf rx-output-amplitude {
                   description "Receive output amplitude setting";
                   type enumeration {
                     enum "400mV" {
                       description "No equalization for 100mV - 400mV amplitude";
                     }
                     enum "600mV" {
                       description "No equalization for 300mV - 600mV amplitude";
                     }
                     enum "800mV" {
                       description "No equalization for 400mV - 800mV amplitude";
                     }
                     enum "1200mV" {
                       description "No equalization for 600mV - 1200mV amplitude";
                     }
                   }
                 }
                 leaf tx-squelch {
                   description "Transmit squelch ON/OFF";
                   type enumeration {
                     enum "off" {
                       description "Transmit squelch OFF for optics";
                     }
                     enum "on" {
                       description "Transmit squelch ON for optics";
                     }
                   }
                 }
                 leaf rx-squelch {
                   description "Receive squelch ON/OFF";
                   type enumeration {
                     enum "off" {
                       description "Receive squelch OFF for optics";
                     }
                     enum "on" {
                       description "Receive squelch ON for optics";
                     }
                   }
                 }
                 leaf tx-rate-select {
                   description "Transmit rate select for optics";
                   type union {
                     type string {
                       pattern "<.*>|$.*";
                     }
                     type int32 {
                       range "0 .. 3";
                     }
                   }
                 }
                 leaf rx-rate-select {
                   description "Receive rate select for optics";
                   type union {
                     type string {
                       pattern "<.*>|$.*";
                     }
                     type int32 {
                       range "0 .. 3";
                     }
                   }
                 }
               }
             }
             case case_2 {
               container lane-all {
                 presence "enable lane-all";
                 description "Apply settings to all lane";
                 uses apply-advanced;
                 leaf tx-laser {
                   description "Transmit Laser ON/OFF";
                   type enumeration {
                     enum "off" {
                       description "Transmit laser OFF for optics";
                     }
                     enum "on" {
                       description "Transmit laser ON for optics";
                     }
                   }
                 }
                 leaf rx-output {
                   description "Receive output ON/OFF";
                   type enumeration {
                     enum "off" {
                       description "Receive output OFF for optics";
                     }
                     enum "on" {
                       description "Receive output ON for optics";
                     }
                   }
                 }
                 leaf tx-cdr {
                   description "Transmit Clock and Data Recovery ON/OFF";
                   type enumeration {
                     enum "off" {
                       description "Transmit Clock and Data Recovery OFF for optics";
                     }
                     enum "on" {
                       description "Transmit Clock and Data Recovery ON for optics";
                     }
                   }
                 }
                 leaf rx-cdr {
                   description "Receive Clock and Data Recovery ON/OFF";
                   type enumeration {
                     enum "off" {
                       description "Receive Clock and Data Recovery OFF for optics";
                     }
                     enum "on" {
                       description "Receive Clock and Data Recovery ON for optics";
                     }
                   }
                 }
                 leaf tx-input-equalization-adaptive {
                   description "Transmit adaptive equalization ON/OFF";
                   type enumeration {
                     enum "off" {
                       description "Transmit adaptive equalization OFF for optics";
                     }
                     enum "on" {
                       description "Transmit adaptive equalization ON for optics";
                     }
                   }
                 }
                 leaf tx-input-equalization-manual {
                   description "Transmit manual equalization for optics";
                   units "dB";
                   type union {
                     type string {
                       pattern "<.*>|$.*";
                     }
                     type int32 {
                       range "0 .. 15";
                     }
                   }
                 }
                 leaf rx-output-emphasis {
                   description "Receive output emphasis for optics";
                   units "dB";
                   type union {
                     type string {
                       pattern "<.*>|$.*";
                     }
                     type int32 {
                       range "0 .. 15";
                     }
                   }
                 }
                 leaf rx-output-amplitude {
                   description "Receive output amplitude setting";
                   type enumeration {
                     enum "400mV" {
                       description "No equalization for 100mV - 400mV amplitude";
                     }
                     enum "600mV" {
                       description "No equalization for 300mV - 600mV amplitude";
                     }
                     enum "800mV" {
                       description "No equalization for 400mV - 800mV amplitude";
                     }
                     enum "1200mV" {
                       description "No equalization for 600mV - 1200mV amplitude";
                     }
                   }
                 }
                 leaf tx-squelch {
                   description "Transmit squelch ON/OFF";
                   type enumeration {
                     enum "off" {
                       description "Transmit squelch OFF for optics";
                     }
                     enum "on" {
                       description "Transmit squelch ON for optics";
                     }
                   }
                 }
                 leaf rx-squelch {
                   description "Receive squelch ON/OFF";
                   type enumeration {
                     enum "off" {
                       description "Receive squelch OFF for optics";
                     }
                     enum "on" {
                       description "Receive squelch ON for optics";
                     }
                   }
                 }
                 leaf tx-rate-select {
                   description "Transmit rate select for optics";
                   type union {
                     type string {
                       pattern "<.*>|$.*";
                     }
                     type int32 {
                       range "0 .. 3";
                     }
                   }
                 }
                 leaf rx-rate-select {
                   description "Receive rate select for optics";
                   type union {
                     type string {
                       pattern "<.*>|$.*";
                     }
                     type int32 {
                       range "0 .. 3";
                     }
                   }
                 }
               }
             }
           }
         }
         container otn-options {
           description "Optical Transmission Network interface-specific options";
           uses otn_options_type;
         }
         container tdm-options {
           description "Time division multiplexing (TDM) interface-specific options";
           uses tdm_options_type;
         }
         container och-options {
           description "Optical channel configuration options";
           uses och-attributes;
         }
         container otu-options {
           description "Optical transmission unit configuration options";
           uses otu-attributes;
         }
         container odu-options {
           description "Optical data unit configuration options";
           uses odu-attributes;
         }
         container ett-options {
           description "Transport ethernet client configuration options";
           uses ett-attributes;
         }
         container fastether-options {
           description "Fast Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           choice auto-negotiation-choice {
             leaf auto-negotiation {
               description "Enable auto-negotiation";
               type empty;
             }
             leaf no-auto-negotiation {
               description "Don't enable auto-negotiation";
               type empty;
             }
           }
           leaf ingress-rate-limit {
             description "Ingress rate at port";
             units "megabits per second";
             type union {
               type string {
                 pattern "<.*>|$.*";
               }
               type uint32 {
                 range "1 .. 100";
               }
             }
           }
           list source-address-filter {
             key name;
             ordered-by user;
             description "Source address filters";
             leaf name {
               description "Remote MAC address";
               type jt:mac-addr;
             }
           }
           container redundant-parent {
             description " Parent of this interface";
             uses apply-advanced;
             leaf parent {
               description "Join a redundant ethernet interface";
               type union {
                 type jt:interface-device;
                 type string {
                   pattern "<.*>|$.*";
                 }
               }
             }
           }
           container ieee-802.3ad {
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           container mpls {
             description "MPLS options";
             uses mpls_ifd_options;
           }
           leaf ignore-l3-incompletes {
             description "Ignore L3 incomplete errors";
             type empty;
           }
         }
         container redundant-ether-options {
           description "Ethernet redundancy options";
           uses apply-advanced;
           leaf redundancy-group {
             description "Redundancy group of this interface";
             type union {
               type string {
                 pattern "<.*>|$.*";
               }
               type uint16 {
                 range "1 .. 128";
               }
             }
           }
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           list source-address-filter {
             key name;
             ordered-by user;
             description "Source address filters";
             leaf name {
               description "Remote MAC address";
               type jt:mac-addr;
             }
           }
           leaf mru {
             description "Maximum receive packet size";
             type union {
               type string {
                 pattern "<.*>|$.*";
               }
               type uint32;
             }
           }
           leaf link-speed {
             description "Link speed of individual interface that joins the RETH";
             type enumeration {
               enum "10m" {
                 description "Links are 10M";
               }
               enum "100m" {
                 description "Links are 100M";
               }
               enum "1g" {
                 description "Links are 1G";
               }
               enum "10g" {
                 description "Links are 10G";
               }
               enum "25g" {
                 description "Links are 25G";
               }
             }
           }
           leaf minimum-links {
             description "Minimum number of active links";
             default "1";
             type union {
               type string {
                 pattern "<.*>|$.*";
               }
               type uint16 {
                 range "1 .. 8";
               }
             }
           }
           container lacp {
             description "Link Aggregation Control Protocol configuration";
             uses apply-advanced;
             choice mode {
               case case_1 {
                 leaf active {
                   description "Initiate transmission of LACP packets";
                   type empty;
                 }
               }
               case case_2 {
                 leaf passive {
                   description "Respond to LACP packets";
                   type empty;
                 }
               }
             }
             leaf periodic {
               description "Timer interval for periodic transmission of LACP packets";
               type enumeration {
                 enum "fast" {
                   description "Receive packets every second";
                 }
                 enum "slow" {
                   description "Receive packets every 30 seconds";
                 }
               }
             }
           }
         }
         container aggregated-ether-options {
           description "Aggregated Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           leaf autostate-exclude {
             description "Interface will not contribute to IRB state";
             type empty;
           }
           container link-protection {
             presence "enable link-protection";
             description "Enable link protection mode";
             uses apply-advanced;
             leaf revertive {
               description "Revert back from active backup link to primary, if primary is UP";
               type empty;
             }
             leaf non-revertive {
               description "Do not revert back (default mode) from active backup link to primary, if primary is UP";
               type empty;
             }
             leaf backup-state {
               description "Link protection backup link state";
               default "accept-data";
               type enumeration {
                 enum "accept-data" {
                   description "Accept data on receive channel of backup link";
                 }
                 enum "discard-data" {
                   description "Discard data on receive channel of backup link";
                 }
                 enum "down" {
                   description "Backup link is marked down";
                 }
               }
             }
             container rtg-config {
               presence "enable rtg-config";
               description "RTG enable on AE";
               uses apply-advanced;
               leaf preempt-cutover-timer {
                 description "RTG preempt-cutover-timer in seconds";
                 default "1";
                 type union {
                   type string {
                     pattern "<.*>|$.*";
                   }
                   type uint32 {
                     range "0 .. 255";
                   }
                 }
               }
             }
           }
           choice fcoe-lag-choice {
             leaf fcoe-lag {
               description "Enable FIP/FCoE LAG";
               type empty;
             }
             leaf no-fcoe-lag {
               description "Don't enable FIP/FCoE LAG";
               type empty;
             }
           }
           list source-address-filter {
             key name;
             ordered-by user;
             description "Source address filters";
             leaf name {
               description "Remote MAC address";
               type jt:mac-addr;
             }
           }
           container configured-flow-control {
             presence "enable configured-flow-control";
             description "Enable flow control";
             uses apply-advanced;
             leaf rx-buffers {
               description "Enable/Disable Rx buffers";
               type enumeration {
                 enum "on" {
                   description "Enable Rx buffers";
                 }
                 enum "off" {
                   description "Disable Rx buffers";
                 }
               }
             }
             leaf tx-buffers {
               description "Enable/Disable Tx buffers";
               type enumeration {
                 enum "on" {
                   description "Enable Tx buffers";
                 }
                 enum "off" {
                   description "Disable Tx buffers";
                 }
               }
             }
           }
           container load-balance {
             uses aggregate-load-balance;
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 9000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container damping {
               description "BFD flap damping parameters";
               uses apply-advanced;
               leaf suppress {
                 description "Suppress threshold for figure-of-merit value";
                 default "5000";
                 type union {
                   type string {
                     pattern "<.*>|$.*";
                   }
                   type uint32 {
                     range "1000 .. 200000";
                   }
                 }
               }
               leaf reuse {
                 description "Reuse threshold for figure-of-merit value";
                 default "1000";
                 type union {
                   type string {
                     pattern "<.*>|$.*";
                   }
                   type uint32 {
                     range "1000 .. 200000";
                   }
                 }
               }
               leaf max-suppress-time {
                 description "Maximum hold-down time";
                 default "600";
                 units "seconds";
                 type union {
                   type string {
                     pattern "<.*>|$.*";
                   }
                   type uint32 {
                     range "1 .. 20000";
                   }
                 }
               }
               leaf half-life-interval {
                 description "Decay half life interval";
                 default "30";
                 units "seconds";
                 type union {
                   type string {
                     pattern "<.*>|$.*";
                   }
                   type uint32 {
                     range "1 .. 600";
                   }
                 }
               }
               leaf increment {
                 description "Increments applied to figure-of-merit value for every flap";
                 default "1000";
                 type union {
                   type string {
                     pattern "<.*>|$.*";
                   }
                   type uint32 {
                     range "1000 .. 20000";
                   }
                 }
               }
             }
             leaf neighbor {
               description "BFD neighbor address";
               type jt:ipaddr;
             }
             leaf local-address {
               description "BFD local address";
               type jt:ipaddr;
             }
             leaf holddown-interval {
               description "Time to hold the session-UP notification to the client";
               units "milliseconds";
               type union {
                 type string {
                   pattern "<.*>|$.*";
                 }
                 type uint32 {
                   range "0 .. 255000";
                 }
               }
             }
           }
           leaf minimum-links {
             description "Minimum number of aggregated links";
             type union {
               type string {
                 pattern "<.*>|$.*";
               }
               type uint16;
             }
           }
           container minimum-bandwidth {
             presence "enable minimum-bandwidth";
             description "Minimum bandwidth configured for aggregated bundle";
             uses apply-advanced;
             leaf bw-value {
               description "Bandwidth value";
               default "1";
               type union {
                 type uint64;
                 type string {
                   pattern "<.*>|$.*";
                 }
               }
             }
             leaf bw-unit {
               description "Bandwidth unit";
               type enumeration {
                 enum "bps" {
                   description "Links are in bits per sec";
                 }
                 enum "kbps" {
                   description "Links are in kilo bits per sec";
                 }
                 enum "mbps" {
                   description "Links are in mega bits per sec";
                 }
                 enum "gbps" {
                   description "Links are in giga bits per sec ";
                 }
               }
             }
           }
           container targeted-options {
             presence "enable targeted-options";
             description "Targeting specific options";
             uses apply-advanced;
             leaf type {
               description "Targeting type of AE bundle";
               type enumeration {
                 enum "auto" {
                   description "Targeting type is Auto";
                 }
                 enum "manual" {
                   description "Targeting type is Manual";
                 }
               }
             }
             choice redundancy_choice {
               case case_1 {
                 leaf logical-interface-fpc-redundancy {
                   description "Enable FPC redundancy for logical interfaces";
                   type empty;
                 }
               }
               case case_2 {
                 leaf logical-interface-chassis-redundancy {
                   description "Enable CHASSIS redundancy for logical interfaces";
                   type empty;
                 }
               }
             }
             container rebalance-periodic {
               presence "enable rebalance-periodic";
               uses apply-advanced;
               leaf start-time {
                 description "Start time of the rebalance operation ( Wall clock time )";
                 type jt:time-of-day;
               }
               leaf interval {
                 description "Interval of the rebalance operation in hrs";
                 type union {
                   type string {
                     pattern "<.*>|$.*";
                   }
                   type uint32 {
                     range "1 .. 24";
                   }
                 }
               }
             }
             leaf rebalance-subscriber-granularity {
               description "Max subscriber aggregate weight";
               type union {
                 type string {
                   pattern "<.*>|$.*";
                 }
                 type uint32 {
                   range "1 .. 65535";
                 }
               }
             }
           }
           choice redundancy_choice {
             case case_1 {
               leaf logical-interface-fpc-redundancy {
                 description "Enable FPC redundancy for logical interfaces";
                 type empty;
               }
             }
             case case_2 {
               leaf logical-interface-chassis-redundancy {
                 description "Enable CHASSIS redundancy for logical interfaces";
                 type empty;
               }
             }
           }
           container rebalance-periodic {
             uses apply-advanced;
             leaf start-time {
               description "Start time of the rebalance operation ( Wall clock time )";
               type jt:time-of-day;
             }
             leaf interval {
               description "Interval of the rebalance operation in hrs";
               type union {
                 type string {
                   pattern "<.*>|$.*";
                 }
                 type uint32 {
                   range "1 .. 24";
                 }
               }
             }
           }
           leaf pad-to-minimum-frame-size {
             description "Pad Tx vlan tagged frame to minimum of 68 bytes";
             type empty;
           }
           leaf link-speed {
             description "Link speed of individual interface that joins the AE";
             type enumeration {
               enum "10m" {
                 description "Links are 10M";
               }
               enum "100m" {
                 description "Links are 100M";
               }
               enum "1g" {
                 description "Links are 1G";
               }
               enum "2.5g" {
                 description "Links are 2.5G";
               }
               enum "5g" {
                 description "Links are 5G";
               }
               enum "8g" {
                 description "Links are 8G";
               }
               enum "10g" {
                 description "Links are 10G";
               }
               enum "25g" {
                 description "Links are 25G";
               }
               enum "40g" {
                 description "Links are 40G";
               }
               enum "50g" {
                 description "Links are 50G";
               }
               enum "80g" {
                 description "Links are 80G";
               }
               enum "100g" {
                 description "Links are 100G";
               }
               enum "200g" {
                 description "Links are 200G";
               }
               enum "400g" {
                 description "Links are 400G";
               }
               enum "800g" {
                 description "Links are 800G";
               }
               enum "oc192" {
                 description "Links are OC-192";
               }
               enum "mixed" {
                 description "Links are various speeds";
               }
             }
           }
           container local-bias {
             presence "enable local-bias";
             description "Turn on local bias functionality";
             uses apply-advanced;
             leaf disable {
               description "Disable local-bias";
               type empty;
             }
           }
           leaf local-minimum-links-threshold {
             description "Specify threshold for minimum links per VC/VCF member";
             type union {
               type string {
                 pattern "<.*>|$.*";
               }
               type uint16 {
                 range "1 .. 100";
               }
             }
           }
           leaf resilient-hash {
             description "Turn on resilient-hash";
             type empty;
           }
           container dlb {
             description "Enable DLB on LAG";
             uses apply-advanced;
             choice mode {
               case case_1 {
                 leaf per-packet {
                   description "Per-packet link assignment";
                   type empty;
                 }
               }
               case case_2 {
                 leaf assigned-flow {
                   description "Fixed link assignment";
                   type empty;
                 }
               }
               case case_3 {
                 container flowlet {
                   presence "enable flowlet";
                   description "Inactivity-based link assignment";
                   uses apply-advanced;
                   leaf inactivity-interval {
                     description " Minimum inactivity interval in micro-seconds for link re-assignment";
                     default "256";
                     type union {
                       type string {
                         pattern "<.*>|$.*";
                       }
                       type uint32;
                     }
                   }
                 }
               }
             }
           }
           container lacp {
             description "Link Aggregation Control Protocol configuration";
             uses apply-advanced;
             choice mode {
               case case_1 {
                 leaf active {
                   description "Initiate transmission of LACP packets";
                   type empty;
                 }
               }
               case case_2 {
                 leaf passive {
                   description "Respond to LACP packets";
                   type empty;
                 }
               }
             }
             leaf periodic {
               description "Timer interval for periodic transmission of LACP packets";
               type enumeration {
                 enum "fast" {
                   description "Receive packets every second";
                 }
                 enum "slow" {
                   description "Receive packets every 30 seconds";
                 }
               }
             }
             leaf multiplier {
               description "LACP timeout detection multiplier";
               type union {
                 type string {
                   pattern "<.*>|$.*";
                 }
                 type uint32 {
                   range "3 .. 30";
                 }
               }
             }
             leaf fast-failover {
               description "To turn on LACP fast-failover";
               type empty;
             }
             container link-protection {
               presence "enable link-protection";
               uses apply-advanced;
               leaf disable {
                 description "To turn off LACP link-protection";
                 type empty;
               }
               choice mode {
                 case case_1 {
                   leaf revertive {
                     description "Switch links when better priority link comes up";
                     type empty;
                   }
                 }
                 case case_2 {
                   leaf non-revertive {
                     description "Do not switch links when better priority link comes up";
                     type empty;
                   }
                 }
               }
               container rtg-config {
                 presence "enable rtg-config";
                 description "RTG Feature enable on AE";
                 uses apply-advanced;
                 leaf preempt-cutover-timer {
                   description "RTG preempt-cutover-timer in seconds";
                   default "1";
                   type union {
                     type string {
                       pattern "<.*>|$.*";
                     }
                     type uint32 {
                       range "0 .. 255";
                     }
                   }
                 }
               }
             }
             leaf accept-data {
               description "Keep receiving traffic even when LACP goes down";
               type empty;
             }
             leaf sync-reset {
               description "On minimum-link failure notify out of sync to peer";
               type enumeration {
                 enum "disable" {
                   description "To disable minimum-link failure handling at LACP level";
                 }
                 enum "enable" {
                   description "To enable minimum-link failure handling at LACP level";
                 }
               }
             }
             leaf system-priority {
               description "Priority of the system (0 ... 65535)";
               type string;
             }
             leaf system-id {
               description "Node's System ID, encoded as a MAC address";
               type jt:mac-addr;
             }
             leaf admin-key {
               description "Node's administrative key";
               type union {
                 type uint16;
                 type string {
                   pattern "<.*>|$.*";
                 }
               }
             }
             container hold-time {
               description "Hold time for link up and link down for AE link members";
               leaf up {
                 description "Link up hold time for the AE link members";
                 units "seconds";
                 type union {
                   type string {
                     pattern "<.*>|$.*";
                   }
                   type uint16 {
                     range "1 .. 6000";
                   }
                 }
               }
             }
             leaf aggregate-wait-time {
               description "Aggregate wait time for the AE";
               units "seconds";
               type union {
                 type string {
                   pattern "<.*>|$.*";
                 }
                 type uint16 {
                   range "0 .. 1800";
                 }
               }
             }
             leaf force-up {
               description "Forceup AE interface with LACP";
               type empty;
             }
             leaf no-peer-loopback-validation {
               description "Skip MCLAG peer loop back validation for LACP PDUs on Forceup AE interface";
               type empty;
             }
           }
           list link-protection-sub-group {
             key name;
             ordered-by user;
             description "Link Protection subgroup configuration";
             leaf name {
               description "Name of the subgroup";
               type string {
                 length "2 .. 64";
               }
             }
             uses apply-advanced;
             choice type {
               case case_1 {
                 leaf primary {
                   description "Primary subgroup for N:N link-protection mode";
                   type empty;
                 }
               }
               case case_2 {
                 leaf backup {
                   description "Backup subgroup for N:N link-protection mode";
                   type empty;
                 }
               }
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             container storm-control {
               description "Storm control profile name to bind";
               uses apply-advanced;
               leaf profile-name {
                 description "Profile name";
                 type string;
               }
             }
             container recovery-timeout {
               description "Recovery timeout for this interface";
               leaf time-in-seconds {
                 units "seconds";
                 type union {
                   type string {
                     pattern "<.*>|$.*";
                   }
                   type uint32 {
                     range "10 .. 3600";
                   }
                 }
               }
             }
             leaf mac-learn-enable {
               description "Learn MAC addresses dynamically";
               type empty;
             }
           }
           container mc-ae {
             description "Multi-chassis aggregation (MC-AE) network device configuration";
             uses apply-advanced;
             leaf mc-ae-id {
               description "MC-AE group id";
               type union {
                 type string {
                   pattern "<.*>|$.*";
                 }
                 type uint16 {
                   range "1 .. 65535";
                 }
               }
             }
             leaf redundancy-group {
               description "Redundancy group id";
               default "1";
               type union {
                 type string {
                   pattern "<.*>|$.*";
                 }
                 type uint32 {
                   range "1 .. 4294967294";
                 }
               }
             }
             leaf chassis-id {
               description "Chassis id of MC-AE network device";
               type union {
                 type string {
                   pattern "<.*>|$.*";
                 }
                 type uint16 {
                   range "0 .. 1";
                 }
               }
             }
             leaf mode {
               description "Mode of the MC-AE";
               type enumeration {
                 enum "active-active" {
                   description "MC-AE in active-active mode";
                 }
               }
             }
             leaf status-control {
               description "Status of the MC-AE chassis";
               type enumeration {
                 enum "active" {
                   description "Chassis is Active";
                 }
                 enum "standby" {
                   description "Chassis is Standby";
                 }
               }
             }
             leaf switchover-mode {
               description "Switchover mode";
               type enumeration {
                 enum "revertive" {
                   description "Switch mcae node when preferred link comes up";
                 }
                 enum "non-revertive" {
                   description "Do not switch mcae node when preferred link comes up";
                 }
               }
             }
             leaf revert-time {
               description "Wait interval before performing switchover";
               default "3";
               units "minute";
               type union {
                 type string {
                   pattern "<.*>|$.*";
                 }
                 type uint32 {
                   range "1 .. 10";
                 }
               }
             }
             leaf init-delay-time {
               description "Init delay timer for mcae sm for min traffic loss";
               units "seconds";
               type union {
                 type string {
                   pattern "<.*>|$.*";
                 }
                 type uint16 {
                   range "1 .. 6000";
                 }
               }
             }
             leaf recovery-delay-time {
               description "Delay timer for bringing up ICL, ICCP";
               units "seconds";
               type union {
                 type string {
                   pattern "<.*>|$.*";
                 }
                 type uint16 {
                   range "1 .. 6000";
                 }
               }
             }
             leaf enhanced-convergence {
               description "Optimized convergence time for mcae";
               type empty;
             }
             container events {
               presence "enable events";
               description "MCAE related events";
               uses apply-advanced;
               container iccp-peer-down {
                 presence "enable iccp-peer-down";
                 description "Define behavior in the event of ICCP peer down";
                 uses apply-advanced;
                 leaf force-icl-down {
                   description "Bring down ICL logical interface";
                   type empty;
                 }
                 leaf prefer-status-control-active {
                   description "Keep this node up (recommended only on status-control active)";
                   type empty;
                 }
               }
             }
           }
           leaf share-standby {
             description "Share the resources with standby ports, needs FPC reboot to take effect";
             type empty;
           }
         }
         container es-options {
           description "ES PIC interface-specific options";
           uses apply-advanced;
           leaf backup-interface {
             description "Name of backup interface";
             type union {
               type jt:interface-device;
               type string {
                 pattern "<.*>|$.*";
               }
             }
           }
         }
         container dsl-options {
           description "DSL interface-specific options";
           uses apply-advanced;
           leaf operating-mode {
             description "DSL operating mode";
             type enumeration {
               enum "auto" {
                 description "Autonegotiate mode";
               }
               enum "ansi-dmt" {
                 description "ANSI T1.413 Issue II mode";
               }
               enum "itu-dmt" {
                 description "ITU G.992.1 mode";
               }
               enum "etsi" {
                 description "ETSI TS 101 388 V1.3.1 mode";
               }
               enum "itu-annexb-ur2" {
                 description "ITU G.992.1 UR-2 mode";
               }
               enum "itu-annexb-non-ur2" {
                 description "ITU G.992.1 Non UR-2 mode";
               }
               enum "itu-dmt-bis" {
                 description "ITU G.992.3 mode";
               }
               enum "adsl2plus" {
                 description "ITU G.992.5 mode";
               }
               enum "annexm-itu-dmt-bis" {
                 description "AnnexM ITU G.992.3 mode";
               }
               enum "annexm-adsl2plus" {
                 description "AnnexM ITU G.992.5 mode";
               }
             }
           }
         }
         container vdsl-options {
           description "VDSL interface-specific options";
           uses apply-advanced;
           leaf vdsl-profile {
             description "VDSL profile";
             type enumeration {
               enum "auto" {
                 description "Auto";
               }
               enum "8a" {
                 description "Profile 8a";
               }
               enum "8b" {
                 description "Profile 8b";
               }
               enum "8c" {
                 description "Profile 8c";
               }
               enum "8d" {
                 description "Profile 8d";
               }
               enum "12a" {
                 description "Profile 12a";
               }
               enum "12b" {
                 description "Profile 12b";
               }
               enum "17a" {
                 description "Profile 17a";
               }
             }
           }
           leaf sra {
             description "DSL SRA";
             default "disable";
             type enumeration {
               enum "enable" {
                 description "Enable SRA";
               }
               enum "disable" {
                 description "Disable SRA";
               }
             }
           }
           leaf v43 {
             description "DSL V43 tones";
             default "enable";
             type enumeration {
               enum "enable" {
                 description "Enable V43";
               }
               enum "disable" {
                 description "Disable V43";
               }
             }
           }
           leaf sos {
             description "Enable SOS";
             type empty;
           }
         }
         container dsl-sfp-options {
           description "DSL SFP options";
           uses apply-advanced;
           container adsl-options {
             description "ADSL options";
             uses apply-advanced;
             leaf vpi {
               description "Virtual path identifier";
               type union {
                 type string {
                   pattern "<.*>|$.*";
                 }
                 type uint32 {
                   range "0 .. 255";
                 }
               }
             }
             leaf vci {
               description "Virtual circuit identifier";
               type union {
                 type string {
                   pattern "<.*>|$.*";
                 }
                 type uint32 {
                   range "32 .. 65535";
                 }
               }
             }
             leaf encap {
               description "Encapsulation";
               type enumeration {
                 enum "bypass" {
                   description "Bypass";
                 }
                 enum "llcsnap-bridged-802dot1q" {
                   description "LLCSNAP bridged 802.1q";
                 }
                 enum "llcsnap-routed-ip" {
                   description "LLCSNAP routed ip";
                 }
                 enum "vc-mux-bridged" {
                   description "VC MUX bridged";
                 }
                 enum "vc-mux-routed-ip" {
                   description "VC MUX routed ip";
                 }
                 enum "generic" {
                   description "Generic";
                 }
               }
             }
             leaf annex {
               description "Annex type";
               type enumeration {
                 enum "auto" {
                   description "Annex type auto";
                 }
                 enum "annexj-off" {
                   description "Annex type annexj turn off";
                 }
               }
             }
           }
           container vdsl-options {
             description "VDSL options";
             uses apply-advanced;
             leaf profile {
               description "VDSL profile";
               type enumeration {
                 enum "auto" {
                   description "Automatic";
                 }
                 enum "8a" {
                   description "Profile 8a";
                 }
                 enum "8b" {
                   description "Profile 8b";
                 }
                 enum "8c" {
                   description "Profile 8c";
                 }
                 enum "8d" {
                   description "Profile 8d";
                 }
                 enum "12a" {
                   description "Profile 12a";
                 }
                 enum "12b" {
                   description "Profile 12b";
                 }
                 enum "17a" {
                   description "Profile 17a";
                 }
                 enum "30a" {
                   description "Profile 30a";
                 }
               }
             }
             leaf carrier {
               description "Carrier setting";
               type enumeration {
                 enum "auto" {
                   description "Automatic";
                 }
                 enum "a43" {
                   description "Carrier A43";
                 }
                 enum "b43" {
                   description "Carrier B43";
                 }
               }
             }
           }
           container gfast-options {
             description "G.fast options";
             uses apply-advanced;
             leaf carrier {
               description "Carrier setting";
               type enumeration {
                 enum "a43" {
                   description "Carrier A43";
                 }
                 enum "a43c" {
                   description "Carrier A43C";
                 }
                 enum "b43" {
                   description "Carrier B43";
                 }
                 enum "b43c" {
                   description "Carrier B43C";
                 }
               }
             }
           }
         }
         container shdsl-options {
           description "SHDSL interface-specific options";
           uses apply-advanced;
           leaf annex {
             description "Type of SHDSL annex";
             default "annex-b";
             type enumeration {
               enum "annex-a" {
                 description "Annex-a PIC";
               }
               enum "annex-b" {
                 description "Annex-b PIC";
               }
               enum "annex-f" {
                 description "Annex-f PIC";
               }
               enum "annex-g" {
                 description "Annex-g PIC";
               }
               enum "annex-auto" {
                 description "Annex-auto PIC";
               }
             }
           }
           leaf line-rate {
             description "SHDSL line rate";
             type string;
           }
           leaf loopback {
             description "Loopback mode";
             type enumeration {
               enum "local" {
                 description "Local loopback";
               }
               enum "remote" {
                 description "Remote loopback";
               }
             }
           }
           container snr-margin {
             presence "enable snr-margin";
             description "Signal to noise ratio margin";
             uses apply-advanced;
             leaf current {
               description "Current signal to noise ratio margin";
               units "dB";
               type string;
             }
             leaf snext {
               description "SNEXT signal to noise ratio margin";
               units "dB";
               type string;
             }
           }
         }
         container data-input {
           description "Configuration for drop-insert data input";
           uses apply-advanced;
           choice input-choice {
             case case_1 {
               leaf system {
                 description "Data sourced from system";
                 type empty;
               }
             }
             case case_2 {
               leaf interface {
                 description "Interface that acts as data source";
                 type union {
                   type jt:interface-device;
                   type string {
                     pattern "<.*>|$.*";
                   }
                 }
               }
             }
           }
         }
         container switch-options {
           description "Front end ports configuration";
           uses apply-advanced;
           list switch-port {
             key name;
             leaf name {
               description "Front end port number";
               type union {
                 type string {
                   pattern "<.*>|$.*";
                 }
                 type uint32 {
                   range "0 .. 15";
                 }
               }
             }
             uses apply-advanced;
             choice auto-negotiation-choice {
               leaf auto-negotiation {
                 description "Enable auto-negotiation";
                 type empty;
               }
               leaf no-auto-negotiation {
                 description "Don't enable auto-negotiation";
                 type empty;
               }
             }
             leaf link-mode {
               description "Link operational mode";
               type enumeration {
                 enum "half-duplex" {
                   description "Half-duplex operation";
                 }
                 enum "full-duplex" {
                   description "Full-duplex operation";
                 }
               }
             }
             leaf speed {
               description "Link speed";
               type enumeration {
                 enum "10m" {
                 }
                 enum "100m" {
                 }
                 enum "1g" {
                 }
               }
             }
             leaf vlan-id {
               description "VLAN ID for this port";
               type union {
                 type string {
                   pattern "<.*>|$.*";
                 }
                 type uint32 {
                   range "0 .. 4094";
                 }
               }
             }
             leaf cascade-port {
               description "Port externally connected to another cascade port";
               type empty;
             }
           }
         }
         container container-options {
           description "Container interface specific options";
           uses apply-advanced;
           container container-type {
             presence "enable container-type";
             description "Protocol type of the container interface";
             uses apply-advanced;
             choice container-type-choice {
               case case_1 {
                 container aps {
                   description "APS options on the container";
                   presence "enable aps";
                   uses aps_type;
                 }
               }
             }
           }
           container member-interface-type {
             description "Link type of members of container";
             uses apply-advanced;
             choice member_interface_type_choice {
               case case_1 {
                 container sonet {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                       enum "oc192" {
                         description "Links are OC-192";
                       }
                       enum "oc768" {
                         description "Links are OC-768";
                       }
                       enum "mixed" {
                         description "Links are of different speeds";
                       }
                     }
                   }
                 }
               }
               case case_2 {
                 container atm {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                     }
                   }
                 }
               }
               case case_3 {
                 container channelized-sonet {
                   uses apply-advanced;
                   leaf member-interface-speed {
                     description "Link speed of members of container";
                     type enumeration {
                       enum "coc3" {
                         description "Links are COC-3";
                       }
                       enum "coc12" {
                         description "Links are COC-12";
                       }
                       enum "coc48" {
                         description "Links are COC-48";
                       }
                       enum "coc192" {
                         description "Links are COC-192";
                       }
                       enum "coc768" {
                         description "Links are COC-768";
                       }
                     }
                   }
                 }
               }
               case case_4 {
                 container channelized-sdh {
                   uses apply-advanced;
                   leaf member-interface-speed {
                     description "Link speed of members of container";
                     type enumeration {
                       enum "cstm1" {
                         description "Links are cstm-1";
                       }
                       enum "cstm4" {
                         description "Links are cstm-4";
                       }
                       enum "cstm16" {
                         description "Links are cstm-16";
                       }
                       enum "coc64" {
                         description "Links are cstm-64";
                       }
                       enum "cstm256" {
                         description "Links are cstm256";
                       }
                     }
                   }
                 }
               }
             }
           }
           container redundancy {
             description "Container interface redundancy options";
             uses apply-advanced;
             container hold-time {
               description "Hold time for link up and link down";
               leaf up {
                 description "Link up hold time";
                 units "milliseconds";
                 type union {
                   type string {
                     pattern "<.*>|$.*";
                   }
                   type uint32 {
                     range "0 .. 65534";
                   }
                 }
               }
               leaf down {
                 description "Link down hold time";
                 units "milliseconds";
                 type union {
                   type string {
                     pattern "<.*>|$.*";
                   }
                   type uint32 {
                     range "0 .. 65534";
                   }
                 }
               }
             }
           }
           leaf-list container-list {
             ordered-by user;
             description "List of container interfaces this member link is associated to";
             type union {
               type jt:interface-device;
               type string {
                 pattern "<.*>|$.*";
               }
             }
           }
           choice redundancy-type {
             case case_1 {
               choice aps-redundancy {
                 case case_1 {
                   leaf primary {
                     description "This member link is primary interface of the container";
                     type empty;
                   }
                 }
                 case case_2 {
                   leaf standby {
                     description "This member link is standby interface of the container";
                     type empty;
                   }
                 }
               }
             }
           }
           leaf fast-aps {
             description "Fast APS switch";
             type empty;
           }
           leaf allow-configuration-override {
             description "Allow physical configuration of member link to override container configuration";
             type empty;
           }
         }
         container layer2-policer {
           description "Layer2 policing for interface";
           uses apply-advanced;
           choice layer2-input-policer-choice {
             case case_1 {
               leaf input-policer {
                 description "Two-color policer for received packets";
                 type string;
               }
             }
             case case_2 {
               leaf input-hierarchical-policer {
                 description "Hierarchical policer for received packets";
                 type string;
               }
             }
           }
         }
         list unit {
           key name;
           description "Logical interface";
           leaf name {
             type string;
           }
           uses apply-advanced;
           leaf interface-tag {
             description "Interface tag name";
             type string {
               length "1 .. 64";
             }
           }
           container policer-overhead {
             description "Policer overhead adjustment for this unit";
             uses apply-advanced;
             leaf policer-overhead-value {
               description "Policer overhead bytes to be accounted in ingress and egress";
               units "bytes";
               type union {
                 type string {
                   pattern "<.*>|$.*";
                 }
                 type int32;
               }
             }
             leaf ingress {
               description "Ingress value in bytes";
               units "bytes";
               type union {
                 type string {
                   pattern "<.*>|$.*";
                 }
                 type int32 {
                   range "-64 .. 64";
                 }
               }
             }
             leaf egress {
               description "Egress value in bytes";
               units "bytes";
               type union {
                 type string {
                   pattern "<.*>|$.*";
                 }
                 type int32 {
                   range "-64 .. 64";
                 }
               }
             }
           }
           leaf alias {
             description "Interface alias";
             type string;
           }
           leaf enhanced-convergence {
             description "Optimize convergence time for L3";
             type empty;
           }
           leaf proxy-macip-advertisement {
             description "Proxy advertisement of type 2 MAC+IP route for EVPN";
             type empty;
           }
           leaf virtual-gateway-accept-data {
             description "Accept packets destined for virtual gateway address";
             type empty;
           }
           container peer-psd {
             presence "enable peer-psd";
             description "Peer psd";
             leaf psd-name {
               description "Peer psd name";
               type string;
             }
           }
           container peer-interface {
             presence "enable peer-interface";
             description "Peer interface";
             uses apply-advanced;
             leaf interface-name {
               description "Peer interface name";
               type union {
                 type jt:interface-unit;
                 type string {
                   pattern "<.*>|$.*";
                 }
               }
             }
           }
           container interface-shared-with {
             presence "enable interface-shared-with";
             description "Specify which PSD owns this logical interface";
             uses apply-advanced;
             leaf psd-name {
               description "Name of protected system domain (psd[1-31], ex. psd2)";
               type string {
               }
             }
           }
           choice enable-disable {
             case case_1 {
               leaf disable {
                 description "Disable this logical interface";
                 type empty;
               }
             }
           }
           leaf passive-monitor-mode {
             description "Use interface to tap packets from another router";
             type empty;
           }
           leaf per-session-scheduler {
             description "Enable per-session queuing on an IQ2 interface";
             type empty;
           }
           container account-layer2-overhead {
             presence "enable account-layer2-overhead";
             description "Account layer2 overhead in IFL byte statistics";
             uses apply-advanced;
             leaf overhead-value {
               description "Layer2 overhead bytes to be accounted in ingress and egress";
               units "bytes";
               type union {
                 type string {
                   pattern "<.*>|$.*";
                 }
                 type int8 {
                   range "-128 .. 127";
                 }
               }
             }
             leaf ingress {
               description "Layer2 overhead bytes to be accounted in ingress";
               units "bytes";
               type union {
                 type string {
                   pattern "<.*>|$.*";
                 }
                 type int8 {
                   range "-128 .. 127";
                 }
               }
             }
             leaf egress {
               description "Layer2 overhead bytes to be accounted in egress";
               units "bytes";
               type union {
                 type string {
                   pattern "<.*>|$.*";
                 }
                 type int8 {
                   range "-128 .. 127";
                 }
               }
             }
           }
           container forwarding-class-accounting {
             presence "enable forwarding-class-accounting";
             description "Configure Forwarding-class-accounting parameters for IFL ";
             uses apply-advanced;
             leaf direction {
               description "Direction of the traffic to be accounted for IFL";
               type enumeration {
                 enum "ingress" {
                   description "Enable forwarding-class-accounting for ingress traffic";
                 }
                 enum "egress" {
                   description "Enable forwarding-class-accounting for egress traffic";
                 }
                 enum "both" {
                   description "Enable forwarding-class-accounting for both directions";
                 }
               }
             }
             container enhanced {
               presence "enable enhanced";
               uses apply-advanced;
               leaf traffic-type {
                 description "Traffic-type to be accounted for forwarding-class-accounting for IFL";
                 type enumeration {
                   enum "unicast-statistics" {
                     description "Count only unicast traffic for forwarding-class-accounting for IFL ";
                   }
                   enum "multicast-statistics" {
                     description "Count only multicast traffic for forwarding-class-accounting for IFL";
                   }
                 }
               }
               leaf family {
                 description "Protocol traffic to be accounted for forwarding-class-accounting for IFL";
                 type enumeration {
                   enum "inet" {
                     description "Enable forwarding-class-accounting for IPv4 family only for IFL";
                   }
                   enum "inet6" {
                     description "Enable forwarding-class-accounting for IPv6 family only for IFL";
                   }
                   enum "both" {
                     description "Enable forwarding-class-accounting for both IPv4 and IPv6 family for IFL";
                   }
                 }
               }
               leaf direction {
                 description "Direction of the traffic to be accounted for forwarding-class-accounting for IFL";
                 type enumeration {
                   enum "ingress" {
                     description "Enable forwarding-class-accounting for ingress traffic for IFL";
                   }
                   enum "egress" {
                     description "Enable forwarding-class-accounting for egress traffic for IFL";
                   }
                   enum "both" {
                     description "Enable forwarding-class-accounting for both ingress and egress traffic for IFL";
                   }
                 }
               }
               leaf overhead-bytes {
                 description "Per octet overhead bytes to be accounted for forwarding-class-accounting for IFL ";
                 default "0";
                 type union {
                   type string {
                     pattern "<.*>|$.*";
                   }
                   type uint32 {
                     range "0 .. 255";
                   }
                 }
               }
             }
           }
           leaf clear-dont-fragment-bit {
             description "Clear DF bit in packet (AS PIC and J-series only as well as MIF)";
             type empty;
           }
           leaf packet-inject-enable {
             description "Enable packet inject functionality on this IFL";
             type empty;
           }
           leaf reassemble-packets {
             description "Do reassembly of fragmented tunnel packets";
             type empty;
           }
           container ip-address-owner {
             description "Define the owner for IP addresses hosted on this interface";
             choice ip-address-owner-options {
               case case_1 {
                 leaf service-plane {
                   description "IP address defined on this interface is hosted by service plane";
                   type empty;
                 }
               }
               case case_2 {
                 leaf routing-engine {
                   description "IP address defined on this interface is hosted by routing engine";
                   type empty;
                 }
               }
             }
           }
           container services-options {
             description "Services interface-specific options";
             uses apply-advanced;
           }
           container rpm {
             description "Enable RPM service on this interface";
             uses apply-advanced;
             choice rpm_or_twamp {
               case case_1 {
                 choice rpm-type {
                   case case_1 {
                     leaf client {
                       description "Client mode";
                       type empty;
                     }
                   }
                   case case_2 {
                     leaf server {
                       description "Server mode";
                       type empty;
                     }
                   }
                   case case_3 {
                     leaf client-delegate-probes {
                       description "Client delegate probe mode";
                       type empty;
                     }
                   }
                 }
               }
               case case_2 {
                 leaf twamp-server {
                   description "Set TWAMP server mode on this interface";
                   type empty;
                 }
               }
               case case_3 {
                 leaf twamp-client {
                   description "Set TWAMP client mode on this interface";
                   type empty;
                 }
               }
             }
           }
           leaf description {
             description "Text description of interface";
             type string;
           }
           leaf metadata {
             description "Text metadata attached to interface";
             type string;
           }
           container dial-options {
             description "Dial options";
             uses apply-advanced;
             choice interface_id_choice {
               case case_1 {
                 leaf l2tp-interface-id {
                   description "Identifier for group of PPP sessions";
                   type string {
                     length "1 .. 63";
                   }
                 }
               }
               case case_2 {
                 leaf ipsec-interface-id {
                   description "Identifier for group of dynamic peers";
                   type string {
                     length "1 .. 63";
                   }
                 }
               }
             }
             choice ifl_type {
               case case_1 {
                 leaf dedicated {
                   description "Use this unit for only one PPP/IPSec session";
                   type empty;
                 }
               }
               case case_2 {
                 leaf shared {
                   description "Share this unit for multiple PPP/IPSec sessions";
                   type empty;
                 }
               }
             }
           }
           container actual-transit-statistics {
             presence "enable actual-transit-statistics";
             description "Actual transit statistics";
           }
           list demux-source {
             key name;
             ordered-by user;
             description "Demux based on source address";
             uses demux_options_table;
           }
           list demux-destination {
             key name;
             ordered-by user;
             description "Demux based on destination address";
             uses demux_options_table;
           }
           container demux {
             description "Demux based on source or destination address";
             uses apply-advanced;
             container inet {
               presence "enable inet";
               description "Family inet";
               uses apply-advanced;
               leaf address {
                 description "Address type";
                 type enumeration {
                   enum "source" {
                     description "Demux based on source address";
                   }
                   enum "destination" {
                     description "Demux based on destination address";
                   }
                 }
               }
               container auto-configure {
                 description "Auto configuration";
                 uses dynamic_ipv4_type;
               }
             }
             container inet6 {
               presence "enable inet6";
               description "Family inet6";
               uses apply-advanced;
               leaf address {
                 description "Address type";
                 type enumeration {
                   enum "source" {
                     description "Demux based on source address";
                   }
                   enum "destination" {
                     description "Demux based on destination address";
                   }
                 }
               }
               container auto-configure {
                 description "Auto configuration";
                 uses dynamic_ipv6_type;
               }
             }
           }
           leaf encapsulation {
             description "Logical link-layer encapsulation";
             type enumeration {
               enum "atm-nlpid" {
                 description "ATM NLPID encapsulation";
               }
               enum "atm-cisco-nlpid" {
                 description "Cisco-compatible ATM NLPID encapsulation";
               }
               enum "atm-snap" {
                 description "ATM LLC/SNAP encapsulation";
               }
               enum "atm-vc-mux" {
                 description "ATM VC multiplexing";
               }
               enum "atm-ccc-vc-mux" {
                 description "ATM VC for CCC";
               }
               enum "atm-tcc-vc-mux" {
                 description "ATM VC for translational cross-connect";
               }
               enum "atm-tcc-snap" {
                 description "ATM LLC/SNAP for translational cross-connect";
               }
               enum "atm-ccc-cell-relay" {
                 description "ATM cell relay for CCC";
               }
               enum "vlan-vci-ccc" {
                 description "CCC for VLAN Q-in-Q and ATM VPI/VCI interworking";
               }
               enum "ether-over-atm-llc" {
                 description "Ethernet over ATM (LLC/SNAP) encapsulation";
               }
               enum "ether-vpls-over-atm-llc" {
                 description "Ethernet VPLS over ATM (bridging) encapsulation";
               }
               enum "ppp-over-ether-over-atm-llc" {
                 description "PPPoE over ATM (LLC/SNAP) encapsulation";
               }
               enum "ppp-over-ether" {
                 description "PPPoE encapsulation";
               }
               enum "atm-ppp-vc-mux" {
                 description "ATM PPP over raw AAL5";
               }
               enum "atm-ppp-llc" {
                 description "ATM PPP over AAL5/LLC";
               }
               enum "atm-mlppp-llc" {
                 description "ATM MLPPP over AAL5/LLC";
               }
               enum "frame-relay-ppp" {
                 description "PPP over Frame Relay";
               }
               enum "frame-relay-ccc" {
                 description "Frame Relay DLCI for CCC";
               }
               enum "frame-relay" {
                 description "Frame Relay DLCI";
               }
               enum "frame-relay-tcc" {
                 description "Frame Relay DLCI for translational cross-connect";
               }
               enum "frame-relay-ether-type" {
                 description "Cisco-compatible Frame Relay Encapsulation DLCI";
               }
               enum "frame-relay-ether-type-tcc" {
                 description "Cisco-compatible Frame Relay Encapsulation DLCI for TCC";
               }
               enum "ether-vpls-fr" {
                 description "Ethernet VPLS over Frame Relay (bridging) encapsulation";
               }
               enum "vlan-ccc" {
                 description "802.1q tagging for a cross-connect";
               }
               enum "ethernet-ccc" {
                 description "Ethernet for a cross-connect";
               }
               enum "vlan-vpls" {
                 description "VLAN virtual private LAN service";
               }
               enum "vlan-bridge" {
                 description "VLAN layer-2 bridging";
               }
               enum "ethernet-tcc" {
                 description "Ethernet translational cross-connect";
               }
               enum "dix" {
                 description "Ethernet DIXv2 (RFC 894)";
               }
               enum "ethernet" {
                 description "Ethernet II (RFC 894)";
               }
               enum "ethernet-vpls" {
                 description "Ethernet II virtual private LAN service";
               }
               enum "ethernet-bridge" {
                 description "Ethernet II bridging";
               }
               enum "vlan" {
                 description "802.1q-tagged Ethernet";
               }
               enum "vlan-tcc" {
                 description "802.1q tagging for a translational cross-connect";
               }
               enum "multilink-ppp" {
                 description "Multilink PPP";
               }
               enum "multilink-frame-relay-end-to-end" {
                 description "Multilink Frame Relay end-to-end (FRF.15)";
               }
               enum "ppp-ccc" {
                 description "Serial PPP device for a cross-connect";
               }
             }
           }
           leaf gre {
             description "Allow GRE packets";
             type empty;
           }
           leaf mtu {
             description "Maximum transmission unit packet size";
             type union {
               type string {
                 pattern "<.*>|$.*";
               }
               type uint32;
             }
           }
           choice pointedness {
             case case_1 {
               leaf point-to-point {
                 description "Point-to-point connection";
                 type empty;
               }
             }
             case case_2 {
               leaf multipoint {
                 description "Multipoint connection";
                 type empty;
               }
             }
           }
           leaf bandwidth {
             description "Logical unit bandwidth (informational only)";
             type string;
           }
           leaf global-layer2-domainid {
             description "Global Layer-2 Identifier for this interface";
             type union {
               type string {
                 pattern "<.*>|$.*";
               }
               type uint32 {
                 range "5 .. 4094";
               }
             }
           }
           container radio-router {
             description "Parameters for dynamic link cost management";
             presence "enable radio-router";
             uses dynamic_ifbw_parms_type;
           }
           choice traps-choice {
             leaf traps {
               description "Enable SNMP notifications on state changes";
               type empty;
             }
             leaf no-traps {
               description "Don't enable SNMP notifications on state changes";
               type empty;
             }
           }
           choice routing-services-choice {
             leaf routing-services {
               description "Enable routing services";
               status deprecated;
               type empty;
             }
             leaf no-routing-services {
               description "Don't enable routing services";
               status deprecated;
               type empty;
             }
           }
           container routing-service {
             description "Routing Services on this interface";
             uses apply-advanced;
             choice enable-disable {
               case case_1 {
                 leaf enable {
                   description "Enable Routing Service";
                   type empty;
                 }
               }
               case case_2 {
                 leaf disable {
                   description "Disable Routing Service";
                   type empty;
                 }
               }
             }
           }
           container arp-resp {
             presence "enable arp-resp";
             description "Knob to control ARP response on the interface, default is restricted";
             choice arp-response-options {
               case case_1 {
                 leaf unrestricted {
                   description "Enable unrestricted ARP respone on the interface";
                   type empty;
                 }
               }
               case case_2 {
                 leaf restricted {
                   description "Enable restricted proxy ARP response on the interface";
                   type empty;
                 }
               }
             }
           }
           container proxy-arp {
             presence "enable proxy-arp";
             description "Enable proxy ARP on the interface, default is unrestricted";
             choice proxyarp-options {
               case case_1 {
                 leaf unrestricted {
                   description "Enable unrestricted proxy ARP on the interface";
                   type empty;
                 }
               }
               case case_2 {
                 leaf restricted {
                   description "Enable restricted proxy ARP on the interface";
                   type empty;
                 }
               }
             }
           }
           choice vlan_choice {
             case case_1 {
               leaf vlan-id {
                 description "Virtual LAN identifier value for 802.1q VLAN tags";
                 type string;
               }
             }
             case case_2 {
               leaf vlan-id-range {
                 description "Virtual LAN identifier range of form vid1-vid2";
                 type jt:vlan-range;
               }
             }
             case case_3 {
               leaf-list inner-vlan-id-swap-ranges {
                 description "Inner vlan-id swap range(s) of form vid1-vid2 for dynamic L2 VLANs";
                 type jt:vlan-range;
               }
             }
             case case_4 {
               leaf-list vlan-id-list {
                 description "List of VLAN identifiers";
                 type jt:vlan-range;
               }
             }
             case case_5 {
               leaf-list vlan-tag {
                 ordered-by user;
                 description "IEEE 802.1q tag list for VLAN tagged frames";
                 status deprecated;
                 type string;
               }
             }
             case case_6 {
               container vlan-tags {
                 presence "enable vlan-tags";
                 description "IEEE 802.1q tags";
                 leaf outer {
                   description "[tpid.]vlan-id, tpid format is 0xNNNN and is optional";
                   type string;
                 }
                 choice inner_choice {
                   case case_1 {
                     leaf inner {
                       description "[tpid.]vlan-id, tpid format is 0xNNNN and is optional";
                       type string;
                     }
                   }
                   case case_2 {
                     leaf inner-range {
                       description "[tpid.]vid1-vid2, tpid format is 0xNNNN and is optional";
                       type string {
                       }
                     }
                   }
                   case case_3 {
                     leaf-list inner-list {
                       description "List of VLAN identifiers";
                       type jt:vlan-range;
                     }
                   }
                 }
               }
             }
           }
           leaf deep-vlan-qualified-learning {
             description "Enable qualified MAC-address learning on the specified vlan tag";
             type union {
               type string {
                 pattern "<.*>|$.*";
               }
               type uint32 {
                 range 3;
               }
             }
           }
           leaf native-inner-vlan-id {
             description "Native virtual LAN identifier for singly tagged frames";
             type union {
               type string {
                 pattern "<.*>|$.*";
               }
               type uint32 {
                 range "0 .. 4094";
               }
             }
           }
           container inner-vlan-id-range {
             description "Inner vlan-id range start <start-vlan-id> end <end-vlan-id>";
             leaf start {
               description "Inner vlan-id range's start value";
               type union {
                 type string {
                   pattern "<.*>|$.*";
                 }
                 type uint32 {
                   range "32 .. 4094";
                 }
               }
             }
             leaf end {
               description "Inner vlan-id range's end value";
               type union {
                 type string {
                   pattern "<.*>|$.*";
                 }
                 type uint32 {
                   range "32 .. 4094";
                 }
               }
             }
           }
           container accept-source-mac {
             description "Remote media access control address to/from which to accept traffic";
             uses apply-advanced;
             list mac-address {
               key name;
               description "Remote MAC address";
               uses mac_list;
             }
           }
           container input-vlan-map {
             description "VLAN map operation on input";
             uses vlan_map;
           }
           container output-vlan-map {
             description "VLAN map operation on output";
             uses vlan_map;
           }
           leaf swap-by-poppush {
             description "Pop original vlan tag and then push a new vlan tag";
             type empty;
           }
           leaf receive-lsp {
             description "Name of incoming label-switched path";
             type string;
           }
           leaf transmit-lsp {
             description "Name of outgoing label-switched path";
             type string;
           }
           leaf dlci {
             description "Frame Relay data-link control identifier";
             type union {
               type string {
                 pattern "<.*>|$.*";
               }
               type uint32 {
                 range "1 .. 1022";
               }
             }
           }
           leaf multicast-dlci {
             description "Frame Relay data-link control identifier for multicast packets";
             type union {
               type string {
                 pattern "<.*>|$.*";
               }
               type uint32 {
                 range "1 .. 1022";
               }
             }
           }
           choice vci_type {
             case case_1 {
               leaf vci {
                 description "ATM point-to-point virtual circuit identifier ([vpi.]vci)";
                 type jt:atm-vci;
               }
             }
             case case_2 {
               leaf allow-any-vci {
                 description "Allow all VCIs to open in atm-ccc-cell-relay mode";
                 type empty;
               }
             }
             case case_3 {
               leaf vpi {
                 description "ATM point-to-point virtual path identifier (vpi)";
                 type union {
                   type string {
                     pattern "<.*>|$.*";
                   }
                   type uint32 {
                     range "0 .. 255";
                   }
                 }
               }
             }
             case case_4 {
               leaf trunk-id {
                 description "ATM trunk identifier";
                 type union {
                   type string {
                     pattern "<.*>|$.*";
                   }
                   type uint32 {
                     range "0 .. 31";
                   }
                 }
               }
             }
           }
           leaf no-vpivci-swapping {
             description "Do not swap VPI/VCI for Cell Relay";
             type empty;
           }
           choice psn_vci_type {
             case case_1 {
               leaf psn-vci {
                 description "PSN VCI";
                 type jt:atm-vci;
               }
             }
             case case_2 {
               leaf psn-vpi {
                 description "PSN VPI";
                 type union {
                   type string {
                     pattern "<.*>|$.*";
                   }
                   type uint32 {
                     range "0 .. 255";
                   }
                 }
               }
             }
           }
           container atm-l2circuit-mode {
             description "Select ATM Layer 2 circuit transport mode";
             choice mode_choice {
               case case_1 {
                 leaf cell {
                   description "ATM Layer 2 circuit cell mode";
                   type empty;
                 }
               }
               case case_2 {
                 leaf aal5 {
                   description "ATM Layer 2 circuit AAL5 mode";
                   type empty;
                 }
               }
             }
           }
           container vci-range {
             description "ATM VCI range start <start-vci> end <end-vci>";
             leaf start {
               description "ATM VCI range's start value";
               type union {
                 type string {
                   pattern "<.*>|$.*";
                 }
                 type uint16 {
                   range "32 .. 4094";
                 }
               }
             }
             leaf end {
               description "ATM VCI range's end value";
               type union {
                 type string {
                   pattern "<.*>|$.*";
                 }
                 type uint16 {
                   range "32 .. 4094";
                 }
               }
             }
           }
           leaf trunk-bandwidth {
             description "ATM trunk bandwidth";
             units "bits per second";
             type string;
           }
           leaf multicast-vci {
             description "ATM virtual circuit identifier for multicast packets";
             type jt:atm-vci;
           }
           container shaping {
             description "Virtual circuit traffic-shaping options";
             uses dcd_shaping_config;
           }
           container oam-period {
             description "OAM cell period";
             choice oam_period_choices {
               case case_1 {
                 leaf oam-period {
                   description "OAM cell period";
                   units "seconds";
                   type union {
                     type string {
                       pattern "<.*>|$.*";
                     }
                     type uint32 {
                       range "1 .. 900";
                     }
                   }
                 }
               }
               case case_2 {
                 container disable {
                   presence "enable disable";
                   description "Disable F5 OAM loopback";
                 }
               }
             }
           }
           container oam-liveness {
             description "OAM virtual circuit liveness parameters";
             uses apply-advanced;
             leaf up-count {
               description "Number of OAM cells to consider VC up";
               type union {
                 type string {
                   pattern "<.*>|$.*";
                 }
                 type uint32 {
                   range "1 .. 255";
                 }
               }
             }
             leaf down-count {
               description "Number of OAM cells to consider VC down";
               type union {
                 type string {
                   pattern "<.*>|$.*";
                 }
                 type uint32 {
                   range "1 .. 255";
                 }
               }
             }
           }
           container ppp-options {
             description "Point-to-Point Protocol interface-specific options";
             uses ppp_options_type;
           }
           container pppoe-options {
             description "PPP over Ethernet interface-specific options";
             uses pppoe_options_type;
           }
           container pppoe-underlying-options {
             description "PPP over Ethernet underlying interface-specific options";
             uses pppoe_underlying_options_type;
           }
           container advisory-options {
             description "Interface-specific recommendations";
             uses advisory_options_type;
           }
           container auto-configure {
             description "Auto configuration";
             uses auto_configure_vlan_type;
           }
           container demux-options {
             description "IP demux interface-specific options";
             uses demux_options_type;
           }
           container targeted-distribution {
             presence "enable targeted-distribution";
             description "Interface participates in targeted-distribution";
             uses apply-advanced;
             leaf primary-list {
               description "Primary targeted distribution list";
               type string {
                 length "1 .. 20";
               }
             }
             leaf backup-list {
               description "Backup targeted distribution list";
               type string {
                 length "1 .. 20";
               }
             }
             leaf standby-list {
               description "Standby targeted distribution list";
               type string {
                 length "1 .. 20";
               }
             }
           }
           container targeted-options {
             presence "enable targeted-options";
             description "Targeting specific options";
             uses apply-advanced;
             leaf weight {
               description "Targeting weight for subscriber";
               type string;
             }
             leaf primary {
               description "Primary link for the subscriber";
               type union {
                 type jt:interface-device;
                 type string {
                   pattern "<.*>|$.*";
                 }
               }
             }
             leaf backup {
               description "Backup link for the subscriber";
               type union {
                 type jt:interface-device;
                 type string {
                   pattern "<.*>|$.*";
                 }
               }
             }
             leaf group {
               description "Group name to which the subscriber is associated";
               type string {
               }
             }
           }
           choice keepalive_choices {
             case case_1 {
               container keepalives {
                 description "Send or demand keepalive messages";
                 presence "enable keepalives";
                 uses keepalives_type;
               }
             }
             case case_2 {
               leaf no-keepalives {
                 description "Do not send or demand keepalive messages";
                 type empty;
               }
             }
           }
           leaf inverse-arp {
             description "Enable inverse ARP";
             type empty;
           }
           leaf transmit-weight {
             description "ATM2 transmit weight for VC under VP tunnel";
             type union {
               type string {
                 pattern "<.*>|$.*";
               }
               type uint16 {
                 range "1 .. 32767";
               }
             }
           }
           container epd-threshold {
             description "Early packet discard threshold for ATM2";
             uses epd_threshold_config;
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf atm-scheduler-map {
             description "Assign ATM2 CoS scheduling map";
             type union {
               type string {
                 pattern "default";
               }
               type string;
             }
           }
           leaf mrru {
             description "Maximum received reconstructed unit";
             units "bytes";
             type union {
               type string {
                 pattern "<.*>|$.*";
               }
               type uint16 {
                 range "1500 .. 4500";
               }
             }
           }
           leaf short-sequence {
             description "Short sequence number header format (MLPPP only)";
             type empty;
           }
           leaf fragment-threshold {
             description "Fragmentation threshold";
             units "bytes";
             type union {
               type string {
                 pattern "<.*>|$.*";
               }
               type uint32 {
                 range "64 .. 4500";
               }
             }
           }
           leaf drop-timeout {
             description "Drop timeout";
             units "milliseconds";
             type union {
               type string {
                 pattern "<.*>|$.*";
               }
               type uint16 {
                 range "0 .. 2000";
               }
             }
           }
           leaf disable-mlppp-inner-ppp-pfc {
             description "Disable compression for inner PPP header in MLPPP payload";
             type empty;
           }
           leaf minimum-links {
             description "Minimum number of links to sustain the bundle";
             type union {
               type string {
                 pattern "<.*>|$.*";
               }
               type uint16;
             }
           }
           leaf multilink-max-classes {
             description "Number of multilink classes";
             type union {
               type string {
                 pattern "<.*>|$.*";
               }
               type uint16;
             }
           }
           container compression {
             presence "enable compression";
             description "Various packet header compressions";
             uses apply-advanced;
             container rtp {
               presence "enable rtp";
               description "Compress and decompress RTP";
               uses apply-advanced;
               leaf f-max-period {
                 description "Maximum number of compressed packets between transmission of full headers";
                 type union {
                   type string {
                     pattern "<.*>|$.*";
                   }
                   type uint32 {
                     range "1 .. 65535";
                   }
                 }
               }
               leaf-list queues {
                 ordered-by user;
                 description "Queue holding RTP packets. Default is queue 1";
                 type enumeration {
                   enum "q0" {
                     description "RTP packets assigned to queue 0";
                   }
                   enum "q1" {
                     description "RTP packets assigned to queue 1";
                   }
                   enum "q2" {
                     description "RTP packets assigned to queue 2";
                   }
                   enum "q3" {
                     description "RTP packets assigned to queue 3";
                   }
                 }
               }
               container port {
                 presence "enable port";
                 description "UDP destination ports reserved for RTP packets";
                 leaf minimum {
                   type union {
                     type string {
                       pattern "<.*>|$.*";
                     }
                     type uint32 {
                       range "0 .. 65535";
                     }
                   }
                 }
                 leaf maximum {
                   type union {
                     type string {
                       pattern "<.*>|$.*";
                     }
                     type uint32 {
                       range "0 .. 65535";
                     }
                   }
                 }
               }
               container maximum-contexts {
                 description "Maximum number of simultaneous RTP contexts";
                 leaf number {
                   description "Maximum number of simultaneous RTP contexts";
                   type union {
                     type string {
                       pattern "<.*>|$.*";
                     }
                     type uint32 {
                       range "16 .. 2048";
                     }
                   }
                 }
               }
             }
           }
           leaf interleave-fragments {
             description "Interleave long packets with high priority ones";
             type empty;
           }
           leaf link-layer-overhead {
             description "Link layer bit stuffing overhead (0.0 .. 50.0 percent)";
             type jt:unsigned-float;
           }
           leaf accounting-profile {
             description "Accounting profile name";
             type string;
           }
           leaf peer-unit {
             description "Peer unit number";
             type union {
               type string {
                 pattern "<.*>|$.*";
               }
               type uint32 {
                 range "0 .. 16385";
               }
             }
           }
           container tunnel {
             description "Tunnel parameters";
             uses apply-advanced;
             container encapsulation {
               presence "enable encapsulation";
               description "Encapsulation over tunnel";
               container vxlan-gpe {
                 presence "enable vxlan-gpe";
                 uses apply-advanced;
                 container source {
                   uses apply-advanced;
                   leaf address {
                     description "Interface address prefix";
                     type jt:ipv4addr;
                   }
                   leaf mac-address {
                     description "Interface source mac address";
                     type jt:mac-addr;
                   }
                   leaf interface {
                     description "Name of the interface";
                     type union {
                       type jt:interface-name;
                       type string {
                         pattern "<.*>|$.*";
                       }
                     }
                   }
                 }
                 container destination {
                   uses apply-advanced;
                   leaf address {
                     description "Interface address prefix";
                     type jt:ipv4addr;
                   }
                   leaf mac-address {
                     description "Interface destination mac address";
                     type jt:mac-addr;
                   }
                 }
                 leaf tunnel-endpoint {
                   description "Tunnel end point type";
                   type enumeration {
                     enum "vxlan" {
                       description "To configure vxlan tunnel-end-point";
                     }
                   }
                 }
                 container source-udp-port-range {
                   description "Value range for source-udp-port";
                   leaf min {
                     description "Minimum range value";
                     type union {
                       type string {
                         pattern "<.*>|$.*";
                       }
                       type uint32 {
                         range "1 .. 65535";
                       }
                     }
                   }
                   leaf max {
                     description "Maximum range value";
                     type union {
                       type string {
                         pattern "<.*>|$.*";
                       }
                       type uint32 {
                         range "1 .. 65535";
                       }
                     }
                   }
                 }
                 leaf destination-udp-port {
                   description "Value to write to the destination-udp-port field";
                   type union {
                     type string {
                       pattern "<.*>|$.*";
                     }
                     type uint32 {
                       range "1 .. 65535";
                     }
                   }
                 }
                 leaf vni {
                   description "Value to write to the vni field";
                   type union {
                     type string {
                       pattern "<.*>|$.*";
                     }
                     type uint32 {
                       range "0 .. 16777214";
                     }
                   }
                 }
               }
               container udp {
                 presence "enable udp";
                 description "Family for tunnel encapsulation udp";
                 uses apply-advanced;
                 container source {
                   uses apply-advanced;
                   leaf address {
                     description "Interface address prefix";
                     type jt:ipv4addr;
                   }
                   leaf interface {
                     description "Name of the interface";
                     type union {
                       type jt:interface-name;
                       type string {
                         pattern "<.*>|$.*";
                       }
                     }
                   }
                 }
                 container destination {
                   uses apply-advanced;
                   leaf address {
                     description "Interface address prefix";
                     type jt:ipv4addr;
                   }
                 }
               }
               container ipip {
                 presence "enable ipip";
                 description "Family for tunnel encapsulation ipip";
                 uses apply-advanced;
                 container source {
                   uses apply-advanced;
                   leaf address {
                     description "Interface address prefix";
                     type jt:ipv4addr;
                   }
                   leaf interface {
                     description "Name of the interface";
                     type union {
                       type jt:interface-name;
                       type string {
                         pattern "<.*>|$.*";
                       }
                     }
                   }
                 }
                 container destination {
                   uses apply-advanced;
                   leaf address {
                     description "Interface address prefix";
                     type jt:ipv4addr;
                   }
                 }
               }
             }
             leaf encap-type {
               description "Tunnel encapsulation type";
               type enumeration {
                 enum "ipv4" {
                   description "Tunnel IPv4 encapsulation";
                 }
                 enum "ipv6" {
                   description "Tunnel IPv6 encapsulation";
                 }
               }
             }
             choice source_type {
               case case_1 {
                 leaf source {
                   description "Tunnel source address";
                   type jt:ipaddr;
                 }
               }
               case case_2 {
                 leaf source-hostname {
                   description "Tunnel source hostname";
                   type string;
                 }
               }
               case case_3 {
                 leaf source-interface {
                   description "Tunnel source interface";
                   type union {
                     type jt:interface-name;
                     type string {
                       pattern "<.*>|$.*";
                     }
                   }
                 }
               }
             }
             choice destination_type {
               case case_1 {
                 leaf destination {
                   description "Tunnel destination address";
                   type jt:ipaddr;
                 }
               }
               case case_2 {
                 leaf destination-hostname {
                   description "Tunnel destination hostname";
                   type string;
                 }
               }
             }
             leaf key {
               description "Tunnel key";
               type union {
                 type string {
                   pattern "<.*>|$.*";
                 }
                 type uint32 {
                   range "0 .. 4294967295";
                 }
               }
             }
             leaf backup-destination {
               description "Backup tunnel destination";
               type jt:ipaddr;
             }
             choice fragmentation {
               case case_1 {
                 leaf allow-fragmentation {
                   description "Do not set DF bit on packets";
                   type empty;
                 }
               }
               case case_2 {
                 leaf do-not-fragment {
                   description "Set DF bit on packets";
                   type empty;
                 }
               }
             }
             leaf ttl {
               description "Time to live";
               type union {
                 type string {
                   pattern "<.*>|$.*";
                 }
                 type uint32 {
                   range "1 .. 255";
                 }
               }
             }
             leaf traffic-class {
               description "TOS/Traffic class field of IP-header";
               type union {
                 type string {
                   pattern "<.*>|$.*";
                 }
                 type uint32 {
                   range "0 .. 255";
                 }
               }
             }
             leaf flow-label {
               description "Flow label field of IP6-header";
               type union {
                 type string {
                   pattern "<.*>|$.*";
                 }
                 type uint32 {
                   range "0 .. 1048575";
                 }
               }
             }
             choice path-mtu-discovery-choice {
               leaf path-mtu-discovery {
                 description "Enable path MTU discovery for tunnels";
                 type empty;
               }
               leaf no-path-mtu-discovery {
                 description "Don't enable path MTU discovery for tunnels";
                 type empty;
               }
             }
             container routing-instance {
               description "Routing instance to which tunnel ends belong";
               uses apply-advanced;
               leaf destination {
                 description "Routing instance of tunnel destination";
                 type string {
                 }
               }
             }
           }
           leaf compression-device {
             description "Logical interface used for compression";
             type union {
               type jt:interface-unit;
               type string {
                 pattern "<.*>|$.*";
               }
             }
           }
           container atm-policer {
             description "ATM policing for logical interface";
             uses apply-advanced;
             leaf input-atm-policer {
               description "Input atm policer";
               type string;
             }
           }
           container layer2-policer {
             description "Layer2 policing for logical interface";
             uses apply-advanced;
             choice layer2-input-policer-choice {
               case case_1 {
                 leaf input-policer {
                   description "Two-color policer for received packets";
                   type string;
                 }
               }
               case case_2 {
                 leaf input-hierarchical-policer {
                   description "Hierarchical policer for received packets";
                   type string;
                 }
               }
               case case_3 {
                 leaf input-three-color {
                   description "Color-blind three-color policer for received packets";
                   type string;
                 }
               }
             }
             choice layer2-output-policer-choice {
               case case_1 {
                 leaf output-policer {
                   description "Two-color policer for transmitted packets";
                   type string;
                 }
               }
               case case_2 {
                 leaf output-three-color {
                   description "Three-color policer for transmitted packets";
                   type string;
                 }
               }
             }
           }
           container filter {
             description "Filters to apply to all families configured under this logical interface";
             uses apply-advanced;
             choice chain_choice {
               case case_1 {
                 leaf-list chain {
                   ordered-by user;
                   description "List of filter modules applied to TAG packets ";
                   type string;
                   max-elements 6;
                 }
               }
             }
             choice input_choice {
               case case_1 {
                 container input {
                   description "Name of filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
             }
             choice output_choice {
               case case_1 {
                 container output {
                   description "Name of filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
             }
           }
           list multi-chassis-protection {
             key name;
             description "Inter-Chassis protection configuration";
             uses multi-chassis-protection-group-ifl;
           }
           leaf statistics {
             description "Enable statistics collection in PFE";
             type empty;
           }
           container esi {
             presence "enable esi";
             description "ESI configuration of logical interface";
             uses apply-advanced;
             container auto-derive {
               description "Auto-derive ESI value for the interface";
               uses apply-advanced;
               choice esitype {
                 case case_1 {
                   leaf lacp-pe-system-id-and-admin-key {
                     description "Auto-derive ESI from lacp";
                     type empty;
                   }
                 }
               }
             }
             leaf identifier {
               description "ESI value for the interface";
               type jt:esi;
             }
             choice mode {
               case case_1 {
                 leaf single-active {
                   description "Single-active mode";
                   type empty;
                 }
               }
               case case_2 {
                 leaf all-active {
                   description "All-active mode";
                   type empty;
                 }
               }
             }
             container df-election-granularity {
               presence "enable df-election-granularity";
               description "DF Election Granularity Selection ";
               uses apply-advanced;
               choice mode {
                 case case_1 {
                   container per-esi {
                     presence "enable per-esi";
                     description "DF Election Granularity Per Esi";
                     uses apply-advanced;
                     leaf lacp-oos-on-ndf {
                       description "Lacp Oos";
                       type empty;
                     }
                   }
                 }
                 case case_2 {
                   leaf per-esi-vlan {
                     description "Per Esi Vlan";
                     type empty;
                   }
                 }
               }
             }
             container df-election-type {
               presence "enable df-election-type";
               description "DF Election Type";
               uses apply-advanced;
               choice pref_choice {
                 case case_1 {
                   container preference {
                     presence "enable preference";
                     description "Preference based DF election";
                     uses apply-advanced;
                     leaf value {
                       description "Preference value for EVPN Multihoming DF election";
                       default "32767";
                       type union {
                         type string {
                           pattern "<.*>|$.*";
                         }
                         type uint32 {
                           range "0 .. 65535";
                         }
                       }
                     }
                   }
                 }
               }
               choice mod_choice {
                 case case_1 {
                   container mod {
                     presence "enable mod";
                     description "MOD based DF election";
                   }
                 }
               }
             }
             leaf source-bmac {
               description "Unicast Source B-MAC address per ESI for PBB-EVPN";
               type jt:mac-unicast;
             }
           }
           choice virtual-gateway {
             case case_1 {
               leaf no-auto-virtual-gateway-esi {
                 description "Disable auto ESI generation for virtual gateway address";
                 type empty;
               }
             }
             case case_2 {
               container virtual-gateway-esi {
                 description "ESI configuration of virtual gateway";
                 uses apply-advanced;
                 leaf identifier {
                   description "ESI value for the interface";
                   type jt:esi;
                 }
                 choice mode {
                   case case_1 {
                     leaf single-active {
                       description "Single-active mode";
                       type empty;
                     }
                   }
                   case case_2 {
                     leaf all-active {
                       description "All-active mode";
                       type empty;
                     }
                   }
                 }
               }
             }
           }
           container service {
             description "Service operations";
             uses apply-advanced;
             list pcef {
               key name;
               ordered-by user;
               description "PCEF configuration";
               leaf name {
                 description "PCEF Profile name";
                 type string;
               }
               uses apply-advanced;
               leaf activate-all {
                 description "Activate all rules and rulebases in the pcef profile";
                 type empty;
               }
               list activate {
                 key name;
                 ordered-by user;
                 description "Name of pcef profile rule or rulebase to activate";
                 leaf name {
                   description "Name of pcef profile rule or rulebase to activate";
                   type string;
                 }
                 uses apply-advanced;
               }
             }
           }
           choice generate-eui64-choice {
             leaf generate-eui64 {
               description "To generate Link Local EUI-64 addresses";
               type empty;
             }
             leaf no-generate-eui64 {
               description "Don't to generate Link Local EUI-64 addresses";
               type empty;
             }
           }
           container family {
             description "Protocol family";
             container inet {
               presence "enable inet";
               description "IPv4 parameters";
               uses apply-advanced;
               container dhcp {
                 description "Dynamic Host Configuration Protocol client configuration";
                 presence "enable dhcp";
                 uses dhcp-client-type;
               }
               container targeted-broadcast {
                 presence "enable targeted-broadcast";
                 description "Directed broadcast";
                 uses apply-advanced;
                 choice targeted-bcast-choice {
                   case case_1 {
                     leaf forward-and-send-to-re {
                       description "Allow packets to be forwarded and sent to re";
                       type empty;
                     }
                   }
                   case case_2 {
                     leaf forward-only {
                       description "Allow packets only to be forwarded";
                       type empty;
                     }
                   }
                 }
               }
               leaf destination-class-usage {
                 description "Enable destination class usage on this interface";
                 status deprecated;
                 type empty;
               }
               leaf transit-options-packets {
                 description "Transit IP options packets (don't send to Routing Engine)";
                 status deprecated;
                 type empty;
               }
               leaf transit-ttl-exceeded {
                 description "Transit IP TTL-exceeded packets (don't send to Routing Engine)";
                 status deprecated;
                 type empty;
               }
               leaf receive-options-packets {
                 description "Receive IP options packets (don't send to Routing Engine)";
                 type empty;
               }
               leaf receive-ttl-exceeded {
                 description "Receive IP TTL-exceeded packets (don't send to Routing Engine)";
                 type empty;
               }
               container accounting {
                 description "Configure interface-based accounting options";
                 uses apply-advanced;
                 container source-class-usage {
                   description "Enable source class usage on this interface";
                   uses apply-advanced;
                   leaf input {
                     description "Specify this interface for source-class-usage input";
                     type empty;
                   }
                   leaf output {
                     description "Specify this interface for source-class-usage output";
                     type empty;
                   }
                 }
                 leaf destination-class-usage {
                   description "Enable destination class usage on this interface";
                   type empty;
                 }
               }
               leaf mac-validate {
                 description "Validate source MAC address";
                 type enumeration {
                   enum "strict" {
                     description "Strict mac-validation";
                   }
                   enum "loose" {
                     description "Loose mac-validation";
                   }
                 }
               }
               container rpf-check {
                 presence "enable rpf-check";
                 description "Enable reverse-path-forwarding checks on this interface";
                 uses apply-advanced;
                 leaf fail-filter {
                   description "Name of filter applied to packets failing RPF check";
                   type string;
                 }
                 container mode {
                   description "Mode for reverse path forwarding";
                   leaf loose {
                     description "Reverse-path-forwarding loose mode";
                     type empty;
                   }
                 }
               }
               leaf mtu {
                 description "Protocol family maximum transmission unit";
                 type union {
                   type uint32;
                   type string {
                     pattern "<.*>|$.*";
                   }
                 }
               }
               leaf arp-max-cache {
                 description "Max interface ARP nexthop cache size";
                 type union {
                   type string {
                     pattern "<.*>|$.*";
                   }
                   type uint32 {
                     range "1 .. 2000000";
                   }
                 }
               }
               leaf arp-new-hold-limit {
                 description "Max no. of new unresolved nexthops";
                 type union {
                   type string {
                     pattern "<.*>|$.*";
                   }
                   type uint32 {
                     range "1 .. 2000000";
                   }
                 }
               }
               leaf tcp-mss {
                 description "Protocol family tcp maximum segment size";
                 type union {
                   type string {
                     pattern "<.*>|$.*";
                   }
                   type uint32 {
                     range "1 .. 65535";
                   }
                 }
               }
               leaf no-redirects {
                 description "Do not redirect traffic";
                 type empty;
               }
               leaf no-neighbor-learn {
                 description "Disable neighbor address learning on interface";
                 type empty;
               }
               leaf unconditional-src-learn {
                 description "Glean from arp packets even when source cannot be validated";
                 type empty;
               }
               leaf multicast-only {
                 description "Allow only multicast traffic (tunnels only)";
                 type empty;
               }
               leaf primary {
                 description "Candidate for primary interface in system";
                 type empty;
               }
               leaf ipsec-sa {
                 description "Name of security association";
                 type string {
                   length "1 .. 32";
                 }
               }
               leaf allow-filter-on-re {
                 description "Enable kernel filter on network ports";
                 type empty;
               }
               list demux-source {
                 key name;
                 ordered-by user;
                 description "Demux based on source prefix";
                 leaf name {
                   type string;
                 }
                 uses apply-advanced;
               }
               list demux-destination {
                 key name;
                 ordered-by user;
                 description "Demux based on destination prefix";
                 leaf name {
                   type string;
                 }
                 uses apply-advanced;
               }
               container filter {
                 description "Packet filtering";
                 uses apply-advanced;
                 choice input_choice {
                   case case_1 {
                     container input {
                       description "Filter to be applied to received packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 leaf-list output-chain {
                   ordered-by user;
                   description "List of filter modules applied to transmitted packets ";
                   type string;
                 }
                 choice output_choice {
                   case case_1 {
                     container output {
                       description "Filter to be applied to transmitted packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32;
                   }
                 }
                 leaf dialer {
                   description "Name of filter applied on dialer";
                   type string;
                 }
               }
               container ingress-queuing-filter {
                 description "Protocol family ingress-queuing-filter";
                 leaf filter-name {
                   description "Name of the ingress-queuing-filter";
                   type string;
                 }
               }
               container iq-policing-filter {
                 description "Protocol family ingress-queuing-policing-filter";
                 leaf filter-name {
                   description "Name of the ingress-queuing-policing-filter";
                   type string;
                 }
               }
               container simple-filter {
                 description "Filter for doing multifield classification";
                 uses apply-advanced;
                 leaf input {
                   description "Name of simple filter applied to received packets";
                   type string;
                 }
               }
               leaf input-hierarchical-policer {
                 description "Hierarchical policer for received packets";
                 type string;
               }
               container policer {
                 description "Interface policing";
                 uses apply-advanced;
                 leaf disable-arp-policer {
                   description "Disable the arp policer for the interface";
                   type empty;
                 }
                 leaf arp {
                   description "Name of policer applied to received ARP packets";
                   type string;
                 }
                 leaf input {
                   description "Name of policer applied to received packets";
                   type string;
                 }
                 leaf output {
                   description "Name of policer applied to transmitted packets";
                   type string;
                 }
               }
               container sampling {
                 description "Interface sampling";
                 uses apply-advanced;
                 leaf input {
                   description "Sample all packets input on this interface";
                   type empty;
                 }
                 leaf output {
                   description "Sample all packets output on this interface";
                   type empty;
                 }
               }
               container service {
                 description "Service operations";
                 uses apply-advanced;
                 container input {
                   description "Service sets to consider for received packets";
                   uses apply-advanced;
                   list service-set {
                     key name;
                     ordered-by user;
                     description "Service set to consider for received packets";
                     leaf name {
                       description "Name of service set";
                       type string {
                       }
                     }
                     uses apply-advanced;
                     leaf service-filter {
                       description "Name of service filter";
                       type string;
                     }
                   }
                   leaf post-service-filter {
                     description "Post-service filter to apply to received packets";
                     type string;
                   }
                 }
                 container output {
                   description "Service sets to consider for transmitted packets";
                   uses apply-advanced;
                   list service-set {
                     key name;
                     ordered-by user;
                     description "Service set to consider for transmitted packets";
                     leaf name {
                       description "Name of service set";
                       type string {
                       }
                     }
                     uses apply-advanced;
                     leaf service-filter {
                       description "Name of service filter";
                       type string;
                     }
                   }
                 }
               }
               list next-hop-tunnel {
                 key name;
                 ordered-by user;
                 description "One or more next-hop tunnel tables";
                 leaf name {
                   description "Next-hop tunnel gateway address";
                   type string;
                 }
                 uses apply-advanced;
                 leaf ipsec-vpn {
                   description "Name of IPSec VPN";
                   type string;
                 }
               }
               choice tunnel-termination-status {
                 case case_1 {
                   leaf tunnel-termination {
                     description "Tunnel termination";
                     type empty;
                   }
                 }
                 case case_2 {
                   leaf no-tunnel-termination {
                     description "No Tunnel termination";
                     type empty;
                   }
                 }
               }
               leaf tunnel-loopback {
                 description "Allows tunnel packet processing on IRB underlay using the loopback path";
                 type empty;
               }
               list address {
                 key name;
                 ordered-by user;
                 description "Interface address/destination prefix";
                 leaf name {
                   description "Interface address/destination prefix";
                   type jt:ipv4prefix;
                 }
                 uses apply-advanced;
                 leaf destination {
                   description "Destination address";
                   type jt:ipv4addr;
                 }
                 leaf destination-profile {
                   description "Profile to use for destination address";
                   type string;
                 }
                 leaf broadcast {
                   description "Broadcast address";
                   type jt:ipv4addr;
                 }
                 leaf primary {
                   description "Candidate for primary address in system";
                   type empty;
                 }
                 leaf preferred {
                   description "Preferred address on interface";
                   type empty;
                 }
                 leaf master-only {
                   description "Master management IP address for router";
                   type empty;
                 }
                 list multipoint-destination {
                   key name;
                   ordered-by user;
                   description "Multipoint NBMA destination";
                   leaf name {
                     description "Destination address";
                     type jt:ipv4addr;
                   }
                   uses apply-advanced;
                   choice link-address {
                     case case_1 {
                       leaf dlci {
                         description "Frame Relay data-link control identifier";
                         type union {
                           type string {
                             pattern "<.*>|$.*";
                           }
                           type uint32 {
                             range "1 .. 1022";
                           }
                         }
                       }
                     }
                     case case_2 {
                       leaf vci {
                         description "ATM virtual circuit identifier ([vpi.]vci)";
                         type jt:atm-vci;
                       }
                     }
                   }
                   container shaping {
                     description "Virtual circuit traffic-shaping options";
                     uses dcd_shaping_config;
                   }
                   container oam-period {
                     description "OAM cell period";
                     choice oam_period_choices {
                       case case_1 {
                         leaf oam_period {
                           description "OAM cell period";
                           units "seconds";
                           type union {
                             type string {
                               pattern "<.*>|$.*";
                             }
                             type uint32 {
                               range "1 .. 900";
                             }
                           }
                         }
                       }
                       case case_2 {
                         container disable {
                           presence "enable disable";
                           description "Disable OAM loopback";
                         }
                       }
                     }
                   }
                   container oam-liveness {
                     description "OAM virtual circuit liveness parameters";
                     uses apply-advanced;
                     leaf up-count {
                       description "Number of OAM cells to consider VC up";
                       type union {
                         type string {
                           pattern "<.*>|$.*";
                         }
                         type uint32 {
                           range "1 .. 255";
                         }
                       }
                     }
                     leaf down-count {
                       description "Number of OAM cells to consider VC down";
                       type union {
                         type string {
                           pattern "<.*>|$.*";
                         }
                         type uint32 {
                           range "1 .. 255";
                         }
                       }
                     }
                   }
                   leaf inverse-arp {
                     description "Enable inverse ARP reply messages";
                     type empty;
                   }
                   leaf transmit-weight {
                     description "ATM2 transmit weight for VC under VP tunnel";
                     type union {
                       type string {
                         pattern "<.*>|$.*";
                       }
                       type uint16 {
                         range "1 .. 32767";
                       }
                     }
                   }
                   container epd-threshold {
                     description "Early packet discard threshold for ATM2";
                     uses epd_threshold_config;
                   }
                 }
                 list arp {
                   key name;
                   ordered-by user;
                   description "Static Address Resolution Protocol entries";
                   leaf name {
                     description "Destination IP address";
                     type jt:ipv4addr;
                   }
                   leaf l2-interface {
                     description "Layer 2 interface name for ARP entry";
                     type union {
                       type jt:interface-name;
                       type string {
                         pattern "<.*>|$.*";
                       }
                     }
                   }
                   choice mac_address_type {
                     case case_1 {
                       leaf mac {
                         description "MAC address";
                         type jt:mac-unicast;
                       }
                     }
                     case case_2 {
                       leaf multicast-mac {
                         description "Multicast MAC address";
                         type jt:mac-multicast;
                       }
                     }
                   }
                   leaf publish {
                     description "Reply to ARP requests for this entry";
                     type empty;
                   }
                   leaf flood-as-unknown-unicast {
                     description "Broadcast the packet with unicast MAC";
                     type empty;
                   }
                 }
                 list host-discovery {
                   key name;
                   ordered-by user;
                   description "Discover servers IP based on subnet range";
                   max-elements 8;
                   leaf name {
                     description "IP address subnet range";
                     type jt:ipv4prefix;
                   }
                   leaf aging-timer {
                     description "ARP aging timer";
                     type union {
                       type string {
                         pattern "<.*>|$.*";
                       }
                       type uint32 {
                         range "10 .. 1200";
                       }
                     }
                   }
                   leaf discovery-interval {
                     description "ARP proactive discovery time";
                     type union {
                       type string {
                         pattern "<.*>|$.*";
                       }
                       type uint32 {
                         range "3 .. 300";
                       }
                     }
                   }
                 }
                 container web-authentication {
                   description "Parameters for web-based firewall-user authentication";
                   uses apply-advanced;
                   leaf http {
                     description "Enable authentication via HTTP";
                     type empty;
                   }
                   leaf https {
                     description "Enable authentication via HTTPS";
                     type empty;
                   }
                   leaf redirect-to-https {
                     description "Web authentication redirect to HTTPS";
                     type empty;
                   }
                 }
                 list vrrp-group {
                   key name;
                   ordered-by user;
                   description "VRRP group";
                   uses vrrp-group;
                 }
                 leaf virtual-gateway-address {
                   description "Virtual Gateway IP address";
                   type jt:ipv4addr;
                 }
               }
               container unnumbered-address {
                 description "Unnumbered interface address/destination prefix";
                 leaf source {
                   description "Interface from which to take local address";
                   type union {
                     type jt:interface-unit;
                     type string {
                       pattern "<.*>|$.*";
                     }
                   }
                 }
                 leaf preferred-source-address {
                   description "Preferred address on the donor interface";
                   type string;
                 }
                 leaf destination {
                   description "Destination address";
                   type jt:ipv4addr;
                 }
                 leaf destination-profile {
                   description "Profile to use for destination address";
                   type string;
                 }
               }
               container location-pool-address {
                 presence "enable location-pool-address";
                 description "Location-based IP address pool";
                 uses apply-advanced;
                 leaf pool-name {
                   description "Pool name";
                   type string {
                     length "1 .. 64";
                   }
                 }
               }
               leaf negotiate-address {
                 description "Negotiate address with remote";
                 type empty;
               }
               leaf destination-udp-port {
                 description "Choose destination UDP port number";
                 type union {
                   type string {
                     pattern "<.*>|$.*";
                   }
                   type uint32 {
                     range "10000 .. 10009";
                   }
                 }
               }
               container auto-configure {
                 description "Auto configuration";
                 uses dynamic_ipv4_type;
               }
               leaf clear-dont-fragment-bit {
                 description "Clear DF bit in packet (AS PIC and J-series only as well as MIF)";
                 type empty;
               }
             }
             container iso {
               presence "enable iso";
               description "OSI ISO protocol parameters";
               uses apply-advanced;
               list address {
                 key name;
                 ordered-by user;
                 description "Interface address";
                 leaf name {
                   description "Interface address";
                   type jt:isoaddr;
                 }
                 uses apply-advanced;
               }
               leaf mtu {
                 description "Protocol family maximum transmission unit";
                 type union {
                   type uint32;
                   type string {
                     pattern "<.*>|$.*";
                   }
                 }
               }
               leaf destination-udp-port {
                 description "Choose destination UDP port number";
                 type union {
                   type string {
                     pattern "<.*>|$.*";
                   }
                   type uint32 {
                     range "10030 .. 10039";
                   }
                 }
               }
             }
             container inet6 {
               presence "enable inet6";
               description "IPv6 protocol parameters";
               uses apply-advanced;
               container dhcpv6-client {
                 description "Dynamic Host Configuration Protocol DHCPv6 client configuration";
                 uses apply-advanced;
                 leaf client-type {
                   description "DHCPv6 client type";
                   type enumeration {
                     enum "stateful" {
                       description "Stateful client type for address assignment.";
                     }
                     enum "autoconfig" {
                       description "Autoconfig  client type for router-advertisement";
                     }
                   }
                 }
                 list client-ia-type {
                   key name;
                   ordered-by user;
                   description "DHCPv6 client identity association type";
                   leaf name {
                     type enumeration {
                       enum "ia-na" {
                         description "Identity Association-Non-temporary Address";
                       }
                       enum "ia-pd" {
                         description "Identity Association-Prefix Address";
                       }
                     }
                   }
                   uses apply-advanced;
                 }
                 container rapid-commit {
                   presence "enable rapid-commit";
                   description "Option is used to signal the use of the two message exchange for address assignment";
                 }
                 leaf interface-identifier {
                   description "Identifier for this interface";
                   type jt:ipv6addr;
                 }
                 leaf use-ra-prefix {
                   description "Assign interface IP from RA prefix when ia-na address not received";
                   type empty;
                 }
                 container prefix-delegating {
                   description "Prefix delegating parameters";
                   uses apply-advanced;
                   leaf preferred-prefix-length {
                     description "Client preferred prefix length";
                     type union {
                       type string {
                         pattern "<.*>|$.*";
                       }
                       type uint32 {
                         range "0 .. 64";
                       }
                     }
                   }
                   leaf sub-prefix-length {
                     description "The sub prefix length for LAN interfaces";
                     type union {
                       type string {
                         pattern "<.*>|$.*";
                       }
                       type uint32 {
                         range "1 .. 127";
                       }
                     }
                   }
                 }
                 container client-identifier {
                   description "DHCP Server identifies a client by client-identifier value ";
                   leaf duid-type {
                     description "DUID identifying a client";
                     type enumeration {
                       enum "duid-llt" {
                         description "Link-layer address plus time";
                       }
                       enum "vendor" {
                         description "Vendor-assigned unique ID based on Enterprise Number";
                       }
                       enum "duid-ll" {
                         description "Link-layer address";
                       }
                     }
                   }
                 }
                 leaf vendor-id {
                   description "Vendor class id for the dhcpv6 client";
                   type string {
                     length "1 .. 60";
                   }
                 }
                 list req-option {
                   key name;
                   ordered-by user;
                   description "DHCPV6 client requested option configuration";
                   leaf name {
                     type enumeration {
                       enum "dns-server" {
                         description "Dns-server option";
                       }
                       enum "domain" {
                         description "Dns-server option";
                       }
                       enum "ntp-server" {
                         description "Ntp-server option";
                       }
                       enum "time-zone" {
                         description "Time-zone option";
                       }
                       enum "sip-server" {
                         description "Sip-server option";
                       }
                       enum "sip-domain" {
                         description "Sip-domain option";
                       }
                       enum "nis-server" {
                         description "Nis-server option";
                       }
                       enum "nis-domain" {
                         description "Nis-domain option";
                       }
                       enum "fqdn" {
                         description "Fully-qualified-domain option";
                       }
                       enum "vendor-spec" {
                         description "Vendor-spec option";
                       }
                       enum "zero-touch-redirect" {
                         description "Zero-touch-redirect";
                       }
                       enum "bootfile-url" {
                         description "Bootfile url";
                       }
                       enum "bootfile-param" {
                         description "Bootfile param";
                       }
                     }
                   }
                   uses apply-advanced;
                 }
                 container options {
                   description "DHCP options";
                   uses apply-advanced;
                   list number {
                     key name;
                     description "DHCP option code";
                     leaf name {
                       description "DHCP option identifier code";
                       type union {
                         type string {
                           pattern "<.*>|$.*";
                         }
                         type uint32 {
                           range "1 .. 254";
                         }
                       }
                     }
                     choice option-type-choice {
                       case case_1 {
                         leaf hex-string {
                           description "Hexadecimal string";
                           type string {
                             length "1 .. 510";
                           }
                         }
                       }
                     }
                   }
                 }
                 leaf retransmission-attempt {
                   description "Number of attempts to retransmit the DHCPV6 client protocol packet";
                   default "9";
                   type union {
                     type string {
                       pattern "<.*>|$.*";
                     }
                     type uint32 {
                       range "0 .. 50000";
                     }
                   }
                 }
                 container no-dns-install {
                   presence "enable no-dns-install";
                   description "Not propagate DNS to kernel";
                 }
                 container update-router-advertisement {
                   description "Dhcpv6 client update rpd for prefix delegation";
                   uses apply-advanced;
                   list interface {
                     key name;
                     ordered-by user;
                     description "Interfaces on which to delegate prefix";
                     max-elements 3;
                     leaf name {
                       description "Interfaces-name on which to delegate prefix";
                       type union {
                         type jt:interface-name;
                         type string {
                           pattern "<.*>|$.*";
                         }
                       }
                     }
                     uses apply-advanced;
                     leaf interface-identifier {
                       description "Identifier for this interface";
                       type jt:ipv6addr;
                     }
                     leaf prefix-identifier {
                       description "Prefix identifier for prefix used in this interface";
                       type jt:ipv6addr;
                     }
                     choice managed-configuration-choice {
                       leaf managed-configuration {
                         description "Set managed address configuration";
                         type empty;
                       }
                       leaf no-managed-configuration {
                         description "Don't set managed address configuration";
                         type empty;
                       }
                     }
                     choice other-stateful-configuration-choice {
                       leaf other-stateful-configuration {
                         description "Set other stateful configuration";
                         type empty;
                       }
                       leaf no-other-stateful-configuration {
                         description "Don't set other stateful configuration";
                         type empty;
                       }
                     }
                     leaf max-advertisement-interval {
                       description "Maximum advertisement interval";
                       units "seconds";
                       type union {
                         type string {
                           pattern "<.*>|$.*";
                         }
                         type uint32 {
                           range "4 .. 1800";
                         }
                       }
                     }
                     leaf min-advertisement-interval {
                       description "Minimum advertisement interval";
                       units "seconds";
                       type union {
                         type string {
                           pattern "<.*>|$.*";
                         }
                         type uint32 {
                           range "3 .. 1350";
                         }
                       }
                     }
                     choice enable-recursive-dns-server-option-choice {
                       leaf enable-recursive-dns-server-option {
                         description "Enables the recursive DNS server option";
                         type empty;
                       }
                       leaf no-enable-recursive-dns-server-option {
                         description "Don't enables the recursive DNS server option";
                         type empty;
                       }
                     }
                   }
                 }
                 leaf update-server {
                   description "Propagate TCP/IP settings to DHCP server";
                   type empty;
                 }
               }
               container rpf-check {
                 presence "enable rpf-check";
                 description "Enable reverse-path-forwarding checks on this interface";
                 uses apply-advanced;
                 leaf fail-filter {
                   description "Name of filter applied to packets failing RPF check";
                   type string;
                 }
                 container mode {
                   description "Mode for reverse path forwarding";
                   leaf loose {
                     description "Reverse-path-forwarding loose mode";
                     type empty;
                   }
                 }
               }
               container accounting {
                 description "Interface-based accounting options";
                 uses apply-advanced;
                 container source-class-usage {
                   uses apply-advanced;
                   leaf input {
                     description "Interface for source-class-usage input";
                     type empty;
                   }
                   leaf output {
                     description "Interface for source-class-usage output";
                     type empty;
                   }
                 }
                 leaf destination-class-usage {
                   description "Enable destination class usage on this interface";
                   type empty;
                 }
               }
               leaf mtu {
                 description "Protocol family maximum transmission unit";
                 type union {
                   type uint32;
                   type string {
                     pattern "<.*>|$.*";
                   }
                 }
               }
               leaf tcp-mss {
                 description "Protocol family tcp maximum segment size";
                 type union {
                   type string {
                     pattern "<.*>|$.*";
                   }
                   type uint32 {
                     range "1 .. 65535";
                   }
                 }
               }
               leaf nd6-stale-time {
                 description "Stale time to reconfirm reachability with inet6 neighbour";
                 units "seconds";
                 type union {
                   type string {
                     pattern "<.*>|$.*";
                   }
                   type uint32 {
                     range "1 .. 18000";
                   }
                 }
               }
               leaf no-neighbor-learn {
                 description "Disable neighbor address learning on interface";
                 type empty;
               }
               leaf slaac-enable {
                 description "Enable slaac on management interface";
                 type empty;
               }
               container ndp-proxy {
                 description "Enable ndp proxy on interface";
                 uses apply-advanced;
                 leaf interface-restricted {
                   description "Enable ndp interface proxy restricted to interface";
                   type empty;
                 }
                 leaf interface-unrestricted {
                   description "Enable ndp interface proxy unrestricted to interface";
                   type empty;
                 }
               }
               container dad-proxy {
                 description "DAD proxy on interface";
                 uses apply-advanced;
                 leaf interface-restricted {
                   description "Enable DAD interface proxy restricted to interface";
                   type empty;
                 }
                 leaf interface-unrestricted {
                   description "Enable DAD interface proxy unrestricted to interface";
                   type empty;
                 }
               }
               leaf nd6-max-cache {
                 description "Max interface ND nexthop cache size";
                 type union {
                   type string {
                     pattern "<.*>|$.*";
                   }
                   type uint32 {
                     range "1 .. 2000000";
                   }
                 }
               }
               leaf nd6-new-hold-limit {
                 description "Max no. of new unresolved nexthops";
                 type union {
                   type string {
                     pattern "<.*>|$.*";
                   }
                   type uint32 {
                     range "1 .. 2000000";
                   }
                 }
               }
               leaf no-redirects {
                 description "Do not redirect traffic";
                 type empty;
               }
               leaf allow-filter-on-re {
                 description "Enable kernel filter on network ports";
                 type empty;
               }
               container filter {
                 description "Packet filtering";
                 uses apply-advanced;
                 choice input_choice {
                   case case_1 {
                     container input {
                       description "Filter to be applied to received packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 choice output_choice {
                   case case_1 {
                     container output {
                       description "Filter to be applied to transmitted packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 leaf-list input-chain {
                   ordered-by user;
                   description "List of filter modules applied to received packets ";
                   type string;
                 }
                 leaf-list output-chain {
                   ordered-by user;
                   description "List of filter modules applied to transmitted packets ";
                   type string;
                 }
                 container adf {
                   description "Ascend Data Filter definition";
                   uses apply-advanced;
                   list rule {
                     key name;
                     ordered-by user;
                     description "Set of ADF rules";
                     leaf name {
                       description "Value for a single rule";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32;
                   }
                 }
                 leaf dialer {
                   description "Name of filter applied on dialer";
                   type string;
                 }
               }
               container ingress-queuing-filter {
                 description "Protocol family ingress-queuing-filter";
                 leaf filter-name {
                   description "Name of the ingress-queuing-filter";
                   type string;
                 }
               }
               leaf input-hierarchical-policer {
                 description "Hierarchical policer for received packets";
                 type string;
               }
               container policer {
                 description "Interface policing";
                 uses apply-advanced;
                 leaf input {
                   description "Name of policer applied to received packets";
                   type string;
                 }
                 leaf output {
                   description "Name of policer applied to transmitted packets";
                   type string;
                 }
               }
               container sampling {
                 description "Interface sampling";
                 uses apply-advanced;
                 leaf input {
                   description "Sample all packets input on this interface";
                   type empty;
                 }
                 leaf output {
                   description "Sample all packets output on this interface";
                   type empty;
                 }
               }
               container service {
                 description "Service operations";
                 uses apply-advanced;
                 container input {
                   description "Service sets to consider for received packets";
                   uses apply-advanced;
                   list service-set {
                     key name;
                     ordered-by user;
                     description "Service set to consider for received packets";
                     leaf name {
                       description "Name of service set";
                       type string {
                       }
                     }
                     uses apply-advanced;
                     leaf service-filter {
                       description "Name of service filter";
                       type string;
                     }
                   }
                   leaf post-service-filter {
                     description "Post-service filter to apply to received packets";
                     type string;
                   }
                 }
                 container output {
                   description "Service sets to consider for transmitted packets";
                   uses apply-advanced;
                   list service-set {
                     key name;
                     ordered-by user;
                     description "Service set to consider for transmitted packets";
                     leaf name {
                       description "Name of service set";
                       type string {
                       }
                     }
                     uses apply-advanced;
                     leaf service-filter {
                       description "Name of service filter";
                       type string;
                     }
                   }
                 }
               }
               choice tunnel-termination-status {
                 case case_1 {
                   leaf tunnel-termination {
                     description "Tunnel termination";
                     type empty;
                   }
                 }
                 case case_2 {
                   leaf no-tunnel-termination {
                     description "No Tunnel termination";
                     type empty;
                   }
                 }
               }
               list address {
                 key name;
                 ordered-by user;
                 description "Interface address or destination prefix";
                 leaf name {
                   description "Interface address or destination prefix";
                   type jt:ipv6prefix;
                 }
                 uses apply-advanced;
                 leaf destination {
                   description "Destination address";
                   type jt:ipv6addr;
                 }
                 leaf eui-64 {
                   description "Generate EUI-64 interface ID";
                   type empty;
                 }
                 leaf primary {
                   description "Candidate for primary address in system";
                   type empty;
                 }
                 leaf preferred {
                   description "Preferred address on interface";
                   type empty;
                 }
                 leaf master-only {
                   description "Master management IP address for router";
                   type empty;
                 }
                 list ndp {
                   key name;
                   ordered-by user;
                   description "Static Neighbor Discovery Protocol  entries";
                   leaf name {
                     description "Destination IP address";
                     type jt:ipv6addr;
                   }
                   leaf l2-interface {
                     description "Layer 2 interface name for NDP entry";
                     type union {
                       type jt:interface-name;
                       type string {
                         pattern "<.*>|$.*";
                       }
                     }
                   }
                   choice mac_address_type {
                     case case_1 {
                       leaf mac {
                         description "MAC address";
                         type jt:mac-unicast;
                       }
                     }
                     case case_2 {
                       leaf multicast-mac {
                         description "Multicast MAC address";
                         type jt:mac-multicast;
                       }
                     }
                   }
                   leaf publish {
                     description "Reply to NDP requests for this entry";
                     type empty;
                   }
                 }
                 list vrrp-inet6-group {
                   key name;
                   ordered-by user;
                   description "VRRP group";
                   uses vrrp-group;
                 }
                 container web-authentication {
                   description "Parameters for web-based firewall-user authentication";
                   uses apply-advanced;
                   leaf http {
                     description "Enable authentication via HTTP";
                     type empty;
                   }
                   leaf https {
                     description "Enable authentication via HTTPS";
                     type empty;
                   }
                   leaf redirect-to-https {
                     description "Web authentication redirect to HTTPS";
                     type empty;
                   }
                 }
                 leaf virtual-gateway-address {
                   description "Virtual Gateway IP address";
                   type jt:ipv6addr;
                 }
                 leaf subnet-router-anycast {
                   description "Create a subnet roter anycast address for this address.";
                   type empty;
                 }
               }
               list demux-source {
                 key name;
                 ordered-by user;
                 description "Demux based on source prefix";
                 leaf name {
                   type string;
                 }
                 uses apply-advanced;
               }
               list demux-destination {
                 key name;
                 ordered-by user;
                 description "Demux based on destination prefix";
                 leaf name {
                   type string;
                 }
                 uses apply-advanced;
               }
               container unnumbered-address {
                 description "Unnumbered interface address/destination prefix";
                 leaf source {
                   description "Interface from which to take local address";
                   type union {
                     type jt:interface-unit;
                     type string {
                       pattern "<.*>|$.*";
                     }
                   }
                 }
                 leaf preferred-source-address {
                   description "Preferred address on the donor interface";
                   type string;
                 }
               }
               choice dad-disable-choice {
                 leaf dad-disable {
                   description "Disable duplicate-address-detection";
                   type empty;
                 }
                 leaf no-dad-disable {
                   description "Don't disable duplicate-address-detection";
                   type empty;
                 }
               }
               leaf destination-udp-port {
                 description "Choose destination UDP port number";
                 type union {
                   type string {
                     pattern "<.*>|$.*";
                   }
                   type uint32 {
                     range "10010 .. 10019";
                   }
                 }
               }
               container auto-configure {
                 description "Auto configuration";
                 uses dynamic_ipv6_type;
               }
               leaf negotiate-address {
                 description "Negotiate address with remote";
                 type empty;
               }
             }
             container mpls {
               presence "enable mpls";
               description "MPLS protocol parameters";
               uses apply-advanced;
               leaf mtu {
                 description "Protocol family maximum transmission unit";
                 type union {
                   type uint32;
                   type string {
                     pattern "<.*>|$.*";
                   }
                 }
               }
               leaf maximum-labels {
                 description "Protocol family maximum number of labels";
                 type union {
                   type string {
                     pattern "<.*>|$.*";
                   }
                   type uint32;
                 }
               }
               container filter {
                 description "Packet filtering";
                 uses apply-advanced;
                 choice input_choice {
                   case case_1 {
                     leaf input {
                       description "Name of filter applied to received packets";
                       type string;
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 choice output_choice {
                   case case_1 {
                     leaf output {
                       description "Name of filter applied to transmitted packets";
                       type string;
                     }
                   }
                   case case_2 {
                     leaf-list output-list {
                       ordered-by user;
                       description "List of filter modules applied to transmitted packets ";
                       type string;
                     }
                   }
                 }
                 leaf-list output-chain {
                   ordered-by user;
                   description "List of filter modules applied to transmitted packets ";
                   type string;
                 }
                 leaf group {
                   description "Interface group to which interface belongs";
                   type union {
                     type string {
                       pattern "<.*>|$.*";
                     }
                     type uint32 {
                       range "1 .. 255";
                     }
                   }
                 }
                 leaf dialer {
                   description "Name of filter applied on dialer";
                   type string;
                 }
               }
               container ingress-queuing-filter {
                 description "Protocol family ingress-queuing-filter";
                 leaf filter-name {
                   description "Name of the ingress-queuing-filter";
                   type string;
                 }
               }
               leaf input-hierarchical-policer {
                 description "Hierarchical policer for received packets";
                 type string;
               }
               container policer {
                 description "Interface policing";
                 uses apply-advanced;
                 leaf input {
                   description "Name of policer applied to received packets";
                   type string;
                 }
                 leaf output {
                   description "Name of policer applied to transmitted packets";
                   type string;
                 }
               }
               leaf destination-udp-port {
                 description "Choose destination UDP port number";
                 type union {
                   type string {
                     pattern "<.*>|$.*";
                   }
                   type uint32 {
                     range "10020 .. 10029";
                   }
                 }
               }
             }
             container mlppp {
               description "Multilink PPP protocol parameters";
               uses apply-advanced;
               leaf bundle {
                 description "Logical interface name this link will join";
                 type string;
               }
               choice anchor-points {
                 case case_1 {
                   leaf service-interface {
                     description "Services interface to use";
                     type union {
                       type jt:interface-device;
                       type string {
                         pattern "<.*>|$.*";
                       }
                     }
                   }
                 }
                 case case_2 {
                   leaf service-device-pool {
                     description "Service interface pool name to use";
                     type string {
                       length "1 .. 63";
                     }
                   }
                 }
               }
               leaf dynamic-profile {
                 description " dynamic profile for interface to use";
                 type string {
                   length "1 .. 80";
                 }
               }
             }
             container mlfr-end-to-end {
               presence "enable mlfr-end-to-end";
               description "Multilink Frame Relay end-to-end protocol parameters";
               uses apply-advanced;
               leaf bundle {
                 description "Logical interface name this link will join";
                 type union {
                   type jt:interface-unit;
                   type string {
                     pattern "<.*>|$.*";
                   }
                 }
               }
             }
             container mlfr-uni-nni {
               presence "enable mlfr-uni-nni";
               description "Multilink Frame Relay UNI NNI protocol parameters";
               uses apply-advanced;
               leaf bundle {
                 description "Logical interface name this link will join";
                 type union {
                   type jt:interface-unit;
                   type string {
                     pattern "<.*>|$.*";
                   }
                 }
               }
             }
             container ccc {
               presence "enable ccc";
               description "Circuit cross-connect parameters";
               uses apply-advanced;
               leaf mtu {
                 description "Protocol family maximum transmission unit";
                 type union {
                   type uint32;
                   type string {
                     pattern "<.*>|$.*";
                   }
                 }
               }
               container filter {
                 description "Packet filtering";
                 uses apply-advanced;
                 choice input_choice {
                   case case_1 {
                     leaf input {
                       description "Name of filter applied to received packets";
                       type string;
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 choice output_choice {
                   case case_1 {
                     leaf output {
                       description "Name of filter applied to transmitted packets";
                       type string;
                     }
                   }
                   case case_2 {
                     leaf-list output-list {
                       ordered-by user;
                       description "List of filter modules applied to transmitted packets ";
                       type string;
                     }
                   }
                 }
                 leaf-list output-chain {
                   ordered-by user;
                   description "List of filter modules applied to transmitted packets ";
                   type string;
                 }
                 leaf group {
                   description "Interface group to which interface belongs";
                   type union {
                     type string {
                       pattern "<.*>|$.*";
                     }
                     type uint32 {
                       range "1 .. 255";
                     }
                   }
                 }
               }
               container ingress-queuing-filter {
                 description "Protocol family ingress-queuing-filter";
                 leaf filter-name {
                   description "Name of the ingress-queuing-filter";
                   type string;
                 }
               }
               container policer {
                 description "Interface policing";
                 uses apply-advanced;
                 leaf input {
                   description "Name of policer applied to received packets";
                   type string;
                 }
                 leaf output {
                   description "Name of policer applied to transmitted packets";
                   type string;
                 }
               }
               leaf translate-fecn-and-becn {
                 description "Translate FECN and BECN bits";
                 type empty;
               }
               choice de-or-plp {
                 case case_1 {
                   leaf translate-discard-eligible {
                     description "Translate DE bit";
                     type empty;
                   }
                 }
                 case case_2 {
                   leaf translate-plp-control-word-de {
                     description "Translate PLP to/from Martini Control DE bit";
                     type empty;
                   }
                 }
               }
               leaf keep-address-and-control {
                 description "Don't strip PPP address and control bytes";
                 type empty;
               }
             }
             container tcc {
               presence "enable tcc";
               description "Translational cross-connect parameters";
               uses apply-advanced;
               container policer {
                 description "Interface policing";
                 uses apply-advanced;
                 leaf input {
                   description "Name of policer applied to received packets";
                   type string;
                 }
                 leaf output {
                   description "Name of policer applied to transmitted packets";
                   type string;
                 }
               }
               container proxy {
                 presence "enable proxy";
                 uses apply-advanced;
                 leaf inet-address {
                   description "Remote host address on non-Ethernet side of Ethernet TCC";
                   type jt:ipv4addr;
                 }
               }
               container remote {
                 presence "enable remote";
                 uses apply-advanced;
                 leaf inet-address {
                   description "Remote host address on Ethernet side of Ethernet TCC";
                   type jt:ipv4addr;
                 }
                 leaf mac-address {
                   description "Remote host MAC address on Ethernet side of Ethernet TCC";
                   type jt:mac-addr;
                 }
               }
               leaf-list protocols {
                 ordered-by user;
                 description "Protocols supported on TCC interface";
                 type enumeration {
                   enum "mpls" {
                     description "Multiprotocol Label Switching";
                   }
                   enum "inet" {
                     description "IP version 4";
                   }
                   enum "iso" {
                     description "International Organization for Standardization";
                   }
                   enum "inet6" {
                     description "IP version 6";
                   }
                 }
               }
             }
             container vpls {
               presence "enable vpls";
               description "Virtual private LAN service parameters";
               uses apply-advanced;
               leaf core-facing {
                 description "Interface is core facing";
                 type empty;
               }
               container filter {
                 description "Packet filtering";
                 uses apply-advanced;
                 choice input_choice {
                   case case_1 {
                     container input {
                       description "Filter to be applied to received packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 leaf-list output-chain {
                   ordered-by user;
                   description "List of filter modules applied to transmitted packets ";
                   type string;
                 }
                 choice output_choice {
                   case case_1 {
                     container output {
                       description "Filter to be applied to transmitted packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32 {
                       range "1 .. 255";
                     }
                   }
                 }
               }
               container ingress-queuing-filter {
                 description "Protocol family ingress-queuing-filter";
                 leaf filter-name {
                   description "Name of the ingress-queuing-filter";
                   type string;
                 }
               }
               container iq-policing-filter {
                 description "Protocol family ingress-queuing-policing-filter";
                 leaf filter-name {
                   description "Name of the ingress-queuing-policing-filter";
                   type string;
                 }
               }
               container policer {
                 description "Interface policing";
                 uses apply-advanced;
                 leaf input {
                   description "Name of policer applied to received packets";
                   type string;
                 }
                 leaf output {
                   description "Name of policer applied to transmitted packets";
                   type string;
                 }
               }
               container sampling {
                 description "Interface sampling";
                 uses apply-advanced;
                 leaf input {
                   description "Sample all packets input on this interface";
                   type empty;
                 }
                 leaf output {
                   description "Sample all packets output on this interface";
                   type empty;
                 }
               }
             }
             container bridge {
               presence "enable bridge";
               description "Layer-2 bridging parameters";
               uses apply-advanced;
               leaf core-facing {
                 description "Interface is core facing";
                 type empty;
               }
               container filter {
                 description "Packet filtering";
                 uses apply-advanced;
                 choice input_choice {
                   case case_1 {
                     container input {
                       description "Filter to be applied to received packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 leaf-list output-chain {
                   ordered-by user;
                   description "List of filter modules applied to transmitted packets ";
                   type string;
                 }
                 choice output_choice {
                   case case_1 {
                     container output {
                       description "Filter to be applied to transmitted packets";
                       leaf filter-name {
                         description "Name of the filter";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32 {
                       range "1 .. 255";
                     }
                   }
                 }
               }
               container ingress-queuing-filter {
                 description "Protocol family ingress-queuing-filter";
                 leaf filter-name {
                   description "Name of the ingress-queuing-filter";
                   type string;
                 }
               }
               container iq-policing-filter {
                 description "Protocol family ingress-queuing-policing-filter";
                 leaf filter-name {
                   description "Name of the ingress-queuing-policing-filter";
                   type string;
                 }
               }
               container policer {
                 description "Interface policing";
                 uses apply-advanced;
                 leaf input {
                   description "Name of policer applied to received packets";
                   type string;
                 }
                 leaf output {
                   description "Name of policer applied to transmitted packets";
                   type string;
                 }
               }
               leaf interface-mode {
                 description "Interface mode (access or trunk)";
                 type enumeration {
                   enum "access" {
                     description "Interface mode is access";
                   }
                   enum "trunk" {
                     description "Interface mode is trunk";
                   }
                 }
               }
               leaf vlan-auto-sense {
                 description "Enable VLAN auto sense on this interface";
                 type empty;
               }
               leaf bridge-domain-type {
                 description "Bridge domain type (svlan or bvlan)";
                 type enumeration {
                   enum "svlan" {
                     description "Bridge domain type svlan";
                   }
                   enum "bvlan" {
                     description "Bridge domain type bvlan";
                   }
                 }
               }
               leaf inter-switch-link {
                 description "PVLAN inter switch link";
                 type empty;
               }
               choice vlan_list {
                 case case_1 {
                   leaf vlan-id {
                     description "Access mode and trunk mode VLAN membership";
                     type union {
                       type string {
                         pattern "<.*>|$.*";
                       }
                       type uint32 {
                         range "1 .. 4094";
                       }
                     }
                   }
                 }
                 case case_2 {
                   leaf-list vlan-id-list {
                     description "Trunk mode VLAN membership for this interface";
                     type jt:vlan-range;
                   }
                 }
                 case case_3 {
                   leaf-list inner-vlan-id-list {
                     description "Trunk mode VLAN membership for this interface based on inner VLAN tag";
                     type jt:vlan-range;
                   }
                 }
               }
               container vlan-rewrite {
                 description "Specify vlan translation";
                 uses apply-advanced;
                 list translate {
                   key name;
                   ordered-by user;
                   description "Translate incoming VLAN tag";
                   leaf name {
                     description "Specify the incoming VLAN tag";
                     type union {
                       type string {
                         pattern "<.*>|$.*";
                       }
                       type uint32 {
                         range "1 .. 4094";
                       }
                     }
                   }
                   leaf to-vlan-id {
                     description "Specify the bridge-domain VLAN-ID";
                     type union {
                       type string {
                         pattern "<.*>|$.*";
                       }
                       type uint32 {
                         range "1 .. 4094";
                       }
                     }
                   }
                 }
               }
               choice isid_list {
                 case case_1 {
                   leaf isid-list {
                     description "Specify the ISID list";
                     type enumeration {
                       enum "all-service-groups" {
                         description "Map all ISIDs specified under the service-groups";
                       }
                       enum "all" {
                         description "Map all ISIDs";
                       }
                     }
                   }
                 }
               }
               container storm-control {
                 description "Storm control profile name to bind";
                 uses apply-advanced;
                 leaf profile-name {
                   description "Profile name";
                   type string;
                 }
               }
               container recovery-timeout {
                 description "Recovery timeout for this interface";
                 leaf time-in-seconds {
                   units "seconds";
                   type union {
                     type string {
                       pattern "<.*>|$.*";
                     }
                     type uint32 {
                       range "10 .. 3600";
                     }
                   }
                 }
               }
               container sampling {
                 description "Interface sampling";
                 uses apply-advanced;
                 leaf input {
                   description "Sample all packets input on this interface";
                   type empty;
                 }
                 leaf output {
                   description "Sample all packets output on this interface";
                   type empty;
                 }
               }
             }
             container ethernet-switching {
               description "Ethernet switching parameters";
               presence "enable ethernet-switching";
               uses ethernet-switching-type;
             }
             container fibre-channel {
               description "Fibre channel switching parameters";
               presence "enable fibre-channel";
               uses fibre-channel-type;
             }
             container pppoe {
               description "PPP over Ethernet underlying interface-specific options";
               presence "enable pppoe";
               uses pppoe_underlying_options_type;
             }
             container any {
               presence "enable any";
               description "Parameters for 'any' family";
               uses apply-advanced;
               container filter {
                 description "Layer 2 packet filtering";
                 uses apply-advanced;
                 leaf input {
                   description "Name of filter applied to received packets";
                   type string {
                   }
                 }
                 leaf group {
                   description "Group to which interface belongs";
                   type union {
                     type string {
                       pattern "<.*>|$.*";
                     }
                     type uint32 {
                       range "1 .. 255";
                     }
                   }
                 }
               }
             }
             uses apply-advanced;
           }
           leaf service-domain {
             description "Service domain to which interface belongs";
             type enumeration {
               enum "inside" {
                 description "Inside network";
               }
               enum "outside" {
                 description "Outside network";
               }
             }
           }
           leaf copy-tos-to-outer-ip-header {
             description "Copy IP payload header's ToS field to GRE delivery header";
             type empty;
           }
           leaf copy-tos-to-outer-ip-header-transit {
             description "Copy IP ToS field to GRE header for transit packets";
             type empty;
           }
           leaf force-control-packets-on-transit-path {
             description "Force control packets to follow transit path";
             type empty;
           }
           container load-balancing-options {
             description "AMS subunit load balancing options";
             uses apply-advanced;
             leaf preferred-active {
               description "Preferred active Interface name";
               type union {
                 type jt:interface-device;
                 type string {
                   pattern "<.*>|$.*";
                 }
               }
             }
             leaf disable-hash {
               description "Hash based distribution is not needed for this subunit";
               type empty;
             }
             leaf modulo-key {
               description "Modulo based distribution";
               type enumeration {
                 enum "source-ip" {
                   description "Source Ip Address";
                 }
                 enum "destination-ip" {
                   description "Destination Ip Address";
                 }
               }
             }
             container hash-keys {
               uses apply-advanced;
               leaf-list ingress-key {
                 ordered-by user;
                 description "Hash Key for the ingress direction";
                 type enumeration {
                   enum "source-ip" {
                     description "Source Ip Address";
                   }
                   enum "destination-ip" {
                     description "Destination Ip Address";
                   }
                   enum "protocol" {
                     description "Protocol";
                   }
                   enum "iif" {
                     description "Incoming Interface";
                   }
                 }
               }
               leaf-list egress-key {
                 ordered-by user;
                 description "Hash Key for the egress direction";
                 status deprecated;
                 type enumeration {
                   enum "source-ip" {
                     description "Source Ip Address";
                     status deprecated;
                   }
                   enum "destination-ip" {
                     description "Destination Ip Address";
                     status deprecated;
                   }
                   enum "protocol" {
                     description "Protocol";
                     status deprecated;
                   }
                   enum "oif" {
                     description "Outgoing Interface";
                     status deprecated;
                   }
                 }
               }
               leaf ipv6-source-prefix-length {
                 description "IPv6 source prefix length for hash computation";
                 type enumeration {
                   enum "56" {
                     description "56 bit IPv6 address prefix";
                   }
                   enum "64" {
                     description "64 bit IPv6 address prefix";
                   }
                   enum "96" {
                     description "96 bit IPv6 address prefix";
                   }
                   enum "128" {
                     description "Complete 128 bit IPv6 address";
                   }
                 }
               }
             }
           }
           container interface-state {
             description "IRB interface state computation";
             uses apply-advanced;
             choice state {
               case case_1 {
                 leaf local {
                   description "IRB State computation based on local interface state";
                   type empty;
                 }
               }
               case case_2 {
                 leaf remote {
                   description "IRB State computation based on remote reachability";
                   type empty;
                 }
               }
               case case_3 {
                 leaf local-remote {
                   description "IRB State computation based on local or remote reachability";
                   type empty;
                 }
               }
               case case_4 {
                 leaf local-interface {
                   description "IRB State computation based on loopback AE port state";
                   type union {
                     type jt:interface-name;
                     type string {
                       pattern "<.*>|$.*";
                     }
                   }
                 }
               }
             }
             leaf local-count {
               description "Minimum number of local layer2 link in up state to consider IRB up";
               type union {
                 type uint16;
                 type string {
                   pattern "<.*>|$.*";
                 }
               }
             }
             leaf vtep-count {
               description "Minimum number of VTEP link in up state to consider IRB up";
               type union {
                 type uint16;
                 type string {
                   pattern "<.*>|$.*";
                 }
               }
             }
             container hold-time {
               description "Delay before marking interface up or down for defect";
               uses apply-advanced;
               leaf up {
                 description "Delay in seconds before marking IRB interface up";
                 units "seconds";
                 type union {
                   type uint32;
                   type string {
                     pattern "<.*>|$.*";
                   }
                 }
               }
               leaf down {
                 description "Delay in seconds before marking IRB interface down";
                 units "seconds";
                 type union {
                   type uint32;
                   type string {
                     pattern "<.*>|$.*";
                   }
                 }
               }
             }
           }
           leaf mac {
             description "Configure logical interface MAC address";
             type jt:mac-unicast;
           }
           leaf virtual-gateway-v4-mac {
             description "Configure virtual gateway IPV4 virtual MAC address";
             type jt:mac-unicast;
           }
           leaf virtual-gateway-v6-mac {
             description "Configure virtual gateway IPV6 virtual MAC address";
             type jt:mac-unicast;
           }
           leaf no-dhcp-flood {
             description "Disable dhcp flooding";
             type empty;
           }
           container forwarding-options {
             description "Aggregated Ethernet interface forwarding-options";
             uses apply-advanced;
             container load-balance-stateful {
               description "Stateful load balancing";
               uses apply-advanced;
               leaf per-flow {
                 description "Enable feature";
                 type empty;
               }
               leaf rebalance {
                 description "Rebalancing interval";
                 units "per minute";
                 type union {
                   type string {
                     pattern "<.*>|$.*";
                   }
                   type uint32 {
                     range "1 .. 1000";
                   }
                 }
               }
               leaf load-type {
                 description "Load - defines the flows";
                 type enumeration {
                   enum "high" {
                     description "If the no of flows on this aggregate is large(1000-10000 flows) ";
                   }
                   enum "medium" {
                     description "If the no of flows on this aggregate is moderate(100-1000 flows)";
                   }
                   enum "low" {
                     description "If the no of flows on this aggregate is less(1-100)";
                   }
                 }
               }
             }
           }
           leaf etree-ac-role {
             description "ETREE attachment circuit role";
             type enumeration {
               enum "root" {
                 description "ETREE root interface";
               }
               enum "leaf" {
                 description "ETREE leaf interface";
               }
             }
           }
           container load-balance {
             description "Load-balance weight per subscriber interface";
             uses apply-advanced;
             leaf weight {
               description "Load-balance weight";
               type union {
                 type string {
                   pattern "<.*>|$.*";
                 }
                 type uint32 {
                   range "1 .. 1000";
                 }
               }
             }
           }
           container explicit-proxy {
             presence "enable explicit-proxy";
             description "Attach explicit proxy profiles";
             uses apply-advanced;
             leaf-list profile {
               description "Explicit proxy profile name";
               type string {
                 length "1 .. 63";
               }
             }
           }
           container dialer-options {
             presence "enable dialer-options";
             description "Dialer options";
             uses apply-advanced;
             leaf pool {
               description "Dialer pool";
               type string {
                 length "1 .. 64";
               }
             }
             leaf-list route {
               ordered-by user;
               description "Route on dialer";
               type jt:ipprefix;
             }
             leaf always-on {
               description "Always keep on-line";
               type empty;
             }
             leaf-list dial-string {
               ordered-by user;
               description "String to dial out";
               type string {
                 length "1 .. 63";
               }
               max-elements 15;
             }
             container incoming-map {
               description "Map incoming call to dialer";
               uses apply-advanced;
               choice caller-type {
                 case case_1 {
                   list caller {
                     key name;
                     ordered-by user;
                     description "Caller Id to be screened";
                     max-elements 300;
                     leaf name {
                       description "Caller ID (upto 15 digits)";
                       type string {
                       }
                     }
                   }
                 }
                 case case_2 {
                   leaf accept-all {
                     description "Accept all incoming calls";
                     type empty;
                   }
                 }
               }
             }
             leaf callback {
               description "Call back on any incoming call to the dialer";
               type empty;
             }
             leaf callback-wait-period {
               description "Time to wait before calling back";
               units "seconds";
               type union {
                 type string {
                   pattern "<.*>|$.*";
                 }
                 type uint32 {
                   range "2 .. 255";
                 }
               }
             }
             leaf redial-delay {
               description "Time to wait before redialing";
               units "seconds";
               type union {
                 type string {
                   pattern "<.*>|$.*";
                 }
                 type uint32 {
                   range "2 .. 255";
                 }
               }
             }
             leaf self-recover-time {
               description "Sub-interface self-recover time";
               units "seconds";
               type union {
                 type string {
                   pattern "<.*>|$.*";
                 }
                 type uint32 {
                   range "2 .. 120";
                 }
               }
             }
             leaf idle-timeout {
               description "Delay before taking down the interface";
               default "120";
               units "seconds";
               type union {
                 type string {
                   pattern "<.*>|$.*";
                 }
                 type uint32 {
                   range "0 .. 4294967295";
                 }
               }
             }
             list watch-list {
               key name;
               description "Dialer watch list";
               leaf name {
                 description "Address prefix";
                 type jt:ipprefix-only;
               }
               uses apply-advanced;
             }
             leaf load-threshold {
               description "Load threshold for adding interfaces";
               type union {
                 type string {
                   pattern "<.*>|$.*";
                 }
                 type uint32 {
                   range "0 .. 100";
                 }
               }
             }
             leaf load-interval {
               description "Interval used to calculate average load";
               units "seconds";
               type union {
                 type string {
                   pattern "<.*>|$.*";
                 }
                 type uint32 {
                   range "20 .. 180";
                 }
               }
             }
             leaf activation-delay {
               description "Activation delay";
               units "seconds";
               type union {
                 type string {
                   pattern "<.*>|$.*";
                 }
                 type uint32 {
                   range "1 .. 4294967295";
                 }
               }
             }
             leaf deactivation-delay {
               description "Deactivation delay";
               units "seconds";
               type union {
                 type string {
                   pattern "<.*>|$.*";
                 }
                 type uint32 {
                   range "1 .. 4294967295";
                 }
               }
             }
             leaf initial-route-check {
               description "Delay to check primary after the router is up";
               default "120";
               units "seconds";
               type union {
                 type string {
                   pattern "<.*>|$.*";
                 }
                 type uint16 {
                   range "1 .. 300";
                 }
               }
             }
           }
           container backup-options {
             description "Backup interface configuration options";
             uses apply-advanced;
             leaf interface {
               description "Backup interface";
               type union {
                 type jt:interface-name;
                 type string {
                   pattern "<.*>|$.*";
                 }
               }
             }
           }
         }
         container no-partition {
           description "Use channelizable interface as clear channel";
           leaf interface-type {
             description "Interface type";
             type enumeration {
               enum "e1" {
                 description "E1 interface";
               }
               enum "t1" {
                 description "T1 interface";
               }
               enum "at" {
                 description "ATM interface";
               }
               enum "t3" {
                 description "T3 interface";
               }
               enum "e3" {
                 description "E3 interface";
               }
               enum "ct3" {
                 description "Channelized T3 interface";
               }
               enum "so" {
                 description "SONET interface";
               }
               enum "cau4" {
                 description "CAU4 interface";
               }
             }
           }
         }
         list partition {
           key name;
           ordered-by user;
           description "Channelized interface partition";
           leaf name {
             description "Sublevel interface partition index (for example, 1, 3-4)";
             type string;
           }
           leaf oc-slice {
             description "Range of SONET/SDH slices (for example, 1, 7-9)";
             type string;
           }
           leaf timeslots {
             description "Timeslots [(1..24) for T1, (1..31) for E1]; for example, 1-3,4,9,22-24 (no spaces)";
             type string;
           }
           leaf interface-type {
             description "Sublevel interface type";
             type enumeration {
               enum "ds" {
                 description "DS0 interface";
               }
               enum "e1" {
                 description "E1 interface";
               }
               enum "t1" {
                 description "T1 interface";
               }
               enum "at" {
                 description "ATM interface";
               }
               enum "ct1" {
                 description "Channelized T1 interface";
               }
               enum "ce1" {
                 description "Channelized E1 interface";
               }
               enum "t3" {
                 description "T3 interface";
               }
               enum "ct3" {
                 description "Channelized T3 interface";
               }
               enum "e3" {
                 description "E3 interface";
               }
               enum "so" {
                 description "SONET interface";
               }
               enum "coc1" {
                 description "Channelized OC1 interface";
               }
               enum "cau4" {
                 description "Channelized AU4 interface";
               }
               enum "dc" {
                 description "D channel interface";
               }
               enum "bc" {
                 description "B channel interface";
               }
             }
           }
         }
         container radius-options {
           description "Interface RADIUS Options";
           uses radius_options_vlan_type;
         }
         leaf rpf-stats {
           description "Enable Reverse path forwarding stats for this interface";
           type empty;
         }
         container redundant-pseudo-interface-options {
           description "Pseudo interface redundancy options";
           uses apply-advanced;
           leaf redundancy-group {
             description "Redundancy group of this interface";
             type union {
               type string {
                 pattern "<.*>|$.*";
               }
               type uint16 {
                 range "0 .. 255";
               }
             }
           }
         }
         container modem-options {
           description "MODEM interface-specific options";
           uses apply-advanced;
           leaf init-command-string {
             description "AT command string to initialize modem";
             type string {
               length "1 .. 127";
             }
           }
           leaf dialin {
             default "console";
             type enumeration {
               enum "console" {
                 description "Management console access";
               }
               enum "routable" {
                 description "Routable access";
               }
             }
           }
         }
         leaf act-sim {
           description "Default SIM slot to connect LTE network";
           type union {
             type string {
               pattern "<.*>|$.*";
             }
             type uint32;
           }
         }
         container cellular-options {
           presence "enable cellular-options";
           description "Cellular interface specific options";
           uses apply-advanced;
           list sim {
             key name;
             description "SIM slot to connect LTE network";
             leaf name {
               description "SIM slot number";
               type union {
                 type string {
                   pattern "<.*>|$.*";
                 }
                 type uint32;
               }
             }
             uses apply-advanced;
             container select-profile {
               description "Profile to be applied";
               leaf profile-id {
                 description "Profile to be used for data calls";
                 type union {
                   type string {
                     pattern "<.*>|$.*";
                   }
                   type uint32 {
                     range "1 .. 16";
                   }
                 }
               }
             }
             container radio-access {
               description "Select radio access technology";
               choice rat-value {
                 case case_1 {
                   leaf automatic {
                     description "Automatically selects radio access type";
                     type empty;
                   }
                 }
                 case case_2 {
                   leaf umts-3g-only {
                     description "3G only";
                     type empty;
                   }
                 }
                 case case_3 {
                   leaf umts-3g-preferred {
                     description "UMTS 3G Preferred";
                     type empty;
                   }
                 }
                 case case_4 {
                   leaf lte-only {
                     description "Only LTE";
                     type empty;
                   }
                 }
                 case case_5 {
                   leaf lte-preferred {
                     description "LTE Preferred";
                     type empty;
                   }
                 }
               }
             }
             leaf encrypted-sim-unlock-code {
               description "Encrypted PIN";
               type jt:unreadable;
             }
             leaf gateway {
               description "Set customer gateway for LTE network";
               type jt:ipprefix;
             }
           }
         }
         container isdn-options {
           description "ISDN interface-specific options";
           uses apply-advanced;
           leaf switch-type {
             description "ISDN switch type";
             type enumeration {
               enum "ni1" {
                 description "NI1 BRI variant";
               }
               enum "etsi" {
                 description "ETSI variant";
               }
               enum "att5e" {
                 description "ATT5E variant";
               }
               enum "ntdms100" {
                 description "NTDMS100 variant";
               }
               enum "ntt" {
                 description "INS NET (NTT) PRI/BRI variant";
               }
               enum "ni2" {
                 description "NI2 PRI variant";
               }
             }
           }
           leaf media-type {
             description "IDSN media type - voice, data or both";
             default "data";
             type enumeration {
               enum "data" {
                 description "Data";
               }
               enum "voice" {
                 description "Voice";
               }
               enum "combined" {
                 description "Combined";
               }
             }
           }
           leaf spid1 {
             description "Service profile identifier";
             type string {
               length "1 .. 20";
             }
           }
           leaf spid2 {
             description "Additional service profile identifier";
             type string {
               length "1 .. 20";
             }
           }
           leaf calling-number {
             description "Calling number included in outgoing calls";
             type string {
             }
           }
           list incoming-called-number {
             key name;
             ordered-by user;
             description "Incoming called number to be screened";
             max-elements 30;
             leaf name {
               description "Number called (upto 15 digits)";
               type string {
               }
             }
             leaf reject {
               description "Reject the called number";
               type empty;
             }
           }
           leaf tei-option {
             description "ISDN terminal endpoint identifier negotiation options";
             type enumeration {
               enum "first-call" {
                 description "Terminal endpoint identifier negotiation during first call";
               }
               enum "power-up" {
                 description "Terminal endpoint identifier negotiation during power-up";
               }
             }
           }
           leaf static-tei-val {
             description "Static TEI value";
             type union {
               type string {
                 pattern "<.*>|$.*";
               }
               type uint32 {
                 range "0 .. 63";
               }
             }
           }
           leaf t310 {
             description "Timer T310 value";
             units "seconds";
             type union {
               type string {
                 pattern "<.*>|$.*";
               }
               type uint32 {
                 range "1 .. 65536";
               }
             }
           }
           leaf bchannel-allocation {
             description "Allocate PRI dialout b-channel in ascending/descending order";
             default "descending";
             type enumeration {
               enum "ascending" {
                 description "Allocate b-channel in ascending order";
               }
               enum "descending" {
                 description "Allocate b-channel in descending order";
               }
             }
           }
         }
         container dialer-options {
           presence "enable dialer-options";
           description "Dialer options";
           uses apply-advanced;
           list pool {
             key name;
             description "Dialer pool";
             max-elements 30;
             leaf name {
               description "Dialer pool identifier";
               type string {
                 length "1 .. 64";
               }
             }
             leaf priority {
               description "Dialer pool priority";
               type union {
                 type string {
                   pattern "<.*>|$.*";
                 }
                 type uint32 {
                   range "1 .. 255";
                 }
               }
             }
           }
         }
       }
       list interface {
         key name;
         uses interfaces_type;
       }
     }
     list logical-systems {
       key name;
       ordered-by user;
       description "Logical systems";
       leaf name {
         description "Logical system name";
         type string {
         }
       }
       uses apply-advanced;
       container interfaces {
         description "Interface configuration";
         uses apply-advanced;
         list pic-set {
           key name;
           ordered-by user;
           description "NP bundling configuration";
           leaf name {
             description "Pic set name";
             type string {
               length "1 .. 127";
             }
           }
           uses apply-advanced;
           list interface {
             key name;
             ordered-by user;
             description "One or more interfaces that use this picset";
             leaf name {
               description "Interface name";
               type string {
                 length "1 .. 127";
               }
             }
             uses apply-advanced;
           }
           list fpc {
             key name;
             ordered-by user;
             leaf name {
               description "FPC slot number";
               type union {
                 type string {
                   pattern "<.*>|$.*";
                 }
                 type uint32;
               }
             }
             uses apply-advanced;
             list pic {
               key name;
               ordered-by user;
               description "Physical Interface Card number";
               leaf name {
                 description "PIC slot number";
                 type union {
                   type string {
                     pattern "<.*>|$.*";
                   }
                   type uint32;
                 }
               }
               uses apply-advanced;
             }
           }
         }
         list interface-set {
           key name;
           description "Logical interface set configuration";
           leaf name {
             type string;
           }
           uses apply-advanced;
           container load-balance {
             description "Load-balance weight per subscriber interface-set";
             uses apply-advanced;
             leaf weight {
               description "Load-balance weight";
               type union {
                 type string {
                   pattern "<.*>|$.*";
                 }
                 type uint32 {
                   range "1 .. 1000";
                 }
               }
             }
           }
           leaf targeted-distribution {
             description "Interface participates in targeted-distribution";
             type empty;
           }
           container targeted-options {
             presence "enable targeted-options";
             description "Targeting specific options";
             uses apply-advanced;
             leaf weight {
               description "Targeting weight for interface set";
               type string;
             }
           }
           list interface {
             key name;
             description "One or more interfaces that belong to interface set";
             leaf name {
               description "Interface name";
               type union {
                 type jt:interface-device;
                 type string {
                   pattern "<.*>|$.*";
                 }
               }
             }
             uses apply-advanced;
             list unit {
               key name;
               description "One or more logical interface unit numbers";
               leaf name {
                 description "Unit number";
                 type union {
                   type string {
                     pattern "<.*>|$.*";
                   }
                   type uint32 {
                     range "0 .. 1073741823";
                   }
                 }
               }
               uses apply-advanced;
             }
             list vlan-tags-outer {
               key name;
               description "One or more outer VLAN tags";
               leaf name {
                 description "VLAN tag ID";
                 type union {
                   type string {
                     pattern "<.*>|$.*";
                   }
                   type uint32 {
                     range "0 .. 4094";
                   }
                 }
               }
               uses apply-advanced;
             }
           }
           container pppoe-underlying-options {
             description "PPP over Ethernet underlying interface-specific options";
             uses pppoe_underlying_options_type;
           }
         }
         container stacked-interface-set {
           presence "enable stacked-interface-set";
           description "Stacked interface set configuration";
           uses apply-advanced;
           list interface-set {
             key name;
             ordered-by user;
             description "Stacked parent interface set configuration";
             leaf name {
               type string;
             }
             uses apply-advanced;
             list interface-set {
               key name;
               ordered-by user;
               description "Stacked child interface set configuration";
               leaf name {
                 type string;
               }
               uses apply-advanced;
             }
           }
         }
         container traceoptions {
           description "Interface trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             description "Tracing parameters";
             leaf name {
               type enumeration {
                 enum "all" {
                   description "Enable all configuration logging";
                 }
                 enum "kernel" {
                   description "Log configuration IPC messages to kernel";
                 }
                 enum "change-events" {
                   description "Log changes that produce configuration events";
                 }
                 enum "kernel-detail" {
                   description "Log details of configuration messages to kernel";
                 }
                 enum "config-states" {
                   description "Log the configuration state machine changes";
                 }
                 enum "resource-usage" {
                   description "Log the resource usage for different states";
                 }
                 enum "gres-events" {
                   description "Log the events related to GRES ";
                 }
                 enum "select-events" {
                   description "Log the events on select state machine ";
                 }
                 enum "bfd-events" {
                   description "Log BFD related events";
                 }
                 enum "lib-events" {
                   description "Log DCD library related events";
                 }
                 enum "reserved" {
                   description "Reserved DCD logs";
                 }
                 enum "emergency" {
                   description "Log DCD emergency events";
                 }
                 enum "alert" {
                   description "Log DCD alert events";
                 }
                 enum "critical" {
                   description "Log DCD critical events";
                 }
                 enum "error" {
                   description "Log DCD error events";
                 }
                 enum "warning" {
                   description "Log DCD warning events";
                 }
                 enum "notice" {
                   description "Log DCD notification events";
                 }
                 enum "informational" {
                   description "Log DCD informations";
                 }
                 enum "debugging" {
                   description "Log DCD debug events";
                 }
                 enum "verbose" {
                   description "Log DCD debug all events";
                 }
                 enum "japi" {
                   description "Log DCD JAPI events";
                 }
               }
             }
             leaf disable {
               description "Disable this trace flag";
               type empty;
             }
           }
         }
         list interface-range {
           key name;
           ordered-by user;
           description "Interface ranges configuration";
           leaf name {
             description "Interface-range name";
             type string {
               length "1 .. 128";
             }
           }
           list member {
             key name;
             ordered-by user;
             description "Interfaces belonging to the interface range";
             leaf name {
               description "Member interface name";
               type union {
                 type jt:interface-range-wild;
                 type string {
                   pattern "<.*>|$.*";
                 }
               }
             }
             uses apply-advanced;
           }
           list member-range {
             key name;
             ordered-by user;
             description "Interfaces range in <start-range> to <end-range> format";
             leaf name {
               type union {
                 type jt:interface-device;
                 type string {
                   pattern "<.*>|$.*";
                 }
               }
             }
             leaf end-range {
               type union {
                 type jt:interface-device;
                 type string {
                   pattern "<.*>|$.*";
                 }
               }
             }
           }
           uses apply-advanced;
           leaf description {
             description "Text description of interface";
             type string;
           }
           leaf external-model-name {
             description "Name for interface as configured using 3rd-party model";
             type string;
           }
           container management-ethernet-redundancy {
             presence "enable management-ethernet-redundancy";
             description "Management Interface Redundancy";
             uses apply-advanced;
             choice enable_choice {
               case case_1 {
                 leaf redundancy-enable {
                   description "Enable Managment Ethernet Redundancy";
                   type empty;
                 }
               }
               case case_2 {
                 leaf redundancy-disable {
                   description "Disable  Managment Ethernet Redundancy";
                   type empty;
                 }
               }
             }
             leaf connectivity-test-interval {
               description "Connectivity test interval";
               default "5";
               units "seconds";
               type union {
                 type string {
                   pattern "<.*>|$.*";
                 }
                 type uint32 {
                   range "1 .. 10";
                 }
               }
             }
             leaf connectivity-test-response-interval {
               description "Connectivity test response wait time";
               default "5";
               units "seconds";
               type union {
                 type string {
                   pattern "<.*>|$.*";
                 }
                 type uint32 {
                   range "1 .. 10";
                 }
               }
             }
             leaf remote-ipv4-address {
               description "Destination IPV4 address to reach remote ";
               default "nil";
               type jt:ipv4addr;
             }
             leaf remote-ipv6-address {
               description "Destination IPV6 address to reach remote";
               default "nil";
               type jt:ipv6addr;
             }
             leaf number-of-connectivity-retries {
               description "Number of Connectivity retries ";
               default "2";
               type union {
                 type string {
                   pattern "<.*>|$.*";
                 }
                 type uint32 {
                   range "1 .. 8";
                 }
               }
             }
           }
           leaf metadata {
             description "Text metadata attached to interface";
             type string;
           }
           choice enable-disable {
             case case_1 {
               leaf disable {
                 description "Disable this interface";
                 type empty;
               }
             }
           }
           leaf promiscuous-mode {
             description "Enable promiscuous mode for L3 interface";
             type empty;
           }
           leaf port-mirror-instance {
             description "Port-mirror the packet to specified instance";
             type string {
               length "1 .. 64";
             }
           }
           leaf multicast-statistics {
             description "Enable multicast statistics";
             type empty;
           }
           leaf oam-on-svlan {
             description "Propagate SVLAN OAM state to CVLANs";
             type empty;
           }
           container fabric-options {
             description "Fabric interface specific options";
             uses apply-advanced;
             list member-interfaces {
               key name;
               description "Member interface for the fabric interface";
               leaf name {
                 description "Interface name of member";
                 type union {
                   type jt:interface-device;
                   type string {
                     pattern "<.*>|$.*";
                   }
                 }
               }
               uses apply-advanced;
             }
             container remote-chassis {
               presence "enable remote-chassis";
               description "Remote chassis reachability";
               uses apply-advanced;
               leaf destination {
                 description "Destination IP address to reach remote chassis";
                 type jt:ipv4addr;
               }
             }
           }
           container traceoptions {
             presence "enable traceoptions";
             description "Interface trace options";
             uses apply-advanced;
             list flag {
               key name;
               ordered-by user;
               description "Tracing parameters";
               leaf name {
                 type enumeration {
                   enum "ipc" {
                     description "Trace interface IPC messages";
                   }
                   enum "event" {
                     description "Trace interface events";
                   }
                   enum "media" {
                     description "Trace interface media changes";
                   }
                   enum "all" {
                     description "Enable all interface trace flags";
                   }
                   enum "q921" {
                     description "Trace ISDN Q.921 frames";
                   }
                   enum "q931" {
                     description "Trace ISDN Q.931 frames";
                   }
                 }
               }
             }
             container file {
               presence "enable file";
               description "Trace file information for ISDN decoded frames";
               uses apply-advanced;
               leaf filename {
                 description "Name of file in which to write trace information";
                 type string {
                   length "1 .. 1024";
                 }
               }
               leaf size {
                 description "Maximum trace file size";
                 default "128k";
                 type string;
               }
               leaf files {
                 description "Maximum number of trace files";
                 default "10";
                 type union {
                   type uint32;
                   type string {
                     pattern "<.*>|$.*";
                   }
                 }
               }
               choice world-readable-choice {
                 leaf world-readable {
                   description "Allow any user to read the log file";
                   type empty;
                 }
                 leaf no-world-readable {
                   description "Don't allow any user to read the log file";
                   type empty;
                 }
               }
             }
           }
           leaf passive-monitor-mode {
             description "Use interface to tap packets from another router";
             type empty;
           }
           choice keepalive_choices {
             case case_1 {
               container keepalives {
                 description "Send or demand keepalive messages";
                 presence "enable keepalives";
                 uses keepalives_type;
               }
             }
             case case_2 {
               leaf no-keepalives {
                 description "Do not send keepalive messages";
                 type empty;
               }
             }
           }
           choice traps-choice {
             leaf traps {
               description "Enable SNMP notifications on state changes";
               type empty;
             }
             leaf no-traps {
               description "Don't enable SNMP notifications on state changes";
               type empty;
             }
           }
           choice interface-mib-choice {
             leaf interface-mib {
               description "Enable interface-related MIBs";
               type empty;
             }
             leaf no-interface-mib {
               description "Don't enable interface-related MIBs";
               type empty;
             }
           }
           leaf accounting-profile {
             description "Accounting profile name";
             type string;
           }
           container anchor-point {
             description "Anchor point";
             uses apply-advanced;
             leaf interface-name {
               description "Interface name";
               type union {
                 type jt:interface-device;
                 type string {
                   pattern "<.*>|$.*";
                 }
               }
             }
           }
           container targeted-options {
             description "Targeting specific options for PS/RLT active-active mode";
             uses apply-advanced;
             leaf type {
               description "Targeting type of PS";
               type enumeration {
                 enum "manual" {
                   description "Targeting type is Manual";
                 }
               }
             }
             choice redundancy_choice {
               case case_1 {
                 leaf logical-interface-fpc-redundancy {
                   description "Enable FPC redundancy for logical interfaces";
                   type empty;
                 }
               }
               case case_2 {
                 leaf logical-interface-chassis-redundancy {
                   description "Enable CHASSIS redundancy for logical interfaces";
                   type empty;
                 }
               }
             }
             container rebalance-periodic {
               presence "enable rebalance-periodic";
               uses apply-advanced;
               leaf start-time {
                 description "Start time of the rebalance operation ( Wall clock time )";
                 type jt:time-of-day;
               }
               leaf interval {
                 description "Interval of the rebalance operation in hrs";
                 type union {
                   type string {
                     pattern "<.*>|$.*";
                   }
                   type uint32 {
                     range "1 .. 24";
                   }
                 }
               }
             }
             leaf rebalance-subscriber-granularity {
               description "Max subscriber aggregate weight";
               type union {
                 type string {
                   pattern "<.*>|$.*";
                 }
                 type uint32 {
                   range "1 .. 65535";
                 }
               }
             }
           }
           choice bypass-queueing-chip-choice {
             leaf bypass-queueing-chip {
               description "Enable to bypass queueing chip";
               type empty;
             }
             leaf no-bypass-queueing-chip {
               description "Don't enable to bypass queueing chip";
               type empty;
             }
           }
           choice scheduler_type {
             case case_1 {
               choice per-unit-scheduler-choice {
                 leaf per-unit-scheduler {
                   description "Enable subunit queuing on Frame Relay or VLAN IQ interface";
                   type empty;
                 }
                 leaf no-per-unit-scheduler {
                   description "Don't enable subunit queuing on Frame Relay or VLAN IQ interface";
                   type empty;
                 }
               }
             }
             case case_2 {
               leaf shared-scheduler {
                 description "Enabled shared queuing on an IQ2 interface";
                 type empty;
               }
             }
             case case_3 {
               container hierarchical-scheduler {
                 presence "enable hierarchical-scheduler";
                 description "Enable hierarchical scheduling";
                 leaf maximum-hierarchy-levels {
                   description "Maximum hierarchy levels";
                   type union {
                     type string {
                       pattern "<.*>|$.*";
                     }
                     type uint32;
                   }
                 }
                 leaf maximum-l2-nodes {
                   description "Maximum l2 nodes, allowed numbers are power of 2 between 1 and 16k (needs FPC reboot)";
                   default "1";
                   type union {
                     type string {
                       pattern "<.*>|$.*";
                     }
                     type uint32 {
                       range "1 .. 16384";
                     }
                   }
                 }
                 leaf maximum-l3-nodes {
                   description "Maximum l3 nodes, allowed numbers are power of 2 between 2 and 32k (needs FPC reboot)";
                   default "16384";
                   type union {
                     type string {
                       pattern "<.*>|$.*";
                     }
                     type uint32 {
                       range "2 .. 32768";
                     }
                   }
                 }
                 leaf implicit-hierarchy {
                   description "Implicit hierarchy (follows interface hierarchy)";
                   type empty;
                 }
               }
             }
           }
           leaf l2tp-maximum-session {
             description "Maximum L2TP session";
             type union {
               type string {
                 pattern "<.*>|$.*";
               }
               type uint32 {
                 range "0 .. 64000";
               }
             }
           }
           leaf schedulers {
             description "Number of schedulers to allocate for interface";
             type union {
               type uint32;
               type string {
                 pattern "<.*>|$.*";
               }
             }
           }
           leaf interface-transmit-statistics {
             description "Interface statistics based on the transmitted packets";
             type empty;
           }
           leaf cascade-port {
             description "Cascade port";
             type empty;
           }
           leaf dce {
             description "Respond to Frame Relay status enquiry messages";
             type empty;
           }
           choice vlan_tag_mode {
             case case_1 {
               leaf vlan-tagging {
                 description "802.1q VLAN tagging support";
                 type empty;
               }
             }
             case case_2 {
               leaf stacked-vlan-tagging {
                 description "Stacked 802.1q VLAN tagging support";
                 type empty;
               }
             }
             case case_3 {
               leaf flexible-vlan-tagging {
                 description "Support for no tagging, or single and double 802.1q VLAN tagging";
                 type empty;
               }
             }
             case case_4 {
               leaf vlan-vci-tagging {
                 description "CCC for VLAN Q-in-Q and ATM VPI/VCI interworking";
                 type empty;
               }
             }
           }
           leaf native-vlan-id {
             description "Virtual LAN identifier for untagged frames";
             type union {
               type string {
                 pattern "<.*>|$.*";
               }
               type uint32 {
                 range "0 .. 4094";
               }
             }
           }
           leaf no-native-vlan-insert {
             description "Disable native-vlan-id insertion to untagged frames";
             type empty;
           }
           leaf vlan-offload {
             description "Offload VLAN filtering to NIC HW";
             type empty;
           }
           leaf input-native-vlan-push {
             description "Control native-vlan-id insertion to untagged frames when input-vlan-map push is configured";
             type enumeration {
               enum "disable" {
                 description "Disable input-native-vlan-push";
               }
               enum "enable" {
                 description "Enable input-native-vlan-push";
               }
             }
           }
           leaf no-pseudowire-down-on-core-isolation {
             description "Do not bring the pseudowire down in the event of EVPN Core isolation";
             type empty;
           }
           leaf number-of-sub-ports {
             description "Number of channels to create for a port";
             type union {
               type string {
                 pattern "<.*>|$.*";
               }
               type uint32 {
                 range "1 .. 8";
               }
             }
           }
           leaf unused {
             description "Disable physical port";
             type empty;
           }
           leaf speed {
             description "Link speed";
             type enumeration {
               enum "auto" {
                 description "Enable auto negotiation of interface speed";
               }
               enum "auto-10m-100m" {
                 description "Enable auto negotiation of limiting interface speed to 10m/100m";
               }
               enum "10m" {
               }
               enum "100m" {
               }
               enum "1g" {
               }
               enum "2.5g" {
               }
               enum "5g" {
               }
               enum "10g" {
               }
               enum "25g" {
               }
               enum "40g" {
               }
               enum "50g" {
               }
               enum "100g" {
               }
               enum "200g" {
               }
               enum "400g" {
               }
               enum "800g" {
               }
               enum "oc3" {
               }
               enum "oc12" {
               }
               enum "oc48" {
               }
             }
           }
           container forwarding-class-accounting {
             presence "enable forwarding-class-accounting";
             description "Configure Forwarding-class-accounting parameters";
             uses apply-advanced;
             leaf direction {
               description "Direction of the traffic to be accounted for IFD";
               type enumeration {
                 enum "ingress" {
                   description "Enable forwarding-class-accounting for ingress traffic";
                 }
                 enum "egress" {
                   description "Enable forwarding-class-accounting for egress traffic";
                 }
                 enum "both" {
                   description "Enable forwarding-class-accounting for both directions";
                 }
               }
             }
             container enhanced {
               presence "enable enhanced";
               uses apply-advanced;
               leaf traffic-type {
                 description "Traffic-type to be accounted for forwarding-class-accounting";
                 type enumeration {
                   enum "unicast-statistics" {
                     description "Count only unicast traffic for forwarding-class-accounting";
                   }
                   enum "multicast-statistics" {
                     description "Count only multicast traffic for forwarding-class-accounting";
                   }
                 }
               }
               leaf family {
                 description "Protocol traffic to be accounted for forwarding-class-accounting";
                 type enumeration {
                   enum "inet" {
                     description "Enable forwarding-class-accounting for IPv4 family only";
                   }
                   enum "inet6" {
                     description "Enable forwarding-class-accounting for IPv6 family only";
                   }
                   enum "both" {
                     description "Enable forwarding-class-accounting for both IPv4 and IPv6 family only";
                   }
                 }
               }
               leaf direction {
                 description "Direction of the traffic to be accounted for forwarding-class-accounting";
                 type enumeration {
                   enum "ingress" {
                     description "Enable forwarding-class-accounting for ingress traffic";
                   }
                   enum "egress" {
                     description "Enable forwarding-class-accounting for egress traffic";
                   }
                   enum "both" {
                     description "Enable forwarding-class-accounting for both ingress and egress traffic";
                   }
                 }
               }
               leaf overhead-bytes {
                 description "Per octet overhead bytes to be accounted for forwarding-class-accounting";
                 default "0";
                 type union {
                   type string {
                     pattern "<.*>|$.*";
                   }
                   type uint32 {
                     range "0 .. 255";
                   }
                 }
               }
             }
           }
           container auto-configure {
             description "Auto configuration";
             uses auto_configure_vlan_type;
           }
           leaf mtu {
             description "Maximum transmit packet size";
             type union {
               type string {
                 pattern "<.*>|$.*";
               }
               type uint32;
             }
           }
           container hold-time {
             description "Hold time for link up and link down";
             leaf up {
               description "Link up hold time";
               units "milliseconds";
               type union {
                 type uint32;
                 type string {
                   pattern "<.*>|$.*";
                 }
               }
             }
             leaf down {
               description "Link down hold time";
               units "milliseconds";
               type union {
                 type uint32;
                 type string {
                   pattern "<.*>|$.*";
                 }
               }
             }
           }
           container damping {
             description "Interface damping parameters";
             uses apply-advanced;
             leaf half-life {
               description "Damping half life time";
               default "5";
               units "seconds";
               type union {
                 type string {
                   pattern "<.*>|$.*";
                 }
                 type uint32 {
                   range "1 .. 30";
                 }
               }
             }
             leaf max-suppress {
               description "Maximum suppress time";
               default "20";
               units "seconds";
               type union {
                 type string {
                   pattern "<.*>|$.*";
                 }
                 type uint32 {
                   range "1 .. 20000";
                 }
               }
             }
             leaf reuse {
               description "Reuse threshold";
               default "1000";
               type union {
                 type string {
                   pattern "<.*>|$.*";
                 }
                 type uint32 {
                   range "1 .. 20000";
                 }
               }
             }
             leaf suppress {
               description "Suppress threshold";
               default "2000";
               type union {
                 type string {
                   pattern "<.*>|$.*";
                 }
                 type uint32 {
                   range "1 .. 20000";
                 }
               }
             }
             leaf enable {
               description "Enable interface damping";
               type empty;
             }
           }
           container link-degrade-monitor {
             presence "enable link-degrade-monitor";
             description "Enable link degrade monitoring";
             uses apply-advanced;
             choice enable_choice {
               case case_1 {
                 leaf link-degrade-monitor-enable {
                   description "Enable Link Degrade Monitoring";
                   type empty;
                 }
               }
               case case_2 {
                 leaf no-link-degrade-monitor-enable {
                   description "Disable Link Degrade Monitoring";
                   type empty;
                 }
               }
             }
             container actions {
               description "Action upon link degrade event";
               uses apply-advanced;
               choice action_choice {
                 case case_1 {
                   leaf media-based {
                     description "Media based";
                     type empty;
                   }
                 }
               }
             }
             container recovery {
               description "Link degrade recovery mechanism";
               uses apply-advanced;
               leaf timer {
                 description "Auto recovery timer in seconds";
                 default "1800";
                 type union {
                   type uint32;
                   type string {
                     pattern "<.*>|$.*";
                   }
                 }
               }
               choice receovery_choice {
                 case case_1 {
                   leaf auto {
                     description "Automatic recovery";
                     type empty;
                   }
                 }
                 case case_2 {
                   leaf manual {
                     description "Manual recovery";
                     type empty;
                   }
                 }
               }
             }
             container thresholds {
               description "Link degrade threshold parameters";
               uses apply-advanced;
               leaf set {
                 description "BER at which link considered degraded(1..16)";
                 default "1e-7";
                 type string {
                 }
               }
               leaf clear {
                 description "BER at which link considered improved(1..16)";
                 default "1e-12";
                 type string {
                 }
               }
               leaf warning-set {
                 description "BER at which link degrade warning raised(1..16)";
                 default "1e-9";
                 type string {
                 }
               }
               leaf warning-clear {
                 description "BER at which link degrade warning cleared(1..16)";
                 default "1e-11";
                 type string {
                 }
               }
               leaf interval {
                 description "Consecutive link degrade events";
                 default "10";
                 type union {
                   type string {
                     pattern "<.*>|$.*";
                   }
                   type uint32 {
                     range "1 .. 256";
                   }
                 }
               }
             }
           }
           container satop-options {
             description "Structure-Agnostic TDM over Packet protocol options";
             uses apply-advanced;
             leaf idle-pattern {
               description "An 8-bit hexadecimal pattern to replace TDM data in a lost packet";
               type union {
                 type string {
                   pattern "<.*>|$.*";
                 }
                 type uint32 {
                   range "0 .. 255";
                 }
               }
             }
             leaf payload-size {
               description "Number of payload bytes per packet";
               type union {
                 type string {
                   pattern "<.*>|$.*";
                 }
                 type uint32 {
                   range "64 .. 1024";
                 }
               }
             }
             container excessive-packet-loss-rate {
               description "Packet loss options";
               uses apply-advanced;
               leaf threshold {
                 description "Percentile designating the threshold of excessive packet loss rate";
                 type union {
                   type string {
                     pattern "<.*>|$.*";
                   }
                   type uint8 {
                     range "1 .. 100";
                   }
                 }
               }
               leaf sample-period {
                 description "Number of milliseconds over which excessive packet loss rate is calculated";
                 type union {
                   type string {
                     pattern "<.*>|$.*";
                   }
                   type uint32 {
                     range "1000 .. 65535";
                   }
                 }
               }
             }
             choice jitter-buffer-size {
               case case_1 {
                 leaf jitter-buffer-packets {
                   description "Number of packets in jitter buffer before packet data is played out in the line";
                   type union {
                     type string {
                       pattern "<.*>|$.*";
                     }
                     type uint32 {
                       range "1 .. 64";
                     }
                   }
                 }
               }
               case case_2 {
                 leaf jitter-buffer-latency {
                   description "Number of milliseconds delay in jitter buffer before packet data is played out in the line";
                   units "milliseconds";
                   type union {
                     type string {
                       pattern "<.*>|$.*";
                     }
                     type uint32 {
                       range "1 .. 1000";
                     }
                   }
                 }
               }
               case case_3 {
                 leaf jitter-buffer-auto-adjust {
                   description "Automatically adjust jitter buffer";
                   type empty;
                 }
               }
             }
             leaf bit-rate {
               description "In multiples of DS0";
               type union {
                 type string {
                   pattern "<.*>|$.*";
                 }
                 type uint32 {
                   range "1 .. 10240";
                 }
               }
             }
           }
           container cesopsn-options {
             description "Structure-Aware TDM over Packet protocol options";
             uses apply-advanced;
             leaf idle-pattern {
               description "An 8-bit hexadecimal pattern to replace TDM data in a lost packet";
               type union {
                 type string {
                   pattern "<.*>|$.*";
                 }
                 type uint32 {
                   range "0 .. 255";
                 }
               }
             }
             leaf packetization-latency {
               description "Number of microseconds to create packets";
               units "microseconds";
               type union {
                 type string {
                   pattern "<.*>|$.*";
                 }
                 type uint32 {
                   range "1000 .. 8000";
                 }
               }
             }
             leaf payload-size {
               description "Number of payload bytes per packet";
               type union {
                 type string {
                   pattern "<.*>|$.*";
                 }
                 type uint32 {
                   range "64 .. 1024";
                 }
               }
             }
             container excessive-packet-loss-rate {
               description "Packet loss options";
               uses apply-advanced;
               leaf threshold {
                 description "Percentile designating the threshold of excessive packet loss rate";
                 type union {
                   type string {
                     pattern "<.*>|$.*";
                   }
                   type uint8 {
                     range "1 .. 100";
                   }
                 }
               }
               leaf sample-period {
                 description "Number of milliseconds over which excessive packet loss rate is calculated";
                 type union {
                   type string {
                     pattern "<.*>|$.*";
                   }
                   type uint32 {
                     range "1000 .. 65535";
                   }
                 }
               }
             }
             choice jitter-buffer-size {
               case case_1 {
                 leaf jitter-buffer-packets {
                   description "Number of packets in jitter buffer before packet data is played out in the line";
                   type union {
                     type string {
                       pattern "<.*>|$.*";
                     }
                     type uint32 {
                       range "1 .. 64";
                     }
                   }
                 }
               }
               case case_2 {
                 leaf jitter-buffer-latency {
                   description "Number of milliseconds delay in jitter buffer before packet data is played out in the line";
                   units "milliseconds";
                   type union {
                     type string {
                       pattern "<.*>|$.*";
                     }
                     type uint32 {
                       range "1 .. 1000";
                     }
                   }
                 }
               }
               case case_3 {
                 leaf jitter-buffer-auto-adjust {
                   description "Automatically adjust jitter buffer";
                   type empty;
                 }
               }
             }
             leaf bit-rate {
               description "In multiples of DS0";
               type union {
                 type string {
                   pattern "<.*>|$.*";
                 }
                 type uint32 {
                   range "1 .. 10240";
                 }
               }
             }
           }
           container ima-group-options {
             description "IMA group options";
             uses apply-advanced;
             leaf frame-length {
               description "Frame length (cells)";
               type enumeration {
                 enum "32" {
                 }
                 enum "64" {
                 }
                 enum "128" {
                 }
                 enum "256" {
                 }
               }
             }
             leaf symmetry {
               description "Symmetry of IMA group";
               default "symmetrical-config-and-operation";
               type enumeration {
                 enum "symmetrical-config-and-operation" {
                 }
                 enum "symmetrical-config-asymmetrical-operation" {
                 }
               }
             }
             leaf transmit-clock {
               description "Transmit clock";
               type enumeration {
                 enum "common" {
                   description "Common transmit clock";
                 }
                 enum "independent" {
                   description "Independent transmit clock";
                 }
               }
             }
             leaf version {
               description "IMA specification version";
               type enumeration {
                 enum "1.0" {
                   description "Version 1.0";
                 }
                 enum "1.1" {
                   description "Version 1.1";
                 }
               }
             }
             container minimum-links {
               description "IMA group minimum active links";
               choice minimum_links_type {
                 case case_1 {
                   leaf symmetrical {
                     description "Minimum active receive and transmit links";
                     type union {
                       type string {
                         pattern "<.*>|$.*";
                       }
                       type uint32 {
                         range "1 .. 32";
                       }
                     }
                   }
                 }
               }
             }
             container frame-synchronization {
               description "IMA group frame synchronization state parameters";
               uses apply-advanced;
               leaf alpha {
                 description "Consecutive invalid ICP cells";
                 type union {
                   type string {
                     pattern "<.*>|$.*";
                   }
                   type uint32 {
                     range "1 .. 2";
                   }
                 }
               }
               leaf beta {
                 description "Consecutive errored ICP cells";
                 type union {
                   type string {
                     pattern "<.*>|$.*";
                   }
                   type uint32 {
                     range "1 .. 5";
                   }
                 }
               }
               leaf gamma {
                 description "Consecutive valid ICP cells";
                 type union {
                   type string {
                     pattern "<.*>|$.*";
                   }
                   type uint32 {
                     range "1 .. 5";
                   }
                 }
               }
             }
             container test-procedure {
               description "IMA group test pattern procedure";
               uses apply-advanced;
               leaf period {
                 description "Length of IMA pattern test";
                 units "seconds";
                 type union {
                   type string {
                     pattern "<.*>|$.*";
                   }
                   type uint32 {
                     range "1 .. 4294967294";
                   }
                 }
               }
               leaf interface {
                 description "Interface name of the IMA link to test";
                 type union {
                   type jt:interface-device;
                   type string {
                     pattern "<.*>|$.*";
                   }
                 }
               }
               leaf pattern {
                 description "IMA test pattern";
                 type union {
                   type string {
                     pattern "<.*>|$.*";
                   }
                   type uint32 {
                     range "1 .. 254";
                   }
                 }
               }
             }
             leaf differential-delay {
               description "Maximum differential delay among links in the IMA group";
               units "milliseconds";
               type union {
                 type string {
                   pattern "<.*>|$.*";
                 }
                 type uint32 {
                   range "1 .. 56";
                 }
               }
             }
           }
           container ima-link-options {
             description "IMA link options";
             uses apply-advanced;
             leaf group-id {
               description "IMA group ID this IMA link belongs to";
               type union {
                 type string {
                   pattern "<.*>|$.*";
                 }
                 type uint32;
               }
             }
           }
           list multi-chassis-protection {
             key name;
             description "Inter-Chassis protection configuration";
             uses multi-chassis-protection-group;
           }
           container clocking {
             description "Interface clock source";
             choice clocking_choices {
               case case_1 {
                 leaf internal {
                   description "Clocking provided by local system";
                   type empty;
                 }
               }
               case case_2 {
                 container external {
                   presence "enable external";
                   description "Clocking provided by DCE (loop timing)";
                   uses apply-advanced;
                   leaf interface {
                     description "Interface that acts as clock source";
                     type union {
                       type jt:interface-device;
                       type string {
                         pattern "<.*>|$.*";
                       }
                     }
                   }
                 }
               }
             }
             uses apply-advanced;
           }
           leaf link-mode {
             description "Link operational mode";
             type enumeration {
               enum "automatic" {
                 description "Automatically negotiate duplex";
               }
               enum "half-duplex" {
                 description "Half-duplex operation";
               }
               enum "full-duplex" {
                 description "Full-duplex operation";
               }
             }
           }
           leaf media-type {
             description "Interface media type (copper or fiber)";
             type enumeration {
               enum "copper" {
                 description "Copper as media";
               }
               enum "fiber" {
                 description "Fiber as media";
               }
             }
           }
           leaf encapsulation {
             description "Physical link-layer encapsulation";
             type enumeration {
               enum "ethernet" {
                 description "Ethernet physical media";
               }
               enum "fddi" {
                 description "FDDI physical media";
               }
               enum "token-ring" {
                 description "Token Ring physical media";
               }
               enum "ppp" {
                 description "Serial PPP device";
               }
               enum "ppp-ccc" {
                 description "Serial PPP device for a cross-connect";
               }
               enum "ppp-tcc" {
                 description "Serial PPP device for a translational cross-connect";
               }
               enum "ether-vpls-ppp" {
                 description "Ethernet VPLS over PPP (bridging) device";
               }
               enum "frame-relay" {
                 description "Frame Relay encapsulation";
               }
               enum "frame-relay-ccc" {
                 description "Frame Relay for cross-connect";
               }
               enum "frame-relay-tcc" {
                 description "Frame Relay for translational cross-connect";
               }
               enum "extended-frame-relay-ccc" {
                 description "Any Frame Relay DLCI for cross-connect";
               }
               enum "extended-frame-relay-tcc" {
                 description "Any Frame Relay DLCI for translational cross-connect";
               }
               enum "flexible-frame-relay" {
                 description "Multiple Frame Relay encapsulations";
               }
               enum "frame-relay-port-ccc" {
                 description "Frame Relay port encapsulation for a cross-connect";
               }
               enum "frame-relay-ether-type" {
                 description "Cisco-compatible Frame Relay encapsulation";
               }
               enum "frame-relay-ether-type-tcc" {
                 description "Cisco-compatible Frame Relay encapsulation for translational cross-connect";
               }
               enum "extended-frame-relay-ether-type-tcc" {
                 description "Cisco-compatible Frame Relay encapsulation any DLCI for translational cross-connect";
               }
               enum "cisco-hdlc" {
                 description "Cisco-compatible HDLC framing";
               }
               enum "cisco-hdlc-ccc" {
                 description "Cisco-compatible HDLC framing for a cross-connect";
               }
               enum "cisco-hdlc-tcc" {
                 description "Cisco-compatible HDLC framing for a translational cross-connect";
               }
               enum "vlan-ccc" {
                 description "802.1q tagging for a cross-connect";
               }
               enum "extended-vlan-ccc" {
                 description "Nonstandard TPID tagging for a cross-connect";
               }
               enum "ethernet-ccc" {
                 description "Ethernet cross-connect";
               }
               enum "flexible-ethernet-services" {
                 description "Allows per-unit Ethernet encapsulation configuration";
               }
               enum "smds-dxi" {
                 description "SMDS DXI framing";
               }
               enum "atm-pvc" {
                 description "ATM permanent virtual circuits";
               }
               enum "atm-ccc-cell-relay" {
                 description "ATM cell relay encapsulation for cross-connect";
               }
               enum "ethernet-over-atm" {
                 description "Ethernet over ATM encapsulation";
               }
               enum "ethernet-tcc" {
                 description "Ethernet translational cross-connect";
               }
               enum "extended-vlan-tcc" {
                 description "802.1q tagging for a translational cross-connect";
               }
               enum "multilink-frame-relay-uni-nni" {
                 description "Multilink Frame Relay UNI NNI (FRF.16) encapsulation";
               }
               enum "satop" {
                 description "Structure-Agnostic TDM over Packet encapsulation";
               }
               enum "cesopsn" {
                 description "Structure-Agnostic TDM over Packet encapsulation";
               }
               enum "ima" {
                 description "Inverse Multiplexing for ATM";
               }
               enum "ethernet-vpls" {
                 description "Ethernet virtual private LAN service";
               }
               enum "ethernet-bridge" {
                 description "Ethernet layer-2 bridging";
               }
               enum "vlan-vpls" {
                 description "VLAN virtual private LAN service";
               }
               enum "vlan-vci-ccc" {
                 description "CCC for VLAN Q-in-Q and ATM VPI/VCI interworking";
               }
               enum "extended-vlan-vpls" {
                 description "Extended VLAN virtual private LAN service";
               }
               enum "extended-vlan-bridge" {
                 description "VLAN layer-2 bridging";
               }
               enum "multilink-ppp" {
                 description "Multilink PPP";
               }
               enum "generic-services" {
                 description "Generic services";
               }
             }
           }
           leaf network-isolation-profile {
             description "Attach a network isolation profile on this interface";
             type string;
           }
           container esi {
             description "ESI configuration of multi-homed interface";
             uses apply-advanced;
             container auto-derive {
               description "Auto-derive ESI value for the interface";
               uses apply-advanced;
               choice esitype {
                 case case_1 {
                   leaf lacp-pe-system-id-and-admin-key {
                     description "Auto-derive ESI from lacp pe system-id and admin key";
                     type empty;
                   }
                 }
                 case case_2 {
                   leaf type-1-lacp {
                     description "Auto-generate Type1 ESI LACP";
                     type empty;
                   }
                 }
                 case case_3 {
                   container type-3-system-mac {
                     description "Auto-generate Type3 ESI System-mac";
                     uses apply-advanced;
                     leaf mac {
                       description "System mac";
                       type jt:mac-unicast;
                     }
                     leaf local-discriminator {
                       description "Local-discriminator";
                       type union {
                         type string {
                           pattern "<.*>|$.*";
                         }
                         type int32 {
                           range "0 .. 16777215";
                         }
                       }
                     }
                   }
                 }
               }
             }
             leaf identifier {
               description "ESI value for the interface";
               type jt:esi;
             }
             choice mode {
               case case_1 {
                 leaf single-active {
                   description "Single-active mode";
                   type empty;
                 }
               }
               case case_2 {
                 leaf all-active {
                   description "All-active mode";
                   type empty;
                 }
               }
             }
             container df-election-granularity {
               presence "enable df-election-granularity";
               description "DF Election Granularity Selection ";
               uses apply-advanced;
               choice mode {
                 case case_1 {
                   container per-esi {
                     presence "enable per-esi";
                     description "DF Election Granularity Per Esi";
                     uses apply-advanced;
                     leaf lacp-oos-on-ndf {
                       description "Lacp Oos";
                       type empty;
                     }
                   }
                 }
                 case case_2 {
                   leaf per-esi-vlan {
                     description "Per Esi Vlan";
                     type empty;
                   }
                 }
               }
             }
             container df-election-type {
               presence "enable df-election-type";
               description "DF Election Type";
               uses apply-advanced;
               choice pref_choice {
                 case case_1 {
                   container preference {
                     presence "enable preference";
                     description "Preference based DF election";
                     uses apply-advanced;
                     leaf value {
                       description "Preference value for EVPN Multihoming DF election";
                       default "32767";
                       type union {
                         type string {
                           pattern "<.*>|$.*";
                         }
                         type uint32 {
                           range "0 .. 65535";
                         }
                       }
                     }
                   }
                 }
               }
               choice mod_choice {
                 case case_1 {
                   container mod {
                     presence "enable mod";
                     description "MOD based DF election";
                   }
                 }
               }
             }
             leaf source-bmac {
               description "Unicast Source B-MAC address per ESI for PBB-EVPN";
               type jt:mac-unicast;
             }
           }
           container framing {
             description "Frame type";
             uses apply-advanced;
             choice frame {
               case case_1 {
                 leaf lan-phy {
                   description "802.3ae 10-Gbps LAN-mode interface";
                   type empty;
                 }
               }
               case case_2 {
                 leaf wan-phy {
                   description "802.3ae 10-Gbps WAN-mode interface";
                   type empty;
                 }
               }
               case case_3 {
                 leaf sonet {
                   description "SONET framing";
                   type empty;
                 }
               }
               case case_4 {
                 leaf sdh {
                   description "SDH framing";
                   type empty;
                 }
               }
             }
             leaf precise-bandwidth {
               description "Use precise bandwidth for 10G wan-phy interface";
               type empty;
             }
           }
           leaf unidirectional {
             description "Unidirectional Mode";
             type empty;
           }
           container lmi {
             description "Local Management Interface settings";
             uses apply-advanced;
             leaf n391dte {
               description "DTE full status polling interval";
               type union {
                 type string {
                   pattern "<.*>|$.*";
                 }
                 type uint16 {
                   range "1 .. 255";
                 }
               }
             }
             leaf n392dce {
               description "DCE error threshold";
               type union {
                 type string {
                   pattern "<.*>|$.*";
                 }
                 type uint16 {
                   range "1 .. 10";
                 }
               }
             }
             leaf n392dte {
               description "DTE error threshold";
               type union {
                 type string {
                   pattern "<.*>|$.*";
                 }
                 type uint16 {
                   range "1 .. 10";
                 }
               }
             }
             leaf n393dce {
               description "DCE monitored event count";
               type union {
                 type string {
                   pattern "<.*>|$.*";
                 }
                 type uint16 {
                   range "1 .. 10";
                 }
               }
             }
             leaf n393dte {
               description "DTE monitored event count";
               type union {
                 type string {
                   pattern "<.*>|$.*";
                 }
                 type uint16 {
                   range "1 .. 10";
                 }
               }
             }
             leaf t391dte {
               description "DTE polling timer";
               units "seconds";
               type union {
                 type string {
                   pattern "<.*>|$.*";
                 }
                 type uint16 {
                   range "5 .. 30";
                 }
               }
             }
             leaf t392dce {
               description "DCE polling verification timer";
               units "seconds";
               type union {
                 type string {
                   pattern "<.*>|$.*";
                 }
                 type uint16 {
                   range "5 .. 30";
                 }
               }
             }
             leaf lmi-type {
               description "Specify the Frame Relay LMI type";
               type enumeration {
                 enum "ansi" {
                   description "Use ANSI Annex D LMI";
                 }
                 enum "itu" {
                   description "Use ITU Q933a Annex A LMI";
                 }
                 enum "c-lmi" {
                   description "Use Consortium LMI";
                 }
               }
             }
           }
           container mlfr-uni-nni-bundle-options {
             description "Multilink Frame Relay UNI NNI (FRF.16) management settings";
             uses apply-advanced;
             container cisco-interoperability {
               description "FRF.16 Cisco interoperability settings";
               uses apply-advanced;
               leaf send-lip-remove-link-for-link-reject {
                 description "Send Link Integrity Protocol remove link on receiving add-link rejection";
                 type empty;
               }
             }
             leaf mrru {
               description "Maximum received reconstructed unit";
               units "bytes";
               type union {
                 type string {
                   pattern "<.*>|$.*";
                 }
                 type uint16 {
                   range "1500 .. 4500";
                 }
               }
             }
             leaf yellow-differential-delay {
               description "Yellow differential delay among bundle links to give warning";
               units "milliseconds";
               type union {
                 type string {
                   pattern "<.*>|$.*";
                 }
                 type uint16 {
                   range "3 .. 2000";
                 }
               }
             }
             leaf red-differential-delay {
               description "Red differential delay among bundle links to take action";
               units "milliseconds";
               type union {
                 type string {
                   pattern "<.*>|$.*";
                 }
                 type uint16 {
                   range "5 .. 2000";
                 }
               }
             }
             leaf action-red-differential-delay {
               description "Type of actions when differential delay exceeds red limit";
               type enumeration {
                 enum "remove-link" {
                   description "Remove bundle link from service when exceeding red limit";
                 }
                 enum "disable-tx" {
                   description "Disable transfer of bundle link when exceeding red limit";
                 }
               }
             }
             leaf fragment-threshold {
               description "Fragmentation threshold";
               units "bytes";
               type union {
                 type string {
                   pattern "<.*>|$.*";
                 }
                 type uint32 {
                   range "64 .. 16320";
                 }
               }
             }
             leaf drop-timeout {
               description "Drop timeout";
               units "milliseconds";
               type union {
                 type string {
                   pattern "<.*>|$.*";
                 }
                 type uint16 {
                   range "0 .. 2000";
                 }
               }
             }
             leaf link-layer-overhead {
               description "Link layer bit stuffing overhead (0.0 .. 50.0 percent)";
               type jt:unsigned-float;
             }
             leaf lmi-type {
               description "Specify the multilink Frame Relay UNI NNI LMI type";
               type enumeration {
                 enum "ansi" {
                   description "Use ANSI Annex D LMI";
                 }
                 enum "itu" {
                   description "Use ITU Q933a Annex A LMI";
                 }
                 enum "c-lmi" {
                   description "Use Consortium LMI";
                 }
               }
             }
             leaf minimum-links {
               description "Minimum number of links to sustain the bundle";
               type union {
                 type string {
                   pattern "<.*>|$.*";
                 }
                 type uint16 {
                   range "1 .. 8";
                 }
               }
             }
             leaf hello-timer {
               description "LIP hello timer";
               type union {
                 type string {
                   pattern "<.*>|$.*";
                 }
                 type uint16 {
                   range "5 .. 180";
                 }
               }
             }
             leaf acknowledge-timer {
               description "LIP ack timer";
               type union {
                 type string {
                   pattern "<.*>|$.*";
                 }
                 type uint16 {
                   range "1 .. 10";
                 }
               }
             }
             leaf acknowledge-retries {
               description "LIP ack retry times";
               type union {
                 type string {
                   pattern "<.*>|$.*";
                 }
                 type uint16 {
                   range "1 .. 5";
                 }
               }
             }
             leaf n391 {
               description "Multilink Frame Relay UNI NNI full status polling counter";
               type union {
                 type string {
                   pattern "<.*>|$.*";
                 }
                 type uint16 {
                   range "1 .. 255";
                 }
               }
             }
             leaf n392 {
               description "Multilink Frame Relay UNI NNI LMI error threshold";
               type union {
                 type string {
                   pattern "<.*>|$.*";
                 }
                 type uint16 {
                   range "1 .. 10";
                 }
               }
             }
             leaf n393 {
               description "Multilink Frame Relay UNI NNI LMI monitored event count";
               type union {
                 type string {
                   pattern "<.*>|$.*";
                 }
                 type uint16 {
                   range "1 .. 10";
                 }
               }
             }
             leaf t391 {
               description "Multilink Frame Relay UNI NNI link integrity verify polling timer";
               type union {
                 type string {
                   pattern "<.*>|$.*";
                 }
                 type uint16 {
                   range "5 .. 30";
                 }
               }
             }
             leaf t392 {
               description "Multilink Frame Relay UNI NNI polling verification timer";
               type union {
                 type string {
                   pattern "<.*>|$.*";
                 }
                 type uint16 {
                   range "5 .. 30";
                 }
               }
             }
           }
           leaf mac {
             description "Hardware MAC address";
             type jt:mac-unicast;
           }
           leaf no-forwarding-viable {
             description "Disable forwarding";
             type empty;
           }
           container p4rt {
             description "P4-runtime interfaces";
             uses apply-advanced;
             leaf id {
               description "Port number";
               type union {
                 type string {
                   pattern "<.*>|$.*";
                 }
                 type uint64 {
                   range "1 .. 4294967296";
                 }
               }
             }
             leaf node-id {
               description "Device Id";
               type union {
                 type string {
                   pattern "<.*>|$.*";
                 }
                 type uint64 {
                   range "1 .. 18446744073709551615";
                 }
               }
             }
           }
           container receive-bucket {
             description "Set receive bucket parameters";
             uses dcd_rx_bucket_config;
           }
           container transmit-bucket {
             description "Set transmit bucket parameters";
             uses dcd_tx_bucket_config;
           }
           leaf shared-interface {
             description "Enable shared interface on the interface";
             type empty;
           }
           container sonet-options {
             description "SONET interface-specific options";
             uses sonet_options_type;
           }
           container logical-tunnel-options {
             description "Logical Tunnel interface-specific options";
             uses apply-advanced;
             container link-protection {
               presence "enable link-protection";
               description "Enable link protection mode";
               uses apply-advanced;
               leaf revertive {
                 description "Revert back (Default mode) from active backup link to primary, if primary is UP";
                 type empty;
               }
               leaf non-revertive {
                 description "Do not revert back from active backup link to primary, if primary is UP";
                 type empty;
               }
             }
             leaf per-unit-mac-disable {
               description "Disable the creation of per unit mac address on LT IFLs for VPLS/CCC encaps";
               type empty;
             }
             container load-balance {
               uses aggregate-load-balance;
             }
             leaf distribution-list {
               description "Distribution list to which interface belongs";
               type string {
                 length "1 .. 20";
               }
             }
           }
           container aggregated-sonet-options {
             description "Aggregated SONET interface-specific options";
             uses apply-advanced;
             leaf minimum-links {
               description "Minimum number of aggregated links";
               type union {
                 type string {
                   pattern "<.*>|$.*";
                 }
                 type uint16;
               }
             }
             leaf link-speed {
               description "Aggregated links speed";
               type enumeration {
                 enum "oc3" {
                   description "Links are OC-3c or STM-1c";
                 }
                 enum "oc12" {
                   description "Links are OC-12c or STM-4c";
                 }
                 enum "oc48" {
                   description "Links are OC-48c or STM-16c";
                 }
                 enum "oc192" {
                   description "Links are OC-192c or STM-64c";
                 }
                 enum "oc768" {
                   description "Links are OC-768c or STM-256c";
                 }
                 enum "mixed" {
                   description "Links are various speeds";
                 }
               }
             }
             leaf minimum-bandwidth {
               description "Minimum bandwidth necessary to sustain bundle";
               units "bps";
               type union {
                 type string {
                   pattern "<.*>|$.*";
                 }
                 type uint64 {
                   range "0 .. 159232000000";
                 }
               }
             }
           }
           container atm-options {
             description "ATM interface-specific options";
             uses apply-advanced;
             leaf pic-type {
               description "Type of ATM PIC (ATM I, ATM II or ATM CE)";
               type enumeration {
                 enum "atm-ce" {
                   description "CE PIC";
                 }
                 enum "atm2" {
                   description "ATM II IQ PIC";
                 }
                 enum "atm1" {
                   description "ATM I PIC";
                 }
               }
             }
             leaf cell-bundle-size {
               description "L2 circuit cell bundle size";
               units "cells";
               type union {
                 type string {
                   pattern "<.*>|$.*";
                 }
                 type uint32 {
                   range "1 .. 176";
                 }
               }
             }
             leaf cell-bundle-timeout {
               description "L2 circuit cell bundle timeout";
               units "microseconds";
               type union {
                 type string {
                   pattern "<.*>|$.*";
                 }
                 type uint32 {
                   range "1 .. 512";
                 }
               }
             }
             leaf plp-to-clp {
               description "Enable ATM2 PLP to CLP copy";
               type empty;
             }
             leaf use-null-cw {
               description "Always insert/strip null control words with cell-relay";
               type empty;
             }
             container promiscuous-mode {
               presence "enable promiscuous-mode";
               description "Set ATM interface to promiscuous mode";
               uses apply-advanced;
               list vpi {
                 key name;
                 ordered-by user;
                 description "Open this VPI in promiscuous mode";
                 leaf name {
                   description "Virtual path index";
                   type union {
                     type string {
                       pattern "<.*>|$.*";
                     }
                     type uint32 {
                       range "0 .. 255";
                     }
                   }
                 }
               }
             }
             list vpi {
               key name;
               ordered-by user;
               description "Define a virtual path";
               leaf name {
                 description "Virtual path index";
                 type union {
                   type string {
                     pattern "<.*>|$.*";
                   }
                   type uint32 {
                     range "0 .. 255";
                   }
                 }
               }
               uses apply-advanced;
               leaf maximum-vcs {
                 description "Maximum number of virtual circuits on this VP";
                 type union {
                   type uint32;
                   type string {
                     pattern "<.*>|$.*";
                   }
                 }
               }
               container shaping {
                 description "Virtual path traffic-shaping options";
                 uses dcd_shaping_config;
               }
               container oam-period {
                 description "F4 OAM cell period";
                 choice oam_period_choices {
                   case case_1 {
                     leaf oam-period {
                       description "F4 OAM cell period";
                       units "seconds";
                       type union {
                         type string {
                           pattern "<.*>|$.*";
                         }
                         type uint32 {
                           range "1 .. 900";
                         }
                       }
                     }
                   }
                   case case_2 {
                     container disable {
                       presence "enable disable";
                       description "Disable F4 OAM loopback";
                     }
                   }
                 }
               }
               container oam-liveness {
                 description "F4 OAM virtual path liveness parameters";
                 uses apply-advanced;
                 leaf up-count {
                   description "Number of F4 OAM cells to consider VP up";
                   type union {
                     type string {
                       pattern "<.*>|$.*";
                     }
                     type uint32 {
                       range "1 .. 255";
                     }
                   }
                 }
                 leaf down-count {
                   description "Number of F4 OAM cells to consider VP down";
                   type union {
                     type string {
                       pattern "<.*>|$.*";
                     }
                     type uint32 {
                       range "1 .. 255";
                     }
                   }
                 }
               }
             }
             container ilmi {
               presence "enable ilmi";
               description "Enable Interim Local Management Interface";
               uses apply-advanced;
             }
             list linear-red-profiles {
               key name;
               ordered-by user;
               description "ATM2 CoS virtual circuit drop profiles";
               leaf name {
                 description "Linear RED profile name";
                 type string {
                 }
               }
               leaf queue-depth {
                 description "Maximum queue depth";
                 units "cells";
                 type string;
               }
               leaf high-plp-threshold {
                 description "Fill level percentage when linear RED is applied for high PLP";
                 type union {
                   type string {
                     pattern "<.*>|$.*";
                   }
                   type uint32 {
                     range "0 .. 100";
                   }
                 }
               }
               leaf low-plp-threshold {
                 description "Fill level percentage when linear RED is applied for low PLP";
                 type union {
                   type string {
                     pattern "<.*>|$.*";
                   }
                   type uint32 {
                     range "0 .. 100";
                   }
                 }
               }
               leaf high-plp-max-threshold {
                 description "Fill level percentage with 100 percent packet drop for high PLP";
                 type union {
                   type string {
                     pattern "<.*>|$.*";
                   }
                   type uint32 {
                     range "0 .. 100";
                   }
                 }
               }
               leaf low-plp-max-threshold {
                 description "Fill level percentage with 100 percent packet drop for low PLP";
                 type union {
                   type string {
                     pattern "<.*>|$.*";
                   }
                   type uint32 {
                     range "0 .. 100";
                   }
                 }
               }
             }
             list scheduler-maps {
               key name;
               ordered-by user;
               description "ATM2 CoS parameters assigned to forwarding classes";
               leaf name {
                 description "ATM2 CoS scheduler map name";
                 type string {
                 }
               }
               uses apply-advanced;
               leaf vc-cos-mode {
                 description "ATM2 virtual circuit CoS mode";
                 type enumeration {
                   enum "strict" {
                     description "Always schedule high priority queue first";
                   }
                   enum "alternate" {
                     description "Every other packet from high priority queue (default)";
                   }
                 }
               }
               list forwarding-class {
                 key name;
                 ordered-by user;
                 description "Scheduling parameters associated with forwarding class";
                 leaf name {
                   description "Forwarding class name";
                   type string {
                   }
                 }
                 uses apply-advanced;
                 leaf priority {
                   description "Queuing priority assigned to forwarding class";
                   type enumeration {
                     enum "low" {
                       description "Low priority queuing";
                     }
                     enum "high" {
                       description "High priority queuing";
                     }
                   }
                 }
                 container transmit-weight {
                   description "Transmit weight";
                   choice weight-method {
                     case case_1 {
                       leaf percent {
                         description "Transmit weight as percentage";
                         type union {
                           type string {
                             pattern "<.*>|$.*";
                           }
                           type uint32 {
                             range "5 .. 100";
                           }
                         }
                       }
                     }
                     case case_2 {
                       leaf cells {
                         description "Transmit weight by cells count";
                         type string;
                       }
                     }
                   }
                 }
                 choice drop-profile-method {
                   case case_1 {
                     container epd-threshold {
                       description "Early packet discard threshold for ATM2";
                       uses epd_threshold_config;
                     }
                   }
                   case case_2 {
                     leaf linear-red-profile {
                       description "Linear RED profile profile name";
                       type string;
                     }
                   }
                 }
               }
             }
             container mpls {
               description "MPLS options";
               uses mpls_ifd_options;
             }
             choice payload-scrambler-choice {
               leaf payload-scrambler {
                 description "Enable payload scrambling";
                 type empty;
               }
               leaf no-payload-scrambler {
                 description "Don't enable payload scrambling";
                 type empty;
               }
             }
           }
           container multiservice-options {
             description "Multiservice interface-specific options";
             uses apply-advanced;
             choice syslog-choice {
               leaf syslog {
                 description "Enable system logging on this interface";
                 type empty;
               }
               leaf no-syslog {
                 description "Don't enable system logging on this interface";
                 type empty;
               }
             }
             choice core-dump-choice {
               leaf core-dump {
                 description "Enable core dumping on this interface";
                 type empty;
               }
               leaf no-core-dump {
                 description "Don't enable core dumping on this interface";
                 type empty;
               }
             }
             choice dump-on-flow-control-choice {
               leaf dump-on-flow-control {
                 description "Enable dumping for this interface on prolonged flow-control";
                 status deprecated;
                 type empty;
               }
               leaf no-dump-on-flow-control {
                 description "Don't enable dumping for this interface on prolonged flow-control";
                 status deprecated;
                 type empty;
               }
             }
             choice reset-on-flow-control-choice {
               leaf reset-on-flow-control {
                 description "Enable resetting this interface on prolonged flow-control";
                 status deprecated;
                 type empty;
               }
               leaf no-reset-on-flow-control {
                 description "Don't enable resetting this interface on prolonged flow-control";
                 status deprecated;
                 type empty;
               }
             }
             container flow-control-options {
               description "Flow control configuration";
               uses apply-advanced;
               leaf dump-on-flow-control {
                 description "Cause core dump during prolonged flow-control";
                 type empty;
               }
               leaf reset-on-flow-control {
                 description "Reset interface during prolonged flow-control";
                 type empty;
               }
               leaf down-on-flow-control {
                 description "Bring interface down during prolonged flow-control";
                 type empty;
               }
               leaf up-on-flow-control {
                 description "Keep interface up during prolonged flow-control";
                 type empty;
               }
             }
           }
           container ggsn-options {
             description "GGSN interface-specific options";
             uses apply-advanced;
             choice syslog-choice {
               leaf syslog {
                 description "Enable system logging on this interface";
                 type empty;
               }
               leaf no-syslog {
                 description "Don't enable system logging on this interface";
                 type empty;
               }
             }
             choice core-dump-choice {
               leaf core-dump {
                 description "Enable core dumping on this interface";
                 type empty;
               }
               leaf no-core-dump {
                 description "Don't enable core dumping on this interface";
                 type empty;
               }
             }
           }
           container ppp-options {
             description "Point-to-Point Protocol (PPP) interface-specific options";
             uses ppp_options_type;
           }
           container redundancy-options {
             description "Redundancy options";
             uses apply-advanced;
             leaf primary {
               description "Specify the primary interface";
               type union {
                 type jt:interface-device;
                 type string {
                   pattern "<.*>|$.*";
                 }
               }
             }
             leaf secondary {
               description "Specify the secondary interface";
               type union {
                 type jt:interface-device;
                 type string {
                   pattern "<.*>|$.*";
                 }
               }
             }
             container redundancy-peer {
               description "Specify information for peer";
               uses apply-advanced;
               leaf ipaddress {
                 description "Specify the IP address";
                 type jt:ipv4addr;
               }
             }
             container redundancy-local {
               description "Specify information for the local peer";
               uses apply-advanced;
               leaf data-address {
                 description "Specify the HA local data IP address";
                 type jt:ipv4addr;
               }
             }
             leaf routing-instance {
               description "Specify routing-instance for the HA traffic";
               type string;
             }
             leaf replication-threshold {
               description "Duration for which flow should remain active for replication";
               default "180";
               units "seconds";
               type union {
                 type string {
                   pattern "<.*>|$.*";
                 }
                 type uint32 {
                   range "60 .. 3600";
                 }
               }
             }
             container replication-options {
               description "Specify state replication attributes";
               uses apply-advanced;
               leaf mtu {
                 description "Specify the maximal packet size for replicated data";
                 default "1500";
                 type union {
                   type string {
                     pattern "<.*>|$.*";
                   }
                   type uint32 {
                     range "1500 .. 8000";
                   }
                 }
               }
             }
             container replicate-services {
               description "Replicate services state from active to backup";
               uses apply-advanced;
               leaf pgcp {
                 description "Replicate the PGCP service state";
                 type empty;
               }
             }
           }
           container load-balancing-options {
             description "Load-balancing on services pics";
             uses apply-advanced;
             list member-interface {
               key name;
               max-elements 36;
               leaf name {
                 description "Interface name";
                 type union {
                   type jt:interface-device;
                   type string {
                     pattern "<.*>|$.*";
                   }
                 }
               }
               uses apply-advanced;
               container redundancy-group {
                 description "Group id to represent a pair of active-backup mams";
                 leaf description {
                   description "Text description mapping the redundancy group id";
                   type string;
                 }
                 leaf group-id {
                   description "Value for Redundancy-group";
                   type union {
                     type string {
                       pattern "<.*>|$.*";
                     }
                     type uint32 {
                       range "1 .. 18";
                     }
                   }
                 }
               }
             }
             container member-failure-options {
               description "Load balancing member failure handling options";
               uses apply-advanced;
               choice member-failure {
                 case case_1 {
                   container redistribute-all-traffic {
                     presence "enable redistribute-all-traffic";
                     description "On a member failure, redistribute traffic to ams";
                     uses apply-advanced;
                     leaf enable-rejoin {
                       description "Failed member can rejoin after recovery";
                       type empty;
                     }
                   }
                 }
                 case case_2 {
                   container drop-member-traffic {
                     presence "enable drop-member-traffic";
                     description "On a member failure, drop its traffic";
                     uses apply-advanced;
                     leaf rejoin-timeout {
                       description "Wait time(in seconds) for failed member to rejoin";
                       default "120";
                       type union {
                         type string {
                           pattern "<.*>|$.*";
                         }
                         type uint32 {
                           range "0 .. 1000";
                         }
                       }
                     }
                     leaf enable-rejoin {
                       description "Failed member can join after recovery";
                       type empty;
                     }
                   }
                 }
               }
             }
             leaf no-bundle-flap {
               description "No bundle flap on member addition - recommended only with IPSec services";
               type empty;
             }
             container high-availability-options {
               description "High Availability options for Load-balancing";
               uses apply-advanced;
               choice ha-type {
                 case case_1 {
                   container many-to-one {
                     description "N:1 High Availability model";
                     uses apply-advanced;
                     leaf preferred-backup {
                       description "Preferred backup Interface name";
                       type union {
                         type jt:interface-device;
                         type string {
                           pattern "<.*>|$.*";
                         }
                       }
                     }
                   }
                 }
                 case case_2 {
                   container one-to-one {
                     description "1:1 High Availability model";
                     uses apply-advanced;
                     list redundancy-group {
                       key name;
                       ordered-by user;
                       description "Group number for linking HA member for intra-chassis";
                       leaf name {
                         description "Value for HA Redundancy-group";
                         type union {
                           type string {
                             pattern "<.*>|$.*";
                           }
                           type uint32 {
                             range "1 .. 18";
                           }
                         }
                       }
                       leaf preferred-backup {
                         description "Preferred backup Interface name for Redundancy group";
                         type union {
                           type jt:interface-device;
                           type string {
                             pattern "<.*>|$.*";
                           }
                         }
                       }
                     }
                     leaf preferred-backup {
                       description "Preferred backup Interface name";
                       type union {
                         type jt:interface-device;
                         type string {
                           pattern "<.*>|$.*";
                         }
                       }
                     }
                   }
                 }
               }
             }
           }
           container aggregated-inline-services-options {
             description "Aggregated Inline Service interface specific options";
             uses apply-advanced;
             leaf primary-interface {
               description "Specify the primary interface";
               type union {
                 type jt:interface-device;
                 type string {
                   pattern "<.*>|$.*";
                 }
               }
             }
             leaf secondary-interface {
               description "Specify the secondary interface";
               type union {
                 type jt:interface-device;
                 type string {
                   pattern "<.*>|$.*";
                 }
               }
             }
           }
           container anchoring-options {
             description "Groups anchoring PFEs or FPCs together.";
             uses apply-advanced;
             leaf apfe-group-set {
               description "Ties up different anchoring groups to share similar fate";
               type string {
                 length "1 .. 32";
               }
             }
             list primary-list {
               key name;
               description "Primary anchoring PFE name.";
               leaf name {
                 description "Anchoring PFE name.";
                 type string {
                 }
               }
               uses apply-advanced;
             }
             container secondary {
               presence "enable secondary";
               description "Secondary anchoring PFE name.";
               uses apply-advanced;
               leaf anchoring-device-name {
                 description "Anchoring PFE name.";
                 type string {
                 }
               }
             }
             choice mode {
               case case_1 {
                 leaf warm-standby {
                   description "Delayed failover to secondary when primary fails";
                   type empty;
                 }
               }
             }
           }
           container lsq-failure-options {
             description "Link services queuing failure options";
             uses apply-advanced;
             list trigger-link-failure {
               key name;
               ordered-by user;
               description "Link on which to trigger failure";
               leaf name {
                 description "Interface name";
                 type union {
                   type jt:interface-device;
                   type string {
                     pattern "<.*>|$.*";
                   }
                 }
               }
               uses apply-advanced;
             }
             choice no-termination-request-choice {
               leaf no-termination-request {
                 description "Do not send PPP termination requests";
                 type empty;
               }
               leaf no-no-termination-request {
                 description "Don't do not send PPP termination requests";
                 type empty;
               }
             }
           }
           container redundancy-group {
             description "Redundancy group configuration";
             uses apply-advanced;
             list member-interface {
               key name;
               description "Member interface for the redundancy group";
               leaf name {
                 description "Interface name of member";
                 type union {
                   type jt:interface-device;
                   type string {
                     pattern "<.*>|$.*";
                   }
                 }
               }
               uses apply-advanced;
               choice redundancy {
                 case case_1 {
                   leaf active {
                     description "Active interface";
                     type empty;
                   }
                 }
                 case case_2 {
                   leaf backup {
                     description "Backup interface";
                     type empty;
                   }
                 }
               }
             }
             leaf maximum-links {
               type union {
                 type string {
                   pattern "<.*>|$.*";
                 }
                 type uint32 {
                   range "2 .. 32";
                 }
               }
             }
           }
           container services-options {
             description "Services interface-specific options";
             uses apply-advanced;
             container syslog {
               description "Define system log parameters";
               uses log-object;
             }
             container jflow-log {
               description "Define Jflow-log parameters.";
               uses apply-advanced;
               leaf message-rate-limit {
                 description "Maximum jflow-log NAT error events allowed per second from this interface";
                 units "messages per second";
                 type union {
                   type string {
                     pattern "<.*>|$.*";
                   }
                   type uint32 {
                     range "1 .. 2147483647";
                   }
                 }
               }
             }
             container deterministic-nat-configuration-log-interval {
               presence "enable deterministic-nat-configuration-log-interval";
               description "Define Deterministic NAT parameters";
               uses apply-advanced;
               leaf interval {
                 description "Interval in which deterministic NAT logs are generated";
                 units "seconds";
                 type union {
                   type string {
                     pattern "<.*>|$.*";
                   }
                   type uint32 {
                     range "1800 .. 86400";
                   }
                 }
               }
             }
             leaf open-timeout {
               description "Timeout period for TCP session establishment";
               units "seconds";
               type union {
                 type string {
                   pattern "<.*>|$.*";
                 }
                 type uint32 {
                   range "4 .. 300";
                 }
               }
             }
             leaf close-timeout {
               description "Timeout period for TCP session tear-down";
               units "seconds";
               type union {
                 type string {
                   pattern "<.*>|$.*";
                 }
                 type uint32 {
                   range "2 .. 300";
                 }
               }
             }
             leaf inactivity-timeout {
               description "Inactivity timeout period for established sessions (4..86400)";
               units "seconds";
               type union {
                 type uint32;
                 type string {
                   pattern "<.*>|$.*";
                 }
               }
             }
             leaf inactivity-tcp-timeout {
               description "Inactivity timeout period for TCP established sessions";
               units "seconds";
               type union {
                 type string {
                   pattern "<.*>|$.*";
                 }
                 type uint32 {
                   range "4 .. 86400";
                 }
               }
             }
             leaf inactivity-asymm-tcp-timeout {
               description "Inactivity timeout period for asymmetric TCP established sessions";
               units "seconds";
               type union {
                 type string {
                   pattern "<.*>|$.*";
                 }
                 type uint32 {
                   range "4 .. 86400";
                 }
               }
             }
             leaf inactivity-non-tcp-timeout {
               description "Inactivity timeout period for non-TCP established sessions";
               units "seconds";
               type union {
                 type string {
                   pattern "<.*>|$.*";
                 }
                 type uint32 {
                   range "4 .. 86400";
                 }
               }
             }
             leaf session-timeout {
               description "Session timeout period for established sessions";
               units "seconds";
               type union {
                 type string {
                   pattern "<.*>|$.*";
                 }
                 type uint32 {
                   range "4 .. 86400";
                 }
               }
             }
             leaf disable-global-timeout-override {
               description "Disallow overriding  global inactivity or session timeout";
               type empty;
             }
             leaf tcp-tickles {
               description "Number of TCP keep-alive packets to be sent for bi-directional TCP flows";
               default "4";
               type union {
                 type string {
                   pattern "<.*>|$.*";
                 }
                 type uint8 {
                   range "0 .. 30";
                 }
               }
             }
             container trio-flow-offload {
               presence "enable trio-flow-offload";
               description "Allow PIC to offload flows to Trio-based PFE";
               uses apply-advanced;
               leaf minimum-bytes {
                 description "Attempt flow offload after minimum bytes are seen on the flow";
                 type union {
                   type uint32;
                   type string {
                     pattern "<.*>|$.*";
                   }
                 }
               }
             }
             leaf fragment-limit {
               description "Maximum number of fragments allowed for a packet";
               default "64";
               type union {
                 type string {
                   pattern "<.*>|$.*";
                 }
                 type uint8 {
                   range "1 .. 250";
                 }
               }
             }
             leaf reassembly-timeout {
               description "Re-assembly timeout (seconds) for fragments of a packet";
               default "4";
               units "seconds";
               type union {
                 type string {
                   pattern "<.*>|$.*";
                 }
                 type uint8 {
                   range "1 .. 60";
                 }
               }
             }
             leaf cgn-pic {
               description "PIC will be used for Carrier Grade NAT configuration only";
               type empty;
             }
             leaf pba-interim-logging-interval {
               description "Interim logging interval in seconds";
               default "0";
               units "seconds";
               type union {
                 type string {
                   pattern "<.*>|$.*";
                 }
                 type uint32 {
                   range "0 .. 86400";
                 }
               }
             }
             container session-limit {
               presence "enable session-limit";
               description "Session limit";
               uses apply-advanced;
               leaf maximum {
                 description "Maximum number of sessions allowed simultaneously";
                 type string;
               }
               leaf rate {
                 description "Maximum number of new sessions allowed per second";
                 type string;
               }
               leaf cpu-load-threshold {
                 description "CPU limit in percentage for auto-tuning of session rate";
                 units "percent";
                 type union {
                   type string {
                     pattern "<.*>|$.*";
                   }
                   type uint8 {
                     range "1 .. 100";
                   }
                 }
               }
             }
             leaf enable-subscriber-analysis {
               description "Enable subscriber analysis on the interface";
               type empty;
             }
             leaf disable-subscriber-analysis {
               description "Disable subscriber analysis on the interface";
               type empty;
             }
             leaf disable-usp-tracing {
               description "Disable usp tracing on this pic";
               type empty;
             }
             leaf disable-drop-flows {
               description "Disable drop flows on this pic";
               type empty;
             }
             container ignore-errors {
               presence "enable ignore-errors";
               description "Ignore anomalies or errors";
               leaf tcp {
                 description "TCP protocol errors";
                 type empty;
               }
               leaf alg {
                 description "ALG anomalies or errors";
                 type empty;
               }
             }
             container capture {
               description "Packet capture for SFW and NAT on the Services PIC";
               uses apply-advanced;
               leaf capture-size {
                 description "The number of packets to store";
                 type union {
                   type string {
                     pattern "<.*>|$.*";
                   }
                   type uint32 {
                     range "1 .. 344000";
                   }
                 }
               }
               leaf pkt-size {
                 description "Number of bytes to be saved from each packet";
                 type union {
                   type string {
                     pattern "<.*>|$.*";
                   }
                   type uint16 {
                     range "64 .. 15000";
                   }
                 }
               }
               leaf logs-per-packet {
                 description "The number of trace messages stored for each packet";
                 type union {
                   type string {
                     pattern "<.*>|$.*";
                   }
                   type uint16 {
                     range "0 .. 500";
                   }
                 }
               }
               leaf max-log-line-size {
                 description "The maximum length of a stored trace message";
                 type union {
                   type uint8;
                   type string {
                     pattern "<.*>|$.*";
                   }
                 }
               }
               container filter {
                 presence "enable filter";
                 description "Filtering options for the packet capture";
                 uses apply-advanced;
                 container source-ip {
                   description "Filter based on source-ip (and wildcard)";
                   leaf ip {
                     description "Source IP";
                     type jt:ipaddr;
                   }
                   leaf wildcard {
                     description "Source IP wildcard";
                     type jt:ipaddr;
                   }
                 }
                 container dest-ip {
                   description "Filter based on dest-ip (and wildcard)";
                   leaf ip {
                     description "Dest IP";
                     type jt:ipaddr;
                   }
                   leaf wildcard {
                     description "Dest IP wildcard";
                     type jt:ipaddr;
                   }
                 }
                 container sw-sip {
                   description "Filter based on source softwire ip (and wildcard)";
                   leaf ip {
                     description "Source softwire IP";
                     type jt:ipv6addr;
                   }
                   leaf wildcard {
                     description "Source IP wildcard";
                     type jt:ipv6addr;
                   }
                 }
                 container sw-dip {
                   description "Filter based on destination softwire ip (and wildcard)";
                   leaf ip {
                     description "Destination softwire IP";
                     type jt:ipaddr;
                   }
                   leaf wildcard {
                     description "Destination IP wildcard";
                     type jt:ipaddr;
                   }
                 }
                 container sport-range {
                   description "Filter based on source port";
                   leaf low {
                     description "Source port range start";
                     type union {
                       type uint16;
                       type string {
                         pattern "<.*>|$.*";
                       }
                     }
                   }
                   leaf high {
                     description "Source port range end";
                     type union {
                       type uint16;
                       type string {
                         pattern "<.*>|$.*";
                       }
                     }
                   }
                 }
                 container dport-range {
                   description "Filter based on destination port";
                   leaf low {
                     description "Destination port range start";
                     type union {
                       type uint16;
                       type string {
                         pattern "<.*>|$.*";
                       }
                     }
                   }
                   leaf high {
                     description "Destination port range end";
                     type union {
                       type uint16;
                       type string {
                         pattern "<.*>|$.*";
                       }
                     }
                   }
                 }
                 leaf proto {
                   description "Filter based on L4 protocol";
                   type enumeration {
                     enum "icmp" {
                     }
                     enum "tcp" {
                     }
                     enum "udp" {
                     }
                   }
                 }
               }
             }
             container flow {
               description "Define flow parameters";
               uses apply-advanced;
               container traceoptions {
                 description "Trace options for flow services";
                 uses flow-traceoptions-object;
               }
             }
             leaf fpc-pic-information {
               description "Include FPC and PIC slot number in the syslogs";
               type empty;
             }
             leaf utc-timestamp {
               description "Use UTC time for security log timestamps";
               type empty;
             }
             leaf syslog-local-system-timestamp {
               description "Use local system time for services syslog timestamp";
               type empty;
             }
           }
           container t3-options {
             description "T3 interface-specific options";
             uses apply-advanced;
             leaf loopback {
               description "Loopback mode";
               type enumeration {
                 enum "local" {
                   description "Local loopback";
                 }
                 enum "remote" {
                   description "Remote loopback";
                 }
                 enum "payload" {
                   description "Payload loopback";
                 }
               }
             }
             choice long-buildout-choice {
               leaf long-buildout {
                 description "Set hardware to drive line longer than 255 feet";
                 type empty;
               }
               leaf no-long-buildout {
                 description "Don't set hardware to drive line longer than 255 feet";
                 type empty;
               }
             }
             choice loop-timing-choice {
               leaf loop-timing {
                 description "Set loop timing for T3";
                 type empty;
               }
               leaf no-loop-timing {
                 description "Don't set loop timing for T3";
                 type empty;
               }
             }
             choice unframed-choice {
               leaf unframed {
                 description "Enable unframed mode";
                 type empty;
               }
               leaf no-unframed {
                 description "Don't enable unframed mode";
                 type empty;
               }
             }
             container compatibility-mode {
               description "Set CSU compatibility mode";
               choice vendor {
                 case case_1 {
                   container larscom {
                     presence "enable larscom";
                     description "Compatible with Larscom CSU";
                     leaf subrate {
                       description "Set subrate value";
                       type union {
                         type string {
                           pattern "<.*>|$.*";
                         }
                         type uint32 {
                           range "1 .. 14";
                         }
                       }
                     }
                   }
                 }
                 case case_2 {
                   container verilink {
                     presence "enable verilink";
                     description "Compatible with Verilink CSU (not on 2/4-port T3 PIC)";
                     leaf subrate {
                       description "Set subrate value";
                       type union {
                         type string {
                           pattern "<.*>|$.*";
                         }
                         type uint32 {
                           range "1 .. 28";
                         }
                       }
                     }
                   }
                 }
                 case case_3 {
                   container adtran {
                     presence "enable adtran";
                     description "Compatible with Adtran CSU (not on 2/4-port T3 PIC)";
                     leaf subrate {
                       description "Set subrate value";
                       type union {
                         type string {
                           pattern "<.*>|$.*";
                         }
                         type uint32 {
                           range "1 .. 588";
                         }
                       }
                     }
                   }
                 }
                 case case_4 {
                   container kentrox {
                     presence "enable kentrox";
                     description "Compatible with Kentrox CSU";
                     leaf subrate {
                       description "Set subrate value (not on 2/4-port T3 PIC)";
                       type union {
                         type string {
                           pattern "<.*>|$.*";
                         }
                         type uint32 {
                           range "1 .. 69";
                         }
                       }
                     }
                   }
                 }
                 case case_5 {
                   container digital-link {
                     presence "enable digital-link";
                     description "Compatible with Digital Link CSU";
                     leaf subrate {
                       description "Set subrate value";
                       type enumeration {
                         enum "301Kb" {
                           description "301 Kbps";
                         }
                         enum "601Kb" {
                           description "601 Kbps";
                         }
                         enum "902Kb" {
                           description "902 Kbps";
                         }
                         enum "1.2Mb" {
                           description "1.2 Mbps";
                         }
                         enum "1.5Mb" {
                           description "1.5 Mbps";
                         }
                         enum "1.8Mb" {
                           description "1.8 Mbps";
                         }
                         enum "2.1Mb" {
                           description "2.1 Mbps";
                         }
                         enum "2.4Mb" {
                           description "2.4 Mbps";
                         }
                         enum "2.7Mb" {
                           description "2.7 Mbps";
                         }
                         enum "3.0Mb" {
                           description "3.0 Mbps";
                         }
                         enum "3.3Mb" {
                           description "3.3 Mbps";
                         }
                         enum "3.6Mb" {
                           description "3.6 Mbps";
                         }
                         enum "3.9Mb" {
                           description "3.9 Mbps";
                         }
                         enum "4.2Mb" {
                           description "4.2 Mbps";
                         }
                         enum "4.5Mb" {
                           description "4.5 Mbps";
                         }
                         enum "4.8Mb" {
                           description "4.8 Mbps";
                         }
                         enum "5.1Mb" {
                           description "5.1 Mbps";
                         }
                         enum "5.4Mb" {
                           description "5.4 Mbps";
                         }
                         enum "5.7Mb" {
                           description "5.7 Mbps";
                         }
                         enum "6.0Mb" {
                           description "6.0 Mbps";
                         }
                         enum "6.3Mb" {
                           description "6.3 Mbps";
                         }
                         enum "6.6Mb" {
                           description "6.6 Mbps";
                         }
                         enum "6.9Mb" {
                           description "6.9 Mbps";
                         }
                         enum "7.2Mb" {
                           description "7.2 Mbps";
                         }
                         enum "7.5Mb" {
                           description "7.5 Mbps";
                         }
                         enum "7.8Mb" {
                           description "7.8 Mbps";
                         }
                         enum "8.1Mb" {
                           description "8.1 Mbps";
                         }
                         enum "8.4Mb" {
                           description "8.4 Mbps";
                         }
                         enum "8.7Mb" {
                           description "8.7 Mbps";
                         }
                         enum "9.0Mb" {
                           description "9.0 Mbps";
                         }
                         enum "9.3Mb" {
                           description "9.3 Mbps";
                         }
                         enum "9.6Mb" {
                           description "9.6 Mbps";
                         }
                         enum "9.9Mb" {
                           description "9.9 Mbps";
                         }
                         enum "10.2Mb" {
                           description "10.2 Mbps";
                         }
                         enum "10.5Mb" {
                           description "10.5 Mbps";
                         }
                         enum "10.8Mb" {
                           description "10.8 Mbps";
                         }
                         enum "11.1Mb" {
                           description "11.1 Mbps";
                         }
                         enum "11.4Mb" {
                           description "11.4 Mbps";
                         }
                         enum "11.7Mb" {
                           description "11.7 Mbps";
                         }
                         enum "12.0Mb" {
                           description "12.0 Mbps";
                         }
                         enum "12.3Mb" {
                           description "12.3 Mbps";
                         }
                         enum "12.6Mb" {
                           description "12.6 Mbps";
                         }
                         enum "12.9Mb" {
                           description "12.9 Mbps";
                         }
                         enum "13.2Mb" {
                           description "13.2 Mbps";
                         }
                         enum "13.5Mb" {
                           description "13.5 Mbps";
                         }
                         enum "13.8Mb" {
                           description "13.8 Mbps";
                         }
                         enum "14.1Mb" {
                           description "14.1 Mbps";
                         }
                         enum "14.4Mb" {
                           description "14.4 Mbps";
                         }
                         enum "14.7Mb" {
                           description "14.7 Mbps";
                         }
                         enum "15.0Mb" {
                           description "15.0 Mbps";
                         }
                         enum "15.3Mb" {
                           description "15.3 Mbps";
                         }
                         enum "15.6Mb" {
                           description "15.6 Mbps";
                         }
                         enum "15.9Mb" {
                           description "15.9 Mbps";
                         }
                         enum "16.2Mb" {
                           description "16.2 Mbps";
                         }
                         enum "16.5Mb" {
                           description "16.5 Mbps";
                         }
                         enum "16.8Mb" {
                           description "16.8 Mbps";
                         }
                         enum "17.1Mb" {
                           description "17.1 Mbps";
                         }
                         enum "17.4Mb" {
                           description "17.4 Mbps";
                         }
                         enum "17.7Mb" {
                           description "17.7 Mbps";
                         }
                         enum "18.0Mb" {
                           description "18.0 Mbps";
                         }
                         enum "18.3Mb" {
                           description "18.3 Mbps";
                         }
                         enum "18.6Mb" {
                           description "18.6 Mbps";
                         }
                         enum "18.9Mb" {
                           description "18.9 Mbps";
                         }
                         enum "19.2Mb" {
                           description "19.2 Mbps";
                         }
                         enum "19.5Mb" {
                           description "19.5 Mbps";
                         }
                         enum "19.8Mb" {
                           description "19.8 Mbps";
                         }
                         enum "20.1Mb" {
                           description "20.1 Mbps";
                         }
                         enum "20.5Mb" {
                           description "20.5 Mbps";
                         }
                         enum "20.8Mb" {
                           description "20.8 Mbps";
                         }
                         enum "21.1Mb" {
                           description "21.1 Mbps";
                         }
                         enum "21.4Mb" {
                           description "21.4 Mbps";
                         }
                         enum "21.7Mb" {
                           description "21.7 Mbps";
                         }
                         enum "22.0Mb" {
                           description "22.0 Mbps";
                         }
                         enum "22.3Mb" {
                           description "22.3 Mbps";
                         }
                         enum "22.6Mb" {
                           description "22.6 Mbps";
                         }
                         enum "22.9Mb" {
                           description "22.9 Mbps";
                         }
                         enum "23.2Mb" {
                           description "23.2 Mbps";
                         }
                         enum "23.5Mb" {
                           description "23.5 Mbps";
                         }
                         enum "23.8Mb" {
                           description "23.8 Mbps";
                         }
                         enum "24.1Mb" {
                           description "24.1 Mbps";
                         }
                         enum "24.4Mb" {
                           description "24.4 Mbps";
                         }
                         enum "24.7Mb" {
                           description "24.7 Mbps";
                         }
                         enum "25.0Mb" {
                           description "25.0 Mbps";
                         }
                         enum "25.3Mb" {
                           description "25.3 Mbps";
                         }
                         enum "25.6Mb" {
                           description "25.6 Mbps";
                         }
                         enum "25.9Mb" {
                           description "25.9 Mbps";
                         }
                         enum "26.2Mb" {
                           description "26.2 Mbps";
                         }
                         enum "26.5Mb" {
                           description "26.5 Mbps";
                         }
                         enum "26.8Mb" {
                           description "26.8 Mbps";
                         }
                         enum "27.1Mb" {
                           description "27.1 Mbps";
                         }
                         enum "27.4Mb" {
                           description "27.4 Mbps";
                         }
                         enum "27.7Mb" {
                           description "27.7 Mbps";
                         }
                         enum "28.0Mb" {
                           description "28.0 Mbps";
                         }
                         enum "28.3Mb" {
                           description "28.3 Mbps";
                         }
                         enum "28.6Mb" {
                           description "28.6 Mbps";
                         }
                         enum "28.9Mb" {
                           description "28.9 Mbps";
                         }
                         enum "29.2Mb" {
                           description "29.2 Mbps";
                         }
                         enum "29.5Mb" {
                           description "29.5 Mbps";
                         }
                         enum "29.8Mb" {
                           description "29.8 Mbps";
                         }
                         enum "30.1Mb" {
                           description "30.1 Mbps";
                         }
                         enum "30.4Mb" {
                           description "30.4 Mbps";
                         }
                         enum "30.7Mb" {
                           description "30.7 Mbps";
                         }
                         enum "31.0Mb" {
                           description "31.0 Mbps";
                         }
                         enum "31.3Mb" {
                           description "31.3 Mbps";
                         }
                         enum "31.6Mb" {
                           description "31.6 Mbps";
                         }
                         enum "31.9Mb" {
                           description "31.9 Mbps";
                         }
                         enum "32.2Mb" {
                           description "32.2 Mbps";
                         }
                         enum "32.5Mb" {
                           description "32.5 Mbps";
                         }
                         enum "32.8Mb" {
                           description "32.8 Mbps";
                         }
                         enum "33.1Mb" {
                           description "33.1 Mbps";
                         }
                         enum "33.4Mb" {
                           description "33.4 Mbps";
                         }
                         enum "33.7Mb" {
                           description "33.7 Mbps";
                         }
                         enum "34.0Mb" {
                           description "34.0 Mbps";
                         }
                         enum "34.3Mb" {
                           description "34.3 Mbps";
                         }
                         enum "34.6Mb" {
                           description "34.6 Mbps";
                         }
                         enum "34.9Mb" {
                           description "34.9 Mbps";
                         }
                         enum "35.2Mb" {
                           description "35.2 Mbps";
                         }
                         enum "35.5Mb" {
                           description "35.5 Mbps";
                         }
                         enum "35.8Mb" {
                           description "35.8 Mbps";
                         }
                         enum "36.1Mb" {
                           description "36.1 Mbps";
                         }
                         enum "36.4Mb" {
                           description "36.4 Mbps";
                         }
                         enum "36.7Mb" {
                           description "36.7 Mbps";
                         }
                         enum "37.0Mb" {
                           description "37.0 Mbps";
                         }
                         enum "37.3Mb" {
                           description "37.3 Mbps";
                         }
                         enum "37.6Mb" {
                           description "37.6 Mbps";
                         }
                         enum "37.9Mb" {
                           description "37.9 Mbps";
                         }
                         enum "38.2Mb" {
                           description "38.2 Mbps";
                         }
                         enum "38.5Mb" {
                           description "38.5 Mbps";
                         }
                         enum "38.8Mb" {
                           description "38.8 Mbps";
                         }
                         enum "39.1Mb" {
                           description "39.1 Mbps";
                         }
                         enum "39.4Mb" {
                           description "39.4 Mbps";
                         }
                         enum "39.7Mb" {
                           description "39.7 Mbps";
                         }
                         enum "40.0Mb" {
                           description "40.0 Mbps";
                         }
                         enum "40.3Mb" {
                           description "40.3 Mbps";
                         }
                         enum "40.6Mb" {
                           description "40.6 Mbps";
                         }
                         enum "40.9Mb" {
                           description "40.9 Mbps";
                         }
                         enum "41.2Mb" {
                           description "41.2 Mbps";
                         }
                         enum "41.5Mb" {
                           description "41.5 Mbps";
                         }
                         enum "41.8Mb" {
                           description "41.8 Mbps";
                         }
                         enum "42.1Mb" {
                           description "42.1 Mbps";
                         }
                         enum "42.4Mb" {
                           description "42.4 Mbps";
                         }
                         enum "42.7Mb" {
                           description "42.7 Mbps";
                         }
                         enum "43.0Mb" {
                           description "43.0 Mbps";
                         }
                         enum "43.3Mb" {
                           description "43.3 Mbps";
                         }
                         enum "43.6Mb" {
                           description "43.6 Mbps";
                         }
                         enum "43.9Mb" {
                           description "43.9 Mbps";
                         }
                         enum "44.2Mb" {
                           description "44.2 Mbps";
                         }
                       }
                     }
                   }
                 }
               }
             }
             choice payload-scrambler-choice {
               leaf payload-scrambler {
                 description "Enable payload scrambling";
                 type empty;
               }
               leaf no-payload-scrambler {
                 description "Don't enable payload scrambling";
                 type empty;
               }
             }
             choice cbit-parity-choice {
               leaf cbit-parity {
                 description "Enable C-bit parity mode";
                 type empty;
               }
               leaf no-cbit-parity {
                 description "Don't enable C-bit parity mode";
                 type empty;
               }
             }
             leaf fcs {
               description "Frame checksum";
               type enumeration {
                 enum "32" {
                   description "32-bit mode";
                 }
                 enum "16" {
                   description "16-bit mode";
                 }
               }
             }
             leaf idle-cycle-flag {
               description "Value to transmit in idle cycles";
               type enumeration {
                 enum "flags" {
                   description "Transmit 0x7E in idle cycles";
                 }
                 enum "ones" {
                   description "Transmit 0xFF (all ones) in idle cycles";
                 }
               }
             }
             leaf start-end-flag {
               description "Set start/end flags on transmission";
               type enumeration {
                 enum "shared" {
                   description "Share start/end flags on transmit";
                 }
                 enum "filler" {
                   description "Send two idle cycles between start/end flags";
                 }
               }
             }
             choice feac-loop-respond-choice {
               leaf feac-loop-respond {
                 description "Respond to FEAC loop requests";
                 type empty;
               }
               leaf no-feac-loop-respond {
                 description "Don't respond to FEAC loop requests";
                 type empty;
               }
             }
             leaf bert-algorithm {
               description "Set BERT algorithm";
               type enumeration {
                 enum "pseudo-2e3" {
                   description "Pattern is 2^3 - 1";
                 }
                 enum "pseudo-2e4" {
                   description "Pattern is 2^4 - 1";
                 }
                 enum "pseudo-2e5" {
                   description "Pattern is 2^5 - 1";
                 }
                 enum "pseudo-2e6" {
                   description "Pattern is 2^6 - 1";
                 }
                 enum "pseudo-2e7" {
                   description "Pattern is 2^7 - 1";
                 }
                 enum "pseudo-2e9-o153" {
                   description "Pattern is 2^9 - 1 (per O.153 standard)";
                 }
                 enum "pseudo-2e10" {
                   description "Pattern is 2^10 - 1";
                 }
                 enum "pseudo-2e11-o152" {
                   description "Pattern is 2^11 -1 (per O.152 standard)";
                 }
                 enum "pseudo-2e15-o151" {
                   description "Pattern is 2^15 - 1 (per O.151 standard)";
                 }
                 enum "pseudo-2e17" {
                   description "Pattern is 2^17 - 1";
                 }
                 enum "pseudo-2e18" {
                   description "Pattern is 2^18 - 1";
                 }
                 enum "pseudo-2e20-o153" {
                   description "Pattern is 2^20 - 1 (per O.153 standard)";
                 }
                 enum "pseudo-2e20-o151" {
                   description "Pattern is 2^20 - 1 (per O.151 standard)";
                 }
                 enum "pseudo-2e21" {
                   description "Pattern is 2^21 - 1";
                 }
                 enum "pseudo-2e22" {
                   description "Pattern is 2^22 - 1";
                 }
                 enum "pseudo-2e23-o151" {
                   description "Pattern is 2^23 (per O.151 standard)";
                 }
                 enum "pseudo-2e25" {
                   description "Pattern is 2^25 - 1";
                 }
                 enum "pseudo-2e28" {
                   description "Pattern is 2^28 - 1";
                 }
                 enum "pseudo-2e29" {
                   description "Pattern is 2^29 - 1";
                 }
                 enum "pseudo-2e31" {
                   description "Pattern is 2^31 - 1";
                 }
                 enum "pseudo-2e32" {
                   description "Pattern is 2^32 - 1";
                 }
                 enum "all-ones-repeating" {
                   description "Repeating one bits";
                 }
                 enum "all-zeros-repeating" {
                   description "Repeating zero bits";
                 }
                 enum "alternating-ones-zeros" {
                   description "Alternating ones and zeros";
                 }
                 enum "alternating-double-ones-zeros" {
                   description "Alternating pairs of ones and zeros";
                 }
                 enum "repeating-3-in-24" {
                   description "3 bits in 24 are set";
                 }
                 enum "repeating-1-in-8" {
                   description "1 bit in 8 is set";
                 }
                 enum "repeating-1-in-4" {
                   description "1 bit in 4 is set";
                 }
               }
             }
             leaf bert-error-rate {
               description "Bit error rate (10^-n for n > 0, and zero for n = 0)";
               type union {
                 type string {
                   pattern "<.*>|$.*";
                 }
                 type uint32 {
                   range "0 .. 7";
                 }
               }
             }
             leaf bert-period {
               description "Length of BERT test";
               units "seconds";
               type union {
                 type string {
                   pattern "<.*>|$.*";
                 }
                 type uint32 {
                   range "1 .. 240";
                 }
               }
             }
             leaf buildout {
               description "Line buildout";
               units "feet";
               type union {
                 type string {
                   pattern "<.*>|$.*";
                 }
                 type uint32 {
                   range "0 .. 450";
                 }
               }
             }
             leaf atm-encapsulation {
               description "DS-3 interface encapsulation";
               type enumeration {
                 enum "plcp" {
                   description "PLCP encapsulation";
                 }
                 enum "direct" {
                   description "ATM direct mapping";
                 }
               }
             }
           }
           container e3-options {
             description "E3 interface-specific options";
             uses apply-advanced;
             leaf loopback {
               description "Loopback mode";
               type enumeration {
                 enum "local" {
                   description "Local loopback";
                 }
                 enum "remote" {
                   description "Remote loopback";
                 }
               }
             }
             choice unframed-choice {
               leaf unframed {
                 description "Enable unframed mode";
                 type empty;
               }
               leaf no-unframed {
                 description "Don't enable unframed mode";
                 type empty;
               }
             }
             container compatibility-mode {
               description "Set CSU compatibility mode";
               choice vendor {
                 case case_1 {
                   leaf larscom {
                     description "Compatible with Larscom CSU (only non IQ E3 interfaces)";
                     type empty;
                   }
                 }
                 case case_2 {
                   container digital-link {
                     presence "enable digital-link";
                     description "Compatible with Digital Link CSU";
                     leaf subrate {
                       description "Set subrate value";
                       type enumeration {
                         enum "358Kb" {
                           description "358 Kbps";
                         }
                         enum "716Kb" {
                           description "716 Kbps";
                         }
                         enum "1.1Mb" {
                           description "1.1 Mbps";
                         }
                         enum "1.4Mb" {
                           description "1.4 Mbps";
                         }
                         enum "1.8Mb" {
                           description "1.8 Mbps";
                         }
                         enum "2.1Mb" {
                           description "2.1 Mbps";
                         }
                         enum "2.5Mb" {
                           description "2.5 Mbps";
                         }
                         enum "2.9Mb" {
                           description "2.9 Mbps";
                         }
                         enum "3.2Mb" {
                           description "3.2 Mbps";
                         }
                         enum "3.6Mb" {
                           description "3.6 Mbps";
                         }
                         enum "3.9Mb" {
                           description "3.9 Mbps";
                         }
                         enum "4.3Mb" {
                           description "4.3 Mbps";
                         }
                         enum "4.7Mb" {
                           description "4.7 Mbps";
                         }
                         enum "5.0Mb" {
                           description "5.0 Mbps";
                         }
                         enum "5.4Mb" {
                           description "5.4 Mbps";
                         }
                         enum "5.7Mb" {
                           description "5.7 Mbps";
                         }
                         enum "6.1Mb" {
                           description "6.1 Mbps";
                         }
                         enum "6.4Mb" {
                           description "6.4 Mbps";
                         }
                         enum "6.8Mb" {
                           description "6.8 Mbps";
                         }
                         enum "7.2Mb" {
                           description "7.2 Mbps";
                         }
                         enum "7.5Mb" {
                           description "7.5 Mbps";
                         }
                         enum "7.9Mb" {
                           description "7.9 Mbps";
                         }
                         enum "8.2Mb" {
                           description "8.2 Mbps";
                         }
                         enum "8.6Mb" {
                           description "8.6 Mbps";
                         }
                         enum "9.0Mb" {
                           description "9.0 Mbps";
                         }
                         enum "9.3Mb" {
                           description "9.3 Mbps";
                         }
                         enum "9.7Mb" {
                           description "9.7 Mbps";
                         }
                         enum "10.0Mb" {
                           description "10.0 Mbps";
                         }
                         enum "10.4Mb" {
                           description "10.4 Mbps";
                         }
                         enum "10.7Mb" {
                           description "10.7 Mbps";
                         }
                         enum "11.1Mb" {
                           description "11.1 Mbps";
                         }
                         enum "11.5Mb" {
                           description "11.5 Mbps";
                         }
                         enum "11.8Mb" {
                           description "11.8 Mbps";
                         }
                         enum "12.2Mb" {
                           description "12.2 Mbps";
                         }
                         enum "12.5Mb" {
                           description "12.5 Mbps";
                         }
                         enum "12.9Mb" {
                           description "12.9 Mbps";
                         }
                         enum "13.2Mb" {
                           description "13.2 Mbps";
                         }
                         enum "13.6Mb" {
                           description "13.6 Mbps";
                         }
                         enum "14.0Mb" {
                           description "14.0 Mbps";
                         }
                         enum "14.3Mb" {
                           description "14.3 Mbps";
                         }
                         enum "14.7Mb" {
                           description "14.7 Mbps";
                         }
                         enum "15.0Mb" {
                           description "15.0 Mbps";
                         }
                         enum "15.4Mb" {
                           description "15.4 Mbps";
                         }
                         enum "15.8Mb" {
                           description "15.8 Mbps";
                         }
                         enum "16.1Mb" {
                           description "16.1 Mbps";
                         }
                         enum "16.5Mb" {
                           description "16.5 Mbps";
                         }
                         enum "16.8Mb" {
                           description "16.8 Mbps";
                         }
                         enum "17.2Mb" {
                           description "17.2 Mbps";
                         }
                         enum "17.5Mb" {
                           description "17.5 Mbps";
                         }
                         enum "17.9Mb" {
                           description "17.9 Mbps";
                         }
                         enum "18.3Mb" {
                           description "18.3 Mbps";
                         }
                         enum "18.6Mb" {
                           description "18.6 Mbps";
                         }
                         enum "19.0Mb" {
                           description "19.0 Mbps";
                         }
                         enum "19.3Mb" {
                           description "19.3 Mbps";
                         }
                         enum "19.7Mb" {
                           description "19.7 Mbps";
                         }
                         enum "20.0Mb" {
                           description "20.0 Mbps";
                         }
                         enum "20.4Mb" {
                           description "20.4 Mbps";
                         }
                         enum "20.8Mb" {
                           description "20.8 Mbps";
                         }
                         enum "21.1Mb" {
                           description "21.1 Mbps";
                         }
                         enum "21.5Mb" {
                           description "21.5 Mbps";
                         }
                         enum "21.8Mb" {
                           description "21.8 Mbps";
                         }
                         enum "22.2Mb" {
                           description "22.2 Mbps";
                         }
                         enum "22.6Mb" {
                           description "22.6 Mbps";
                         }
                         enum "22.9Mb" {
                           description "22.9 Mbps";
                         }
                         enum "23.3Mb" {
                           description "23.3 Mbps";
                         }
                         enum "23.6Mb" {
                           description "23.6 Mbps";
                         }
                         enum "24.0Mb" {
                           description "24.0 Mbps";
                         }
                         enum "24.3Mb" {
                           description "24.3 Mbps";
                         }
                         enum "24.7Mb" {
                           description "24.7 Mbps";
                         }
                         enum "25.1Mb" {
                           description "25.1 Mbps";
                         }
                         enum "25.4Mb" {
                           description "25.4 Mbps";
                         }
                         enum "25.8Mb" {
                           description "25.8 Mbps";
                         }
                         enum "26.1Mb" {
                           description "26.1 Mbps";
                         }
                         enum "26.5Mb" {
                           description "26.5 Mbps";
                         }
                         enum "26.9Mb" {
                           description "26.9 Mbps";
                         }
                         enum "27.2Mb" {
                           description "27.2 Mbps";
                         }
                         enum "27.6Mb" {
                           description "27.6 Mbps";
                         }
                         enum "27.9Mb" {
                           description "27.9 Mbps";
                         }
                         enum "28.3Mb" {
                           description "28.3 Mbps";
                         }
                         enum "28.6Mb" {
                           description "28.6 Mbps";
                         }
                         enum "29.0Mb" {
                           description "29.0 Mbps";
                         }
                         enum "29.4Mb" {
                           description "29.4 Mbps";
                         }
                         enum "29.7Mb" {
                           description "29.7 Mbps";
                         }
                         enum "30.1Mb" {
                           description "30.1 Mbps";
                         }
                         enum "30.4Mb" {
                           description "30.4 Mbps";
                         }
                         enum "30.8Mb" {
                           description "30.8 Mbps";
                         }
                         enum "31.1Mb" {
                           description "31.1 Mbps";
                         }
                         enum "31.5Mb" {
                           description "31.5 Mbps";
                         }
                         enum "31.9Mb" {
                           description "31.9 Mbps";
                         }
                         enum "32.2Mb" {
                           description "32.2 Mbps";
                         }
                         enum "32.6Mb" {
                           description "32.6 Mbps";
                         }
                         enum "32.9Mb" {
                           description "32.9 Mbps";
                         }
                         enum "33.3Mb" {
                           description "33.3 Mbps";
                         }
                         enum "33.7Mb" {
                           description "33.7 Mbps";
                         }
                         enum "34.0Mb" {
                           description "34.0 Mbps";
                         }
                       }
                     }
                   }
                 }
                 case case_3 {
                   container kentrox {
                     presence "enable kentrox";
                     description "Compatible with Kentrox CSU";
                     leaf subrate {
                       description "Set subrate value (only for E3 IQ interfaces)";
                       type union {
                         type string {
                           pattern "<.*>|$.*";
                         }
                         type uint32 {
                           range "1 .. 48";
                         }
                       }
                     }
                   }
                 }
               }
             }
             choice payload-scrambler-choice {
               leaf payload-scrambler {
                 description "Enable payload scrambling";
                 type empty;
               }
               leaf no-payload-scrambler {
                 description "Don't enable payload scrambling";
                 type empty;
               }
             }
             leaf fcs {
               description "Frame checksum";
               type enumeration {
                 enum "32" {
                   description "32-bit mode";
                 }
                 enum "16" {
                   description "16-bit mode";
                 }
               }
             }
             leaf idle-cycle-flag {
               description "Value to transmit in idle cycles";
               type enumeration {
                 enum "flags" {
                   description "Transmit 0x7E in idle cycles";
                 }
                 enum "ones" {
                   description "Transmit 0xFF (all ones) in idle cycles";
                 }
               }
             }
             leaf invert-data {
               description "Invert data";
               type empty;
             }
             leaf start-end-flag {
               description "Set start/end flags on transmission";
               type enumeration {
                 enum "shared" {
                   description "Share start/end flags on transmit";
                 }
                 enum "filler" {
                   description "Send two idle cycles between start/end flags";
                 }
               }
             }
             leaf bert-algorithm {
               description "Set BERT algorithm";
               type enumeration {
                 enum "pseudo-2e3" {
                   description "Pattern is 2^3 - 1";
                 }
                 enum "pseudo-2e4" {
                   description "Pattern is 2^4 - 1";
                 }
                 enum "pseudo-2e5" {
                   description "Pattern is 2^5 - 1";
                 }
                 enum "pseudo-2e6" {
                   description "Pattern is 2^6 - 1";
                 }
                 enum "pseudo-2e7" {
                   description "Pattern is 2^7 - 1";
                 }
                 enum "pseudo-2e9-o153" {
                   description "Pattern is 2^9 - 1 (per O.153 standard)";
                 }
                 enum "pseudo-2e10" {
                   description "Pattern is 2^10 - 1";
                 }
                 enum "pseudo-2e11-o152" {
                   description "Pattern is 2^11 -1 (per O.152 standard)";
                 }
                 enum "pseudo-2e15-o151" {
                   description "Pattern is 2^15 - 1 (per O.151 standard)";
                 }
                 enum "pseudo-2e17" {
                   description "Pattern is 2^17 - 1";
                 }
                 enum "pseudo-2e18" {
                   description "Pattern is 2^18 - 1";
                 }
                 enum "pseudo-2e20-o153" {
                   description "Pattern is 2^20 - 1 (per O.153 standard)";
                 }
                 enum "pseudo-2e20-o151" {
                   description "Pattern is 2^20 - 1 (per O.151 standard)";
                 }
                 enum "pseudo-2e21" {
                   description "Pattern is 2^21 - 1";
                 }
                 enum "pseudo-2e22" {
                   description "Pattern is 2^22 - 1";
                 }
                 enum "pseudo-2e23-o151" {
                   description "Pattern is 2^23 (per O.151 standard)";
                 }
                 enum "pseudo-2e25" {
                   description "Pattern is 2^25 - 1";
                 }
                 enum "pseudo-2e28" {
                   description "Pattern is 2^28 - 1";
                 }
                 enum "pseudo-2e29" {
                   description "Pattern is 2^29 - 1";
                 }
                 enum "pseudo-2e31" {
                   description "Pattern is 2^31 - 1";
                 }
                 enum "pseudo-2e32" {
                   description "Pattern is 2^32 - 1";
                 }
                 enum "all-ones-repeating" {
                   description "Repeating one bits";
                 }
                 enum "all-zeros-repeating" {
                   description "Repeating zero bits";
                 }
                 enum "alternating-ones-zeros" {
                   description "Alternating ones and zeros";
                 }
                 enum "alternating-double-ones-zeros" {
                   description "Alternating pairs of ones and zeros";
                 }
                 enum "repeating-3-in-24" {
                   description "3 bits in 24 are set";
                 }
                 enum "repeating-1-in-8" {
                   description "1 bit in 8 is set";
                 }
                 enum "repeating-1-in-4" {
                   description "1 bit in 4 is set";
                 }
               }
             }
             leaf bert-error-rate {
               description "Bit error rate (10^-n for n > 0, and zero for n = 0)";
               type union {
                 type string {
                   pattern "<.*>|$.*";
                 }
                 type uint32 {
                   range "0 .. 7";
                 }
               }
             }
             leaf bert-period {
               description "Length of BERT test";
               units "seconds";
               type union {
                 type string {
                   pattern "<.*>|$.*";
                 }
                 type uint32 {
                   range "1 .. 240";
                 }
               }
             }
             leaf buildout {
               description "Line buildout";
               units "feet";
               type union {
                 type string {
                   pattern "<.*>|$.*";
                 }
                 type uint32 {
                   range "0 .. 450";
                 }
               }
             }
             leaf atm-encapsulation {
               description "E3 interface encapsulation";
               type enumeration {
                 enum "plcp" {
                   description "PLCP encapsulation";
                 }
                 enum "direct" {
                   description "ATM direct mapping";
                 }
               }
             }
             leaf framing {
               description "E3 line format";
               type enumeration {
                 enum "g.751" {
                   description "G.751 format";
                 }
                 enum "g.832" {
                   description "G.832 format";
                 }
               }
             }
           }
           container e1-options {
             description "E1 interface-specific options";
             uses apply-advanced;
             leaf timeslots {
               description "Timeslots (1..32); for example, 1-4,6,9-11,32 (no space)";
               type string;
             }
             leaf loopback {
               description "Loopback mode";
               type enumeration {
                 enum "local" {
                   description "Local loopback";
                 }
                 enum "remote" {
                   description "Remote loopback";
                 }
               }
             }
             leaf framing {
               description "Framing mode";
               type enumeration {
                 enum "g704" {
                   description "G704 mode with CRC4";
                 }
                 enum "unframed" {
                   description "Unframed mode";
                 }
                 enum "g704-no-crc4" {
                   description "G704 mode without CRC4";
                 }
               }
             }
             leaf fcs {
               description "Frame checksum";
               type enumeration {
                 enum "32" {
                   description "32-bit mode";
                 }
                 enum "16" {
                   description "16-bit mode";
                 }
               }
             }
             leaf invert-data {
               description "Invert data";
               type empty;
             }
             leaf idle-cycle-flag {
               description "Value to transmit in idle cycles";
               type enumeration {
                 enum "flags" {
                   description "Transmit 0x7E in idle cycles";
                 }
                 enum "ones" {
                   description "Transmit 0xFF (all ones) in idle cycles";
                 }
               }
             }
             leaf start-end-flag {
               description "Set start/end flags on transmission";
               type enumeration {
                 enum "shared" {
                   description "Share start/end flags on transmit";
                 }
                 enum "filler" {
                   description "Send two idle cycles between start/end flags";
                 }
               }
             }
             leaf bert-algorithm {
               description "Set BERT algorithm";
               type enumeration {
                 enum "pseudo-2e3" {
                   description "Pattern is 2^3 - 1";
                 }
                 enum "pseudo-2e4" {
                   description "Pattern is 2^4 - 1";
                 }
                 enum "pseudo-2e5" {
                   description "Pattern is 2^5 - 1";
                 }
                 enum "pseudo-2e6" {
                   description "Pattern is 2^6 - 1";
                 }
                 enum "pseudo-2e7" {
                   description "Pattern is 2^7 - 1";
                 }
                 enum "pseudo-2e9-o153" {
                   description "Pattern is 2^9 - 1 (per O.153 standard)";
                 }
                 enum "pseudo-2e10" {
                   description "Pattern is 2^10 - 1";
                 }
                 enum "pseudo-2e11-o152" {
                   description "Pattern is 2^11 -1 (per O.152 standard)";
                 }
                 enum "pseudo-2e15-o151" {
                   description "Pattern is 2^15 - 1 (per O.151 standard)";
                 }
                 enum "pseudo-2e17" {
                   description "Pattern is 2^17 - 1";
                 }
                 enum "pseudo-2e18" {
                   description "Pattern is 2^18 - 1";
                 }
                 enum "pseudo-2e20-o153" {
                   description "Pattern is 2^20 - 1 (per O.153 standard)";
                 }
                 enum "pseudo-2e20-o151" {
                   description "Pattern is 2^20 - 1 (per O.151 standard)";
                 }
                 enum "pseudo-2e21" {
                   description "Pattern is 2^21 - 1";
                 }
                 enum "pseudo-2e22" {
                   description "Pattern is 2^22 - 1";
                 }
                 enum "pseudo-2e23-o151" {
                   description "Pattern is 2^23 (per O.151 standard)";
                 }
                 enum "pseudo-2e25" {
                   description "Pattern is 2^25 - 1";
                 }
                 enum "pseudo-2e28" {
                   description "Pattern is 2^28 - 1";
                 }
                 enum "pseudo-2e29" {
                   description "Pattern is 2^29 - 1";
                 }
                 enum "pseudo-2e31" {
                   description "Pattern is 2^31 - 1";
                 }
                 enum "pseudo-2e32" {
                   description "Pattern is 2^32 - 1";
                 }
                 enum "all-ones-repeating" {
                   description "Repeating one bits";
                 }
                 enum "all-zeros-repeating" {
                   description "Repeating zero bits";
                 }
                 enum "alternating-ones-zeros" {
                   description "Alternating ones and zeros";
                 }
                 enum "alternating-double-ones-zeros" {
                   description "Alternating pairs of ones and zeros";
                 }
                 enum "repeating-3-in-24" {
                   description "3 bits in 24 are set";
                 }
                 enum "repeating-1-in-8" {
                   description "1 bit in 8 is set";
                 }
                 enum "repeating-1-in-4" {
                   description "1 bit in 4 is set";
                 }
               }
             }
             leaf bert-error-rate {
               description "Bit error rate (10^-n for n > 0, and zero for n = 0)";
               type union {
                 type string {
                   pattern "<.*>|$.*";
                 }
                 type uint32 {
                   range "0 .. 7";
                 }
               }
             }
             leaf bert-period {
               description "Length of BERT test";
               units "seconds";
               type union {
                 type string {
                   pattern "<.*>|$.*";
                 }
                 type uint32 {
                   range "1 .. 86400";
                 }
               }
             }
           }
           container t1-options {
             description "T1 interface-specific options";
             uses apply-advanced;
             leaf timeslots {
               description "Timeslots (1..24; for example, 1-3,4,9,22-24 (no space)";
               type string;
             }
             leaf voice-timeslots {
               description "Voice timeslots (1..24),for example, 1-3,4,9,22-24 (no space)";
               type string;
             }
             leaf disable-remote-alarm-detection {
               description "Disable detection of a remote alarm";
               type enumeration {
                 enum "yellow" {
                   description "Disable yellow alarm detection";
                 }
               }
             }
             leaf loopback {
               description "Loopback mode";
               type enumeration {
                 enum "local" {
                   description "Local loopback";
                 }
                 enum "remote" {
                   description "Remote loopback";
                 }
                 enum "payload" {
                   description "Payload loopback";
                 }
               }
             }
             leaf buildout {
               description "Line buildout";
               type enumeration {
                 enum "0-132" {
                   description "Line buildout is between 0-132 feet";
                 }
                 enum "133-265" {
                   description "Line buildout is between 133-265 feet";
                 }
                 enum "266-398" {
                   description "Line buildout is between 266-398 feet";
                 }
                 enum "399-531" {
                   description "Line buildout is between 399-531 feet";
                 }
                 enum "532-655" {
                   description "Line buildout is between 532-655 feet";
                 }
                 enum "long-0db" {
                   description "Long buildout with 0 dB transmit attenuation";
                 }
                 enum "long-7.5db" {
                   description "Long buildout with 7.5 dB transmit attenuation";
                 }
                 enum "long-15db" {
                   description "Long buildout with 15 dB transmit attenuation";
                 }
                 enum "long-22.5db" {
                   description "Long buildout with 22.5 dB transmit attenuation";
                 }
               }
             }
             leaf byte-encoding {
               description "Byte encoding";
               type enumeration {
                 enum "nx64" {
                   description "8 bits per byte";
                 }
                 enum "nx56" {
                   description "7 bits per byte";
                 }
               }
             }
             leaf line-encoding {
               description "Line encoding";
               type enumeration {
                 enum "ami" {
                   description "Automatic mark inversion";
                 }
                 enum "b8zs" {
                   description "8-bit zero suppression";
                 }
               }
             }
             leaf invert-data {
               description "Invert data";
               type empty;
             }
             leaf framing {
               description "Framing mode";
               type enumeration {
                 enum "sf" {
                   description "Super frame";
                 }
                 enum "esf" {
                   description "Extended super frame";
                 }
               }
             }
             leaf fcs {
               description "Frame checksum";
               type enumeration {
                 enum "32" {
                   description "32-bit mode";
                 }
                 enum "16" {
                   description "16-bit mode";
                 }
               }
             }
             leaf idle-cycle-flag {
               description "Value to transmit in idle cycles";
               type enumeration {
                 enum "flags" {
                   description "Transmit 0x7E in idle cycles";
                 }
                 enum "ones" {
                   description "Transmit 0xFF (all ones) in idle cycles";
                 }
               }
             }
             leaf start-end-flag {
               description "Set start/end flags on transmission";
               type enumeration {
                 enum "shared" {
                   description "Share start/end flags on transmit";
                 }
                 enum "filler" {
                   description "Send two idle cycles between start/end flags";
                 }
               }
             }
             leaf bert-algorithm {
               description "Set BERT algorithm";
               type enumeration {
                 enum "pseudo-2e3" {
                   description "Pattern is 2^3 - 1";
                 }
                 enum "pseudo-2e4" {
                   description "Pattern is 2^4 - 1";
                 }
                 enum "pseudo-2e5" {
                   description "Pattern is 2^5 - 1";
                 }
                 enum "pseudo-2e6" {
                   description "Pattern is 2^6 - 1";
                 }
                 enum "pseudo-2e7" {
                   description "Pattern is 2^7 - 1";
                 }
                 enum "pseudo-2e9-o153" {
                   description "Pattern is 2^9 - 1 (per O.153 standard)";
                 }
                 enum "pseudo-2e10" {
                   description "Pattern is 2^10 - 1";
                 }
                 enum "pseudo-2e11-o152" {
                   description "Pattern is 2^11 -1 (per O.152 standard)";
                 }
                 enum "pseudo-2e15-o151" {
                   description "Pattern is 2^15 - 1 (per O.151 standard)";
                 }
                 enum "pseudo-2e17" {
                   description "Pattern is 2^17 - 1";
                 }
                 enum "pseudo-2e18" {
                   description "Pattern is 2^18 - 1";
                 }
                 enum "pseudo-2e20-o153" {
                   description "Pattern is 2^20 - 1 (per O.153 standard)";
                 }
                 enum "pseudo-2e20-o151" {
                   description "Pattern is 2^20 - 1 (per O.151 standard)";
                 }
                 enum "pseudo-2e21" {
                   description "Pattern is 2^21 - 1";
                 }
                 enum "pseudo-2e22" {
                   description "Pattern is 2^22 - 1";
                 }
                 enum "pseudo-2e23-o151" {
                   description "Pattern is 2^23 (per O.151 standard)";
                 }
                 enum "pseudo-2e25" {
                   description "Pattern is 2^25 - 1";
                 }
                 enum "pseudo-2e28" {
                   description "Pattern is 2^28 - 1";
                 }
                 enum "pseudo-2e29" {
                   description "Pattern is 2^29 - 1";
                 }
                 enum "pseudo-2e31" {
                   description "Pattern is 2^31 - 1";
                 }
                 enum "pseudo-2e32" {
                   description "Pattern is 2^32 - 1";
                 }
                 enum "all-ones-repeating" {
                   description "Repeating one bits";
                 }
                 enum "all-zeros-repeating" {
                   description "Repeating zero bits";
                 }
                 enum "alternating-ones-zeros" {
                   description "Alternating ones and zeros";
                 }
                 enum "alternating-double-ones-zeros" {
                   description "Alternating pairs of ones and zeros";
                 }
                 enum "repeating-3-in-24" {
                   description "3 bits in 24 are set";
                 }
                 enum "repeating-1-in-8" {
                   description "1 bit in 8 is set";
                 }
                 enum "repeating-1-in-4" {
                   description "1 bit in 4 is set";
                 }
               }
             }
             leaf bert-error-rate {
               description "Bit error rate (10^-n for n > 0, and zero for n = 0)";
               type union {
                 type string {
                   pattern "<.*>|$.*";
                 }
                 type uint32 {
                   range "0 .. 7";
                 }
               }
             }
             leaf bert-period {
               description "Length of BERT test";
               units "seconds";
               type union {
                 type string {
                   pattern "<.*>|$.*";
                 }
                 type uint32 {
                   range "1 .. 86400";
                 }
               }
             }
             leaf remote-loopback-respond {
               description "Respond to loop requests from remote end";
               type empty;
             }
             leaf crc-major-alarm-threshold {
               description "CRC Major alarm threshold value";
               default "5e-5";
               type enumeration {
                 enum "1e-3" {
                   description "1 crc error in 10^3 bits";
                 }
                 enum "5e-4" {
                   description "5 crc errors in 10^4 bits";
                 }
                 enum "1e-4" {
                   description "1 crc error in 10^4 bits";
                 }
                 enum "5e-5" {
                   description "5 crc errors in 10^5 bits";
                 }
                 enum "1e-5" {
                   description "1 crc error in 10^5 bits";
                 }
               }
             }
             leaf crc-minor-alarm-threshold {
               description "CRC Minor alarm threshold value";
               default "5e-6";
               type enumeration {
                 enum "1e-3" {
                   description "1 crc error in 10^3 bits";
                 }
                 enum "5e-4" {
                   description "5 crc errors in 10^4 bits";
                 }
                 enum "1e-4" {
                   description "1 crc error in 10^4 bits";
                 }
                 enum "5e-5" {
                   description "5 crc errors in 10^5 bits";
                 }
                 enum "1e-5" {
                   description "1 crc error in 10^5 bits";
                 }
                 enum "5e-6" {
                   description "5 crc errors in 10^6 bits";
                 }
                 enum "1e-6" {
                   description "1 crc error in 10^6 bits";
                 }
               }
             }
             leaf alarm-compliance {
               description "Enforce standard for alarm reporting";
               type enumeration {
                 enum "accunet-t1-5-service" {
                   description "T1.5 interface specification";
                 }
               }
             }
           }
           container ds0-options {
             description "DS-0 interface-specific options";
             uses apply-advanced;
             leaf loopback {
               description "Loopback mode";
               type enumeration {
                 enum "payload" {
                   description "Payload loopback";
                 }
               }
             }
             leaf byte-encoding {
               description "Byte encoding";
               type enumeration {
                 enum "nx64" {
                   description "8 bits per byte";
                 }
                 enum "nx56" {
                   description "7 bits per byte";
                 }
               }
             }
             leaf invert-data {
               description "Invert data";
               type empty;
             }
             leaf fcs {
               description "Frame checksum";
               type enumeration {
                 enum "32" {
                   description "32-bit mode";
                 }
                 enum "16" {
                   description "16-bit mode";
                 }
               }
             }
             leaf idle-cycle-flag {
               description "Value to transmit in idle cycles";
               type enumeration {
                 enum "flags" {
                   description "Transmit 0x7E in idle cycles";
                 }
                 enum "ones" {
                   description "Transmit 0xFF (all ones) in idle cycles";
                 }
               }
             }
             leaf start-end-flag {
               description "Set start/end flags on transmission";
               type enumeration {
                 enum "shared" {
                   description "Share start/end flags on transmit";
                 }
                 enum "filler" {
                   description "Send two idle cycles between start/end flags";
                 }
               }
             }
             leaf bert-algorithm {
               description "Set BERT algorithm";
               type enumeration {
                 enum "pseudo-2e11-o152" {
                   description "Pattern is 2^11 -1 (per O.152 standard)";
                 }
                 enum "pseudo-2e15-o151" {
                   description "Pattern is 2^15 - 1 (per O.151 standard)";
                 }
                 enum "pseudo-2e20-o153" {
                   description "Pattern is 2^20 - 1 (per O.153 standard)";
                 }
                 enum "pseudo-2e20-o151" {
                   description "Pattern is 2^20 - 1 (per O.151 standard)";
                 }
                 enum "all-ones-repeating" {
                   description "Repeating one bits";
                 }
                 enum "all-zeros-repeating" {
                   description "Repeating zero bits";
                 }
                 enum "alternating-ones-zeros" {
                   description "Alternating ones and zeros";
                 }
                 enum "alternating-double-ones-zeros" {
                   description "Alternating pairs of ones and zeros";
                 }
                 enum "repeating-3-in-24" {
                   description "3 bits in 24 are set";
                 }
                 enum "repeating-1-in-8" {
                   description "1 bit in 8 is set";
                 }
                 enum "repeating-1-in-4" {
                   description "1 bit in 4 is set";
                 }
                 enum "repeating-1-in-16" {
                   description "1 bit in 16 is set";
                 }
               }
             }
             leaf bert-error-rate {
               description "Bit error rate (10^-n for n > 0, and zero for n = 0)";
               type union {
                 type string {
                   pattern "<.*>|$.*";
                 }
                 type uint32 {
                   range "0 .. 7";
                 }
               }
             }
             leaf bert-period {
               description "Length of BERT test";
               units "seconds";
               type union {
                 type string {
                   pattern "<.*>|$.*";
                 }
                 type uint32 {
                   range "1 .. 240";
                 }
               }
             }
           }
           container serial-options {
             description "Serial interface-specific options";
             uses apply-advanced;
             leaf line-protocol {
               description "Line protocol to be used";
               default "eia530";
               type enumeration {
                 enum "eia530" {
                   description "Line protocol EIA530";
                 }
                 enum "v.35" {
                   description "Line protocol V.35";
                 }
                 enum "x.21" {
                   description "Line protocol X.21";
                 }
               }
             }
             choice control_leads_choice {
               case case_1 {
                 container dte-options {
                   description "DTE options/control leads";
                   uses apply-advanced;
                   leaf ignore-all {
                     description "Ignore all control leads";
                     type empty;
                   }
                   container dtr {
                     description "Data Transmit Ready signal handling";
                     choice dtr_choices {
                       case case_1 {
                         leaf assert {
                           description "Assert DTR signal";
                           type empty;
                         }
                       }
                       case case_2 {
                         leaf de-assert {
                           description "Deassert DTR signal";
                           type empty;
                         }
                       }
                       case case_3 {
                         leaf normal {
                           description "Normal DTR signal";
                           type empty;
                         }
                       }
                       case case_4 {
                         container auto-synchronize {
                           presence "enable auto-synchronize";
                           description "Normal DTR signal, with autoresynchronization";
                           uses apply-advanced;
                           leaf duration {
                             description "Duration of autoresynchronization";
                             units "milliseconds";
                             type union {
                               type string {
                                 pattern "<.*>|$.*";
                               }
                               type uint16 {
                                 range "1 .. 1000";
                               }
                             }
                           }
                           leaf interval {
                             description "Interval for autoresynchronization";
                             units "seconds";
                             type union {
                               type string {
                                 pattern "<.*>|$.*";
                               }
                               type uint16 {
                                 range "1 .. 31";
                               }
                             }
                           }
                         }
                       }
                     }
                   }
                   leaf control-signal {
                     description "X.21 control signal handling";
                     type enumeration {
                       enum "assert" {
                         description "Assert control signal";
                       }
                       enum "de-assert" {
                         description "Deassert control signal";
                       }
                       enum "normal" {
                         description "Normal control signal";
                       }
                     }
                   }
                   leaf rts {
                     description "Request To Send signal handling";
                     type enumeration {
                       enum "assert" {
                         description "Assert RTS signal";
                       }
                       enum "de-assert" {
                         description "Deassert RTS signal";
                       }
                       enum "normal" {
                         description "Normal RTS signal";
                       }
                     }
                   }
                   leaf dcd {
                     description "Data Carrier Detect signal handling";
                     type enumeration {
                       enum "require" {
                         description "Require DCD signal";
                       }
                       enum "ignore" {
                         description "Ignore DCD signal";
                       }
                       enum "normal" {
                         description "Normal DCD signal";
                       }
                     }
                   }
                   leaf dsr {
                     description "Data Set Ready signal handling";
                     type enumeration {
                       enum "require" {
                         description "Require DSR signal";
                       }
                       enum "ignore" {
                         description "Ignore DSR signal";
                       }
                       enum "normal" {
                         description "Normal DSR signal";
                       }
                     }
                   }
                   leaf cts {
                     description "Clear To Send signal handling";
                     type enumeration {
                       enum "require" {
                         description "Require CTS signal";
                       }
                       enum "ignore" {
                         description "Ignore CTS signal";
                       }
                       enum "normal" {
                         description "Normal CTS signal";
                       }
                     }
                   }
                   leaf indication {
                     description "X.21 Indication signal handling";
                     type enumeration {
                       enum "require" {
                         description "Require Indication signal";
                       }
                       enum "ignore" {
                         description "Ignore Indication signal";
                       }
                       enum "normal" {
                         description "Normal Indication signal";
                       }
                     }
                   }
                   leaf tm {
                     description "Test Mode signal handling";
                     type enumeration {
                       enum "require" {
                         description "Require TM signal";
                       }
                       enum "ignore" {
                         description "Ignore TM signal";
                       }
                       enum "normal" {
                         description "Normal TM signal";
                       }
                     }
                   }
                 }
               }
               case case_2 {
                 container dce-options {
                   description "DCE options";
                   uses apply-advanced;
                   leaf ignore-all {
                     description "Ignore all control leads";
                     type empty;
                   }
                   leaf dtr {
                     description "Data Transmit Ready signal handling";
                     type enumeration {
                       enum "require" {
                         description "Require Data Carrier Detect (DCD) signal";
                       }
                       enum "ignore" {
                         description "Ignore Data Carrier Detect (DCD) signal";
                       }
                       enum "normal" {
                         description "Normal Data Carrier Detect (DCD) signal";
                       }
                     }
                   }
                   leaf rts {
                     description "Request To Send signal handling";
                     type enumeration {
                       enum "require" {
                         description "Require Data Carrier Detect (DCD) signal";
                       }
                       enum "ignore" {
                         description "Ignore Data Carrier Detect (DCD) signal";
                       }
                       enum "normal" {
                         description "Normal Data Carrier Detect (DCD) signal";
                       }
                     }
                   }
                   leaf dcd {
                     description "Data Carrier Detect signal handling";
                     type enumeration {
                       enum "assert" {
                         description "Assert Request To Send (RTS) signal";
                       }
                       enum "de-assert" {
                         description "Deassert Request To Send (RTS) signal";
                       }
                       enum "normal" {
                         description "Normal Request To Send (RTS) signal";
                       }
                     }
                   }
                   leaf dsr {
                     description "Data Set Ready signal handling";
                     type enumeration {
                       enum "assert" {
                         description "Assert Request To Send (RTS) signal";
                       }
                       enum "de-assert" {
                         description "Deassert Request To Send (RTS) signal";
                       }
                       enum "normal" {
                         description "Normal Request To Send (RTS) signal";
                       }
                     }
                   }
                   leaf cts {
                     description "Clear To Send signal handling";
                     type enumeration {
                       enum "assert" {
                         description "Assert Request To Send (RTS) signal";
                       }
                       enum "de-assert" {
                         description "Deassert Request To Send (RTS) signal";
                       }
                       enum "normal" {
                         description "Normal Request To Send (RTS) signal";
                       }
                     }
                   }
                   leaf tm {
                     description "Test Mode signal handling";
                     type enumeration {
                       enum "require" {
                         description "Require TM signal";
                       }
                       enum "ignore" {
                         description "Ignore TM signal";
                       }
                       enum "normal" {
                         description "Normal TM signal";
                       }
                     }
                   }
                   leaf dce-loopback-override {
                     description "DCE loopback override";
                     type empty;
                   }
                 }
               }
             }
             leaf dtr-circuit {
               description "Data Transmit Ready circuit mode";
               type enumeration {
                 enum "balanced" {
                   description "Balanced signal";
                 }
                 enum "unbalanced" {
                   description "Unbalanced signal";
                 }
               }
             }
             leaf dtr-polarity {
               description "Data Transmit Ready signal polarity";
               type enumeration {
                 enum "positive" {
                   description "Positive polarity";
                 }
                 enum "negative" {
                   description "Negative polarity";
                 }
               }
             }
             leaf rts-polarity {
               description "Request To Send signal polarity";
               type enumeration {
                 enum "positive" {
                   description "Positive polarity";
                 }
                 enum "negative" {
                   description "Negative polarity";
                 }
               }
             }
             leaf control-polarity {
               description "X.21 Control signal polarity";
               type enumeration {
                 enum "positive" {
                   description "Positive polarity";
                 }
                 enum "negative" {
                   description "Negative polarity";
                 }
               }
             }
             leaf dcd-polarity {
               description "Data Carrier Detect signal polarity";
               type enumeration {
                 enum "positive" {
                   description "Positive polarity";
                 }
                 enum "negative" {
                   description "Negative polarity";
                 }
               }
             }
             leaf dsr-polarity {
               description "Data Set Ready signal polarity";
               type enumeration {
                 enum "positive" {
                   description "Positive polarity";
                 }
                 enum "negative" {
                   description "Negative polarity";
                 }
               }
             }
             leaf cts-polarity {
               description "Clear To Send signal polarity";
               type enumeration {
                 enum "positive" {
                   description "Positive polarity";
                 }
                 enum "negative" {
                   description "Negative polarity";
                 }
               }
             }
             leaf indication-polarity {
               description "X.21 Indication signal polarity";
               type enumeration {
                 enum "positive" {
                   description "Positive polarity";
                 }
                 enum "negative" {
                   description "Negative polarity";
                 }
               }
             }
             leaf tm-polarity {
               description "Test Mode signal polarity";
               type enumeration {
                 enum "positive" {
                   description "Positive polarity";
                 }
                 enum "negative" {
                   description "Negative polarity";
                 }
               }
             }
             leaf clocking-mode {
               description "Clock mode";
               type enumeration {
                 enum "dce" {
                   description "DCE timing (DTE mode only, not valid for X.21)";
                 }
                 enum "internal" {
                   description "Internal baud timing";
                 }
                 enum "loop" {
                   description "Loop timing";
                 }
               }
             }
             leaf transmit-clock {
               description "Transmit clock phase";
               type enumeration {
                 enum "invert" {
                   description "Shift clock phase 180 degrees";
                 }
               }
             }
             leaf clock-rate {
               description "Interface clock rate";
               type enumeration {
                 enum "2.048mhz" {
                   description "2.048 MHz";
                 }
                 enum "2.341mhz" {
                   description "2.341 MHz";
                 }
                 enum "2.731mhz" {
                   description "2.731 MHz";
                 }
                 enum "3.277mhz" {
                   description "3.277 MHz";
                 }
                 enum "4.096mhz" {
                   description "4.096 MHz";
                 }
                 enum "5.461mhz" {
                   description "5.461 MHz";
                 }
                 enum "8.192mhz" {
                   description "8.192 MHz";
                 }
                 enum "16.384mhz" {
                   description "16.384 MHz";
                 }
                 enum "1.2khz" {
                   description "1.2 KHz";
                 }
                 enum "2.4khz" {
                   description "2.4 KHz";
                 }
                 enum "9.6khz" {
                   description "9.6 KHz";
                 }
                 enum "19.2khz" {
                   description "19.2 KHz";
                 }
                 enum "38.4khz" {
                   description "38.4 KHz";
                 }
                 enum "56.0khz" {
                   description "56.0 KHz";
                 }
                 enum "64.0khz" {
                   description "64.0 KHz";
                 }
                 enum "72.0khz" {
                   description "72.0 KHz";
                 }
                 enum "125.0khz" {
                   description "125.0 KHz";
                 }
                 enum "148.0khz" {
                   description "148.0 KHz";
                 }
                 enum "250.0khz" {
                   description "250.0 KHz";
                 }
                 enum "500.0khz" {
                   description "500.0 KHz";
                 }
                 enum "800.0khz" {
                   description "800.0 KHz";
                 }
                 enum "1.0mhz" {
                   description "1.0 MHz";
                 }
                 enum "1.3mhz" {
                   description "1.3 MHz";
                 }
                 enum "2.0mhz" {
                   description "2.0 MHz";
                 }
                 enum "4.0mhz" {
                   description "4.0 MHz";
                 }
                 enum "8.0mhz" {
                   description "8.0 MHz";
                 }
               }
             }
             leaf loopback {
               description "Loopback mode";
               type enumeration {
                 enum "local" {
                   description "Local loopback";
                 }
                 enum "remote" {
                   description "Remote/LIU loopback";
                 }
                 enum "dce-local" {
                   description "DCE local loopback (DTE mode only)";
                 }
                 enum "dce-remote" {
                   description "DCE remote loopback";
                 }
               }
             }
             leaf encoding {
               description "Line encoding";
               type enumeration {
                 enum "nrz" {
                   description "Non-Return-To-Zero";
                 }
                 enum "nrzi" {
                   description "Non-Return-To-Zero-Invertible";
                 }
               }
             }
             leaf idle-cycle-flag {
               description "Value to transmit in idle cycles";
               type enumeration {
                 enum "flags" {
                   description "Transmit 0x7E in idle cycles";
                 }
                 enum "ones" {
                   description "Transmit 0xFF (all ones) in idle cycles";
                 }
               }
             }
           }
           choice gratuitous-arp-reply-choice {
             leaf gratuitous-arp-reply {
               description "Enable gratuitous ARP reply";
               type empty;
             }
             leaf no-gratuitous-arp-reply {
               description "Don't enable gratuitous ARP reply";
               type empty;
             }
           }
           choice no-gratuitous-arp-request-choice {
             leaf no-gratuitous-arp-request {
               description "Ignore gratuitous ARP request";
               type empty;
             }
             leaf no-no-gratuitous-arp-request {
               description "Don't ignore gratuitous ARP request";
               type empty;
             }
           }
           leaf arp-l2-validate {
             description "Validate ARP against L2";
             type empty;
           }
           container ether-options {
             description "Ethernet interface-specific options";
             uses apply-advanced;
             choice loopback-choice {
               leaf loopback {
                 description "Enable loopback";
                 type empty;
               }
               leaf no-loopback {
                 description "Don't enable loopback";
                 type empty;
               }
             }
             leaf loopback-remote {
               description "Enable remote loopback";
               type empty;
             }
             choice source-filtering-choice {
               leaf source-filtering {
                 description "Enable source address filtering";
                 type empty;
               }
               leaf no-source-filtering {
                 description "Don't enable source address filtering";
                 type empty;
               }
             }
             container ethernet-switch-profile {
               description "Ethernet virtual LAN/media access control-level options";
               uses apply-advanced;
               leaf-list tag-protocol-id {
                 ordered-by user;
                 description "IEEE 802.1q Tag Protocol Identifier values for VLAN-tagged frames";
                 type string;
               }
               container ethernet-policer-profile {
                 description "Ethernet level CoS-based policer configuration";
                 uses apply-advanced;
                 container input-priority-map {
                   description "Input policer priority map";
                   uses cos_policer_input_priority_map;
                 }
                 container output-priority-map {
                   description "Output policer priority map";
                   uses cos_policer_output_priority_map;
                 }
                 list policer {
                   key name;
                   ordered-by user;
                   description "Policer template definition";
                   uses cos_policer;
                 }
               }
               container storm-control {
                 description "Storm control profile name to bind";
                 uses apply-advanced;
                 leaf profile-name {
                   description "Profile name";
                   type string;
                 }
               }
               container recovery-timeout {
                 description "Recovery timeout for this interface";
                 leaf time-in-seconds {
                   units "seconds";
                   type union {
                     type string {
                       pattern "<.*>|$.*";
                     }
                     type uint32 {
                       range "10 .. 3600";
                     }
                   }
                 }
               }
               choice mac-learn-enable-choice {
                 leaf mac-learn-enable {
                   description "Learn MAC addresses dynamically";
                   type empty;
                 }
                 leaf no-mac-learn-enable {
                   description "Don't learn MAC addresses dynamically";
                   type empty;
                 }
               }
             }
             leaf asynchronous-notification {
               description "Enable sending asynchronous notification to peer on CCC-down";
               type empty;
             }
             list source-address-filter {
               key name;
               description "Source address filters";
               leaf name {
                 description "Remote MAC address";
                 type jt:mac-addr;
               }
             }
             choice auto-negotiation-choice {
               leaf auto-negotiation {
                 description "Enable auto-negotiation";
                 type empty;
               }
               leaf no-auto-negotiation {
                 description "Don't enable auto-negotiation";
                 type empty;
               }
             }
             choice flow-control-choice {
               leaf flow-control {
                 description "Enable flow control";
                 type empty;
               }
               leaf no-flow-control {
                 description "Don't enable flow control";
                 type empty;
               }
             }
             container configured-flow-control {
               presence "enable configured-flow-control";
               description "Enable flow control";
               uses apply-advanced;
               leaf rx-buffers {
                 description "Enable/Disable Rx buffers";
                 type enumeration {
                   enum "on" {
                     description "Enable Rx buffers";
                   }
                   enum "off" {
                     description "Disable Rx buffers";
                   }
                 }
               }
               leaf tx-buffers {
                 description "Enable/Disable Tx buffers";
                 type enumeration {
                   enum "on" {
                     description "Enable Tx buffers";
                   }
                   enum "off" {
                     description "Disable Tx buffers";
                   }
                 }
               }
             }
             leaf link-mode {
               description "Link duplex";
               type enumeration {
                 enum "automatic" {
                   description "Automatic negotiate duplex ";
                 }
                 enum "half-duplex" {
                   description "Half-duplex operation";
                 }
                 enum "full-duplex" {
                   description "Full-duplex operation";
                 }
               }
             }
             container mpls {
               description "MPLS options";
               uses mpls_ifd_options;
             }
             leaf ignore-l3-incompletes {
               description "Ignore L3 incomplete errors";
               type empty;
             }
             leaf no-auto-mdix {
               description "Disable auto MDI/MDIX";
               type empty;
             }
             leaf fec {
               description "Forward Error Correction mode";
               type enumeration {
                 enum "none" {
                   description "FEC disabled";
                 }
                 enum "fec91" {
                   description "IEEE 802.3bj Clause 91, Reed-Solomon FEC (RS-FEC)";
                 }
                 enum "fec74" {
                   description "FEC74 enabled";
                 }
                 enum "fec108" {
                   description "IEEE 802.3by Clause 108, Reed-Solomon FEC (RS-FEC) on 25g links";
                 }
                 enum "fec161" {
                   description "IEEE 802.3ck Clause 161 for 100G electrical links";
                 }
               }
             }
             container speed {
               description "Specify speed";
               choice automatic {
                 case case_1 {
                   container auto-negotiation {
                     presence "enable auto-negotiation";
                     description "Enable auto-negotiation";
                     leaf auto-negotiate-10-100 {
                       description "Limits the auto-negotiation to 10m/100m only";
                       type empty;
                     }
                   }
                 }
                 case case_2 {
                   leaf ethernet-10m {
                     description "10Mbps";
                     type empty;
                   }
                 }
                 case case_3 {
                   leaf ethernet-100m {
                     description "100Mbps";
                     type empty;
                   }
                 }
                 case case_4 {
                   leaf ethernet-1g {
                     description "1Gbps";
                     type empty;
                   }
                 }
                 case case_5 {
                   leaf ethernet-10g {
                     description "10Gbps";
                     type empty;
                   }
                 }
               }
             }
             container ieee-802.3ad {
               description "IEEE 802.3ad";
               uses apply-advanced;
               container lacp {
                 description "Link Aggregation Control Protocol configuration";
                 uses apply-advanced;
                 leaf force-up {
                   description "Keep the port up in absence of received LACPDU";
                   type empty;
                 }
                 leaf port-priority {
                   description "Priority of the port (0 ... 65535)";
                   type union {
                     type uint16;
                     type string {
                       pattern "<.*>|$.*";
                     }
                   }
                 }
               }
               leaf bundle {
                 description "Join an aggregated Ethernet interface";
                 type union {
                   type jt:interface-device;
                   type string {
                     pattern "<.*>|$.*";
                   }
                 }
               }
               choice type {
                 case case_1 {
                   leaf primary {
                     description "Primary interface for link-protection mode";
                     type empty;
                   }
                 }
                 case case_2 {
                   leaf backup {
                     description "Backup interface for link-protection mode";
                     type empty;
                   }
                 }
               }
               container link-protection-sub-group {
                 description "Link Protection subgroup configuration";
                 uses apply-advanced;
                 leaf subgroup-name {
                   description "Name of the subgroup";
                   type string {
                     length "2 .. 64";
                   }
                 }
               }
               leaf port-priority {
                 description "Link protection Priority of the port (0 ... 65535)";
                 type union {
                   type uint16;
                   type string {
                     pattern "<.*>|$.*";
                   }
                 }
               }
             }
             leaf ieee-802-3az-eee {
               description "IEEE 802.3az Energy Efficient Ethernet(EEE)";
               type empty;
             }
             leaf mdi-mode {
               description "Cable cross-over mode";
               type enumeration {
                 enum "auto" {
                   description "Automatic mdi/mdi-x mode";
                 }
                 enum "force" {
                   description "Enable auto-MDIX always";
                 }
                 enum "mdi" {
                   description "MDI(straight through) mode";
                 }
                 enum "mdix" {
                   description "MDI Cross-over mode";
                 }
               }
             }
             container redundant-parent {
               description " Parent of this interface";
               uses apply-advanced;
               leaf parent {
                 description "Join a redundant ethernet interface";
                 type union {
                   type jt:interface-device;
                   type string {
                     pattern "<.*>|$.*";
                   }
                 }
               }
             }
             leaf autostate-exclude {
               description "Interface will not contribute to IRB state";
               type empty;
             }
           }
           container fibrechannel-options {
             description "Fibre Channel interface-specific options";
             uses apply-advanced;
             choice loopback-choice {
               leaf loopback {
                 description "Enable loopback";
                 type empty;
               }
               leaf no-loopback {
                 description "Don't enable loopback";
                 type empty;
               }
             }
             leaf bb-sc-n {
               description "B2B state change number";
               type union {
                 type string {
                   pattern "<.*>|$.*";
                 }
                 type uint16 {
                   range "0 .. 15";
                 }
               }
             }
             leaf speed {
               description "Specify speed";
               type enumeration {
                 enum "auto-negotiation" {
                   description "Enable auto-negotiation";
                 }
                 enum "1g" {
                   description "1Gbps";
                 }
                 enum "2g" {
                   description "2Gbps";
                 }
                 enum "4g" {
                   description "4Gbps";
                 }
                 enum "8g" {
                   description "8Gbps";
                 }
               }
             }
           }
           container gigether-options {
             description "Gigabit Ethernet interface-specific options";
             uses apply-advanced;
             choice loopback-choice {
               leaf loopback {
                 description "Enable loopback";
                 type empty;
               }
               leaf no-loopback {
                 description "Don't enable loopback";
                 type empty;
               }
             }
             leaf loopback-remote {
               description "Enable remote loopback";
               type empty;
             }
             choice flow-control-choice {
               leaf flow-control {
                 description "Enable flow control";
                 type empty;
               }
               leaf no-flow-control {
                 description "Don't enable flow control";
                 type empty;
               }
             }
             choice source-filtering-choice {
               leaf source-filtering {
                 description "Enable source address filtering";
                 type empty;
               }
               leaf no-source-filtering {
                 description "Don't enable source address filtering";
                 type empty;
               }
             }
             choice auto_negotiation_option {
               case case_1 {
                 leaf no-auto-negotiation {
                   description "Disable auto-negotiation";
                   type empty;
                 }
               }
               case case_2 {
                 container auto-negotiation {
                   presence "enable auto-negotiation";
                   description "Enable auto-negotiation";
                   leaf remote-fault {
                     type enumeration {
                       enum "local-interface-offline" {
                         description "Disable local interface";
                       }
                       enum "local-interface-online" {
                         description "Enable local interface";
                       }
                     }
                   }
                 }
               }
             }
             leaf mac-mode {
               description "Physical layer protocol of MAC's SERDES interface";
               type enumeration {
                 enum "sgmii" {
                   description "Serial Gigabit Media Independent Interface (10/100/1000 Mbps)";
                 }
                 enum "mac-mode-1000base-x" {
                   description "1000Base-X (1000 Mbps)";
                 }
               }
             }
             leaf asynchronous-notification {
               description "Enable sending asynchronous notification to peer on CCC-down";
               type empty;
             }
             list source-address-filter {
               key name;
               description "Source address filters";
               leaf name {
                 description "Remote MAC address";
                 type jt:mac-addr;
               }
             }
             leaf pad-to-minimum-frame-size {
               description "Pad Tx vlan tagged frame to minimum of 68 bytes";
               type empty;
             }
             container redundant-parent {
               description "Parent of this interface";
               uses apply-advanced;
               leaf parent {
                 description "Join a redundant-ethernet interface";
                 type union {
                   type jt:interface-device;
                   type string {
                     pattern "<.*>|$.*";
                   }
                 }
               }
             }
             container ieee-802.3ad {
               description "IEEE 802.3ad";
               uses apply-advanced;
               container lacp {
                 description "Link Aggregation Control Protocol configuration";
                 uses apply-advanced;
                 leaf port-priority {
                   description "Priority of the port (0 ... 65535)";
                   type union {
                     type uint16;
                     type string {
                       pattern "<.*>|$.*";
                     }
                   }
                 }
               }
               leaf bundle {
                 description "Join an aggregated Ethernet interface";
                 type union {
                   type jt:interface-device;
                   type string {
                     pattern "<.*>|$.*";
                   }
                 }
               }
               leaf link-index {
                 description "Desired child link index within the Aggregated Interface";
                 type union {
                   type string {
                     pattern "<.*>|$.*";
                   }
                   type uint16 {
                     range "0 .. 63";
                   }
                 }
               }
               choice type {
                 case case_1 {
                   leaf primary {
                     description "Primary interface for link-protection mode";
                     type empty;
                   }
                 }
                 case case_2 {
                   leaf backup {
                     description "Backup interface for link-protection mode";
                     type empty;
                   }
                 }
               }
               leaf distribution-list {
                 description "Distribution list to which interface belongs";
                 type string {
                   length "1 .. 20";
                 }
               }
             }
             container ethernet-switch-profile {
               description "Ethernet virtual LAN/media access control-level options";
               uses apply-advanced;
               leaf-list tag-protocol-id {
                 ordered-by user;
                 description "IEEE 802.1q Tag Protocol Identifier values for VLAN-tagged frames";
                 type string;
               }
               container ethernet-policer-profile {
                 description "Ethernet level CoS-based policer configuration";
                 uses apply-advanced;
                 container ieee802.1-priority-map {
                   presence "enable ieee802.1-priority-map";
                   description "Premium priority values for IEEE 802.1p bits";
                   status deprecated;
                   uses apply-advanced;
                   leaf-list premium {
                     ordered-by user;
                     description "Premium policer priority map";
                     type union {
                       type string {
                         pattern "<.*>|$.*";
                       }
                       type uint32 {
                         range "0 .. 7";
                       }
                     }
                   }
                 }
                 container input-priority-map {
                   description "Input policer priority map";
                   uses cos_policer_input_priority_map;
                 }
                 container output-priority-map {
                   description "Output policer priority map";
                   uses cos_policer_output_priority_map;
                 }
                 list policer {
                   key name;
                   ordered-by user;
                   description "Policer template definition";
                   uses cos_policer;
                 }
               }
               container accept-from {
                 description "Accept traffic from or to specified remote MAC";
                 status deprecated;
                 uses apply-advanced;
                 list mac-address {
                   key name;
                   description "Remote MAC";
                   uses mac_list;
                 }
               }
               choice reject-the-rest-choice {
                 leaf reject-the-rest {
                   description "Accept traffic from only the specified MAC addresses";
                   status deprecated;
                   type empty;
                 }
                 leaf no-reject-the-rest {
                   description "Don't accept traffic from only the specified MAC addresses";
                   status deprecated;
                   type empty;
                 }
               }
               leaf mac-learn-enable {
                 description "Learn MAC addresses dynamically";
                 type empty;
               }
             }
             container mpls {
               description "MPLS options";
               uses mpls_ifd_options;
             }
             leaf ignore-l3-incompletes {
               description "Ignore L3 incomplete errors";
               type empty;
             }
             leaf no-auto-mdix {
               description "Disable auto MDI/MDIX";
               type empty;
             }
             leaf ieee-802-3az-eee {
               description "IEEE 802.3az Energy Efficient Ethernet(EEE)";
               type empty;
             }
             leaf mru {
               description "Maximum receive packet size";
               type union {
                 type string {
                   pattern "<.*>|$.*";
                 }
                 type uint32;
               }
             }
             leaf fec {
               description "Forward Error Correction mode";
               type enumeration {
                 enum "none" {
                   description "FEC disabled";
                 }
                 enum "fec91" {
                   description "IEEE 802.3bj Clause 91, Reed-Solomon FEC (RS-FEC)";
                 }
                 enum "fec74" {
                   description "FEC74 enabled";
                 }
                 enum "fec108" {
                   description "IEEE 802.3by Clause 108, Reed-Solomon FEC (RS-FEC) on 25g links";
                 }
                 enum "fec161" {
                   description "IEEE 802.3ck Clause 161 for 100G electrical links";
                 }
               }
             }
             leaf speed {
               description "Speed mode";
               type enumeration {
                 enum "1g" {
                   description "Speed 1g";
                 }
                 enum "10g" {
                   description "Speed 10g";
                 }
               }
             }
           }
           container optics-options {
             description "Optics options";
             uses apply-advanced;
             leaf wavelength {
               description "Wavelength of the optics (nanometers) for 50Ghz/100Ghz spacing";
               type enumeration {
                 enum "1568.77" {
                   description "1568.77 nm/191.1003 THz 50/100Ghz spacing";
                 }
                 enum "1568.36" {
                   description "1568.36 nm/191.15000 THz 6.25/12.5/50GHz spacing";
                 }
                 enum "1568.31" {
                   description "1568.31 nm/191.15625 THz 6.25GHz spacing";
                 }
                 enum "1568.26" {
                   description "1568.26 nm/191.16250 THz 6.25/12.5GHz spacing";
                 }
                 enum "1568.21" {
                   description "1568.21 nm/191.16875 THz 6.25GHz spacing";
                 }
                 enum "1568.16" {
                   description "1568.16 nm/191.17500 THz 6.25/12.5GHz spacing";
                 }
                 enum "1568.11" {
                   description "1568.11 nm/191.18125 THz 6.25GHz spacing";
                 }
                 enum "1568.05" {
                   description "1568.05 nm/191.18750 THz 6.25/12.5GHz spacing";
                 }
                 enum "1568.00" {
                   description "1568.00 nm/191.19375 THz 6.25GHz spacing";
                 }
                 enum "1567.95" {
                   description "1567.95 nm/191.20000 THz 6.25/12.5/50/100GHz spacing";
                 }
                 enum "1567.90" {
                   description "1567.90 nm/191.20625 THz 6.25GHz spacing";
                 }
                 enum "1567.85" {
                   description "1567.85 nm/191.21250 THz 6.25/12.5GHz spacing";
                 }
                 enum "1567.80" {
                   description "1567.80 nm/191.21875 THz 6.25GHz spacing";
                 }
                 enum "1567.75" {
                   description "1567.75 nm/191.22500 THz 6.25/12.5GHz spacing";
                 }
                 enum "1567.70" {
                   description "1567.70 nm/191.23125 THz 6.25GHz spacing";
                 }
                 enum "1567.64" {
                   description "1567.64 nm/191.23750 THz 6.25/12.5GHz spacing";
                 }
                 enum "1567.59" {
                   description "1567.59 nm/191.24375 THz 6.25GHz spacing";
                 }
                 enum "1567.54" {
                   description "1567.54 nm/191.25000 THz 6.25/12.5/50GHz spacing";
                 }
                 enum "1567.49" {
                   description "1567.49 nm/191.25625 THz 6.25GHz spacing";
                 }
                 enum "1567.44" {
                   description "1567.44 nm/191.26250 THz 6.25/12.5GHz spacing";
                 }
                 enum "1567.39" {
                   description "1567.39 nm/191.26875 THz 6.25GHz spacing";
                 }
                 enum "1567.34" {
                   description "1567.34 nm/191.27500 THz 6.25/12.5GHz spacing";
                 }
                 enum "1567.29" {
                   description "1567.29 nm/191.28125 THz 6.25GHz spacing";
                 }
                 enum "1567.23" {
                   description "1567.23 nm/191.28750 THz 6.25/12.5GHz spacing";
                 }
                 enum "1567.18" {
                   description "1567.18 nm/191.29375 THz 6.25GHz spacing";
                 }
                 enum "1567.13" {
                   description "1567.13 nm/191.30000 THz 6.25/12.5/50/100GHz spacing";
                 }
                 enum "1567.08" {
                   description "1567.08 nm/191.30625 THz 6.25GHz spacing";
                 }
                 enum "1567.03" {
                   description "1567.03 nm/191.31250 THz 6.25/12.5GHz spacing";
                 }
                 enum "1566.98" {
                   description "1566.98 nm/191.31875 THz 6.25GHz spacing";
                 }
                 enum "1566.93" {
                   description "1566.93 nm/191.32500 THz 6.25/12.5GHz spacing";
                 }
                 enum "1566.88" {
                   description "1566.88 nm/191.33125 THz 6.25GHz spacing";
                 }
                 enum "1566.83" {
                   description "1566.83 nm/191.33750 THz 6.25/12.5GHz spacing";
                 }
                 enum "1566.77" {
                   description "1566.77 nm/191.34375 THz 6.25GHz spacing";
                 }
                 enum "1566.72" {
                   description "1566.72 nm/191.35000 THz 6.25/12.5/50GHz spacing";
                 }
                 enum "1566.67" {
                   description "1566.67 nm/191.35625 THz 6.25GHz spacing";
                 }
                 enum "1566.62" {
                   description "1566.62 nm/191.36250 THz 6.25/12.5GHz spacing";
                 }
                 enum "1566.57" {
                   description "1566.57 nm/191.36875 THz 6.25GHz spacing";
                 }
                 enum "1566.52" {
                   description "1566.52 nm/191.37500 THz 6.25/12.5/75GHz spacing";
                 }
                 enum "1566.47" {
                   description "1566.47 nm/191.38125 THz 6.25GHz spacing";
                 }
                 enum "1566.42" {
                   description "1566.42 nm/191.38750 THz 6.25/12.5GHz spacing";
                 }
                 enum "1566.36" {
                   description "1566.36 nm/191.39375 THz 6.25GHz spacing";
                 }
                 enum "1566.31" {
                   description "1566.31 nm/191.40000 THz 6.25/12.5/50/100GHz spacing";
                 }
                 enum "1566.26" {
                   description "1566.26 nm/191.40625 THz 6.25GHz spacing";
                 }
                 enum "1566.21" {
                   description "1566.21 nm/191.41250 THz 6.25/12.5GHz spacing";
                 }
                 enum "1566.16" {
                   description "1566.16 nm/191.41875 THz 6.25GHz spacing";
                 }
                 enum "1566.11" {
                   description "1566.11 nm/191.42500 THz 6.25/12.5GHz spacing";
                 }
                 enum "1566.06" {
                   description "1566.06 nm/191.43125 THz 6.25GHz spacing";
                 }
                 enum "1566.01" {
                   description "1566.01 nm/191.43750 THz 6.25/12.5GHz spacing";
                 }
                 enum "1565.96" {
                   description "1565.96 nm/191.44375 THz 6.25GHz spacing";
                 }
                 enum "1565.90" {
                   description "1565.90 nm/191.45000 THz 6.25/12.5/50/75GHz spacing";
                 }
                 enum "1565.85" {
                   description "1565.85 nm/191.45625 THz 6.25GHz spacing";
                 }
                 enum "1565.80" {
                   description "1565.80 nm/191.46250 THz 6.25/12.5GHz spacing";
                 }
                 enum "1565.75" {
                   description "1565.75 nm/191.46875 THz 6.25GHz spacing";
                 }
                 enum "1565.70" {
                   description "1565.70 nm/191.47500 THz 6.25/12.5GHz spacing";
                 }
                 enum "1565.65" {
                   description "1565.65 nm/191.48125 THz 6.25GHz spacing";
                 }
                 enum "1565.60" {
                   description "1565.60 nm/191.48750 THz 6.25/12.5GHz spacing";
                 }
                 enum "1565.55" {
                   description "1565.55 nm/191.49375 THz 6.25GHz spacing";
                 }
                 enum "1565.50" {
                   description "1565.50 nm/191.50000 THz 6.25/12.5/50/100GHz spacing";
                 }
                 enum "1565.44" {
                   description "1565.44 nm/191.50625 THz 6.25GHz spacing";
                 }
                 enum "1565.39" {
                   description "1565.39 nm/191.51250 THz 6.25/12.5GHz spacing";
                 }
                 enum "1565.34" {
                   description "1565.34 nm/191.51875 THz 6.25GHz spacing";
                 }
                 enum "1565.29" {
                   description "1565.29 nm/191.52500 THz 6.25/12.5/75GHz spacing";
                 }
                 enum "1565.24" {
                   description "1565.24 nm/191.53125 THz 6.25GHz spacing";
                 }
                 enum "1565.19" {
                   description "1565.19 nm/191.53750 THz 6.25/12.5GHz spacing";
                 }
                 enum "1565.14" {
                   description "1565.14 nm/191.54375 THz 6.25GHz spacing";
                 }
                 enum "1565.09" {
                   description "1565.09 nm/191.55000 THz 6.25/12.5/50GHz spacing";
                 }
                 enum "1565.04" {
                   description "1565.04 nm/191.55625 THz 6.25GHz spacing";
                 }
                 enum "1564.99" {
                   description "1564.99 nm/191.56250 THz 6.25/12.5GHz spacing";
                 }
                 enum "1564.93" {
                   description "1564.93 nm/191.56875 THz 6.25GHz spacing";
                 }
                 enum "1564.88" {
                   description "1564.88 nm/191.57500 THz 6.25/12.5GHz spacing";
                 }
                 enum "1564.83" {
                   description "1564.83 nm/191.58125 THz 6.25GHz spacing";
                 }
                 enum "1564.78" {
                   description "1564.78 nm/191.58750 THz 6.25/12.5GHz spacing";
                 }
                 enum "1564.73" {
                   description "1564.73 nm/191.59375 THz 6.25GHz spacing";
                 }
                 enum "1564.68" {
                   description "1564.68 nm/191.60000 THz 6.25/12.5/50/75/100GHz spacing";
                 }
                 enum "1564.63" {
                   description "1564.63 nm/191.60625 THz 6.25GHz spacing";
                 }
                 enum "1564.58" {
                   description "1564.58 nm/191.61250 THz 6.25/12.5GHz spacing";
                 }
                 enum "1564.53" {
                   description "1564.53 nm/191.61875 THz 6.25GHz spacing";
                 }
                 enum "1564.47" {
                   description "1564.47 nm/191.62500 THz 6.25/12.5GHz spacing";
                 }
                 enum "1564.42" {
                   description "1564.42 nm/191.63125 THz 6.25GHz spacing";
                 }
                 enum "1564.37" {
                   description "1564.37 nm/191.63750 THz 6.25/12.5GHz spacing";
                 }
                 enum "1564.32" {
                   description "1564.32 nm/191.64375 THz 6.25GHz spacing";
                 }
                 enum "1564.27" {
                   description "1564.27 nm/191.65000 THz 6.25/12.5/50GHz spacing";
                 }
                 enum "1564.22" {
                   description "1564.22 nm/191.65625 THz 6.25GHz spacing";
                 }
                 enum "1564.17" {
                   description "1564.17 nm/191.66250 THz 6.25/12.5GHz spacing";
                 }
                 enum "1564.12" {
                   description "1564.12 nm/191.66875 THz 6.25GHz spacing";
                 }
                 enum "1564.07" {
                   description "1564.07 nm/191.67500 THz 6.25/12.5/75GHz spacing";
                 }
                 enum "1564.02" {
                   description "1564.02 nm/191.68125 THz 6.25GHz spacing";
                 }
                 enum "1563.96" {
                   description "1563.96 nm/191.68750 THz 6.25/12.5GHz spacing";
                 }
                 enum "1563.91" {
                   description "1563.91 nm/191.69375 THz 6.25GHz spacing";
                 }
                 enum "1563.86" {
                   description "1563.86 nm/191.70000 THz 6.25/12.5/50/100GHz spacing";
                 }
                 enum "1563.81" {
                   description "1563.81 nm/191.70625 THz 6.25GHz spacing";
                 }
                 enum "1563.76" {
                   description "1563.76 nm/191.71250 THz 6.25/12.5GHz spacing";
                 }
                 enum "1563.71" {
                   description "1563.71 nm/191.71875 THz 6.25GHz spacing";
                 }
                 enum "1563.66" {
                   description "1563.66 nm/191.72500 THz 6.25/12.5GHz spacing";
                 }
                 enum "1563.61" {
                   description "1563.61 nm/191.73125 THz 6.25GHz spacing";
                 }
                 enum "1563.56" {
                   description "1563.56 nm/191.73750 THz 6.25/12.5GHz spacing";
                 }
                 enum "1563.51" {
                   description "1563.51 nm/191.74375 THz 6.25GHz spacing";
                 }
                 enum "1563.45" {
                   description "1563.45 nm/191.75000 THz 6.25/12.5/50/75GHz spacing";
                 }
                 enum "1563.40" {
                   description "1563.40 nm/191.75625 THz 6.25GHz spacing";
                 }
                 enum "1563.35" {
                   description "1563.35 nm/191.76250 THz 6.25/12.5GHz spacing";
                 }
                 enum "1563.30" {
                   description "1563.30 nm/191.76875 THz 6.25GHz spacing";
                 }
                 enum "1563.25" {
                   description "1563.25 nm/191.77500 THz 6.25/12.5GHz spacing";
                 }
                 enum "1563.20" {
                   description "1563.20 nm/191.78125 THz 6.25GHz spacing";
                 }
                 enum "1563.15" {
                   description "1563.15 nm/191.78750 THz 6.25/12.5GHz spacing";
                 }
                 enum "1563.10" {
                   description "1563.10 nm/191.79375 THz 6.25GHz spacing";
                 }
                 enum "1563.05" {
                   description "1563.05 nm/191.80000 THz 6.25/12.5/50/100GHz spacing";
                 }
                 enum "1563.00" {
                   description "1563.00 nm/191.80625 THz 6.25GHz spacing";
                 }
                 enum "1562.95" {
                   description "1562.95 nm/191.81250 THz 6.25/12.5GHz spacing";
                 }
                 enum "1562.89" {
                   description "1562.89 nm/191.81875 THz 6.25GHz spacing";
                 }
                 enum "1562.84" {
                   description "1562.84 nm/191.82500 THz 6.25/12.5/75GHz spacing";
                 }
                 enum "1562.79" {
                   description "1562.79 nm/191.83125 THz 6.25GHz spacing";
                 }
                 enum "1562.74" {
                   description "1562.74 nm/191.83750 THz 6.25/12.5GHz spacing";
                 }
                 enum "1562.69" {
                   description "1562.69 nm/191.84375 THz 6.25GHz spacing";
                 }
                 enum "1562.64" {
                   description "1562.64 nm/191.85000 THz 6.25/12.5/50GHz spacing";
                 }
                 enum "1562.59" {
                   description "1562.59 nm/191.85625 THz 6.25GHz spacing";
                 }
                 enum "1562.54" {
                   description "1562.54 nm/191.86250 THz 6.25/12.5GHz spacing";
                 }
                 enum "1562.49" {
                   description "1562.49 nm/191.86875 THz 6.25GHz spacing";
                 }
                 enum "1562.44" {
                   description "1562.44 nm/191.87500 THz 6.25/12.5GHz spacing";
                 }
                 enum "1562.39" {
                   description "1562.39 nm/191.88125 THz 6.25GHz spacing";
                 }
                 enum "1562.33" {
                   description "1562.33 nm/191.88750 THz 6.25/12.5GHz spacing";
                 }
                 enum "1562.28" {
                   description "1562.28 nm/191.89375 THz 6.25GHz spacing";
                 }
                 enum "1562.23" {
                   description "1562.23 nm/191.90000 THz 6.25/12.5/50/75/100GHz spacing";
                 }
                 enum "1562.18" {
                   description "1562.18 nm/191.90625 THz 6.25GHz spacing";
                 }
                 enum "1562.13" {
                   description "1562.13 nm/191.91250 THz 6.25/12.5GHz spacing";
                 }
                 enum "1562.08" {
                   description "1562.08 nm/191.91875 THz 6.25GHz spacing";
                 }
                 enum "1562.03" {
                   description "1562.03 nm/191.92500 THz 6.25/12.5GHz spacing";
                 }
                 enum "1561.98" {
                   description "1561.98 nm/191.93125 THz 6.25GHz spacing";
                 }
                 enum "1561.93" {
                   description "1561.93 nm/191.93750 THz 6.25/12.5GHz spacing";
                 }
                 enum "1561.88" {
                   description "1561.88 nm/191.94375 THz 6.25GHz spacing";
                 }
                 enum "1561.83" {
                   description "1561.83 nm/191.95000 THz 6.25/12.5/50GHz spacing";
                 }
                 enum "1561.77" {
                   description "1561.77 nm/191.95625 THz 6.25GHz spacing";
                 }
                 enum "1561.72" {
                   description "1561.72 nm/191.96250 THz 6.25/12.5GHz spacing";
                 }
                 enum "1561.67" {
                   description "1561.67 nm/191.96875 THz 6.25GHz spacing";
                 }
                 enum "1561.62" {
                   description "1561.62 nm/191.97500 THz 6.25/12.5/75GHz spacing";
                 }
                 enum "1561.57" {
                   description "1561.57 nm/191.98125 THz 6.25GHz spacing";
                 }
                 enum "1561.52" {
                   description "1561.52 nm/191.98750 THz 6.25/12.5GHz spacing";
                 }
                 enum "1561.47" {
                   description "1561.47 nm/191.99375 THz 6.25GHz spacing";
                 }
                 enum "1561.42" {
                   description "1561.42 nm/192.00000 THz 6.25/12.5/50/100GHz spacing";
                 }
                 enum "1561.37" {
                   description "1561.37 nm/192.00625 THz 6.25GHz spacing";
                 }
                 enum "1561.32" {
                   description "1561.32 nm/192.01250 THz 6.25/12.5GHz spacing";
                 }
                 enum "1561.27" {
                   description "1561.27 nm/192.01875 THz 6.25GHz spacing";
                 }
                 enum "1561.22" {
                   description "1561.22 nm/192.02500 THz 6.25/12.5GHz spacing";
                 }
                 enum "1561.16" {
                   description "1561.16 nm/192.03125 THz 6.25GHz spacing";
                 }
                 enum "1561.11" {
                   description "1561.11 nm/192.03750 THz 6.25/12.5GHz spacing";
                 }
                 enum "1561.06" {
                   description "1561.06 nm/192.04375 THz 6.25GHz spacing";
                 }
                 enum "1561.01" {
                   description "1561.01 nm/192.05000 THz 6.25/12.5/50G/75Hz spacing";
                 }
                 enum "1560.96" {
                   description "1560.96 nm/192.05625 THz 6.25GHz spacing";
                 }
                 enum "1560.91" {
                   description "1560.91 nm/192.06250 THz 6.25/12.5GHz spacing";
                 }
                 enum "1560.86" {
                   description "1560.86 nm/192.06875 THz 6.25GHz spacing";
                 }
                 enum "1560.81" {
                   description "1560.81 nm/192.07500 THz 6.25/12.5GHz spacing";
                 }
                 enum "1560.76" {
                   description "1560.76 nm/192.08125 THz 6.25GHz spacing";
                 }
                 enum "1560.71" {
                   description "1560.71 nm/192.08750 THz 6.25/12.5GHz spacing";
                 }
                 enum "1560.66" {
                   description "1560.66 nm/192.09375 THz 6.25GHz spacing";
                 }
                 enum "1560.61" {
                   description "1560.61 nm/192.10000 THz 6.25/12.5/50/100GHz spacing";
                 }
                 enum "1560.56" {
                   description "1560.56 nm/192.10625 THz 6.25GHz spacing";
                 }
                 enum "1560.50" {
                   description "1560.50 nm/192.11250 THz 6.25/12.5GHz spacing";
                 }
                 enum "1560.45" {
                   description "1560.45 nm/192.11875 THz 6.25GHz spacing";
                 }
                 enum "1560.40" {
                   description "1560.40 nm/192.12500 THz 6.25/12.5/75GHz spacing";
                 }
                 enum "1560.35" {
                   description "1560.35 nm/192.13125 THz 6.25GHz spacing";
                 }
                 enum "1560.30" {
                   description "1560.30 nm/192.13750 THz 6.25/12.5GHz spacing";
                 }
                 enum "1560.25" {
                   description "1560.25 nm/192.14375 THz 6.25GHz spacing";
                 }
                 enum "1560.20" {
                   description "1560.20 nm/192.15000 THz 6.25/12.5/50GHz spacing";
                 }
                 enum "1560.15" {
                   description "1560.15 nm/192.15625 THz 6.25GHz spacing";
                 }
                 enum "1560.10" {
                   description "1560.10 nm/192.16250 THz 6.25/12.5GHz spacing";
                 }
                 enum "1560.05" {
                   description "1560.05 nm/192.16875 THz 6.25GHz spacing";
                 }
                 enum "1560.00" {
                   description "1560.00 nm/192.17500 THz 6.25/12.5GHz spacing";
                 }
                 enum "1559.95" {
                   description "1559.95 nm/192.18125 THz 6.25GHz spacing";
                 }
                 enum "1559.90" {
                   description "1559.90 nm/192.18750 THz 6.25/12.5GHz spacing";
                 }
                 enum "1559.84" {
                   description "1559.84 nm/192.19375 THz 6.25GHz spacing";
                 }
                 enum "1559.79" {
                   description "1559.79 nm/192.20000 THz 6.25/12.5/50/75/100GHz spacing";
                 }
                 enum "1559.74" {
                   description "1559.74 nm/192.20625 THz 6.25GHz spacing";
                 }
                 enum "1559.69" {
                   description "1559.69 nm/192.21250 THz 6.25/12.5GHz spacing";
                 }
                 enum "1559.64" {
                   description "1559.64 nm/192.21875 THz 6.25GHz spacing";
                 }
                 enum "1559.59" {
                   description "1559.59 nm/192.22500 THz 6.25/12.5GHz spacing";
                 }
                 enum "1559.54" {
                   description "1559.54 nm/192.23125 THz 6.25GHz spacing";
                 }
                 enum "1559.49" {
                   description "1559.49 nm/192.23750 THz 6.25/12.5GHz spacing";
                 }
                 enum "1559.44" {
                   description "1559.44 nm/192.24375 THz 6.25GHz spacing";
                 }
                 enum "1559.39" {
                   description "1559.39 nm/192.25000 THz 6.25/12.5/50GHz spacing";
                 }
                 enum "1559.34" {
                   description "1559.34 nm/192.25625 THz 6.25GHz spacing";
                 }
                 enum "1559.29" {
                   description "1559.29 nm/192.26250 THz 6.25/12.5GHz spacing";
                 }
                 enum "1559.24" {
                   description "1559.24 nm/192.26875 THz 6.25GHz spacing";
                 }
                 enum "1559.19" {
                   description "1559.19 nm/192.27500 THz 6.25/12.5/75GHz spacing";
                 }
                 enum "1559.14" {
                   description "1559.14 nm/192.28125 THz 6.25GHz spacing";
                 }
                 enum "1559.08" {
                   description "1559.08 nm/192.28750 THz 6.25/12.5GHz spacing";
                 }
                 enum "1559.03" {
                   description "1559.03 nm/192.29375 THz 6.25GHz spacing";
                 }
                 enum "1558.98" {
                   description "1558.98 nm/192.30000 THz 6.25/12.5/50/100GHz spacing";
                 }
                 enum "1558.93" {
                   description "1558.93 nm/192.30625 THz 6.25GHz spacing";
                 }
                 enum "1558.88" {
                   description "1558.88 nm/192.31250 THz 6.25/12.5GHz spacing";
                 }
                 enum "1558.83" {
                   description "1558.83 nm/192.31875 THz 6.25GHz spacing";
                 }
                 enum "1558.78" {
                   description "1558.78 nm/192.32500 THz 6.25/12.5GHz spacing";
                 }
                 enum "1558.73" {
                   description "1558.73 nm/192.33125 THz 6.25GHz spacing";
                 }
                 enum "1558.68" {
                   description "1558.68 nm/192.33750 THz 6.25/12.5GHz spacing";
                 }
                 enum "1558.63" {
                   description "1558.63 nm/192.34375 THz 6.25GHz spacing";
                 }
                 enum "1558.58" {
                   description "1558.58 nm/192.35000 THz 6.25/12.5/50/75GHz spacing";
                 }
                 enum "1558.53" {
                   description "1558.53 nm/192.35625 THz 6.25GHz spacing";
                 }
                 enum "1558.48" {
                   description "1558.48 nm/192.36250 THz 6.25/12.5GHz spacing";
                 }
                 enum "1558.43" {
                   description "1558.43 nm/192.36875 THz 6.25GHz spacing";
                 }
                 enum "1558.38" {
                   description "1558.38 nm/192.37500 THz 6.25/12.5GHz spacing";
                 }
                 enum "1558.32" {
                   description "1558.32 nm/192.38125 THz 6.25GHz spacing";
                 }
                 enum "1558.27" {
                   description "1558.27 nm/192.38750 THz 6.25/12.5GHz spacing";
                 }
                 enum "1558.22" {
                   description "1558.22 nm/192.39375 THz 6.25GHz spacing";
                 }
                 enum "1558.17" {
                   description "1558.17 nm/192.40000 THz 6.25/12.5/50/100GHz spacing";
                 }
                 enum "1558.12" {
                   description "1558.12 nm/192.40625 THz 6.25GHz spacing";
                 }
                 enum "1558.07" {
                   description "1558.07 nm/192.41250 THz 6.25/12.5GHz spacing";
                 }
                 enum "1558.02" {
                   description "1558.02 nm/192.41875 THz 6.25GHz spacing";
                 }
                 enum "1557.97" {
                   description "1557.97 nm/192.42500 THz 6.25/12.5/75GHz spacing";
                 }
                 enum "1557.92" {
                   description "1557.92 nm/192.43125 THz 6.25GHz spacing";
                 }
                 enum "1557.87" {
                   description "1557.87 nm/192.43750 THz 6.25/12.5GHz spacing";
                 }
                 enum "1557.82" {
                   description "1557.82 nm/192.44375 THz 6.25GHz spacing";
                 }
                 enum "1557.77" {
                   description "1557.77 nm/192.45000 THz 6.25/12.5/50GHz spacing";
                 }
                 enum "1557.72" {
                   description "1557.72 nm/192.45625 THz 6.25GHz spacing";
                 }
                 enum "1557.67" {
                   description "1557.67 nm/192.46250 THz 6.25/12.5GHz spacing";
                 }
                 enum "1557.62" {
                   description "1557.62 nm/192.46875 THz 6.25GHz spacing";
                 }
                 enum "1557.57" {
                   description "1557.57 nm/192.47500 THz 6.25/12.5GHz spacing";
                 }
                 enum "1557.52" {
                   description "1557.52 nm/192.48125 THz 6.25GHz spacing";
                 }
                 enum "1557.46" {
                   description "1557.46 nm/192.48750 THz 6.25/12.5GHz spacing";
                 }
                 enum "1557.41" {
                   description "1557.41 nm/192.49375 THz 6.25GHz spacing";
                 }
                 enum "1557.36" {
                   description "1557.36 nm/192.50000 THz 6.25/12.5/50/75/100GHz spacing";
                 }
                 enum "1557.31" {
                   description "1557.31 nm/192.50625 THz 6.25GHz spacing";
                 }
                 enum "1557.26" {
                   description "1557.26 nm/192.51250 THz 6.25/12.5GHz spacing";
                 }
                 enum "1557.21" {
                   description "1557.21 nm/192.51875 THz 6.25GHz spacing";
                 }
                 enum "1557.16" {
                   description "1557.16 nm/192.52500 THz 6.25/12.5GHz spacing";
                 }
                 enum "1557.11" {
                   description "1557.11 nm/192.53125 THz 6.25GHz spacing";
                 }
                 enum "1557.06" {
                   description "1557.06 nm/192.53750 THz 6.25/12.5GHz spacing";
                 }
                 enum "1557.01" {
                   description "1557.01 nm/192.54375 THz 6.25GHz spacing";
                 }
                 enum "1556.96" {
                   description "1556.96 nm/192.55000 THz 6.25/12.5/50GHz spacing";
                 }
                 enum "1556.91" {
                   description "1556.91 nm/192.55625 THz 6.25GHz spacing";
                 }
                 enum "1556.86" {
                   description "1556.86 nm/192.56250 THz 6.25/12.5GHz spacing";
                 }
                 enum "1556.81" {
                   description "1556.81 nm/192.56875 THz 6.25GHz spacing";
                 }
                 enum "1556.76" {
                   description "1556.76 nm/192.57500 THz 6.25/12.5/75GHz spacing";
                 }
                 enum "1556.71" {
                   description "1556.71 nm/192.58125 THz 6.25GHz spacing";
                 }
                 enum "1556.66" {
                   description "1556.66 nm/192.58750 THz 6.25/12.5GHz spacing";
                 }
                 enum "1556.61" {
                   description "1556.61 nm/192.59375 THz 6.25GHz spacing";
                 }
                 enum "1556.55" {
                   description "1556.55 nm/192.60000 THz 6.25/12.5/50/100GHz spacing";
                 }
                 enum "1556.50" {
                   description "1556.50 nm/192.60625 THz 6.25GHz spacing";
                 }
                 enum "1556.45" {
                   description "1556.45 nm/192.61250 THz 6.25/12.5GHz spacing";
                 }
                 enum "1556.40" {
                   description "1556.40 nm/192.61875 THz 6.25GHz spacing";
                 }
                 enum "1556.35" {
                   description "1556.35 nm/192.62500 THz 6.25/12.5GHz spacing";
                 }
                 enum "1556.30" {
                   description "1556.30 nm/192.63125 THz 6.25GHz spacing";
                 }
                 enum "1556.25" {
                   description "1556.25 nm/192.63750 THz 6.25/12.5GHz spacing";
                 }
                 enum "1556.20" {
                   description "1556.20 nm/192.64375 THz 6.25GHz spacing";
                 }
                 enum "1556.15" {
                   description "1556.15 nm/192.65000 THz 6.25/12.5/50/75GHz spacing";
                 }
                 enum "1556.10" {
                   description "1556.10 nm/192.65625 THz 6.25GHz spacing";
                 }
                 enum "1556.05" {
                   description "1556.05 nm/192.66250 THz 6.25/12.5GHz spacing";
                 }
                 enum "1556.00" {
                   description "1556.00 nm/192.66875 THz 6.25GHz spacing";
                 }
                 enum "1555.95" {
                   description "1555.95 nm/192.67500 THz 6.25/12.5GHz spacing";
                 }
                 enum "1555.90" {
                   description "1555.90 nm/192.68125 THz 6.25GHz spacing";
                 }
                 enum "1555.85" {
                   description "1555.85 nm/192.68750 THz 6.25/12.5GHz spacing";
                 }
                 enum "1555.80" {
                   description "1555.80 nm/192.69375 THz 6.25GHz spacing";
                 }
                 enum "1555.75" {
                   description "1555.75 nm/192.70000 THz 6.25/12.5/50/100GHz spacing";
                 }
                 enum "1555.70" {
                   description "1555.70 nm/192.70625 THz 6.25GHz spacing";
                 }
                 enum "1555.65" {
                   description "1555.65 nm/192.71250 THz 6.25/12.5GHz spacing";
                 }
                 enum "1555.60" {
                   description "1555.60 nm/192.71875 THz 6.25GHz spacing";
                 }
                 enum "1555.55" {
                   description "1555.55 nm/192.72500 THz 6.25/12.5/75GHz spacing";
                 }
                 enum "1555.49" {
                   description "1555.49 nm/192.73125 THz 6.25GHz spacing";
                 }
                 enum "1555.44" {
                   description "1555.44 nm/192.73750 THz 6.25/12.5GHz spacing";
                 }
                 enum "1555.39" {
                   description "1555.39 nm/192.74375 THz 6.25GHz spacing";
                 }
                 enum "1555.34" {
                   description "1555.34 nm/192.75000 THz 6.25/12.5/50GHz spacing";
                 }
                 enum "1555.29" {
                   description "1555.29 nm/192.75625 THz 6.25GHz spacing";
                 }
                 enum "1555.24" {
                   description "1555.24 nm/192.76250 THz 6.25/12.5GHz spacing";
                 }
                 enum "1555.19" {
                   description "1555.19 nm/192.76875 THz 6.25GHz spacing";
                 }
                 enum "1555.14" {
                   description "1555.14 nm/192.77500 THz 6.25/12.5GHz spacing";
                 }
                 enum "1555.09" {
                   description "1555.09 nm/192.78125 THz 6.25GHz spacing";
                 }
                 enum "1555.04" {
                   description "1555.04 nm/192.78750 THz 6.25/12.5GHz spacing";
                 }
                 enum "1554.99" {
                   description "1554.99 nm/192.79375 THz 6.25GHz spacing";
                 }
                 enum "1554.94" {
                   description "1554.94 nm/192.80000 THz 6.25/12.5/50/75/100GHz spacing";
                 }
                 enum "1554.89" {
                   description "1554.89 nm/192.80625 THz 6.25GHz spacing";
                 }
                 enum "1554.84" {
                   description "1554.84 nm/192.81250 THz 6.25/12.5GHz spacing";
                 }
                 enum "1554.79" {
                   description "1554.79 nm/192.81875 THz 6.25GHz spacing";
                 }
                 enum "1554.74" {
                   description "1554.74 nm/192.82500 THz 6.25/12.5GHz spacing";
                 }
                 enum "1554.69" {
                   description "1554.69 nm/192.83125 THz 6.25GHz spacing";
                 }
                 enum "1554.64" {
                   description "1554.64 nm/192.83750 THz 6.25/12.5GHz spacing";
                 }
                 enum "1554.59" {
                   description "1554.59 nm/192.84375 THz 6.25GHz spacing";
                 }
                 enum "1554.54" {
                   description "1554.54 nm/192.85000 THz 6.25/12.5/50GHz spacing";
                 }
                 enum "1554.49" {
                   description "1554.49 nm/192.85625 THz 6.25GHz spacing";
                 }
                 enum "1554.44" {
                   description "1554.44 nm/192.86250 THz 6.25/12.5GHz spacing";
                 }
                 enum "1554.39" {
                   description "1554.39 nm/192.86875 THz 6.25GHz spacing";
                 }
                 enum "1554.34" {
                   description "1554.34 nm/192.87500 THz 6.25/12.5/75GHz spacing";
                 }
                 enum "1554.29" {
                   description "1554.29 nm/192.88125 THz 6.25GHz spacing";
                 }
                 enum "1554.23" {
                   description "1554.23 nm/192.88750 THz 6.25/12.5GHz spacing";
                 }
                 enum "1554.18" {
                   description "1554.18 nm/192.89375 THz 6.25GHz spacing";
                 }
                 enum "1554.13" {
                   description "1554.13 nm/192.90000 THz 6.25/12.5/50/100GHz spacing";
                 }
                 enum "1554.08" {
                   description "1554.08 nm/192.90625 THz 6.25GHz spacing";
                 }
                 enum "1554.03" {
                   description "1554.03 nm/192.91250 THz 6.25/12.5GHz spacing";
                 }
                 enum "1553.98" {
                   description "1553.98 nm/192.91875 THz 6.25GHz spacing";
                 }
                 enum "1553.93" {
                   description "1553.93 nm/192.92500 THz 6.25/12.5GHz spacing";
                 }
                 enum "1553.88" {
                   description "1553.88 nm/192.93125 THz 6.25GHz spacing";
                 }
                 enum "1553.83" {
                   description "1553.83 nm/192.93750 THz 6.25/12.5GHz spacing";
                 }
                 enum "1553.78" {
                   description "1553.78 nm/192.94375 THz 6.25GHz spacing";
                 }
                 enum "1553.73" {
                   description "1553.73 nm/192.95000 THz 6.25/12.5/50/75GHz spacing";
                 }
                 enum "1553.68" {
                   description "1553.68 nm/192.95625 THz 6.25GHz spacing";
                 }
                 enum "1553.63" {
                   description "1553.63 nm/192.96250 THz 6.25/12.5GHz spacing";
                 }
                 enum "1553.58" {
                   description "1553.58 nm/192.96875 THz 6.25GHz spacing";
                 }
                 enum "1553.53" {
                   description "1553.53 nm/192.97500 THz 6.25/12.5GHz spacing";
                 }
                 enum "1553.48" {
                   description "1553.48 nm/192.98125 THz 6.25GHz spacing";
                 }
                 enum "1553.43" {
                   description "1553.43 nm/192.98750 THz 6.25/12.5GHz spacing";
                 }
                 enum "1553.38" {
                   description "1553.38 nm/192.99375 THz 6.25GHz spacing";
                 }
                 enum "1553.33" {
                   description "1553.33 nm/193.00000 THz 6.25/12.5/50/100GHz spacing";
                 }
                 enum "1553.28" {
                   description "1553.28 nm/193.00625 THz 6.25GHz spacing";
                 }
                 enum "1553.23" {
                   description "1553.23 nm/193.01250 THz 6.25/12.5GHz spacing";
                 }
                 enum "1553.18" {
                   description "1553.18 nm/193.01875 THz 6.25GHz spacing";
                 }
                 enum "1553.13" {
                   description "1553.13 nm/193.02500 THz 6.25/12.5/75GHz spacing";
                 }
                 enum "1553.08" {
                   description "1553.08 nm/193.03125 THz 6.25GHz spacing";
                 }
                 enum "1553.03" {
                   description "1553.03 nm/193.03750 THz 6.25/12.5GHz spacing";
                 }
                 enum "1552.98" {
                   description "1552.98 nm/193.04375 THz 6.25GHz spacing";
                 }
                 enum "1552.93" {
                   description "1552.93 nm/193.05000 THz 6.25/12.5/50GHz spacing";
                 }
                 enum "1552.88" {
                   description "1552.88 nm/193.05625 THz 6.25GHz spacing";
                 }
                 enum "1552.83" {
                   description "1552.83 nm/193.06250 THz 6.25/12.5GHz spacing";
                 }
                 enum "1552.78" {
                   description "1552.78 nm/193.06875 THz 6.25GHz spacing";
                 }
                 enum "1552.73" {
                   description "1552.73 nm/193.07500 THz 6.25/12.5GHz spacing";
                 }
                 enum "1552.68" {
                   description "1552.68 nm/193.08125 THz 6.25GHz spacing";
                 }
                 enum "1552.62" {
                   description "1552.62 nm/193.08750 THz 6.25/12.5GHz spacing";
                 }
                 enum "1552.57" {
                   description "1552.57 nm/193.09375 THz 6.25GHz spacing";
                 }
                 enum "1552.52" {
                   description "1552.52 nm/193.10000 THz 6.25/12.5/50/75/100GHz spacing";
                 }
                 enum "1552.47" {
                   description "1552.47 nm/193.10625 THz 6.25GHz spacing";
                 }
                 enum "1552.42" {
                   description "1552.42 nm/193.11250 THz 6.25/12.5GHz spacing";
                 }
                 enum "1552.37" {
                   description "1552.37 nm/193.11875 THz 6.25GHz spacing";
                 }
                 enum "1552.32" {
                   description "1552.32 nm/193.12500 THz 6.25/12.5GHz spacing";
                 }
                 enum "1552.27" {
                   description "1552.27 nm/193.13125 THz 6.25GHz spacing";
                 }
                 enum "1552.22" {
                   description "1552.22 nm/193.13750 THz 6.25/12.5GHz spacing";
                 }
                 enum "1552.17" {
                   description "1552.17 nm/193.14375 THz 6.25GHz spacing";
                 }
                 enum "1552.12" {
                   description "1552.12 nm/193.15000 THz 6.25/12.5/50GHz spacing";
                 }
                 enum "1552.07" {
                   description "1552.07 nm/193.15625 THz 6.25GHz spacing";
                 }
                 enum "1552.02" {
                   description "1552.02 nm/193.16250 THz 6.25/12.5GHz spacing";
                 }
                 enum "1551.97" {
                   description "1551.97 nm/193.16875 THz 6.25GHz spacing";
                 }
                 enum "1551.92" {
                   description "1551.92 nm/193.17500 THz 6.25/12.5/75GHz spacing";
                 }
                 enum "1551.87" {
                   description "1551.87 nm/193.18125 THz 6.25GHz spacing";
                 }
                 enum "1551.82" {
                   description "1551.82 nm/193.18750 THz 6.25/12.5GHz spacing";
                 }
                 enum "1551.77" {
                   description "1551.77 nm/193.19375 THz 6.25GHz spacing";
                 }
                 enum "1551.72" {
                   description "1551.72 nm/193.20000 THz 6.25/12.5/50/100GHz spacing";
                 }
                 enum "1551.67" {
                   description "1551.67 nm/193.20625 THz 6.25GHz spacing";
                 }
                 enum "1551.62" {
                   description "1551.62 nm/193.21250 THz 6.25/12.5GHz spacing";
                 }
                 enum "1551.57" {
                   description "1551.57 nm/193.21875 THz 6.25GHz spacing";
                 }
                 enum "1551.52" {
                   description "1551.52 nm/193.22500 THz 6.25/12.5GHz spacing";
                 }
                 enum "1551.47" {
                   description "1551.47 nm/193.23125 THz 6.25GHz spacing";
                 }
                 enum "1551.42" {
                   description "1551.42 nm/193.23750 THz 6.25/12.5GHz spacing";
                 }
                 enum "1551.37" {
                   description "1551.37 nm/193.24375 THz 6.25GHz spacing";
                 }
                 enum "1551.32" {
                   description "1551.32 nm/193.25000 THz 6.25/12.5/50/75GHz spacing";
                 }
                 enum "1551.27" {
                   description "1551.27 nm/193.25625 THz 6.25GHz spacing";
                 }
                 enum "1551.22" {
                   description "1551.22 nm/193.26250 THz 6.25/12.5GHz spacing";
                 }
                 enum "1551.17" {
                   description "1551.17 nm/193.26875 THz 6.25GHz spacing";
                 }
                 enum "1551.12" {
                   description "1551.12 nm/193.27500 THz 6.25/12.5GHz spacing";
                 }
                 enum "1551.07" {
                   description "1551.07 nm/193.28125 THz 6.25GHz spacing";
                 }
                 enum "1551.02" {
                   description "1551.02 nm/193.28750 THz 6.25/12.5GHz spacing";
                 }
                 enum "1550.97" {
                   description "1550.97 nm/193.29375 THz 6.25GHz spacing";
                 }
                 enum "1550.92" {
                   description "1550.92 nm/193.30000 THz 6.25/12.5/50/100GHz spacing";
                 }
                 enum "1550.87" {
                   description "1550.87 nm/193.30625 THz 6.25GHz spacing";
                 }
                 enum "1550.82" {
                   description "1550.82 nm/193.31250 THz 6.25/12.5GHz spacing";
                 }
                 enum "1550.77" {
                   description "1550.77 nm/193.31875 THz 6.25GHz spacing";
                 }
                 enum "1550.72" {
                   description "1550.72 nm/193.32500 THz 6.25/12.5/75GHz spacing";
                 }
                 enum "1550.67" {
                   description "1550.67 nm/193.33125 THz 6.25GHz spacing";
                 }
                 enum "1550.62" {
                   description "1550.62 nm/193.33750 THz 6.25/12.5GHz spacing";
                 }
                 enum "1550.57" {
                   description "1550.57 nm/193.34375 THz 6.25GHz spacing";
                 }
                 enum "1550.52" {
                   description "1550.52 nm/193.35000 THz 6.25/12.5/50GHz spacing";
                 }
                 enum "1550.47" {
                   description "1550.47 nm/193.35625 THz 6.25GHz spacing";
                 }
                 enum "1550.42" {
                   description "1550.42 nm/193.36250 THz 6.25/12.5GHz spacing";
                 }
                 enum "1550.37" {
                   description "1550.37 nm/193.36875 THz 6.25GHz spacing";
                 }
                 enum "1550.32" {
                   description "1550.32 nm/193.37500 THz 6.25/12.5GHz spacing";
                 }
                 enum "1550.27" {
                   description "1550.27 nm/193.38125 THz 6.25GHz spacing";
                 }
                 enum "1550.22" {
                   description "1550.22 nm/193.38750 THz 6.25/12.5GHz spacing";
                 }
                 enum "1550.17" {
                   description "1550.17 nm/193.39375 THz 6.25GHz spacing";
                 }
                 enum "1550.12" {
                   description "1550.12 nm/193.40000 THz 6.25/12.5/50/75/100GHz spacing";
                 }
                 enum "1550.07" {
                   description "1550.07 nm/193.40625 THz 6.25GHz spacing";
                 }
                 enum "1550.02" {
                   description "1550.02 nm/193.41250 THz 6.25/12.5GHz spacing";
                 }
                 enum "1549.97" {
                   description "1549.97 nm/193.41875 THz 6.25GHz spacing";
                 }
                 enum "1549.92" {
                   description "1549.92 nm/193.42500 THz 6.25/12.5GHz spacing";
                 }
                 enum "1549.87" {
                   description "1549.87 nm/193.43125 THz 6.25GHz spacing";
                 }
                 enum "1549.82" {
                   description "1549.82 nm/193.43750 THz 6.25/12.5GHz spacing";
                 }
                 enum "1549.77" {
                   description "1549.77 nm/193.44375 THz 6.25GHz spacing";
                 }
                 enum "1549.72" {
                   description "1549.72 nm/193.45000 THz 6.25/12.5/50GHz spacing";
                 }
                 enum "1549.67" {
                   description "1549.67 nm/193.45625 THz 6.25GHz spacing";
                 }
                 enum "1549.62" {
                   description "1549.62 nm/193.46250 THz 6.25/12.5GHz spacing";
                 }
                 enum "1549.57" {
                   description "1549.57 nm/193.46875 THz 6.25GHz spacing";
                 }
                 enum "1549.52" {
                   description "1549.52 nm/193.47500 THz 6.25/12.5/75GHz spacing";
                 }
                 enum "1549.47" {
                   description "1549.47 nm/193.48125 THz 6.25GHz spacing";
                 }
                 enum "1549.42" {
                   description "1549.42 nm/193.48750 THz 6.25/12.5GHz spacing";
                 }
                 enum "1549.37" {
                   description "1549.37 nm/193.49375 THz 6.25GHz spacing";
                 }
                 enum "1549.32" {
                   description "1549.32 nm/193.50000 THz 6.25/12.5/50/100GHz spacing";
                 }
                 enum "1549.26" {
                   description "1549.26 nm/193.50625 THz 6.25GHz spacing";
                 }
                 enum "1549.21" {
                   description "1549.21 nm/193.51250 THz 6.25/12.5GHz spacing";
                 }
                 enum "1549.16" {
                   description "1549.16 nm/193.51875 THz 6.25GHz spacing";
                 }
                 enum "1549.11" {
                   description "1549.11 nm/193.52500 THz 6.25/12.5GHz spacing";
                 }
                 enum "1549.06" {
                   description "1549.06 nm/193.53125 THz 6.25GHz spacing";
                 }
                 enum "1549.01" {
                   description "1549.01 nm/193.53750 THz 6.25/12.5GHz spacing";
                 }
                 enum "1548.96" {
                   description "1548.96 nm/193.54375 THz 6.25GHz spacing";
                 }
                 enum "1548.91" {
                   description "1548.91 nm/193.55000 THz 6.25/12.5/50G/75Hz spacing";
                 }
                 enum "1548.86" {
                   description "1548.86 nm/193.55625 THz 6.25GHz spacing";
                 }
                 enum "1548.81" {
                   description "1548.81 nm/193.56250 THz 6.25/12.5GHz spacing";
                 }
                 enum "1548.76" {
                   description "1548.76 nm/193.56875 THz 6.25GHz spacing";
                 }
                 enum "1548.71" {
                   description "1548.71 nm/193.57500 THz 6.25/12.5GHz spacing";
                 }
                 enum "1548.66" {
                   description "1548.66 nm/193.58125 THz 6.25GHz spacing";
                 }
                 enum "1548.61" {
                   description "1548.61 nm/193.58750 THz 6.25/12.5GHz spacing";
                 }
                 enum "1548.56" {
                   description "1548.56 nm/193.59375 THz 6.25GHz spacing";
                 }
                 enum "1548.51" {
                   description "1548.51 nm/193.60000 THz 6.25/12.5/50/100GHz spacing";
                 }
                 enum "1548.46" {
                   description "1548.46 nm/193.60625 THz 6.25GHz spacing";
                 }
                 enum "1548.41" {
                   description "1548.41 nm/193.61250 THz 6.25/12.5GHz spacing";
                 }
                 enum "1548.36" {
                   description "1548.36 nm/193.61875 THz 6.25GHz spacing";
                 }
                 enum "1548.31" {
                   description "1548.31 nm/193.62500 THz 6.25/12.5/75GHz spacing";
                 }
                 enum "1548.26" {
                   description "1548.26 nm/193.63125 THz 6.25GHz spacing";
                 }
                 enum "1548.21" {
                   description "1548.21 nm/193.63750 THz 6.25/12.5GHz spacing";
                 }
                 enum "1548.16" {
                   description "1548.16 nm/193.64375 THz 6.25GHz spacing";
                 }
                 enum "1548.11" {
                   description "1548.11 nm/193.65000 THz 6.25/12.5/50GHz spacing";
                 }
                 enum "1548.06" {
                   description "1548.06 nm/193.65625 THz 6.25GHz spacing";
                 }
                 enum "1548.02" {
                   description "1548.02 nm/193.66250 THz 6.25/12.5GHz spacing";
                 }
                 enum "1547.97" {
                   description "1547.97 nm/193.66875 THz 6.25GHz spacing";
                 }
                 enum "1547.92" {
                   description "1547.92 nm/193.67500 THz 6.25/12.5GHz spacing";
                 }
                 enum "1547.87" {
                   description "1547.87 nm/193.68125 THz 6.25GHz spacing";
                 }
                 enum "1547.82" {
                   description "1547.82 nm/193.68750 THz 6.25/12.5GHz spacing";
                 }
                 enum "1547.77" {
                   description "1547.77 nm/193.69375 THz 6.25GHz spacing";
                 }
                 enum "1547.72" {
                   description "1547.72 nm/193.70000 THz 6.25/12.5/50/75/100GHz spacing";
                 }
                 enum "1547.67" {
                   description "1547.67 nm/193.70625 THz 6.25GHz spacing";
                 }
                 enum "1547.62" {
                   description "1547.62 nm/193.71250 THz 6.25/12.5GHz spacing";
                 }
                 enum "1547.57" {
                   description "1547.57 nm/193.71875 THz 6.25GHz spacing";
                 }
                 enum "1547.52" {
                   description "1547.52 nm/193.72500 THz 6.25/12.5GHz spacing";
                 }
                 enum "1547.47" {
                   description "1547.47 nm/193.73125 THz 6.25GHz spacing";
                 }
                 enum "1547.42" {
                   description "1547.42 nm/193.73750 THz 6.25/12.5GHz spacing";
                 }
                 enum "1547.37" {
                   description "1547.37 nm/193.74375 THz 6.25GHz spacing";
                 }
                 enum "1547.32" {
                   description "1547.32 nm/193.75000 THz 6.25/12.5/50GHz spacing";
                 }
                 enum "1547.27" {
                   description "1547.27 nm/193.75625 THz 6.25GHz spacing";
                 }
                 enum "1547.22" {
                   description "1547.22 nm/193.76250 THz 6.25/12.5GHz spacing";
                 }
                 enum "1547.17" {
                   description "1547.17 nm/193.76875 THz 6.25GHz spacing";
                 }
                 enum "1547.12" {
                   description "1547.12 nm/193.77500 THz 6.25/12.5/75GHz spacing";
                 }
                 enum "1547.07" {
                   description "1547.07 nm/193.78125 THz 6.25GHz spacing";
                 }
                 enum "1547.02" {
                   description "1547.02 nm/193.78750 THz 6.25/12.5GHz spacing";
                 }
                 enum "1546.97" {
                   description "1546.97 nm/193.79375 THz 6.25GHz spacing";
                 }
                 enum "1546.92" {
                   description "1546.92 nm/193.80000 THz 6.25/12.5/50/100GHz spacing";
                 }
                 enum "1546.87" {
                   description "1546.87 nm/193.80625 THz 6.25GHz spacing";
                 }
                 enum "1546.82" {
                   description "1546.82 nm/193.81250 THz 6.25/12.5GHz spacing";
                 }
                 enum "1546.77" {
                   description "1546.77 nm/193.81875 THz 6.25GHz spacing";
                 }
                 enum "1546.72" {
                   description "1546.72 nm/193.82500 THz 6.25/12.5GHz spacing";
                 }
                 enum "1546.67" {
                   description "1546.67 nm/193.83125 THz 6.25GHz spacing";
                 }
                 enum "1546.62" {
                   description "1546.62 nm/193.83750 THz 6.25/12.5GHz spacing";
                 }
                 enum "1546.57" {
                   description "1546.57 nm/193.84375 THz 6.25GHz spacing";
                 }
                 enum "1546.52" {
                   description "1546.52 nm/193.85000 THz 6.25/12.5/50/75GHz spacing";
                 }
                 enum "1546.47" {
                   description "1546.47 nm/193.85625 THz 6.25GHz spacing";
                 }
                 enum "1546.42" {
                   description "1546.42 nm/193.86250 THz 6.25/12.5GHz spacing";
                 }
                 enum "1546.37" {
                   description "1546.37 nm/193.86875 THz 6.25GHz spacing";
                 }
                 enum "1546.32" {
                   description "1546.32 nm/193.87500 THz 6.25/12.5GHz spacing";
                 }
                 enum "1546.27" {
                   description "1546.27 nm/193.88125 THz 6.25GHz spacing";
                 }
                 enum "1546.22" {
                   description "1546.22 nm/193.88750 THz 6.25/12.5GHz spacing";
                 }
                 enum "1546.17" {
                   description "1546.17 nm/193.89375 THz 6.25GHz spacing";
                 }
                 enum "1546.12" {
                   description "1546.12 nm/193.90000 THz 6.25/12.5/50/100GHz spacing";
                 }
                 enum "1546.07" {
                   description "1546.07 nm/193.90625 THz 6.25GHz spacing";
                 }
                 enum "1546.02" {
                   description "1546.02 nm/193.91250 THz 6.25/12.5GHz spacing";
                 }
                 enum "1545.97" {
                   description "1545.97 nm/193.91875 THz 6.25GHz spacing";
                 }
                 enum "1545.92" {
                   description "1545.92 nm/193.92500 THz 6.25/12.5/75GHz spacing";
                 }
                 enum "1545.87" {
                   description "1545.87 nm/193.93125 THz 6.25GHz spacing";
                 }
                 enum "1545.82" {
                   description "1545.82 nm/193.93750 THz 6.25/12.5GHz spacing";
                 }
                 enum "1545.77" {
                   description "1545.77 nm/193.94375 THz 6.25GHz spacing";
                 }
                 enum "1545.72" {
                   description "1545.72 nm/193.95000 THz 6.25/12.5/50GHz spacing";
                 }
                 enum "1545.67" {
                   description "1545.67 nm/193.95625 THz 6.25GHz spacing";
                 }
                 enum "1545.62" {
                   description "1545.62 nm/193.96250 THz 6.25/12.5GHz spacing";
                 }
                 enum "1545.57" {
                   description "1545.57 nm/193.96875 THz 6.25GHz spacing";
                 }
                 enum "1545.52" {
                   description "1545.52 nm/193.97500 THz 6.25/12.5GHz spacing";
                 }
                 enum "1545.47" {
                   description "1545.47 nm/193.98125 THz 6.25GHz spacing";
                 }
                 enum "1545.42" {
                   description "1545.42 nm/193.98750 THz 6.25/12.5GHz spacing";
                 }
                 enum "1545.37" {
                   description "1545.37 nm/193.99375 THz 6.25GHz spacing";
                 }
                 enum "1545.32" {
                   description "1545.32 nm/194.00000 THz 6.25/12.5/50/75/100GHz spacing";
                 }
                 enum "1545.27" {
                   description "1545.27 nm/194.00625 THz 6.25GHz spacing";
                 }
                 enum "1545.22" {
                   description "1545.22 nm/194.01250 THz 6.25/12.5GHz spacing";
                 }
                 enum "1545.17" {
                   description "1545.17 nm/194.01875 THz 6.25GHz spacing";
                 }
                 enum "1545.12" {
                   description "1545.12 nm/194.02500 THz 6.25/12.5GHz spacing";
                 }
                 enum "1545.07" {
                   description "1545.07 nm/194.03125 THz 6.25GHz spacing";
                 }
                 enum "1545.02" {
                   description "1545.02 nm/194.03750 THz 6.25/12.5GHz spacing";
                 }
                 enum "1544.97" {
                   description "1544.97 nm/194.04375 THz 6.25GHz spacing";
                 }
                 enum "1544.92" {
                   description "1544.92 nm/194.05000 THz 6.25/12.5/50GHz spacing";
                 }
                 enum "1544.87" {
                   description "1544.87 nm/194.05625 THz 6.25GHz spacing";
                 }
                 enum "1544.82" {
                   description "1544.82 nm/194.06250 THz 6.25/12.5GHz spacing";
                 }
                 enum "1544.77" {
                   description "1544.77 nm/194.06875 THz 6.25GHz spacing";
                 }
                 enum "1544.72" {
                   description "1544.72 nm/194.07500 THz 6.25/12.5/75GHz spacing";
                 }
                 enum "1544.68" {
                   description "1544.68 nm/194.08125 THz 6.25GHz spacing";
                 }
                 enum "1544.63" {
                   description "1544.63 nm/194.08750 THz 6.25/12.5GHz spacing";
                 }
                 enum "1544.58" {
                   description "1544.58 nm/194.09375 THz 6.25GHz spacing";
                 }
                 enum "1544.53" {
                   description "1544.53 nm/194.10000 THz 6.25/12.5/50/100GHz spacing";
                 }
                 enum "1544.48" {
                   description "1544.48 nm/194.10625 THz 6.25GHz spacing";
                 }
                 enum "1544.43" {
                   description "1544.43 nm/194.11250 THz 6.25/12.5GHz spacing";
                 }
                 enum "1544.38" {
                   description "1544.38 nm/194.11875 THz 6.25GHz spacing";
                 }
                 enum "1544.33" {
                   description "1544.33 nm/194.12500 THz 6.25/12.5GHz spacing";
                 }
                 enum "1544.28" {
                   description "1544.28 nm/194.13125 THz 6.25GHz spacing";
                 }
                 enum "1544.23" {
                   description "1544.23 nm/194.13750 THz 6.25/12.5GHz spacing";
                 }
                 enum "1544.18" {
                   description "1544.18 nm/194.14375 THz 6.25GHz spacing";
                 }
                 enum "1544.13" {
                   description "1544.13 nm/194.15000 THz 6.25/12.5/50/75GHz spacing";
                 }
                 enum "1544.08" {
                   description "1544.08 nm/194.15625 THz 6.25GHz spacing";
                 }
                 enum "1544.03" {
                   description "1544.03 nm/194.16250 THz 6.25/12.5GHz spacing";
                 }
                 enum "1543.98" {
                   description "1543.98 nm/194.16875 THz 6.25GHz spacing";
                 }
                 enum "1543.93" {
                   description "1543.93 nm/194.17500 THz 6.25/12.5GHz spacing";
                 }
                 enum "1543.88" {
                   description "1543.88 nm/194.18125 THz 6.25GHz spacing";
                 }
                 enum "1543.83" {
                   description "1543.83 nm/194.18750 THz 6.25/12.5GHz spacing";
                 }
                 enum "1543.78" {
                   description "1543.78 nm/194.19375 THz 6.25GHz spacing";
                 }
                 enum "1543.73" {
                   description "1543.73 nm/194.20000 THz 6.25/12.5/50/100GHz spacing";
                 }
                 enum "1543.68" {
                   description "1543.68 nm/194.20625 THz 6.25GHz spacing";
                 }
                 enum "1543.63" {
                   description "1543.63 nm/194.21250 THz 6.25/12.5GHz spacing";
                 }
                 enum "1543.58" {
                   description "1543.58 nm/194.21875 THz 6.25GHz spacing";
                 }
                 enum "1543.53" {
                   description "1543.53 nm/194.22500 THz 6.25/12.5/75GHz spacing";
                 }
                 enum "1543.48" {
                   description "1543.48 nm/194.23125 THz 6.25GHz spacing";
                 }
                 enum "1543.43" {
                   description "1543.43 nm/194.23750 THz 6.25/12.5GHz spacing";
                 }
                 enum "1543.38" {
                   description "1543.38 nm/194.24375 THz 6.25GHz spacing";
                 }
                 enum "1543.33" {
                   description "1543.33 nm/194.25000 THz 6.25/12.5/50GHz spacing";
                 }
                 enum "1543.28" {
                   description "1543.28 nm/194.25625 THz 6.25GHz spacing";
                 }
                 enum "1543.23" {
                   description "1543.23 nm/194.26250 THz 6.25/12.5GHz spacing";
                 }
                 enum "1543.18" {
                   description "1543.18 nm/194.26875 THz 6.25GHz spacing";
                 }
                 enum "1543.13" {
                   description "1543.13 nm/194.27500 THz 6.25/12.5GHz spacing";
                 }
                 enum "1543.08" {
                   description "1543.08 nm/194.28125 THz 6.25GHz spacing";
                 }
                 enum "1543.04" {
                   description "1543.04 nm/194.28750 THz 6.25/12.5GHz spacing";
                 }
                 enum "1542.99" {
                   description "1542.99 nm/194.29375 THz 6.25GHz spacing";
                 }
                 enum "1542.94" {
                   description "1542.94 nm/194.30000 THz 6.25/12.5/50/75/100GHz spacing";
                 }
                 enum "1542.89" {
                   description "1542.89 nm/194.30625 THz 6.25GHz spacing";
                 }
                 enum "1542.84" {
                   description "1542.84 nm/194.31250 THz 6.25/12.5GHz spacing";
                 }
                 enum "1542.79" {
                   description "1542.79 nm/194.31875 THz 6.25GHz spacing";
                 }
                 enum "1542.74" {
                   description "1542.74 nm/194.32500 THz 6.25/12.5GHz spacing";
                 }
                 enum "1542.69" {
                   description "1542.69 nm/194.33125 THz 6.25GHz spacing";
                 }
                 enum "1542.64" {
                   description "1542.64 nm/194.33750 THz 6.25/12.5GHz spacing";
                 }
                 enum "1542.59" {
                   description "1542.59 nm/194.34375 THz 6.25GHz spacing";
                 }
                 enum "1542.54" {
                   description "1542.54 nm/194.35000 THz 6.25/12.5/50GHz spacing";
                 }
                 enum "1542.49" {
                   description "1542.49 nm/194.35625 THz 6.25GHz spacing";
                 }
                 enum "1542.44" {
                   description "1542.44 nm/194.36250 THz 6.25/12.5GHz spacing";
                 }
                 enum "1542.39" {
                   description "1542.39 nm/194.36875 THz 6.25GHz spacing";
                 }
                 enum "1542.34" {
                   description "1542.34 nm/194.37500 THz 6.25/12.5/75GHz spacing";
                 }
                 enum "1542.29" {
                   description "1542.29 nm/194.38125 THz 6.25GHz spacing";
                 }
                 enum "1542.24" {
                   description "1542.24 nm/194.38750 THz 6.25/12.5GHz spacing";
                 }
                 enum "1542.19" {
                   description "1542.19 nm/194.39375 THz 6.25GHz spacing";
                 }
                 enum "1542.14" {
                   description "1542.14 nm/194.40000 THz 6.25/12.5/50/100GHz spacing";
                 }
                 enum "1542.09" {
                   description "1542.09 nm/194.40625 THz 6.25GHz spacing";
                 }
                 enum "1542.04" {
                   description "1542.04 nm/194.41250 THz 6.25/12.5GHz spacing";
                 }
                 enum "1541.99" {
                   description "1541.99 nm/194.41875 THz 6.25GHz spacing";
                 }
                 enum "1541.94" {
                   description "1541.94 nm/194.42500 THz 6.25/12.5GHz spacing";
                 }
                 enum "1541.89" {
                   description "1541.89 nm/194.43125 THz 6.25GHz spacing";
                 }
                 enum "1541.84" {
                   description "1541.84 nm/194.43750 THz 6.25/12.5GHz spacing";
                 }
                 enum "1541.80" {
                   description "1541.80 nm/194.44375 THz 6.25GHz spacing";
                 }
                 enum "1541.75" {
                   description "1541.75 nm/194.45000 THz 6.25/12.5/50/75GHz spacing";
                 }
                 enum "1541.70" {
                   description "1541.70 nm/194.45625 THz 6.25GHz spacing";
                 }
                 enum "1541.65" {
                   description "1541.65 nm/194.46250 THz 6.25/12.5GHz spacing";
                 }
                 enum "1541.60" {
                   description "1541.60 nm/194.46875 THz 6.25GHz spacing";
                 }
                 enum "1541.55" {
                   description "1541.55 nm/194.47500 THz 6.25/12.5GHz spacing";
                 }
                 enum "1541.50" {
                   description "1541.50 nm/194.48125 THz 6.25GHz spacing";
                 }
                 enum "1541.45" {
                   description "1541.45 nm/194.48750 THz 6.25/12.5GHz spacing";
                 }
                 enum "1541.40" {
                   description "1541.40 nm/194.49375 THz 6.25GHz spacing";
                 }
                 enum "1541.35" {
                   description "1541.35 nm/194.50000 THz 6.25/12.5/50/100GHz spacing";
                 }
                 enum "1541.30" {
                   description "1541.30 nm/194.50625 THz 6.25GHz spacing";
                 }
                 enum "1541.25" {
                   description "1541.25 nm/194.51250 THz 6.25/12.5GHz spacing";
                 }
                 enum "1541.20" {
                   description "1541.20 nm/194.51875 THz 6.25GHz spacing";
                 }
                 enum "1541.15" {
                   description "1541.15 nm/194.52500 THz 6.25/12.5/75GHz spacing";
                 }
                 enum "1541.10" {
                   description "1541.10 nm/194.53125 THz 6.25GHz spacing";
                 }
                 enum "1541.05" {
                   description "1541.05 nm/194.53750 THz 6.25/12.5GHz spacing";
                 }
                 enum "1541.00" {
                   description "1541.00 nm/194.54375 THz 6.25GHz spacing";
                 }
                 enum "1540.95" {
                   description "1540.95 nm/194.55000 THz 6.25/12.5/50GHz spacing";
                 }
                 enum "1540.90" {
                   description "1540.90 nm/194.55625 THz 6.25GHz spacing";
                 }
                 enum "1540.85" {
                   description "1540.85 nm/194.56250 THz 6.25/12.5GHz spacing";
                 }
                 enum "1540.80" {
                   description "1540.80 nm/194.56875 THz 6.25GHz spacing";
                 }
                 enum "1540.76" {
                   description "1540.76 nm/194.57500 THz 6.25/12.5GHz spacing";
                 }
                 enum "1540.71" {
                   description "1540.71 nm/194.58125 THz 6.25GHz spacing";
                 }
                 enum "1540.66" {
                   description "1540.66 nm/194.58750 THz 6.25/12.5GHz spacing";
                 }
                 enum "1540.61" {
                   description "1540.61 nm/194.59375 THz 6.25GHz spacing";
                 }
                 enum "1540.56" {
                   description "1540.56 nm/194.60000 THz 6.25/12.5/50/75/100GHz spacing";
                 }
                 enum "1540.51" {
                   description "1540.51 nm/194.60625 THz 6.25GHz spacing";
                 }
                 enum "1540.46" {
                   description "1540.46 nm/194.61250 THz 6.25/12.5GHz spacing";
                 }
                 enum "1540.41" {
                   description "1540.41 nm/194.61875 THz 6.25GHz spacing";
                 }
                 enum "1540.36" {
                   description "1540.36 nm/194.62500 THz 6.25/12.5GHz spacing";
                 }
                 enum "1540.31" {
                   description "1540.31 nm/194.63125 THz 6.25GHz spacing";
                 }
                 enum "1540.26" {
                   description "1540.26 nm/194.63750 THz 6.25/12.5GHz spacing";
                 }
                 enum "1540.21" {
                   description "1540.21 nm/194.64375 THz 6.25GHz spacing";
                 }
                 enum "1540.16" {
                   description "1540.16 nm/194.65000 THz 6.25/12.5/50GHz spacing";
                 }
                 enum "1540.11" {
                   description "1540.11 nm/194.65625 THz 6.25GHz spacing";
                 }
                 enum "1540.06" {
                   description "1540.06 nm/194.66250 THz 6.25/12.5GHz spacing";
                 }
                 enum "1540.01" {
                   description "1540.01 nm/194.66875 THz 6.25GHz spacing";
                 }
                 enum "1539.96" {
                   description "1539.96 nm/194.67500 THz 6.25/12.5/50/75GHz spacing";
                 }
                 enum "1539.91" {
                   description "1539.91 nm/194.68125 THz 6.25GHz spacing";
                 }
                 enum "1539.86" {
                   description "1539.86 nm/194.68750 THz 6.25/12.5GHz spacing";
                 }
                 enum "1539.82" {
                   description "1539.82 nm/194.69375 THz 6.25GHz spacing";
                 }
                 enum "1539.77" {
                   description "1539.77 nm/194.70000 THz 6.25/12.5/50/100GHz spacing";
                 }
                 enum "1539.72" {
                   description "1539.72 nm/194.70625 THz 6.25GHz spacing";
                 }
                 enum "1539.67" {
                   description "1539.67 nm/194.71250 THz 6.25/12.5GHz spacing";
                 }
                 enum "1539.62" {
                   description "1539.62 nm/194.71875 THz 6.25GHz spacing";
                 }
                 enum "1539.57" {
                   description "1539.57 nm/194.72500 THz 6.25/12.5GHz spacing";
                 }
                 enum "1539.52" {
                   description "1539.52 nm/194.73125 THz 6.25GHz spacing";
                 }
                 enum "1539.47" {
                   description "1539.47 nm/194.73750 THz 6.25/12.5GHz spacing";
                 }
                 enum "1539.42" {
                   description "1539.42 nm/194.74375 THz 6.25GHz spacing";
                 }
                 enum "1539.37" {
                   description "1539.37 nm/194.75000 THz 6.25/12.5/50/75GHz spacing";
                 }
                 enum "1539.32" {
                   description "1539.32 nm/194.75625 THz 6.25GHz spacing";
                 }
                 enum "1539.27" {
                   description "1539.27 nm/194.76250 THz 6.25/12.5GHz spacing";
                 }
                 enum "1539.22" {
                   description "1539.22 nm/194.76875 THz 6.25GHz spacing";
                 }
                 enum "1539.17" {
                   description "1539.17 nm/194.77500 THz 6.25/12.5GHz spacing";
                 }
                 enum "1539.12" {
                   description "1539.12 nm/194.78125 THz 6.25GHz spacing";
                 }
                 enum "1539.07" {
                   description "1539.07 nm/194.78750 THz 6.25/12.5GHz spacing";
                 }
                 enum "1539.03" {
                   description "1539.03 nm/194.79375 THz 6.25GHz spacing";
                 }
                 enum "1538.98" {
                   description "1538.98 nm/194.80000 THz 6.25/12.5/50/100GHz spacing";
                 }
                 enum "1538.93" {
                   description "1538.93 nm/194.80625 THz 6.25GHz spacing";
                 }
                 enum "1538.88" {
                   description "1538.88 nm/194.81250 THz 6.25/12.5GHz spacing";
                 }
                 enum "1538.83" {
                   description "1538.83 nm/194.81875 THz 6.25GHz spacing";
                 }
                 enum "1538.78" {
                   description "1538.78 nm/194.82500 THz 6.25/12.5/75GHz spacing";
                 }
                 enum "1538.73" {
                   description "1538.73 nm/194.83125 THz 6.25GHz spacing";
                 }
                 enum "1538.68" {
                   description "1538.68 nm/194.83750 THz 6.25/12.5GHz spacing";
                 }
                 enum "1538.63" {
                   description "1538.63 nm/194.84375 THz 6.25GHz spacing";
                 }
                 enum "1538.58" {
                   description "1538.58 nm/194.85000 THz 6.25/12.5/50GHz spacing";
                 }
                 enum "1538.53" {
                   description "1538.53 nm/194.85625 THz 6.25GHz spacing";
                 }
                 enum "1538.48" {
                   description "1538.48 nm/194.86250 THz 6.25/12.5GHz spacing";
                 }
                 enum "1538.43" {
                   description "1538.43 nm/194.86875 THz 6.25GHz spacing";
                 }
                 enum "1538.38" {
                   description "1538.38 nm/194.87500 THz 6.25/12.5/75GHz spacing";
                 }
                 enum "1538.33" {
                   description "1538.33 nm/194.88125 THz 6.25GHz spacing";
                 }
                 enum "1538.28" {
                   description "1538.28 nm/194.88750 THz 6.25/12.5GHz spacing";
                 }
                 enum "1538.24" {
                   description "1538.24 nm/194.89375 THz 6.25GHz spacing";
                 }
                 enum "1538.19" {
                   description "1538.19 nm/194.90000 THz 6.25/12.5/50/75/100GHz spacing";
                 }
                 enum "1538.14" {
                   description "1538.14 nm/194.90625 THz 6.25GHz spacing";
                 }
                 enum "1538.09" {
                   description "1538.09 nm/194.91250 THz 6.25/12.5GHz spacing";
                 }
                 enum "1538.04" {
                   description "1538.04 nm/194.91875 THz 6.25GHz spacing";
                 }
                 enum "1537.99" {
                   description "1537.99 nm/194.92500 THz 6.25/12.5GHz spacing";
                 }
                 enum "1537.94" {
                   description "1537.94 nm/194.93125 THz 6.25GHz spacing";
                 }
                 enum "1537.89" {
                   description "1537.89 nm/194.93750 THz 6.25/12.5GHz spacing";
                 }
                 enum "1537.84" {
                   description "1537.84 nm/194.94375 THz 6.25GHz spacing";
                 }
                 enum "1537.79" {
                   description "1537.79 nm/194.95000 THz 6.25/12.5/50GHz spacing";
                 }
                 enum "1537.74" {
                   description "1537.74 nm/194.95625 THz 6.25GHz spacing";
                 }
                 enum "1537.69" {
                   description "1537.69 nm/194.96250 THz 6.25/12.5GHz spacing";
                 }
                 enum "1537.64" {
                   description "1537.64 nm/194.96875 THz 6.25GHz spacing";
                 }
                 enum "1537.59" {
                   description "1537.59 nm/194.97500 THz 6.25/12.5/75GHz spacing";
                 }
                 enum "1537.55" {
                   description "1537.55 nm/194.98125 THz 6.25GHz spacing";
                 }
                 enum "1537.50" {
                   description "1537.50 nm/194.98750 THz 6.25/12.5GHz spacing";
                 }
                 enum "1537.45" {
                   description "1537.45 nm/194.99375 THz 6.25GHz spacing";
                 }
                 enum "1537.40" {
                   description "1537.40 nm/195.00000 THz 6.25/12.5/50/100GHz spacing";
                 }
                 enum "1537.35" {
                   description "1537.35 nm/195.00625 THz 6.25GHz spacing";
                 }
                 enum "1537.30" {
                   description "1537.30 nm/195.01250 THz 6.25/12.5GHz spacing";
                 }
                 enum "1537.25" {
                   description "1537.25 nm/195.01875 THz 6.25GHz spacing";
                 }
                 enum "1537.20" {
                   description "1537.20 nm/195.02500 THz 6.25/12.5GHz spacing";
                 }
                 enum "1537.15" {
                   description "1537.15 nm/195.03125 THz 6.25GHz spacing";
                 }
                 enum "1537.10" {
                   description "1537.10 nm/195.03750 THz 6.25/12.5GHz spacing";
                 }
                 enum "1537.05" {
                   description "1537.05 nm/195.04375 THz 6.25GHz spacing";
                 }
                 enum "1537.00" {
                   description "1537.00 nm/195.05000 THz 6.25/12.5/50/75GHz spacing";
                 }
                 enum "1536.95" {
                   description "1536.95 nm/195.05625 THz 6.25GHz spacing";
                 }
                 enum "1536.90" {
                   description "1536.90 nm/195.06250 THz 6.25/12.5GHz spacing";
                 }
                 enum "1536.86" {
                   description "1536.86 nm/195.06875 THz 6.25GHz spacing";
                 }
                 enum "1536.81" {
                   description "1536.81 nm/195.07500 THz 6.25/12.5GHz spacing";
                 }
                 enum "1536.76" {
                   description "1536.76 nm/195.08125 THz 6.25GHz spacing";
                 }
                 enum "1536.71" {
                   description "1536.71 nm/195.08750 THz 6.25/12.5GHz spacing";
                 }
                 enum "1536.66" {
                   description "1536.66 nm/195.09375 THz 6.25GHz spacing";
                 }
                 enum "1536.61" {
                   description "1536.61 nm/195.10000 THz 6.25/12.5/50/100GHz spacing";
                 }
                 enum "1536.56" {
                   description "1536.56 nm/195.10625 THz 6.25GHz spacing";
                 }
                 enum "1536.51" {
                   description "1536.51 nm/195.11250 THz 6.25/12.5GHz spacing";
                 }
                 enum "1536.46" {
                   description "1536.46 nm/195.11875 THz 6.25GHz spacing";
                 }
                 enum "1536.41" {
                   description "1536.41 nm/195.12500 THz 6.25/12.5/75GHz spacing";
                 }
                 enum "1536.36" {
                   description "1536.36 nm/195.13125 THz 6.25GHz spacing";
                 }
                 enum "1536.31" {
                   description "1536.31 nm/195.13750 THz 6.25/12.5GHz spacing";
                 }
                 enum "1536.26" {
                   description "1536.26 nm/195.14375 THz 6.25GHz spacing";
                 }
                 enum "1536.22" {
                   description "1536.22 nm/195.15000 THz 6.25/12.5/50GHz spacing";
                 }
                 enum "1536.17" {
                   description "1536.17 nm/195.15625 THz 6.25GHz spacing";
                 }
                 enum "1536.12" {
                   description "1536.12 nm/195.16250 THz 6.25/12.5GHz spacing";
                 }
                 enum "1536.07" {
                   description "1536.07 nm/195.16875 THz 6.25GHz spacing";
                 }
                 enum "1536.02" {
                   description "1536.02 nm/195.17500 THz 6.25/12.5GHz spacing";
                 }
                 enum "1535.97" {
                   description "1535.97 nm/195.18125 THz 6.25GHz spacing";
                 }
                 enum "1535.92" {
                   description "1535.92 nm/195.18750 THz 6.25/12.5GHz spacing";
                 }
                 enum "1535.87" {
                   description "1535.87 nm/195.19375 THz 6.25GHz spacing";
                 }
                 enum "1535.82" {
                   description "1535.82 nm/195.20000 THz 6.25/12.5/50/75/100GHz spacing";
                 }
                 enum "1535.77" {
                   description "1535.77 nm/195.20625 THz 6.25GHz spacing";
                 }
                 enum "1535.72" {
                   description "1535.72 nm/195.21250 THz 6.25/12.5GHz spacing";
                 }
                 enum "1535.67" {
                   description "1535.67 nm/195.21875 THz 6.25GHz spacing";
                 }
                 enum "1535.63" {
                   description "1535.63 nm/195.22500 THz 6.25/12.5GHz spacing";
                 }
                 enum "1535.58" {
                   description "1535.58 nm/195.23125 THz 6.25GHz spacing";
                 }
                 enum "1535.53" {
                   description "1535.53 nm/195.23750 THz 6.25/12.5GHz spacing";
                 }
                 enum "1535.48" {
                   description "1535.48 nm/195.24375 THz 6.25GHz spacing";
                 }
                 enum "1535.43" {
                   description "1535.43 nm/195.25000 THz 6.25/12.5/50GHz spacing";
                 }
                 enum "1535.38" {
                   description "1535.38 nm/195.25625 THz 6.25GHz spacing";
                 }
                 enum "1535.33" {
                   description "1535.33 nm/195.26250 THz 6.25/12.5GHz spacing";
                 }
                 enum "1535.28" {
                   description "1535.28 nm/195.26875 THz 6.25GHz spacing";
                 }
                 enum "1535.23" {
                   description "1535.23 nm/195.27500 THz 6.25/12.5/75GHz spacing";
                 }
                 enum "1535.18" {
                   description "1535.18 nm/195.28125 THz 6.25GHz spacing";
                 }
                 enum "1535.13" {
                   description "1535.13 nm/195.28750 THz 6.25/12.5GHz spacing";
                 }
                 enum "1535.08" {
                   description "1535.08 nm/195.29375 THz 6.25GHz spacing";
                 }
                 enum "1535.04" {
                   description "1535.04 nm/195.30000 THz 6.25/12.5/50/100GHz spacing";
                 }
                 enum "1534.99" {
                   description "1534.99 nm/195.30625 THz 6.25GHz spacing";
                 }
                 enum "1534.94" {
                   description "1534.94 nm/195.31250 THz 6.25/12.5GHz spacing";
                 }
                 enum "1534.89" {
                   description "1534.89 nm/195.31875 THz 6.25GHz spacing";
                 }
                 enum "1534.84" {
                   description "1534.84 nm/195.32500 THz 6.25/12.5GHz spacing";
                 }
                 enum "1534.79" {
                   description "1534.79 nm/195.33125 THz 6.25GHz spacing";
                 }
                 enum "1534.74" {
                   description "1534.74 nm/195.33750 THz 6.25/12.5GHz spacing";
                 }
                 enum "1534.69" {
                   description "1534.69 nm/195.34375 THz 6.25GHz spacing";
                 }
                 enum "1534.64" {
                   description "1534.64 nm/195.35000 THz 6.25/12.5/50/75GHz spacing";
                 }
                 enum "1534.59" {
                   description "1534.59 nm/195.35625 THz 6.25GHz spacing";
                 }
                 enum "1534.54" {
                   description "1534.54 nm/195.36250 THz 6.25/12.5GHz spacing";
                 }
                 enum "1534.50" {
                   description "1534.50 nm/195.36875 THz 6.25GHz spacing";
                 }
                 enum "1534.45" {
                   description "1534.45 nm/195.37500 THz 6.25/12.5GHz spacing";
                 }
                 enum "1534.40" {
                   description "1534.40 nm/195.38125 THz 6.25GHz spacing";
                 }
                 enum "1534.35" {
                   description "1534.35 nm/195.38750 THz 6.25/12.5GHz spacing";
                 }
                 enum "1534.30" {
                   description "1534.30 nm/195.39375 THz 6.25GHz spacing";
                 }
                 enum "1534.25" {
                   description "1534.25 nm/195.40000 THz 6.25/12.5/50/100GHz spacing";
                 }
                 enum "1534.20" {
                   description "1534.20 nm/195.40625 THz 6.25GHz spacing";
                 }
                 enum "1534.15" {
                   description "1534.15 nm/195.41250 THz 6.25/12.5GHz spacing";
                 }
                 enum "1534.10" {
                   description "1534.10 nm/195.41875 THz 6.25GHz spacing";
                 }
                 enum "1534.05" {
                   description "1534.05 nm/195.42500 THz 6.25/12.5/75GHz spacing";
                 }
                 enum "1534.00" {
                   description "1534.00 nm/195.43125 THz 6.25GHz spacing";
                 }
                 enum "1533.96" {
                   description "1533.96 nm/195.43750 THz 6.25/12.5GHz spacing";
                 }
                 enum "1533.91" {
                   description "1533.91 nm/195.44375 THz 6.25GHz spacing";
                 }
                 enum "1533.86" {
                   description "1533.86 nm/195.45000 THz 6.25/12.5/50GHz spacing";
                 }
                 enum "1533.81" {
                   description "1533.81 nm/195.45625 THz 6.25GHz spacing";
                 }
                 enum "1533.76" {
                   description "1533.76 nm/195.46250 THz 6.25/12.5GHz spacing";
                 }
                 enum "1533.71" {
                   description "1533.71 nm/195.46875 THz 6.25GHz spacing";
                 }
                 enum "1533.66" {
                   description "1533.66 nm/195.47500 THz 6.25/12.5GHz spacing";
                 }
                 enum "1533.61" {
                   description "1533.61 nm/195.48125 THz 6.25GHz spacing";
                 }
                 enum "1533.56" {
                   description "1533.56 nm/195.48750 THz 6.25/12.5GHz spacing";
                 }
                 enum "1533.51" {
                   description "1533.51 nm/195.49375 THz 6.25GHz spacing";
                 }
                 enum "1533.47" {
                   description "1533.47 nm/195.50000 THz 6.25/12.5/50/75/100GHz spacing";
                 }
                 enum "1533.42" {
                   description "1533.42 nm/195.50625 THz 6.25GHz spacing";
                 }
                 enum "1533.37" {
                   description "1533.37 nm/195.51250 THz 6.25/12.5GHz spacing";
                 }
                 enum "1533.32" {
                   description "1533.32 nm/195.51875 THz 6.25GHz spacing";
                 }
                 enum "1533.27" {
                   description "1533.27 nm/195.52500 THz 6.25/12.5GHz spacing";
                 }
                 enum "1533.22" {
                   description "1533.22 nm/195.53125 THz 6.25GHz spacing";
                 }
                 enum "1533.17" {
                   description "1533.17 nm/195.53750 THz 6.25/12.5GHz spacing";
                 }
                 enum "1533.12" {
                   description "1533.12 nm/195.54375 THz 6.25GHz spacing";
                 }
                 enum "1533.07" {
                   description "1533.07 nm/195.55000 THz 6.25/12.5/50GHz spacing";
                 }
                 enum "1533.02" {
                   description "1533.02 nm/195.55625 THz 6.25GHz spacing";
                 }
                 enum "1532.98" {
                   description "1532.98 nm/195.56250 THz 6.25/12.5GHz spacing";
                 }
                 enum "1532.93" {
                   description "1532.93 nm/195.56875 THz 6.25GHz spacing";
                 }
                 enum "1532.88" {
                   description "1532.88 nm/195.57500 THz 6.25/12.5/75GHz spacing";
                 }
                 enum "1532.83" {
                   description "1532.83 nm/195.58125 THz 6.25GHz spacing";
                 }
                 enum "1532.78" {
                   description "1532.78 nm/195.58750 THz 6.25/12.5GHz spacing";
                 }
                 enum "1532.73" {
                   description "1532.73 nm/195.59375 THz 6.25GHz spacing";
                 }
                 enum "1532.68" {
                   description "1532.68 nm/195.60000 THz 6.25/12.5/50/100GHz spacing";
                 }
                 enum "1532.63" {
                   description "1532.63 nm/195.60625 THz 6.25GHz spacing";
                 }
                 enum "1532.58" {
                   description "1532.58 nm/195.61250 THz 6.25/12.5GHz spacing";
                 }
                 enum "1532.53" {
                   description "1532.53 nm/195.61875 THz 6.25GHz spacing";
                 }
                 enum "1532.49" {
                   description "1532.49 nm/195.62500 THz 6.25/12.5GHz spacing";
                 }
                 enum "1532.44" {
                   description "1532.44 nm/195.63125 THz 6.25GHz spacing";
                 }
                 enum "1532.39" {
                   description "1532.39 nm/195.63750 THz 6.25/12.5GHz spacing";
                 }
                 enum "1532.34" {
                   description "1532.34 nm/195.64375 THz 6.25GHz spacing";
                 }
                 enum "1532.29" {
                   description "1532.29 nm/195.65000 THz 6.25/12.5/50/75GHz spacing";
                 }
                 enum "1532.24" {
                   description "1532.24 nm/195.65625 THz 6.25GHz spacing";
                 }
                 enum "1532.19" {
                   description "1532.19 nm/195.66250 THz 6.25/12.5GHz spacing";
                 }
                 enum "1532.14" {
                   description "1532.14 nm/195.66875 THz 6.25GHz spacing";
                 }
                 enum "1532.09" {
                   description "1532.09 nm/195.67500 THz 6.25/12.5GHz spacing";
                 }
                 enum "1532.04" {
                   description "1532.04 nm/195.68125 THz 6.25GHz spacing";
                 }
                 enum "1532.00" {
                   description "1532.00 nm/195.68750 THz 6.25/12.5GHz spacing";
                 }
                 enum "1531.95" {
                   description "1531.95 nm/195.69375 THz 6.25GHz spacing";
                 }
                 enum "1531.90" {
                   description "1531.90 nm/195.70000 THz 6.25/12.5/50/100GHz spacing";
                 }
                 enum "1531.85" {
                   description "1531.85 nm/195.70625 THz 6.25GHz spacing";
                 }
                 enum "1531.80" {
                   description "1531.80 nm/195.71250 THz 6.25/12.5GHz spacing";
                 }
                 enum "1531.75" {
                   description "1531.75 nm/195.71875 THz 6.25GHz spacing";
                 }
                 enum "1531.70" {
                   description "1531.70 nm/195.72500 THz 6.25/12.5/75GHz spacing";
                 }
                 enum "1531.65" {
                   description "1531.65 nm/195.73125 THz 6.25GHz spacing";
                 }
                 enum "1531.60" {
                   description "1531.60 nm/195.73750 THz 6.25/12.5GHz spacing";
                 }
                 enum "1531.56" {
                   description "1531.56 nm/195.74375 THz 6.25GHz spacing";
                 }
                 enum "1531.51" {
                   description "1531.51 nm/195.75000 THz 6.25/12.5/50GHz spacing";
                 }
                 enum "1531.46" {
                   description "1531.46 nm/195.75625 THz 6.25GHz spacing";
                 }
                 enum "1531.41" {
                   description "1531.41 nm/195.76250 THz 6.25/12.5GHz spacing";
                 }
                 enum "1531.36" {
                   description "1531.36 nm/195.76875 THz 6.25GHz spacing";
                 }
                 enum "1531.31" {
                   description "1531.31 nm/195.77500 THz 6.25/12.5GHz spacing";
                 }
                 enum "1531.26" {
                   description "1531.26 nm/195.78125 THz 6.25GHz spacing";
                 }
                 enum "1531.21" {
                   description "1531.21 nm/195.78750 THz 6.25/12.5GHz spacing";
                 }
                 enum "1531.16" {
                   description "1531.16 nm/195.79375 THz 6.25GHz spacing";
                 }
                 enum "1531.12" {
                   description "1531.12 nm/195.80000 THz 6.25/12.5/50/75/100GHz spacing";
                 }
                 enum "1531.07" {
                   description "1531.07 nm/195.80625 THz 6.25GHz spacing";
                 }
                 enum "1531.02" {
                   description "1531.02 nm/195.81250 THz 6.25/12.5GHz spacing";
                 }
                 enum "1530.97" {
                   description "1530.97 nm/195.81875 THz 6.25GHz spacing";
                 }
                 enum "1530.92" {
                   description "1530.92 nm/195.82500 THz 6.25/12.5GHz spacing";
                 }
                 enum "1530.87" {
                   description "1530.87 nm/195.83125 THz 6.25GHz spacing";
                 }
                 enum "1530.82" {
                   description "1530.82 nm/195.83750 THz 6.25/12.5GHz spacing";
                 }
                 enum "1530.77" {
                   description "1530.77 nm/195.84375 THz 6.25GHz spacing";
                 }
                 enum "1530.72" {
                   description "1530.72 nm/195.85000 THz 6.25/12.5/50GHz spacing";
                 }
                 enum "1530.68" {
                   description "1530.68 nm/195.85625 THz 6.25GHz spacing";
                 }
                 enum "1530.63" {
                   description "1530.63 nm/195.86250 THz 6.25/12.5GHz spacing";
                 }
                 enum "1530.58" {
                   description "1530.58 nm/195.86875 THz 6.25GHz spacing";
                 }
                 enum "1530.53" {
                   description "1530.53 nm/195.87500 THz 6.25/12.5/75GHz spacing";
                 }
                 enum "1530.48" {
                   description "1530.48 nm/195.88125 THz 6.25GHz spacing";
                 }
                 enum "1530.43" {
                   description "1530.43 nm/195.88750 THz 6.25/12.5GHz spacing";
                 }
                 enum "1530.38" {
                   description "1530.38 nm/195.89375 THz 6.25GHz spacing";
                 }
                 enum "1530.33" {
                   description "1530.33 nm/195.90000 THz 6.25/12.5/50/100GHz spacing";
                 }
                 enum "1530.29" {
                   description "1530.29 nm/195.90625 THz 6.25GHz spacing";
                 }
                 enum "1530.24" {
                   description "1530.24 nm/195.91250 THz 6.25/12.5GHz spacing";
                 }
                 enum "1530.19" {
                   description "1530.19 nm/195.91875 THz 6.25GHz spacing";
                 }
                 enum "1530.14" {
                   description "1530.14 nm/195.92500 THz 6.25/12.5GHz spacing";
                 }
                 enum "1530.09" {
                   description "1530.09 nm/195.93125 THz 6.25GHz spacing";
                 }
                 enum "1530.04" {
                   description "1530.04 nm/195.93750 THz 6.25/12.5GHz spacing";
                 }
                 enum "1529.99" {
                   description "1529.99 nm/195.94375 THz 6.25GHz spacing";
                 }
                 enum "1529.94" {
                   description "1529.94 nm/195.95000 THz 6.25/12.5/50/75GHz spacing";
                 }
                 enum "1529.89" {
                   description "1529.89 nm/195.95625 THz 6.25GHz spacing";
                 }
                 enum "1529.85" {
                   description "1529.85 nm/195.96250 THz 6.25/12.5GHz spacing";
                 }
                 enum "1529.80" {
                   description "1529.80 nm/195.96875 THz 6.25GHz spacing";
                 }
                 enum "1529.75" {
                   description "1529.75 nm/195.97500 THz 6.25/12.5GHz spacing";
                 }
                 enum "1529.70" {
                   description "1529.70 nm/195.98125 THz 6.25GHz spacing";
                 }
                 enum "1529.65" {
                   description "1529.65 nm/195.98750 THz 6.25/12.5GHz spacing";
                 }
                 enum "1529.60" {
                   description "1529.60 nm/195.99375 THz 6.25GHz spacing";
                 }
                 enum "1529.55" {
                   description "1529.55 nm/196.00000 THz 6.25/12.5/50/100GHz spacing";
                 }
                 enum "1529.50" {
                   description "1529.50 nm/196.00625 THz 6.25GHz spacing";
                 }
                 enum "1529.46" {
                   description "1529.46 nm/196.01250 THz 6.25/12.5GHz spacing";
                 }
                 enum "1529.41" {
                   description "1529.41 nm/196.01875 THz 6.25GHz spacing";
                 }
                 enum "1529.36" {
                   description "1529.36 nm/196.02500 THz 6.25/12.5/75GHz spacing";
                 }
                 enum "1529.31" {
                   description "1529.31 nm/196.03125 THz 6.25GHz spacing";
                 }
                 enum "1529.26" {
                   description "1529.26 nm/196.03750 THz 6.25/12.5GHz spacing";
                 }
                 enum "1529.21" {
                   description "1529.21 nm/196.04375 THz 6.25GHz spacing";
                 }
                 enum "1529.16" {
                   description "1529.16 nm/196.05000 THz 6.25/12.5/50GHz spacing";
                 }
                 enum "1529.11" {
                   description "1529.11 nm/196.05625 THz 6.25GHz spacing";
                 }
                 enum "1529.07" {
                   description "1529.07 nm/196.06250 THz 6.25/12.5GHz spacing";
                 }
                 enum "1529.02" {
                   description "1529.02 nm/196.06875 THz 6.25GHz spacing";
                 }
                 enum "1528.97" {
                   description "1528.97 nm/196.07500 THz 6.25/12.5GHz spacing";
                 }
                 enum "1528.92" {
                   description "1528.92 nm/196.08125 THz 6.25GHz spacing";
                 }
                 enum "1528.87" {
                   description "1528.87 nm/196.08750 THz 6.25/12.5GHz spacing";
                 }
                 enum "1528.82" {
                   description "1528.82 nm/196.09375 THz 6.25GHz spacing";
                 }
                 enum "1528.77" {
                   description "1528.77 nm/196.10000 THz 6.25/12.5/50/75/100GHz spacing";
                 }
                 enum "1528.38" {
                   description "1528.38 nm/196.15040 THz 50Ghz spacing";
                 }
               }
             }
             leaf tx-power {
               description "Transmit laser output power";
               units "dBm";
               type string {
               }
             }
             container loopback {
               presence "enable loopback";
               description "Put the optics in loopback mode";
               uses apply-advanced;
               leaf loopbacktype {
                 description "Set loopback type";
                 type enumeration {
                   enum "media-side-out" {
                     description "Loop media side output back to input";
                   }
                   enum "media-side-in" {
                     description "Loop media side input back to output";
                   }
                   enum "host-side-out" {
                     description "Loop host side output back to input";
                   }
                   enum "host-side-in" {
                     description "Loop host side input back to output";
                   }
                 }
               }
             }
             leaf los-warning-threshold {
               description "LOS warning threshold";
               units "dBm";
               type string;
             }
             leaf los-alarm-threshold {
               description "LOS alarm threshold";
               units "dBm";
               type string;
             }
             leaf modulation-format {
               description "Type of Modulation Format";
               type enumeration {
                 enum "16qam" {
                   description "16-QAM Modulation Format";
                 }
                 enum "8qam" {
                   description "8-QAM MOdulation Format";
                 }
                 enum "qpsk" {
                   description "QPSK Modulation Format";
                 }
               }
             }
             choice laser-enable-choice {
               leaf laser-enable {
                 description "Enable Laser";
                 type empty;
               }
               leaf no-laser-enable {
                 description "Don't enable Laser";
                 type empty;
               }
             }
             choice is-ma-choice {
               leaf is-ma {
                 description "Link is enabled with alarms masked";
                 type empty;
               }
               leaf no-is-ma {
                 description "Don't link is enabled with alarms masked";
                 type empty;
               }
             }
             leaf encoding {
               description "Line encoding";
               type enumeration {
                 enum "differential" {
                   description "Differential phase line encoding";
                 }
                 enum "non-differential" {
                   description "Non-differential phase line encoding";
                 }
               }
             }
             leaf fec {
               description "Forward Error Correction mode";
               type enumeration {
                 enum "sdfec" {
                   description "Sky-Compatible Soft Decision Forward Error Correction";
                 }
                 enum "sdfec25" {
                   description "Denali-Compatible Soft Decision Forward Error Correction with 25 percent overhead";
                 }
                 enum "hgfec" {
                   description "High Gain Forward Error Correction";
                 }
                 enum "sdfec15" {
                   description "Soft Decision Forward Error Correction with 15 percent overhead";
                 }
               }
             }
             leaf high-polarization {
               description "High polarization tracking mode";
               type empty;
             }
             container application {
               description "Config Host and Media Code";
               uses apply-advanced;
               leaf hostid {
                 description "Enter Host Code";
                 type union {
                   type string {
                     pattern "<.*>|$.*";
                   }
                   type uint32 {
                     range "1 .. 300";
                   }
                 }
               }
               leaf mediaid {
                 description "Enter Media Code";
                 type union {
                   type string {
                     pattern "<.*>|$.*";
                   }
                   type uint32 {
                     range "1 .. 300";
                   }
                 }
               }
               leaf domainid {
                 description "Enter Domain ID";
                 type union {
                   type string {
                     pattern "<.*>|$.*";
                   }
                   type uint32 {
                     range "0 .. 300";
                   }
                 }
               }
             }
             container signal-degrade {
               description "Signal degrade thresholds";
               uses apply-advanced;
               leaf interval {
                 description "Time interval";
                 default "10";
                 units "milliseconds";
                 type union {
                   type string {
                     pattern "<.*>|$.*";
                   }
                   type uint32 {
                     range "1 .. 1000";
                   }
                 }
               }
               leaf ber-threshold-clear {
                 description "Ber threshold for signal degrade clear (format: xe-n, example: 4.5e-3)";
                 type string {
                 }
               }
               leaf ber-threshold-signal-degrade {
                 description "Ber threshold for signal-degrade (format: xe-n, example: 4.5e-3)";
                 type string {
                 }
               }
               leaf q-threshold-signal-degrade-clear {
                 description "Q threshold for signal-degrade clear (e.g. 14.26)";
                 units "dB";
                 type string;
               }
               leaf q-threshold-signal-degrade {
                 description "Q threshold for signal-degrade (e.g. 9.26)";
                 units "dB";
                 type string;
               }
             }
             list alarm {
               key name;
               ordered-by user;
               description "Set optic alarms";
               leaf name {
                 type enumeration {
                   enum "low-light-alarm" {
                     description "Enable low light alarm";
                   }
                 }
               }
               uses apply-advanced;
               choice actiontype {
                 case case_1 {
                   leaf syslog {
                     type empty;
                   }
                 }
                 case case_2 {
                   leaf link-down {
                     type empty;
                   }
                 }
               }
             }
             container tca {
               description "Set tca for optic alarms";
               uses apply-advanced;
               container tx-power-high-tca {
                 description "Tx power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute tx power high TCA in dBm";
                   type string {
                   }
                 }
                 leaf threshold-24hrs {
                   description "Threshold for 24 hour tx power high TCA in dBm";
                   type string {
                   }
                 }
               }
               container tx-power-low-tca {
                 description "Tx power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute tx power low TCA in dBm";
                   type string {
                   }
                 }
                 leaf threshold-24hrs {
                   description "Threshold for 24 hour tx power low TCA in dBm";
                   type string {
                   }
                 }
               }
               container rx-power-high-tca {
                 description "Rx power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute rx power high TCA in dBm";
                   type string {
                   }
                 }
                 leaf threshold-24hrs {
                   description "Threshold for 24 hour rx power high TCA in dBm";
                   type string {
                   }
                 }
               }
               container rx-power-low-tca {
                 description "Rx power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute rx power low TCA in dBm";
                   type string {
                   }
                 }
                 leaf threshold-24hrs {
                   description "Threshold for 24 hour rx power low TCA in dBm";
                   type string {
                   }
                 }
               }
               container rx-signal-power-high-tca {
                 description "Rx signal power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute rx signal power high TCA in dBm";
                   type string {
                   }
                 }
                 leaf threshold-24hrs {
                   description "Threshold for 24 hour rx signal power high TCA in dBm";
                   type string {
                   }
                 }
               }
               container rx-signal-power-low-tca {
                 description "Rx signal power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute rx signal power low TCA in dBm";
                   type string {
                   }
                 }
                 leaf threshold-24hrs {
                   description "Threshold for 24 hour rx signal power low TCA in dBm";
                   type string {
                   }
                 }
               }
               container temperature-high-tca {
                 description "Temperature high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute high temperature TCA in celsius";
                   type string {
                   }
                 }
                 leaf threshold-24hrs {
                   description "Threshold for 24 hour high temperature TCA in celsius";
                   type string {
                   }
                 }
               }
               container temperature-low-tca {
                 description "Temperature low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute low temperature TCA in celsius";
                   type string {
                   }
                 }
                 leaf threshold-24hrs {
                   description "Threshold for 24 hour low temperature TCA in celsius";
                   type string {
                   }
                 }
               }
               container carrier-frequency-offset-high-tca {
                 description "Carrier frequency offset high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute frequency offset high TCA in MHz";
                   type string {
                   }
                 }
                 leaf threshold-24hrs {
                   description "Threshold for 24 hour frequency offset high TCA in MHz";
                   type string {
                   }
                 }
               }
               container carrier-frequency-offset-low-tca {
                 description "Carrier frequency offset low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute frequency offset low TCA in MHz";
                   type string {
                   }
                 }
                 leaf threshold-24hrs {
                   description "Threshold for 24 hour frequency offset low TCA in MHz";
                   type string {
                   }
                 }
               }
               container fec-ber {
                 description "Optics Errored Seconds Threshold crossing defect trigger";
                 choice enable-tca-choice {
                   leaf enable-tca {
                     description "Enable the Optics errored seconds threshold crossing alert";
                     type empty;
                   }
                   leaf no-enable-tca {
                     description "Don't enable the Optics errored seconds threshold crossing alert";
                     type empty;
                   }
                 }
                 leaf threshold {
                   description "TCA threshold for BER value in format: xe-n, x is an integer or decimal number, n = 0..9";
                   default "10e-3";
                   type string {
                   }
                 }
                 leaf threshold-24hrs {
                   description "TCA threshold for BER value in format: xe-n, x is an integer or decimal number, n = 0..9";
                   default "10e-3";
                   type string {
                   }
                 }
               }
               container tec-current-high-tca {
                 description "TEC Current high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute TEC Current high TCA in mA";
                   type string {
                   }
                 }
                 leaf threshold-24hrs {
                   description "Threshold for 24 hour TEC Current high TCA in mA";
                   type string {
                   }
                 }
               }
               container tec-current-low-tca {
                 description "TEC Current low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute TEC Current low TCA in mA";
                   type string {
                   }
                 }
                 leaf threshold-24hrs {
                   description "Threshold for 24 hour TEC Current low TCA in mA";
                   type string {
                   }
                 }
               }
               container residual-isi-high-tca {
                 description "Residual ISI high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute Residual ISI high TCA in ps/nm";
                   type string {
                   }
                 }
                 leaf threshold-24hrs {
                   description "Threshold for 24 hour Residual ISI high TCA in ps/nm";
                   type string {
                   }
                 }
               }
               container residual-isi-low-tca {
                 description "Residual ISI low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute Residual ISI low TCA in ps/nm";
                   type string {
                   }
                 }
                 leaf threshold-24hrs {
                   description "Threshold for 24 hour Residual ISI low TCA in ps/nm";
                   type string {
                   }
                 }
               }
               container pam-histogram-high-tca {
                 description "PAM Histogram high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute PAM Histogram high TCA";
                   type string {
                   }
                 }
                 leaf threshold-24hrs {
                   description "Threshold for 24 hour PAM Histogram high TCA";
                   type string {
                   }
                 }
               }
               container snr-low-tca {
                 description "SNR low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute SNR low TCA in dBm ";
                   type string {
                   }
                 }
                 leaf threshold-24hrs {
                   description "Threshold for 24 hour SNR low TCA in dBm";
                   type string {
                   }
                 }
               }
               container fec-corrected-errors-high-tca {
                 description "FEC Corrected Error High Threshold crossing defect trigger";
                 uses apply-advanced;
                 choice enable-tca-choice {
                   leaf enable-tca {
                     description "Enable the FEC Corrected Errors threshold crossing alert";
                     type empty;
                   }
                   leaf no-enable-tca {
                     description "Don't enable the FEC Corrected Errors threshold crossing alert";
                     type empty;
                   }
                 }
                 leaf threshold {
                   description "FEC Corrected-Errs value in format: xe-n, x is an integer or decimal number, n = 0..9";
                   default "10e-3";
                   type string {
                   }
                 }
                 leaf threshold-24hrs {
                   description "FEC Corrected-Errs value in format: xe-n, x is an integer or decimal number, n = 0..9";
                   default "10e-3";
                   type string {
                   }
                 }
               }
               container fec-ucorrected-words-high-tca {
                 description "FEC UCorrected Words High Threshold crossing defect trigger";
                 uses apply-advanced;
                 choice enable-tca-choice {
                   leaf enable-tca {
                     description "Enable the FEC UCorrected Words threshold crossing alert";
                     type empty;
                   }
                   leaf no-enable-tca {
                     description "Don't enable the FEC UCorrected Words threshold crossing alert";
                     type empty;
                   }
                 }
                 leaf threshold {
                   description "FEC UCorrected-Words value in format: xe-n, x is an integer or decimal number, n = 0..9";
                   default "10e-3";
                   type string {
                   }
                 }
                 leaf threshold-24hrs {
                   description "FEC UCorrected-Words value in format: xe-n, x is an integer or decimal number, n = 0..9";
                   default "10e-3";
                   type string {
                   }
                 }
               }
               container laser-frequency-error-high-tca {
                 description "Laser frequency error high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute frequency error high TCA in MHz";
                   type string {
                   }
                 }
                 leaf threshold-24hrs {
                   description "Threshold for 24 hour frequency error high TCA in MHz";
                   type string {
                   }
                 }
               }
               container laser-frequency-error-low-tca {
                 description "Laser frequency error low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute frequency error low TCA in MHz";
                   type string {
                   }
                 }
                 leaf threshold-24hrs {
                   description "Threshold for 24 hour frequency error low TCA in MHz";
                   type string {
                   }
                 }
               }
             }
             list warning {
               key name;
               ordered-by user;
               description "Set optic warnings";
               leaf name {
                 type enumeration {
                   enum "low-light-warning" {
                     description "Enable low light warning";
                   }
                 }
               }
               uses apply-advanced;
               choice actiontype {
                 case case_1 {
                   leaf syslog {
                     description "Set action as syslog";
                     type empty;
                   }
                 }
                 case case_2 {
                   leaf link-down {
                     description "Set action as link-down";
                     type empty;
                   }
                 }
               }
             }
             leaf low-power-mode {
               description "Force optics to low power mode";
               type empty;
             }
             leaf high-power-mode {
               description "High power optic mode";
               type empty;
             }
             leaf host-side-fec {
               description "Host side optics FEC ON/OFF";
               type enumeration {
                 enum "off" {
                   description "Host side FEC OFF for optics";
                 }
                 enum "on" {
                   description "Host side FEC ON for optics";
                 }
               }
             }
             leaf media-side-fec {
               description "Media side FEC ON/OFF";
               type enumeration {
                 enum "off" {
                   description "Media side FEC OFF for optics";
                 }
                 enum "on" {
                   description "Media side FEC ON for optics";
                 }
               }
             }
             choice lane-info {
               case case_1 {
                 list lane {
                   key name;
                   description "Media lane number";
                   leaf name {
                     description "Lane number";
                     type union {
                       type string {
                         pattern "<.*>|$.*";
                       }
                       type uint32 {
                         range "0 .. 7";
                       }
                     }
                   }
                   uses apply-advanced;
                   leaf tx-laser {
                     description "Transmit Laser ON/OFF";
                     type enumeration {
                       enum "off" {
                         description "Transmit laser OFF for optics";
                       }
                       enum "on" {
                         description "Transmit laser ON for optics";
                       }
                     }
                   }
                   leaf rx-output {
                     description "Receive output ON/OFF";
                     type enumeration {
                       enum "off" {
                         description "Receive output OFF for optics";
                       }
                       enum "on" {
                         description "Receive output ON for optics";
                       }
                     }
                   }
                   leaf tx-cdr {
                     description "Transmit Clock and Data Recovery ON/OFF";
                     type enumeration {
                       enum "off" {
                         description "Transmit Clock and Data Recovery OFF for optics";
                       }
                       enum "on" {
                         description "Transmit Clock and Data Recovery ON for optics";
                       }
                     }
                   }
                   leaf rx-cdr {
                     description "Receive Clock and Data Recovery ON/OFF";
                     type enumeration {
                       enum "off" {
                         description "Receive Clock and Data Recovery OFF for optics";
                       }
                       enum "on" {
                         description "Receive Clock and Data Recovery ON for optics";
                       }
                     }
                   }
                   leaf tx-input-equalization-adaptive {
                     description "Transmit adaptive equalization ON/OFF";
                     type enumeration {
                       enum "off" {
                         description "Transmit adaptive equalization OFF for optics";
                       }
                       enum "on" {
                         description "Transmit adaptive equalization ON for optics";
                       }
                     }
                   }
                   leaf tx-input-equalization-manual {
                     description "Transmit manual equalization for optics";
                     units "dB";
                     type union {
                       type string {
                         pattern "<.*>|$.*";
                       }
                       type int32 {
                         range "0 .. 15";
                       }
                     }
                   }
                   leaf rx-output-emphasis {
                     description "Receive output emphasis for optics";
                     units "dB";
                     type union {
                       type string {
                         pattern "<.*>|$.*";
                       }
                       type int32 {
                         range "0 .. 15";
                       }
                     }
                   }
                   leaf rx-output-amplitude {
                     description "Receive output amplitude setting";
                     type enumeration {
                       enum "400mV" {
                         description "No equalization for 100mV - 400mV amplitude";
                       }
                       enum "600mV" {
                         description "No equalization for 300mV - 600mV amplitude";
                       }
                       enum "800mV" {
                         description "No equalization for 400mV - 800mV amplitude";
                       }
                       enum "1200mV" {
                         description "No equalization for 600mV - 1200mV amplitude";
                       }
                     }
                   }
                   leaf tx-squelch {
                     description "Transmit squelch ON/OFF";
                     type enumeration {
                       enum "off" {
                         description "Transmit squelch OFF for optics";
                       }
                       enum "on" {
                         description "Transmit squelch ON for optics";
                       }
                     }
                   }
                   leaf rx-squelch {
                     description "Receive squelch ON/OFF";
                     type enumeration {
                       enum "off" {
                         description "Receive squelch OFF for optics";
                       }
                       enum "on" {
                         description "Receive squelch ON for optics";
                       }
                     }
                   }
                   leaf tx-rate-select {
                     description "Transmit rate select for optics";
                     type union {
                       type string {
                         pattern "<.*>|$.*";
                       }
                       type int32 {
                         range "0 .. 3";
                       }
                     }
                   }
                   leaf rx-rate-select {
                     description "Receive rate select for optics";
                     type union {
                       type string {
                         pattern "<.*>|$.*";
                       }
                       type int32 {
                         range "0 .. 3";
                       }
                     }
                   }
                 }
               }
               case case_2 {
                 container lane-all {
                   presence "enable lane-all";
                   description "Apply settings to all lane";
                   uses apply-advanced;
                   leaf tx-laser {
                     description "Transmit Laser ON/OFF";
                     type enumeration {
                       enum "off" {
                         description "Transmit laser OFF for optics";
                       }
                       enum "on" {
                         description "Transmit laser ON for optics";
                       }
                     }
                   }
                   leaf rx-output {
                     description "Receive output ON/OFF";
                     type enumeration {
                       enum "off" {
                         description "Receive output OFF for optics";
                       }
                       enum "on" {
                         description "Receive output ON for optics";
                       }
                     }
                   }
                   leaf tx-cdr {
                     description "Transmit Clock and Data Recovery ON/OFF";
                     type enumeration {
                       enum "off" {
                         description "Transmit Clock and Data Recovery OFF for optics";
                       }
                       enum "on" {
                         description "Transmit Clock and Data Recovery ON for optics";
                       }
                     }
                   }
                   leaf rx-cdr {
                     description "Receive Clock and Data Recovery ON/OFF";
                     type enumeration {
                       enum "off" {
                         description "Receive Clock and Data Recovery OFF for optics";
                       }
                       enum "on" {
                         description "Receive Clock and Data Recovery ON for optics";
                       }
                     }
                   }
                   leaf tx-input-equalization-adaptive {
                     description "Transmit adaptive equalization ON/OFF";
                     type enumeration {
                       enum "off" {
                         description "Transmit adaptive equalization OFF for optics";
                       }
                       enum "on" {
                         description "Transmit adaptive equalization ON for optics";
                       }
                     }
                   }
                   leaf tx-input-equalization-manual {
                     description "Transmit manual equalization for optics";
                     units "dB";
                     type union {
                       type string {
                         pattern "<.*>|$.*";
                       }
                       type int32 {
                         range "0 .. 15";
                       }
                     }
                   }
                   leaf rx-output-emphasis {
                     description "Receive output emphasis for optics";
                     units "dB";
                     type union {
                       type string {
                         pattern "<.*>|$.*";
                       }
                       type int32 {
                         range "0 .. 15";
                       }
                     }
                   }
                   leaf rx-output-amplitude {
                     description "Receive output amplitude setting";
                     type enumeration {
                       enum "400mV" {
                         description "No equalization for 100mV - 400mV amplitude";
                       }
                       enum "600mV" {
                         description "No equalization for 300mV - 600mV amplitude";
                       }
                       enum "800mV" {
                         description "No equalization for 400mV - 800mV amplitude";
                       }
                       enum "1200mV" {
                         description "No equalization for 600mV - 1200mV amplitude";
                       }
                     }
                   }
                   leaf tx-squelch {
                     description "Transmit squelch ON/OFF";
                     type enumeration {
                       enum "off" {
                         description "Transmit squelch OFF for optics";
                       }
                       enum "on" {
                         description "Transmit squelch ON for optics";
                       }
                     }
                   }
                   leaf rx-squelch {
                     description "Receive squelch ON/OFF";
                     type enumeration {
                       enum "off" {
                         description "Receive squelch OFF for optics";
                       }
                       enum "on" {
                         description "Receive squelch ON for optics";
                       }
                     }
                   }
                   leaf tx-rate-select {
                     description "Transmit rate select for optics";
                     type union {
                       type string {
                         pattern "<.*>|$.*";
                       }
                       type int32 {
                         range "0 .. 3";
                       }
                     }
                   }
                   leaf rx-rate-select {
                     description "Receive rate select for optics";
                     type union {
                       type string {
                         pattern "<.*>|$.*";
                       }
                       type int32 {
                         range "0 .. 3";
                       }
                     }
                   }
                 }
               }
             }
           }
           container otn-options {
             description "Optical Transmission Network interface-specific options";
             uses otn_options_type;
           }
           container tdm-options {
             description "Time division multiplexing (TDM) interface-specific options";
             uses tdm_options_type;
           }
           container och-options {
             description "Optical channel configuration options";
             uses och-attributes;
           }
           container otu-options {
             description "Optical transmission unit configuration options";
             uses otu-attributes;
           }
           container odu-options {
             description "Optical data unit configuration options";
             uses odu-attributes;
           }
           container ett-options {
             description "Transport ethernet client configuration options";
             uses ett-attributes;
           }
           container fastether-options {
             description "Fast Ethernet interface-specific options";
             uses apply-advanced;
             choice loopback-choice {
               leaf loopback {
                 description "Enable loopback";
                 type empty;
               }
               leaf no-loopback {
                 description "Don't enable loopback";
                 type empty;
               }
             }
             choice flow-control-choice {
               leaf flow-control {
                 description "Enable flow control";
                 type empty;
               }
               leaf no-flow-control {
                 description "Don't enable flow control";
                 type empty;
               }
             }
             choice source-filtering-choice {
               leaf source-filtering {
                 description "Enable source address filtering";
                 type empty;
               }
               leaf no-source-filtering {
                 description "Don't enable source address filtering";
                 type empty;
               }
             }
             choice auto-negotiation-choice {
               leaf auto-negotiation {
                 description "Enable auto-negotiation";
                 type empty;
               }
               leaf no-auto-negotiation {
                 description "Don't enable auto-negotiation";
                 type empty;
               }
             }
             leaf ingress-rate-limit {
               description "Ingress rate at port";
               units "megabits per second";
               type union {
                 type string {
                   pattern "<.*>|$.*";
                 }
                 type uint32 {
                   range "1 .. 100";
                 }
               }
             }
             list source-address-filter {
               key name;
               ordered-by user;
               description "Source address filters";
               leaf name {
                 description "Remote MAC address";
                 type jt:mac-addr;
               }
             }
             container redundant-parent {
               description " Parent of this interface";
               uses apply-advanced;
               leaf parent {
                 description "Join a redundant ethernet interface";
                 type union {
                   type jt:interface-device;
                   type string {
                     pattern "<.*>|$.*";
                   }
                 }
               }
             }
             container ieee-802.3ad {
               description "IEEE 802.3ad";
               uses apply-advanced;
               container lacp {
                 description "Link Aggregation Control Protocol configuration";
                 uses apply-advanced;
                 leaf port-priority {
                   description "Priority of the port (0 ... 65535)";
                   type union {
                     type uint16;
                     type string {
                       pattern "<.*>|$.*";
                     }
                   }
                 }
               }
               leaf bundle {
                 description "Join an aggregated Ethernet interface";
                 type union {
                   type jt:interface-device;
                   type string {
                     pattern "<.*>|$.*";
                   }
                 }
               }
               choice type {
                 case case_1 {
                   leaf primary {
                     description "Primary interface for link-protection mode";
                     type empty;
                   }
                 }
                 case case_2 {
                   leaf backup {
                     description "Backup interface for link-protection mode";
                     type empty;
                   }
                 }
               }
             }
             container mpls {
               description "MPLS options";
               uses mpls_ifd_options;
             }
             leaf ignore-l3-incompletes {
               description "Ignore L3 incomplete errors";
               type empty;
             }
           }
           container redundant-ether-options {
             description "Ethernet redundancy options";
             uses apply-advanced;
             leaf redundancy-group {
               description "Redundancy group of this interface";
               type union {
                 type string {
                   pattern "<.*>|$.*";
                 }
                 type uint16 {
                   range "1 .. 128";
                 }
               }
             }
             choice loopback-choice {
               leaf loopback {
                 description "Enable loopback";
                 type empty;
               }
               leaf no-loopback {
                 description "Don't enable loopback";
                 type empty;
               }
             }
             choice flow-control-choice {
               leaf flow-control {
                 description "Enable flow control";
                 type empty;
               }
               leaf no-flow-control {
                 description "Don't enable flow control";
                 type empty;
               }
             }
             choice source-filtering-choice {
               leaf source-filtering {
                 description "Enable source address filtering";
                 type empty;
               }
               leaf no-source-filtering {
                 description "Don't enable source address filtering";
                 type empty;
               }
             }
             list source-address-filter {
               key name;
               ordered-by user;
               description "Source address filters";
               leaf name {
                 description "Remote MAC address";
                 type jt:mac-addr;
               }
             }
             leaf mru {
               description "Maximum receive packet size";
               type union {
                 type string {
                   pattern "<.*>|$.*";
                 }
                 type uint32;
               }
             }
             leaf link-speed {
               description "Link speed of individual interface that joins the RETH";
               type enumeration {
                 enum "10m" {
                   description "Links are 10M";
                 }
                 enum "100m" {
                   description "Links are 100M";
                 }
                 enum "1g" {
                   description "Links are 1G";
                 }
                 enum "10g" {
                   description "Links are 10G";
                 }
                 enum "25g" {
                   description "Links are 25G";
                 }
               }
             }
             leaf minimum-links {
               description "Minimum number of active links";
               default "1";
               type union {
                 type string {
                   pattern "<.*>|$.*";
                 }
                 type uint16 {
                   range "1 .. 8";
                 }
               }
             }
             container lacp {
               description "Link Aggregation Control Protocol configuration";
               uses apply-advanced;
               choice mode {
                 case case_1 {
                   leaf active {
                     description "Initiate transmission of LACP packets";
                     type empty;
                   }
                 }
                 case case_2 {
                   leaf passive {
                     description "Respond to LACP packets";
                     type empty;
                   }
                 }
               }
               leaf periodic {
                 description "Timer interval for periodic transmission of LACP packets";
                 type enumeration {
                   enum "fast" {
                     description "Receive packets every second";
                   }
                   enum "slow" {
                     description "Receive packets every 30 seconds";
                   }
                 }
               }
             }
           }
           container aggregated-ether-options {
             description "Aggregated Ethernet interface-specific options";
             uses apply-advanced;
             choice loopback-choice {
               leaf loopback {
                 description "Enable loopback";
                 type empty;
               }
               leaf no-loopback {
                 description "Don't enable loopback";
                 type empty;
               }
             }
             choice flow-control-choice {
               leaf flow-control {
                 description "Enable flow control";
                 type empty;
               }
               leaf no-flow-control {
                 description "Don't enable flow control";
                 type empty;
               }
             }
             choice source-filtering-choice {
               leaf source-filtering {
                 description "Enable source address filtering";
                 type empty;
               }
               leaf no-source-filtering {
                 description "Don't enable source address filtering";
                 type empty;
               }
             }
             leaf autostate-exclude {
               description "Interface will not contribute to IRB state";
               type empty;
             }
             container link-protection {
               presence "enable link-protection";
               description "Enable link protection mode";
               uses apply-advanced;
               leaf revertive {
                 description "Revert back from active backup link to primary, if primary is UP";
                 type empty;
               }
               leaf non-revertive {
                 description "Do not revert back (default mode) from active backup link to primary, if primary is UP";
                 type empty;
               }
               leaf backup-state {
                 description "Link protection backup link state";
                 default "accept-data";
                 type enumeration {
                   enum "accept-data" {
                     description "Accept data on receive channel of backup link";
                   }
                   enum "discard-data" {
                     description "Discard data on receive channel of backup link";
                   }
                   enum "down" {
                     description "Backup link is marked down";
                   }
                 }
               }
               container rtg-config {
                 presence "enable rtg-config";
                 description "RTG enable on AE";
                 uses apply-advanced;
                 leaf preempt-cutover-timer {
                   description "RTG preempt-cutover-timer in seconds";
                   default "1";
                   type union {
                     type string {
                       pattern "<.*>|$.*";
                     }
                     type uint32 {
                       range "0 .. 255";
                     }
                   }
                 }
               }
             }
             choice fcoe-lag-choice {
               leaf fcoe-lag {
                 description "Enable FIP/FCoE LAG";
                 type empty;
               }
               leaf no-fcoe-lag {
                 description "Don't enable FIP/FCoE LAG";
                 type empty;
               }
             }
             list source-address-filter {
               key name;
               ordered-by user;
               description "Source address filters";
               leaf name {
                 description "Remote MAC address";
                 type jt:mac-addr;
               }
             }
             container configured-flow-control {
               presence "enable configured-flow-control";
               description "Enable flow control";
               uses apply-advanced;
               leaf rx-buffers {
                 description "Enable/Disable Rx buffers";
                 type enumeration {
                   enum "on" {
                     description "Enable Rx buffers";
                   }
                   enum "off" {
                     description "Disable Rx buffers";
                   }
                 }
               }
               leaf tx-buffers {
                 description "Enable/Disable Tx buffers";
                 type enumeration {
                   enum "on" {
                     description "Enable Tx buffers";
                   }
                   enum "off" {
                     description "Disable Tx buffers";
                   }
                 }
               }
             }
             container load-balance {
               uses aggregate-load-balance;
             }
             container bfd-liveness-detection {
               description "Bidirectional Forwarding Detection (BFD) options";
               uses apply-advanced;
               leaf version {
                 description "BFD protocol version number";
                 default "automatic";
                 type enumeration {
                   enum "0" {
                     description "BFD version 0 (deprecated)";
                   }
                   enum "1" {
                     description "BFD version 1";
                   }
                   enum "automatic" {
                     description "Choose BFD version automatically";
                   }
                 }
               }
               leaf minimum-interval {
                 description "Minimum transmit and receive interval";
                 units "milliseconds";
                 type union {
                   type string {
                     pattern "<.*>|$.*";
                   }
                   type uint32 {
                     range "1 .. 255000";
                   }
                 }
               }
               leaf minimum-transmit-interval {
                 description "Minimum transmit interval";
                 status deprecated;
                 units "milliseconds";
                 type union {
                   type string {
                     pattern "<.*>|$.*";
                   }
                   type uint32 {
                     range "1 .. 255000";
                   }
                 }
               }
               leaf minimum-receive-interval {
                 description "Minimum receive interval";
                 units "milliseconds";
                 type union {
                   type string {
                     pattern "<.*>|$.*";
                   }
                   type uint32 {
                     range "1 .. 255000";
                   }
                 }
               }
               leaf multiplier {
                 description "Detection time multiplier";
                 default "3";
                 type union {
                   type string {
                     pattern "<.*>|$.*";
                   }
                   type uint32 {
                     range "1 .. 255";
                   }
                 }
               }
               leaf inline-disable {
                 description "Disable inline mode for this BFD session";
                 type empty;
               }
               leaf pdu-size {
                 description "BFD transport protocol payload size";
                 default "24";
                 type union {
                   type string {
                     pattern "<.*>|$.*";
                   }
                   type uint32 {
                     range "24 .. 9000";
                   }
                 }
               }
               choice adaptation-choice {
                 case case_1 {
                   leaf no-adaptation {
                     description "Disable adaptation";
                     type empty;
                   }
                 }
               }
               container transmit-interval {
                 description "Transmit-interval options";
                 uses apply-advanced;
                 leaf minimum-interval {
                   description "Minimum transmit interval";
                   units "milliseconds";
                   type union {
                     type string {
                       pattern "<.*>|$.*";
                     }
                     type uint32 {
                       range "1 .. 255000";
                     }
                   }
                 }
                 leaf threshold {
                   description "High transmit interval triggering a trap";
                   units "milliseconds";
                   type union {
                     type uint32;
                     type string {
                       pattern "<.*>|$.*";
                     }
                   }
                 }
               }
               container detection-time {
                 description "Detection-time options";
                 uses apply-advanced;
                 leaf threshold {
                   description "High detection-time triggering a trap";
                   units "milliseconds";
                   type union {
                     type uint32;
                     type string {
                       pattern "<.*>|$.*";
                     }
                   }
                 }
               }
               container authentication {
                 description "Authentication options";
                 uses apply-advanced;
                 leaf key-chain {
                   description "Key chain name";
                   type string;
                 }
                 leaf algorithm {
                   description "Algorithm name";
                   type enumeration {
                     enum "simple-password" {
                       description "Simple password";
                     }
                     enum "keyed-md5" {
                       description "Keyed message Digest 5";
                     }
                     enum "meticulous-keyed-md5" {
                       description "Meticulous keyed message Digest 5";
                     }
                     enum "keyed-sha-1" {
                       description "Keyed secure hash algorithm (SHA1) ";
                     }
                     enum "meticulous-keyed-sha-1" {
                       description "Meticulous keyed secure hash algorithm (SHA1) ";
                     }
                   }
                 }
                 leaf loose-check {
                   description "Verify authentication only if authentication is negotiated";
                   type empty;
                 }
               }
               container damping {
                 description "BFD flap damping parameters";
                 uses apply-advanced;
                 leaf suppress {
                   description "Suppress threshold for figure-of-merit value";
                   default "5000";
                   type union {
                     type string {
                       pattern "<.*>|$.*";
                     }
                     type uint32 {
                       range "1000 .. 200000";
                     }
                   }
                 }
                 leaf reuse {
                   description "Reuse threshold for figure-of-merit value";
                   default "1000";
                   type union {
                     type string {
                       pattern "<.*>|$.*";
                     }
                     type uint32 {
                       range "1000 .. 200000";
                     }
                   }
                 }
                 leaf max-suppress-time {
                   description "Maximum hold-down time";
                   default "600";
                   units "seconds";
                   type union {
                     type string {
                       pattern "<.*>|$.*";
                     }
                     type uint32 {
                       range "1 .. 20000";
                     }
                   }
                 }
                 leaf half-life-interval {
                   description "Decay half life interval";
                   default "30";
                   units "seconds";
                   type union {
                     type string {
                       pattern "<.*>|$.*";
                     }
                     type uint32 {
                       range "1 .. 600";
                     }
                   }
                 }
                 leaf increment {
                   description "Increments applied to figure-of-merit value for every flap";
                   default "1000";
                   type union {
                     type string {
                       pattern "<.*>|$.*";
                     }
                     type uint32 {
                       range "1000 .. 20000";
                     }
                   }
                 }
               }
               leaf neighbor {
                 description "BFD neighbor address";
                 type jt:ipaddr;
               }
               leaf local-address {
                 description "BFD local address";
                 type jt:ipaddr;
               }
               leaf holddown-interval {
                 description "Time to hold the session-UP notification to the client";
                 units "milliseconds";
                 type union {
                   type string {
                     pattern "<.*>|$.*";
                   }
                   type uint32 {
                     range "0 .. 255000";
                   }
                 }
               }
             }
             leaf minimum-links {
               description "Minimum number of aggregated links";
               type union {
                 type string {
                   pattern "<.*>|$.*";
                 }
                 type uint16;
               }
             }
             container minimum-bandwidth {
               presence "enable minimum-bandwidth";
               description "Minimum bandwidth configured for aggregated bundle";
               uses apply-advanced;
               leaf bw-value {
                 description "Bandwidth value";
                 default "1";
                 type union {
                   type uint64;
                   type string {
                     pattern "<.*>|$.*";
                   }
                 }
               }
               leaf bw-unit {
                 description "Bandwidth unit";
                 type enumeration {
                   enum "bps" {
                     description "Links are in bits per sec";
                   }
                   enum "kbps" {
                     description "Links are in kilo bits per sec";
                   }
                   enum "mbps" {
                     description "Links are in mega bits per sec";
                   }
                   enum "gbps" {
                     description "Links are in giga bits per sec ";
                   }
                 }
               }
             }
             container targeted-options {
               presence "enable targeted-options";
               description "Targeting specific options";
               uses apply-advanced;
               leaf type {
                 description "Targeting type of AE bundle";
                 type enumeration {
                   enum "auto" {
                     description "Targeting type is Auto";
                   }
                   enum "manual" {
                     description "Targeting type is Manual";
                   }
                 }
               }
               choice redundancy_choice {
                 case case_1 {
                   leaf logical-interface-fpc-redundancy {
                     description "Enable FPC redundancy for logical interfaces";
                     type empty;
                   }
                 }
                 case case_2 {
                   leaf logical-interface-chassis-redundancy {
                     description "Enable CHASSIS redundancy for logical interfaces";
                     type empty;
                   }
                 }
               }
               container rebalance-periodic {
                 presence "enable rebalance-periodic";
                 uses apply-advanced;
                 leaf start-time {
                   description "Start time of the rebalance operation ( Wall clock time )";
                   type jt:time-of-day;
                 }
                 leaf interval {
                   description "Interval of the rebalance operation in hrs";
                   type union {
                     type string {
                       pattern "<.*>|$.*";
                     }
                     type uint32 {
                       range "1 .. 24";
                     }
                   }
                 }
               }
               leaf rebalance-subscriber-granularity {
                 description "Max subscriber aggregate weight";
                 type union {
                   type string {
                     pattern "<.*>|$.*";
                   }
                   type uint32 {
                     range "1 .. 65535";
                   }
                 }
               }
             }
             choice redundancy_choice {
               case case_1 {
                 leaf logical-interface-fpc-redundancy {
                   description "Enable FPC redundancy for logical interfaces";
                   type empty;
                 }
               }
               case case_2 {
                 leaf logical-interface-chassis-redundancy {
                   description "Enable CHASSIS redundancy for logical interfaces";
                   type empty;
                 }
               }
             }
             container rebalance-periodic {
               uses apply-advanced;
               leaf start-time {
                 description "Start time of the rebalance operation ( Wall clock time )";
                 type jt:time-of-day;
               }
               leaf interval {
                 description "Interval of the rebalance operation in hrs";
                 type union {
                   type string {
                     pattern "<.*>|$.*";
                   }
                   type uint32 {
                     range "1 .. 24";
                   }
                 }
               }
             }
             leaf pad-to-minimum-frame-size {
               description "Pad Tx vlan tagged frame to minimum of 68 bytes";
               type empty;
             }
             leaf link-speed {
               description "Link speed of individual interface that joins the AE";
               type enumeration {
                 enum "10m" {
                   description "Links are 10M";
                 }
                 enum "100m" {
                   description "Links are 100M";
                 }
                 enum "1g" {
                   description "Links are 1G";
                 }
                 enum "2.5g" {
                   description "Links are 2.5G";
                 }
                 enum "5g" {
                   description "Links are 5G";
                 }
                 enum "8g" {
                   description "Links are 8G";
                 }
                 enum "10g" {
                   description "Links are 10G";
                 }
                 enum "25g" {
                   description "Links are 25G";
                 }
                 enum "40g" {
                   description "Links are 40G";
                 }
                 enum "50g" {
                   description "Links are 50G";
                 }
                 enum "80g" {
                   description "Links are 80G";
                 }
                 enum "100g" {
                   description "Links are 100G";
                 }
                 enum "200g" {
                   description "Links are 200G";
                 }
                 enum "400g" {
                   description "Links are 400G";
                 }
                 enum "800g" {
                   description "Links are 800G";
                 }
                 enum "oc192" {
                   description "Links are OC-192";
                 }
                 enum "mixed" {
                   description "Links are various speeds";
                 }
               }
             }
             container local-bias {
               presence "enable local-bias";
               description "Turn on local bias functionality";
               uses apply-advanced;
               leaf disable {
                 description "Disable local-bias";
                 type empty;
               }
             }
             leaf local-minimum-links-threshold {
               description "Specify threshold for minimum links per VC/VCF member";
               type union {
                 type string {
                   pattern "<.*>|$.*";
                 }
                 type uint16 {
                   range "1 .. 100";
                 }
               }
             }
             leaf resilient-hash {
               description "Turn on resilient-hash";
               type empty;
             }
             container dlb {
               description "Enable DLB on LAG";
               uses apply-advanced;
               choice mode {
                 case case_1 {
                   leaf per-packet {
                     description "Per-packet link assignment";
                     type empty;
                   }
                 }
                 case case_2 {
                   leaf assigned-flow {
                     description "Fixed link assignment";
                     type empty;
                   }
                 }
                 case case_3 {
                   container flowlet {
                     presence "enable flowlet";
                     description "Inactivity-based link assignment";
                     uses apply-advanced;
                     leaf inactivity-interval {
                       description " Minimum inactivity interval in micro-seconds for link re-assignment";
                       default "256";
                       type union {
                         type string {
                           pattern "<.*>|$.*";
                         }
                         type uint32;
                       }
                     }
                   }
                 }
               }
             }
             container lacp {
               description "Link Aggregation Control Protocol configuration";
               uses apply-advanced;
               choice mode {
                 case case_1 {
                   leaf active {
                     description "Initiate transmission of LACP packets";
                     type empty;
                   }
                 }
                 case case_2 {
                   leaf passive {
                     description "Respond to LACP packets";
                     type empty;
                   }
                 }
               }
               leaf periodic {
                 description "Timer interval for periodic transmission of LACP packets";
                 type enumeration {
                   enum "fast" {
                     description "Receive packets every second";
                   }
                   enum "slow" {
                     description "Receive packets every 30 seconds";
                   }
                 }
               }
               leaf multiplier {
                 description "LACP timeout detection multiplier";
                 type union {
                   type string {
                     pattern "<.*>|$.*";
                   }
                   type uint32 {
                     range "3 .. 30";
                   }
                 }
               }
               leaf fast-failover {
                 description "To turn on LACP fast-failover";
                 type empty;
               }
               container link-protection {
                 presence "enable link-protection";
                 uses apply-advanced;
                 leaf disable {
                   description "To turn off LACP link-protection";
                   type empty;
                 }
                 choice mode {
                   case case_1 {
                     leaf revertive {
                       description "Switch links when better priority link comes up";
                       type empty;
                     }
                   }
                   case case_2 {
                     leaf non-revertive {
                       description "Do not switch links when better priority link comes up";
                       type empty;
                     }
                   }
                 }
                 container rtg-config {
                   presence "enable rtg-config";
                   description "RTG Feature enable on AE";
                   uses apply-advanced;
                   leaf preempt-cutover-timer {
                     description "RTG preempt-cutover-timer in seconds";
                     default "1";
                     type union {
                       type string {
                         pattern "<.*>|$.*";
                       }
                       type uint32 {
                         range "0 .. 255";
                       }
                     }
                   }
                 }
               }
               leaf accept-data {
                 description "Keep receiving traffic even when LACP goes down";
                 type empty;
               }
               leaf sync-reset {
                 description "On minimum-link failure notify out of sync to peer";
                 type enumeration {
                   enum "disable" {
                     description "To disable minimum-link failure handling at LACP level";
                   }
                   enum "enable" {
                     description "To enable minimum-link failure handling at LACP level";
                   }
                 }
               }
               leaf system-priority {
                 description "Priority of the system (0 ... 65535)";
                 type string;
               }
               leaf system-id {
                 description "Node's System ID, encoded as a MAC address";
                 type jt:mac-addr;
               }
               leaf admin-key {
                 description "Node's administrative key";
                 type union {
                   type uint16;
                   type string {
                     pattern "<.*>|$.*";
                   }
                 }
               }
               container hold-time {
                 description "Hold time for link up and link down for AE link members";
                 leaf up {
                   description "Link up hold time for the AE link members";
                   units "seconds";
                   type union {
                     type string {
                       pattern "<.*>|$.*";
                     }
                     type uint16 {
                       range "1 .. 6000";
                     }
                   }
                 }
               }
               leaf aggregate-wait-time {
                 description "Aggregate wait time for the AE";
                 units "seconds";
                 type union {
                   type string {
                     pattern "<.*>|$.*";
                   }
                   type uint16 {
                     range "0 .. 1800";
                   }
                 }
               }
               leaf force-up {
                 description "Forceup AE interface with LACP";
                 type empty;
               }
               leaf no-peer-loopback-validation {
                 description "Skip MCLAG peer loop back validation for LACP PDUs on Forceup AE interface";
                 type empty;
               }
             }
             list link-protection-sub-group {
               key name;
               ordered-by user;
               description "Link Protection subgroup configuration";
               leaf name {
                 description "Name of the subgroup";
                 type string {
                   length "2 .. 64";
                 }
               }
               uses apply-advanced;
               choice type {
                 case case_1 {
                   leaf primary {
                     description "Primary subgroup for N:N link-protection mode";
                     type empty;
                   }
                 }
                 case case_2 {
                   leaf backup {
                     description "Backup subgroup for N:N link-protection mode";
                     type empty;
                   }
                 }
               }
             }
             container ethernet-switch-profile {
               description "Ethernet virtual LAN/media access control-level options";
               uses apply-advanced;
               leaf-list tag-protocol-id {
                 ordered-by user;
                 description "IEEE 802.1q Tag Protocol Identifier values for VLAN-tagged frames";
                 type string;
               }
               container storm-control {
                 description "Storm control profile name to bind";
                 uses apply-advanced;
                 leaf profile-name {
                   description "Profile name";
                   type string;
                 }
               }
               container recovery-timeout {
                 description "Recovery timeout for this interface";
                 leaf time-in-seconds {
                   units "seconds";
                   type union {
                     type string {
                       pattern "<.*>|$.*";
                     }
                     type uint32 {
                       range "10 .. 3600";
                     }
                   }
                 }
               }
               leaf mac-learn-enable {
                 description "Learn MAC addresses dynamically";
                 type empty;
               }
             }
             container mc-ae {
               description "Multi-chassis aggregation (MC-AE) network device configuration";
               uses apply-advanced;
               leaf mc-ae-id {
                 description "MC-AE group id";
                 type union {
                   type string {
                     pattern "<.*>|$.*";
                   }
                   type uint16 {
                     range "1 .. 65535";
                   }
                 }
               }
               leaf redundancy-group {
                 description "Redundancy group id";
                 default "1";
                 type union {
                   type string {
                     pattern "<.*>|$.*";
                   }
                   type uint32 {
                     range "1 .. 4294967294";
                   }
                 }
               }
               leaf chassis-id {
                 description "Chassis id of MC-AE network device";
                 type union {
                   type string {
                     pattern "<.*>|$.*";
                   }
                   type uint16 {
                     range "0 .. 1";
                   }
                 }
               }
               leaf mode {
                 description "Mode of the MC-AE";
                 type enumeration {
                   enum "active-active" {
                     description "MC-AE in active-active mode";
                   }
                 }
               }
               leaf status-control {
                 description "Status of the MC-AE chassis";
                 type enumeration {
                   enum "active" {
                     description "Chassis is Active";
                   }
                   enum "standby" {
                     description "Chassis is Standby";
                   }
                 }
               }
               leaf switchover-mode {
                 description "Switchover mode";
                 type enumeration {
                   enum "revertive" {
                     description "Switch mcae node when preferred link comes up";
                   }
                   enum "non-revertive" {
                     description "Do not switch mcae node when preferred link comes up";
                   }
                 }
               }
               leaf revert-time {
                 description "Wait interval before performing switchover";
                 default "3";
                 units "minute";
                 type union {
                   type string {
                     pattern "<.*>|$.*";
                   }
                   type uint32 {
                     range "1 .. 10";
                   }
                 }
               }
               leaf init-delay-time {
                 description "Init delay timer for mcae sm for min traffic loss";
                 units "seconds";
                 type union {
                   type string {
                     pattern "<.*>|$.*";
                   }
                   type uint16 {
                     range "1 .. 6000";
                   }
                 }
               }
               leaf recovery-delay-time {
                 description "Delay timer for bringing up ICL, ICCP";
                 units "seconds";
                 type union {
                   type string {
                     pattern "<.*>|$.*";
                   }
                   type uint16 {
                     range "1 .. 6000";
                   }
                 }
               }
               leaf enhanced-convergence {
                 description "Optimized convergence time for mcae";
                 type empty;
               }
               container events {
                 presence "enable events";
                 description "MCAE related events";
                 uses apply-advanced;
                 container iccp-peer-down {
                   presence "enable iccp-peer-down";
                   description "Define behavior in the event of ICCP peer down";
                   uses apply-advanced;
                   leaf force-icl-down {
                     description "Bring down ICL logical interface";
                     type empty;
                   }
                   leaf prefer-status-control-active {
                     description "Keep this node up (recommended only on status-control active)";
                     type empty;
                   }
                 }
               }
             }
             leaf share-standby {
               description "Share the resources with standby ports, needs FPC reboot to take effect";
               type empty;
             }
           }
           container es-options {
             description "ES PIC interface-specific options";
             uses apply-advanced;
             leaf backup-interface {
               description "Name of backup interface";
               type union {
                 type jt:interface-device;
                 type string {
                   pattern "<.*>|$.*";
                 }
               }
             }
           }
           container dsl-options {
             description "DSL interface-specific options";
             uses apply-advanced;
             leaf operating-mode {
               description "DSL operating mode";
               type enumeration {
                 enum "auto" {
                   description "Autonegotiate mode";
                 }
                 enum "ansi-dmt" {
                   description "ANSI T1.413 Issue II mode";
                 }
                 enum "itu-dmt" {
                   description "ITU G.992.1 mode";
                 }
                 enum "etsi" {
                   description "ETSI TS 101 388 V1.3.1 mode";
                 }
                 enum "itu-annexb-ur2" {
                   description "ITU G.992.1 UR-2 mode";
                 }
                 enum "itu-annexb-non-ur2" {
                   description "ITU G.992.1 Non UR-2 mode";
                 }
                 enum "itu-dmt-bis" {
                   description "ITU G.992.3 mode";
                 }
                 enum "adsl2plus" {
                   description "ITU G.992.5 mode";
                 }
                 enum "annexm-itu-dmt-bis" {
                   description "AnnexM ITU G.992.3 mode";
                 }
                 enum "annexm-adsl2plus" {
                   description "AnnexM ITU G.992.5 mode";
                 }
               }
             }
           }
           container vdsl-options {
             description "VDSL interface-specific options";
             uses apply-advanced;
             leaf vdsl-profile {
               description "VDSL profile";
               type enumeration {
                 enum "auto" {
                   description "Auto";
                 }
                 enum "8a" {
                   description "Profile 8a";
                 }
                 enum "8b" {
                   description "Profile 8b";
                 }
                 enum "8c" {
                   description "Profile 8c";
                 }
                 enum "8d" {
                   description "Profile 8d";
                 }
                 enum "12a" {
                   description "Profile 12a";
                 }
                 enum "12b" {
                   description "Profile 12b";
                 }
                 enum "17a" {
                   description "Profile 17a";
                 }
               }
             }
             leaf sra {
               description "DSL SRA";
               default "disable";
               type enumeration {
                 enum "enable" {
                   description "Enable SRA";
                 }
                 enum "disable" {
                   description "Disable SRA";
                 }
               }
             }
             leaf v43 {
               description "DSL V43 tones";
               default "enable";
               type enumeration {
                 enum "enable" {
                   description "Enable V43";
                 }
                 enum "disable" {
                   description "Disable V43";
                 }
               }
             }
             leaf sos {
               description "Enable SOS";
               type empty;
             }
           }
           container dsl-sfp-options {
             description "DSL SFP options";
             uses apply-advanced;
             container adsl-options {
               description "ADSL options";
               uses apply-advanced;
               leaf vpi {
                 description "Virtual path identifier";
                 type union {
                   type string {
                     pattern "<.*>|$.*";
                   }
                   type uint32 {
                     range "0 .. 255";
                   }
                 }
               }
               leaf vci {
                 description "Virtual circuit identifier";
                 type union {
                   type string {
                     pattern "<.*>|$.*";
                   }
                   type uint32 {
                     range "32 .. 65535";
                   }
                 }
               }
               leaf encap {
                 description "Encapsulation";
                 type enumeration {
                   enum "bypass" {
                     description "Bypass";
                   }
                   enum "llcsnap-bridged-802dot1q" {
                     description "LLCSNAP bridged 802.1q";
                   }
                   enum "llcsnap-routed-ip" {
                     description "LLCSNAP routed ip";
                   }
                   enum "vc-mux-bridged" {
                     description "VC MUX bridged";
                   }
                   enum "vc-mux-routed-ip" {
                     description "VC MUX routed ip";
                   }
                   enum "generic" {
                     description "Generic";
                   }
                 }
               }
               leaf annex {
                 description "Annex type";
                 type enumeration {
                   enum "auto" {
                     description "Annex type auto";
                   }
                   enum "annexj-off" {
                     description "Annex type annexj turn off";
                   }
                 }
               }
             }
             container vdsl-options {
               description "VDSL options";
               uses apply-advanced;
               leaf profile {
                 description "VDSL profile";
                 type enumeration {
                   enum "auto" {
                     description "Automatic";
                   }
                   enum "8a" {
                     description "Profile 8a";
                   }
                   enum "8b" {
                     description "Profile 8b";
                   }
                   enum "8c" {
                     description "Profile 8c";
                   }
                   enum "8d" {
                     description "Profile 8d";
                   }
                   enum "12a" {
                     description "Profile 12a";
                   }
                   enum "12b" {
                     description "Profile 12b";
                   }
                   enum "17a" {
                     description "Profile 17a";
                   }
                   enum "30a" {
                     description "Profile 30a";
                   }
                 }
               }
               leaf carrier {
                 description "Carrier setting";
                 type enumeration {
                   enum "auto" {
                     description "Automatic";
                   }
                   enum "a43" {
                     description "Carrier A43";
                   }
                   enum "b43" {
                     description "Carrier B43";
                   }
                 }
               }
             }
             container gfast-options {
               description "G.fast options";
               uses apply-advanced;
               leaf carrier {
                 description "Carrier setting";
                 type enumeration {
                   enum "a43" {
                     description "Carrier A43";
                   }
                   enum "a43c" {
                     description "Carrier A43C";
                   }
                   enum "b43" {
                     description "Carrier B43";
                   }
                   enum "b43c" {
                     description "Carrier B43C";
                   }
                 }
               }
             }
           }
           container shdsl-options {
             description "SHDSL interface-specific options";
             uses apply-advanced;
             leaf annex {
               description "Type of SHDSL annex";
               default "annex-b";
               type enumeration {
                 enum "annex-a" {
                   description "Annex-a PIC";
                 }
                 enum "annex-b" {
                   description "Annex-b PIC";
                 }
                 enum "annex-f" {
                   description "Annex-f PIC";
                 }
                 enum "annex-g" {
                   description "Annex-g PIC";
                 }
                 enum "annex-auto" {
                   description "Annex-auto PIC";
                 }
               }
             }
             leaf line-rate {
               description "SHDSL line rate";
               type string;
             }
             leaf loopback {
               description "Loopback mode";
               type enumeration {
                 enum "local" {
                   description "Local loopback";
                 }
                 enum "remote" {
                   description "Remote loopback";
                 }
               }
             }
             container snr-margin {
               presence "enable snr-margin";
               description "Signal to noise ratio margin";
               uses apply-advanced;
               leaf current {
                 description "Current signal to noise ratio margin";
                 units "dB";
                 type string;
               }
               leaf snext {
                 description "SNEXT signal to noise ratio margin";
                 units "dB";
                 type string;
               }
             }
           }
           container data-input {
             description "Configuration for drop-insert data input";
             uses apply-advanced;
             choice input-choice {
               case case_1 {
                 leaf system {
                   description "Data sourced from system";
                   type empty;
                 }
               }
               case case_2 {
                 leaf interface {
                   description "Interface that acts as data source";
                   type union {
                     type jt:interface-device;
                     type string {
                       pattern "<.*>|$.*";
                     }
                   }
                 }
               }
             }
           }
           container switch-options {
             description "Front end ports configuration";
             uses apply-advanced;
             list switch-port {
               key name;
               leaf name {
                 description "Front end port number";
                 type union {
                   type string {
                     pattern "<.*>|$.*";
                   }
                   type uint32 {
                     range "0 .. 15";
                   }
                 }
               }
               uses apply-advanced;
               choice auto-negotiation-choice {
                 leaf auto-negotiation {
                   description "Enable auto-negotiation";
                   type empty;
                 }
                 leaf no-auto-negotiation {
                   description "Don't enable auto-negotiation";
                   type empty;
                 }
               }
               leaf link-mode {
                 description "Link operational mode";
                 type enumeration {
                   enum "half-duplex" {
                     description "Half-duplex operation";
                   }
                   enum "full-duplex" {
                     description "Full-duplex operation";
                   }
                 }
               }
               leaf speed {
                 description "Link speed";
                 type enumeration {
                   enum "10m" {
                   }
                   enum "100m" {
                   }
                   enum "1g" {
                   }
                 }
               }
               leaf vlan-id {
                 description "VLAN ID for this port";
                 type union {
                   type string {
                     pattern "<.*>|$.*";
                   }
                   type uint32 {
                     range "0 .. 4094";
                   }
                 }
               }
               leaf cascade-port {
                 description "Port externally connected to another cascade port";
                 type empty;
               }
             }
           }
           container container-options {
             description "Container interface specific options";
             uses apply-advanced;
             container container-type {
               presence "enable container-type";
               description "Protocol type of the container interface";
               uses apply-advanced;
               choice container-type-choice {
                 case case_1 {
                   container aps {
                     description "APS options on the container";
                     presence "enable aps";
                     uses aps_type;
                   }
                 }
               }
             }
             container member-interface-type {
               description "Link type of members of container";
               uses apply-advanced;
               choice member_interface_type_choice {
                 case case_1 {
                   container sonet {
                     uses apply-advanced;
                     leaf member-interface-speed {
                       description "Link speed of members of container";
                       type enumeration {
                         enum "oc3" {
                           description "Links are OC-3";
                         }
                         enum "oc12" {
                           description "Links are OC-12";
                         }
                         enum "oc48" {
                           description "Links are OC-48";
                         }
                         enum "oc192" {
                           description "Links are OC-192";
                         }
                         enum "oc768" {
                           description "Links are OC-768";
                         }
                         enum "mixed" {
                           description "Links are of different speeds";
                         }
                       }
                     }
                   }
                 }
                 case case_2 {
                   container atm {
                     uses apply-advanced;
                     leaf member-interface-speed {
                       description "Link speed of members of container";
                       type enumeration {
                         enum "oc3" {
                           description "Links are OC-3";
                         }
                         enum "oc12" {
                           description "Links are OC-12";
                         }
                         enum "oc48" {
                           description "Links are OC-48";
                         }
                       }
                     }
                   }
                 }
                 case case_3 {
                   container channelized-sonet {
                     uses apply-advanced;
                     leaf member-interface-speed {
                       description "Link speed of members of container";
                       type enumeration {
                         enum "coc3" {
                           description "Links are COC-3";
                         }
                         enum "coc12" {
                           description "Links are COC-12";
                         }
                         enum "coc48" {
                           description "Links are COC-48";
                         }
                         enum "coc192" {
                           description "Links are COC-192";
                         }
                         enum "coc768" {
                           description "Links are COC-768";
                         }
                       }
                     }
                   }
                 }
                 case case_4 {
                   container channelized-sdh {
                     uses apply-advanced;
                     leaf member-interface-speed {
                       description "Link speed of members of container";
                       type enumeration {
                         enum "cstm1" {
                           description "Links are cstm-1";
                         }
                         enum "cstm4" {
                           description "Links are cstm-4";
                         }
                         enum "cstm16" {
                           description "Links are cstm-16";
                         }
                         enum "coc64" {
                           description "Links are cstm-64";
                         }
                         enum "cstm256" {
                           description "Links are cstm256";
                         }
                       }
                     }
                   }
                 }
               }
             }
             container redundancy {
               description "Container interface redundancy options";
               uses apply-advanced;
               container hold-time {
                 description "Hold time for link up and link down";
                 leaf up {
                   description "Link up hold time";
                   units "milliseconds";
                   type union {
                     type string {
                       pattern "<.*>|$.*";
                     }
                     type uint32 {
                       range "0 .. 65534";
                     }
                   }
                 }
                 leaf down {
                   description "Link down hold time";
                   units "milliseconds";
                   type union {
                     type string {
                       pattern "<.*>|$.*";
                     }
                     type uint32 {
                       range "0 .. 65534";
                     }
                   }
                 }
               }
             }
             leaf-list container-list {
               ordered-by user;
               description "List of container interfaces this member link is associated to";
               type union {
                 type jt:interface-device;
                 type string {
                   pattern "<.*>|$.*";
                 }
               }
             }
             choice redundancy-type {
               case case_1 {
                 choice aps-redundancy {
                   case case_1 {
                     leaf primary {
                       description "This member link is primary interface of the container";
                       type empty;
                     }
                   }
                   case case_2 {
                     leaf standby {
                       description "This member link is standby interface of the container";
                       type empty;
                     }
                   }
                 }
               }
             }
             leaf fast-aps {
               description "Fast APS switch";
               type empty;
             }
             leaf allow-configuration-override {
               description "Allow physical configuration of member link to override container configuration";
               type empty;
             }
           }
           container layer2-policer {
             description "Layer2 policing for interface";
             uses apply-advanced;
             choice layer2-input-policer-choice {
               case case_1 {
                 leaf input-policer {
                   description "Two-color policer for received packets";
                   type string;
                 }
               }
               case case_2 {
                 leaf input-hierarchical-policer {
                   description "Hierarchical policer for received packets";
                   type string;
                 }
               }
             }
           }
           list unit {
             key name;
             description "Logical interface";
             leaf name {
               type string;
             }
             uses apply-advanced;
             leaf interface-tag {
               description "Interface tag name";
               type string {
                 length "1 .. 64";
               }
             }
             container policer-overhead {
               description "Policer overhead adjustment for this unit";
               uses apply-advanced;
               leaf policer-overhead-value {
                 description "Policer overhead bytes to be accounted in ingress and egress";
                 units "bytes";
                 type union {
                   type string {
                     pattern "<.*>|$.*";
                   }
                   type int32;
                 }
               }
               leaf ingress {
                 description "Ingress value in bytes";
                 units "bytes";
                 type union {
                   type string {
                     pattern "<.*>|$.*";
                   }
                   type int32 {
                     range "-64 .. 64";
                   }
                 }
               }
               leaf egress {
                 description "Egress value in bytes";
                 units "bytes";
                 type union {
                   type string {
                     pattern "<.*>|$.*";
                   }
                   type int32 {
                     range "-64 .. 64";
                   }
                 }
               }
             }
             leaf alias {
               description "Interface alias";
               type string;
             }
             leaf enhanced-convergence {
               description "Optimize convergence time for L3";
               type empty;
             }
             leaf proxy-macip-advertisement {
               description "Proxy advertisement of type 2 MAC+IP route for EVPN";
               type empty;
             }
             leaf virtual-gateway-accept-data {
               description "Accept packets destined for virtual gateway address";
               type empty;
             }
             container peer-psd {
               presence "enable peer-psd";
               description "Peer psd";
               leaf psd-name {
                 description "Peer psd name";
                 type string;
               }
             }
             container peer-interface {
               presence "enable peer-interface";
               description "Peer interface";
               uses apply-advanced;
               leaf interface-name {
                 description "Peer interface name";
                 type union {
                   type jt:interface-unit;
                   type string {
                     pattern "<.*>|$.*";
                   }
                 }
               }
             }
             container interface-shared-with {
               presence "enable interface-shared-with";
               description "Specify which PSD owns this logical interface";
               uses apply-advanced;
               leaf psd-name {
                 description "Name of protected system domain (psd[1-31], ex. psd2)";
                 type string {
                 }
               }
             }
             choice enable-disable {
               case case_1 {
                 leaf disable {
                   description "Disable this logical interface";
                   type empty;
                 }
               }
             }
             leaf passive-monitor-mode {
               description "Use interface to tap packets from another router";
               type empty;
             }
             leaf per-session-scheduler {
               description "Enable per-session queuing on an IQ2 interface";
               type empty;
             }
             container account-layer2-overhead {
               presence "enable account-layer2-overhead";
               description "Account layer2 overhead in IFL byte statistics";
               uses apply-advanced;
               leaf overhead-value {
                 description "Layer2 overhead bytes to be accounted in ingress and egress";
                 units "bytes";
                 type union {
                   type string {
                     pattern "<.*>|$.*";
                   }
                   type int8 {
                     range "-128 .. 127";
                   }
                 }
               }
               leaf ingress {
                 description "Layer2 overhead bytes to be accounted in ingress";
                 units "bytes";
                 type union {
                   type string {
                     pattern "<.*>|$.*";
                   }
                   type int8 {
                     range "-128 .. 127";
                   }
                 }
               }
               leaf egress {
                 description "Layer2 overhead bytes to be accounted in egress";
                 units "bytes";
                 type union {
                   type string {
                     pattern "<.*>|$.*";
                   }
                   type int8 {
                     range "-128 .. 127";
                   }
                 }
               }
             }
             container forwarding-class-accounting {
               presence "enable forwarding-class-accounting";
               description "Configure Forwarding-class-accounting parameters for IFL ";
               uses apply-advanced;
               leaf direction {
                 description "Direction of the traffic to be accounted for IFL";
                 type enumeration {
                   enum "ingress" {
                     description "Enable forwarding-class-accounting for ingress traffic";
                   }
                   enum "egress" {
                     description "Enable forwarding-class-accounting for egress traffic";
                   }
                   enum "both" {
                     description "Enable forwarding-class-accounting for both directions";
                   }
                 }
               }
               container enhanced {
                 presence "enable enhanced";
                 uses apply-advanced;
                 leaf traffic-type {
                   description "Traffic-type to be accounted for forwarding-class-accounting for IFL";
                   type enumeration {
                     enum "unicast-statistics" {
                       description "Count only unicast traffic for forwarding-class-accounting for IFL ";
                     }
                     enum "multicast-statistics" {
                       description "Count only multicast traffic for forwarding-class-accounting for IFL";
                     }
                   }
                 }
                 leaf family {
                   description "Protocol traffic to be accounted for forwarding-class-accounting for IFL";
                   type enumeration {
                     enum "inet" {
                       description "Enable forwarding-class-accounting for IPv4 family only for IFL";
                     }
                     enum "inet6" {
                       description "Enable forwarding-class-accounting for IPv6 family only for IFL";
                     }
                     enum "both" {
                       description "Enable forwarding-class-accounting for both IPv4 and IPv6 family for IFL";
                     }
                   }
                 }
                 leaf direction {
                   description "Direction of the traffic to be accounted for forwarding-class-accounting for IFL";
                   type enumeration {
                     enum "ingress" {
                       description "Enable forwarding-class-accounting for ingress traffic for IFL";
                     }
                     enum "egress" {
                       description "Enable forwarding-class-accounting for egress traffic for IFL";
                     }
                     enum "both" {
                       description "Enable forwarding-class-accounting for both ingress and egress traffic for IFL";
                     }
                   }
                 }
                 leaf overhead-bytes {
                   description "Per octet overhead bytes to be accounted for forwarding-class-accounting for IFL ";
                   default "0";
                   type union {
                     type string {
                       pattern "<.*>|$.*";
                     }
                     type uint32 {
                       range "0 .. 255";
                     }
                   }
                 }
               }
             }
             leaf clear-dont-fragment-bit {
               description "Clear DF bit in packet (AS PIC and J-series only as well as MIF)";
               type empty;
             }
             leaf packet-inject-enable {
               description "Enable packet inject functionality on this IFL";
               type empty;
             }
             leaf reassemble-packets {
               description "Do reassembly of fragmented tunnel packets";
               type empty;
             }
             container ip-address-owner {
               description "Define the owner for IP addresses hosted on this interface";
               choice ip-address-owner-options {
                 case case_1 {
                   leaf service-plane {
                     description "IP address defined on this interface is hosted by service plane";
                     type empty;
                   }
                 }
                 case case_2 {
                   leaf routing-engine {
                     description "IP address defined on this interface is hosted by routing engine";
                     type empty;
                   }
                 }
               }
             }
             container services-options {
               description "Services interface-specific options";
               uses apply-advanced;
             }
             container rpm {
               description "Enable RPM service on this interface";
               uses apply-advanced;
               choice rpm_or_twamp {
                 case case_1 {
                   choice rpm-type {
                     case case_1 {
                       leaf client {
                         description "Client mode";
                         type empty;
                       }
                     }
                     case case_2 {
                       leaf server {
                         description "Server mode";
                         type empty;
                       }
                     }
                     case case_3 {
                       leaf client-delegate-probes {
                         description "Client delegate probe mode";
                         type empty;
                       }
                     }
                   }
                 }
                 case case_2 {
                   leaf twamp-server {
                     description "Set TWAMP server mode on this interface";
                     type empty;
                   }
                 }
                 case case_3 {
                   leaf twamp-client {
                     description "Set TWAMP client mode on this interface";
                     type empty;
                   }
                 }
               }
             }
             leaf description {
               description "Text description of interface";
               type string;
             }
             leaf metadata {
               description "Text metadata attached to interface";
               type string;
             }
             container dial-options {
               description "Dial options";
               uses apply-advanced;
               choice interface_id_choice {
                 case case_1 {
                   leaf l2tp-interface-id {
                     description "Identifier for group of PPP sessions";
                     type string {
                       length "1 .. 63";
                     }
                   }
                 }
                 case case_2 {
                   leaf ipsec-interface-id {
                     description "Identifier for group of dynamic peers";
                     type string {
                       length "1 .. 63";
                     }
                   }
                 }
               }
               choice ifl_type {
                 case case_1 {
                   leaf dedicated {
                     description "Use this unit for only one PPP/IPSec session";
                     type empty;
                   }
                 }
                 case case_2 {
                   leaf shared {
                     description "Share this unit for multiple PPP/IPSec sessions";
                     type empty;
                   }
                 }
               }
             }
             container actual-transit-statistics {
               presence "enable actual-transit-statistics";
               description "Actual transit statistics";
             }
             list demux-source {
               key name;
               ordered-by user;
               description "Demux based on source address";
               uses demux_options_table;
             }
             list demux-destination {
               key name;
               ordered-by user;
               description "Demux based on destination address";
               uses demux_options_table;
             }
             container demux {
               description "Demux based on source or destination address";
               uses apply-advanced;
               container inet {
                 presence "enable inet";
                 description "Family inet";
                 uses apply-advanced;
                 leaf address {
                   description "Address type";
                   type enumeration {
                     enum "source" {
                       description "Demux based on source address";
                     }
                     enum "destination" {
                       description "Demux based on destination address";
                     }
                   }
                 }
                 container auto-configure {
                   description "Auto configuration";
                   uses dynamic_ipv4_type;
                 }
               }
               container inet6 {
                 presence "enable inet6";
                 description "Family inet6";
                 uses apply-advanced;
                 leaf address {
                   description "Address type";
                   type enumeration {
                     enum "source" {
                       description "Demux based on source address";
                     }
                     enum "destination" {
                       description "Demux based on destination address";
                     }
                   }
                 }
                 container auto-configure {
                   description "Auto configuration";
                   uses dynamic_ipv6_type;
                 }
               }
             }
             leaf encapsulation {
               description "Logical link-layer encapsulation";
               type enumeration {
                 enum "atm-nlpid" {
                   description "ATM NLPID encapsulation";
                 }
                 enum "atm-cisco-nlpid" {
                   description "Cisco-compatible ATM NLPID encapsulation";
                 }
                 enum "atm-snap" {
                   description "ATM LLC/SNAP encapsulation";
                 }
                 enum "atm-vc-mux" {
                   description "ATM VC multiplexing";
                 }
                 enum "atm-ccc-vc-mux" {
                   description "ATM VC for CCC";
                 }
                 enum "atm-tcc-vc-mux" {
                   description "ATM VC for translational cross-connect";
                 }
                 enum "atm-tcc-snap" {
                   description "ATM LLC/SNAP for translational cross-connect";
                 }
                 enum "atm-ccc-cell-relay" {
                   description "ATM cell relay for CCC";
                 }
                 enum "vlan-vci-ccc" {
                   description "CCC for VLAN Q-in-Q and ATM VPI/VCI interworking";
                 }
                 enum "ether-over-atm-llc" {
                   description "Ethernet over ATM (LLC/SNAP) encapsulation";
                 }
                 enum "ether-vpls-over-atm-llc" {
                   description "Ethernet VPLS over ATM (bridging) encapsulation";
                 }
                 enum "ppp-over-ether-over-atm-llc" {
                   description "PPPoE over ATM (LLC/SNAP) encapsulation";
                 }
                 enum "ppp-over-ether" {
                   description "PPPoE encapsulation";
                 }
                 enum "atm-ppp-vc-mux" {
                   description "ATM PPP over raw AAL5";
                 }
                 enum "atm-ppp-llc" {
                   description "ATM PPP over AAL5/LLC";
                 }
                 enum "atm-mlppp-llc" {
                   description "ATM MLPPP over AAL5/LLC";
                 }
                 enum "frame-relay-ppp" {
                   description "PPP over Frame Relay";
                 }
                 enum "frame-relay-ccc" {
                   description "Frame Relay DLCI for CCC";
                 }
                 enum "frame-relay" {
                   description "Frame Relay DLCI";
                 }
                 enum "frame-relay-tcc" {
                   description "Frame Relay DLCI for translational cross-connect";
                 }
                 enum "frame-relay-ether-type" {
                   description "Cisco-compatible Frame Relay Encapsulation DLCI";
                 }
                 enum "frame-relay-ether-type-tcc" {
                   description "Cisco-compatible Frame Relay Encapsulation DLCI for TCC";
                 }
                 enum "ether-vpls-fr" {
                   description "Ethernet VPLS over Frame Relay (bridging) encapsulation";
                 }
                 enum "vlan-ccc" {
                   description "802.1q tagging for a cross-connect";
                 }
                 enum "ethernet-ccc" {
                   description "Ethernet for a cross-connect";
                 }
                 enum "vlan-vpls" {
                   description "VLAN virtual private LAN service";
                 }
                 enum "vlan-bridge" {
                   description "VLAN layer-2 bridging";
                 }
                 enum "ethernet-tcc" {
                   description "Ethernet translational cross-connect";
                 }
                 enum "dix" {
                   description "Ethernet DIXv2 (RFC 894)";
                 }
                 enum "ethernet" {
                   description "Ethernet II (RFC 894)";
                 }
                 enum "ethernet-vpls" {
                   description "Ethernet II virtual private LAN service";
                 }
                 enum "ethernet-bridge" {
                   description "Ethernet II bridging";
                 }
                 enum "vlan" {
                   description "802.1q-tagged Ethernet";
                 }
                 enum "vlan-tcc" {
                   description "802.1q tagging for a translational cross-connect";
                 }
                 enum "multilink-ppp" {
                   description "Multilink PPP";
                 }
                 enum "multilink-frame-relay-end-to-end" {
                   description "Multilink Frame Relay end-to-end (FRF.15)";
                 }
                 enum "ppp-ccc" {
                   description "Serial PPP device for a cross-connect";
                 }
               }
             }
             leaf gre {
               description "Allow GRE packets";
               type empty;
             }
             leaf mtu {
               description "Maximum transmission unit packet size";
               type union {
                 type string {
                   pattern "<.*>|$.*";
                 }
                 type uint32;
               }
             }
             choice pointedness {
               case case_1 {
                 leaf point-to-point {
                   description "Point-to-point connection";
                   type empty;
                 }
               }
               case case_2 {
                 leaf multipoint {
                   description "Multipoint connection";
                   type empty;
                 }
               }
             }
             leaf bandwidth {
               description "Logical unit bandwidth (informational only)";
               type string;
             }
             leaf global-layer2-domainid {
               description "Global Layer-2 Identifier for this interface";
               type union {
                 type string {
                   pattern "<.*>|$.*";
                 }
                 type uint32 {
                   range "5 .. 4094";
                 }
               }
             }
             container radio-router {
               description "Parameters for dynamic link cost management";
               presence "enable radio-router";
               uses dynamic_ifbw_parms_type;
             }
             choice traps-choice {
               leaf traps {
                 description "Enable SNMP notifications on state changes";
                 type empty;
               }
               leaf no-traps {
                 description "Don't enable SNMP notifications on state changes";
                 type empty;
               }
             }
             choice routing-services-choice {
               leaf routing-services {
                 description "Enable routing services";
                 status deprecated;
                 type empty;
               }
               leaf no-routing-services {
                 description "Don't enable routing services";
                 status deprecated;
                 type empty;
               }
             }
             container routing-service {
               description "Routing Services on this interface";
               uses apply-advanced;
               choice enable-disable {
                 case case_1 {
                   leaf enable {
                     description "Enable Routing Service";
                     type empty;
                   }
                 }
                 case case_2 {
                   leaf disable {
                     description "Disable Routing Service";
                     type empty;
                   }
                 }
               }
             }
             container arp-resp {
               presence "enable arp-resp";
               description "Knob to control ARP response on the interface, default is restricted";
               choice arp-response-options {
                 case case_1 {
                   leaf unrestricted {
                     description "Enable unrestricted ARP respone on the interface";
                     type empty;
                   }
                 }
                 case case_2 {
                   leaf restricted {
                     description "Enable restricted proxy ARP response on the interface";
                     type empty;
                   }
                 }
               }
             }
             container proxy-arp {
               presence "enable proxy-arp";
               description "Enable proxy ARP on the interface, default is unrestricted";
               choice proxyarp-options {
                 case case_1 {
                   leaf unrestricted {
                     description "Enable unrestricted proxy ARP on the interface";
                     type empty;
                   }
                 }
                 case case_2 {
                   leaf restricted {
                     description "Enable restricted proxy ARP on the interface";
                     type empty;
                   }
                 }
               }
             }
             choice vlan_choice {
               case case_1 {
                 leaf vlan-id {
                   description "Virtual LAN identifier value for 802.1q VLAN tags";
                   type string;
                 }
               }
               case case_2 {
                 leaf vlan-id-range {
                   description "Virtual LAN identifier range of form vid1-vid2";
                   type jt:vlan-range;
                 }
               }
               case case_3 {
                 leaf-list inner-vlan-id-swap-ranges {
                   description "Inner vlan-id swap range(s) of form vid1-vid2 for dynamic L2 VLANs";
                   type jt:vlan-range;
                 }
               }
               case case_4 {
                 leaf-list vlan-id-list {
                   description "List of VLAN identifiers";
                   type jt:vlan-range;
                 }
               }
               case case_5 {
                 leaf-list vlan-tag {
                   ordered-by user;
                   description "IEEE 802.1q tag list for VLAN tagged frames";
                   status deprecated;
                   type string;
                 }
               }
               case case_6 {
                 container vlan-tags {
                   presence "enable vlan-tags";
                   description "IEEE 802.1q tags";
                   leaf outer {
                     description "[tpid.]vlan-id, tpid format is 0xNNNN and is optional";
                     type string;
                   }
                   choice inner_choice {
                     case case_1 {
                       leaf inner {
                         description "[tpid.]vlan-id, tpid format is 0xNNNN and is optional";
                         type string;
                       }
                     }
                     case case_2 {
                       leaf inner-range {
                         description "[tpid.]vid1-vid2, tpid format is 0xNNNN and is optional";
                         type string {
                         }
                       }
                     }
                     case case_3 {
                       leaf-list inner-list {
                         description "List of VLAN identifiers";
                         type jt:vlan-range;
                       }
                     }
                   }
                 }
               }
             }
             leaf deep-vlan-qualified-learning {
               description "Enable qualified MAC-address learning on the specified vlan tag";
               type union {
                 type string {
                   pattern "<.*>|$.*";
                 }
                 type uint32 {
                   range 3;
                 }
               }
             }
             leaf native-inner-vlan-id {
               description "Native virtual LAN identifier for singly tagged frames";
               type union {
                 type string {
                   pattern "<.*>|$.*";
                 }
                 type uint32 {
                   range "0 .. 4094";
                 }
               }
             }
             container inner-vlan-id-range {
               description "Inner vlan-id range start <start-vlan-id> end <end-vlan-id>";
               leaf start {
                 description "Inner vlan-id range's start value";
                 type union {
                   type string {
                     pattern "<.*>|$.*";
                   }
                   type uint32 {
                     range "32 .. 4094";
                   }
                 }
               }
               leaf end {
                 description "Inner vlan-id range's end value";
                 type union {
                   type string {
                     pattern "<.*>|$.*";
                   }
                   type uint32 {
                     range "32 .. 4094";
                   }
                 }
               }
             }
             container accept-source-mac {
               description "Remote media access control address to/from which to accept traffic";
               uses apply-advanced;
               list mac-address {
                 key name;
                 description "Remote MAC address";
                 uses mac_list;
               }
             }
             container input-vlan-map {
               description "VLAN map operation on input";
               uses vlan_map;
             }
             container output-vlan-map {
               description "VLAN map operation on output";
               uses vlan_map;
             }
             leaf swap-by-poppush {
               description "Pop original vlan tag and then push a new vlan tag";
               type empty;
             }
             leaf receive-lsp {
               description "Name of incoming label-switched path";
               type string;
             }
             leaf transmit-lsp {
               description "Name of outgoing label-switched path";
               type string;
             }
             leaf dlci {
               description "Frame Relay data-link control identifier";
               type union {
                 type string {
                   pattern "<.*>|$.*";
                 }
                 type uint32 {
                   range "1 .. 1022";
                 }
               }
             }
             leaf multicast-dlci {
               description "Frame Relay data-link control identifier for multicast packets";
               type union {
                 type string {
                   pattern "<.*>|$.*";
                 }
                 type uint32 {
                   range "1 .. 1022";
                 }
               }
             }
             choice vci_type {
               case case_1 {
                 leaf vci {
                   description "ATM point-to-point virtual circuit identifier ([vpi.]vci)";
                   type jt:atm-vci;
                 }
               }
               case case_2 {
                 leaf allow-any-vci {
                   description "Allow all VCIs to open in atm-ccc-cell-relay mode";
                   type empty;
                 }
               }
               case case_3 {
                 leaf vpi {
                   description "ATM point-to-point virtual path identifier (vpi)";
                   type union {
                     type string {
                       pattern "<.*>|$.*";
                     }
                     type uint32 {
                       range "0 .. 255";
                     }
                   }
                 }
               }
               case case_4 {
                 leaf trunk-id {
                   description "ATM trunk identifier";
                   type union {
                     type string {
                       pattern "<.*>|$.*";
                     }
                     type uint32 {
                       range "0 .. 31";
                     }
                   }
                 }
               }
             }
             leaf no-vpivci-swapping {
               description "Do not swap VPI/VCI for Cell Relay";
               type empty;
             }
             choice psn_vci_type {
               case case_1 {
                 leaf psn-vci {
                   description "PSN VCI";
                   type jt:atm-vci;
                 }
               }
               case case_2 {
                 leaf psn-vpi {
                   description "PSN VPI";
                   type union {
                     type string {
                       pattern "<.*>|$.*";
                     }
                     type uint32 {
                       range "0 .. 255";
                     }
                   }
                 }
               }
             }
             container atm-l2circuit-mode {
               description "Select ATM Layer 2 circuit transport mode";
               choice mode_choice {
                 case case_1 {
                   leaf cell {
                     description "ATM Layer 2 circuit cell mode";
                     type empty;
                   }
                 }
                 case case_2 {
                   leaf aal5 {
                     description "ATM Layer 2 circuit AAL5 mode";
                     type empty;
                   }
                 }
               }
             }
             container vci-range {
               description "ATM VCI range start <start-vci> end <end-vci>";
               leaf start {
                 description "ATM VCI range's start value";
                 type union {
                   type string {
                     pattern "<.*>|$.*";
                   }
                   type uint16 {
                     range "32 .. 4094";
                   }
                 }
               }
               leaf end {
                 description "ATM VCI range's end value";
                 type union {
                   type string {
                     pattern "<.*>|$.*";
                   }
                   type uint16 {
                     range "32 .. 4094";
                   }
                 }
               }
             }
             leaf trunk-bandwidth {
               description "ATM trunk bandwidth";
               units "bits per second";
               type string;
             }
             leaf multicast-vci {
               description "ATM virtual circuit identifier for multicast packets";
               type jt:atm-vci;
             }
             container shaping {
               description "Virtual circuit traffic-shaping options";
               uses dcd_shaping_config;
             }
             container oam-period {
               description "OAM cell period";
               choice oam_period_choices {
                 case case_1 {
                   leaf oam-period {
                     description "OAM cell period";
                     units "seconds";
                     type union {
                       type string {
                         pattern "<.*>|$.*";
                       }
                       type uint32 {
                         range "1 .. 900";
                       }
                     }
                   }
                 }
                 case case_2 {
                   container disable {
                     presence "enable disable";
                     description "Disable F5 OAM loopback";
                   }
                 }
               }
             }
             container oam-liveness {
               description "OAM virtual circuit liveness parameters";
               uses apply-advanced;
               leaf up-count {
                 description "Number of OAM cells to consider VC up";
                 type union {
                   type string {
                     pattern "<.*>|$.*";
                   }
                   type uint32 {
                     range "1 .. 255";
                   }
                 }
               }
               leaf down-count {
                 description "Number of OAM cells to consider VC down";
                 type union {
                   type string {
                     pattern "<.*>|$.*";
                   }
                   type uint32 {
                     range "1 .. 255";
                   }
                 }
               }
             }
             container ppp-options {
               description "Point-to-Point Protocol interface-specific options";
               uses ppp_options_type;
             }
             container pppoe-options {
               description "PPP over Ethernet interface-specific options";
               uses pppoe_options_type;
             }
             container pppoe-underlying-options {
               description "PPP over Ethernet underlying interface-specific options";
               uses pppoe_underlying_options_type;
             }
             container advisory-options {
               description "Interface-specific recommendations";
               uses advisory_options_type;
             }
             container auto-configure {
               description "Auto configuration";
               uses auto_configure_vlan_type;
             }
             container demux-options {
               description "IP demux interface-specific options";
               uses demux_options_type;
             }
             container targeted-distribution {
               presence "enable targeted-distribution";
               description "Interface participates in targeted-distribution";
               uses apply-advanced;
               leaf primary-list {
                 description "Primary targeted distribution list";
                 type string {
                   length "1 .. 20";
                 }
               }
               leaf backup-list {
                 description "Backup targeted distribution list";
                 type string {
                   length "1 .. 20";
                 }
               }
               leaf standby-list {
                 description "Standby targeted distribution list";
                 type string {
                   length "1 .. 20";
                 }
               }
             }
             container targeted-options {
               presence "enable targeted-options";
               description "Targeting specific options";
               uses apply-advanced;
               leaf weight {
                 description "Targeting weight for subscriber";
                 type string;
               }
               leaf primary {
                 description "Primary link for the subscriber";
                 type union {
                   type jt:interface-device;
                   type string {
                     pattern "<.*>|$.*";
                   }
                 }
               }
               leaf backup {
                 description "Backup link for the subscriber";
                 type union {
                   type jt:interface-device;
                   type string {
                     pattern "<.*>|$.*";
                   }
                 }
               }
               leaf group {
                 description "Group name to which the subscriber is associated";
                 type string {
                 }
               }
             }
             choice keepalive_choices {
               case case_1 {
                 container keepalives {
                   description "Send or demand keepalive messages";
                   presence "enable keepalives";
                   uses keepalives_type;
                 }
               }
               case case_2 {
                 leaf no-keepalives {
                   description "Do not send or demand keepalive messages";
                   type empty;
                 }
               }
             }
             leaf inverse-arp {
               description "Enable inverse ARP";
               type empty;
             }
             leaf transmit-weight {
               description "ATM2 transmit weight for VC under VP tunnel";
               type union {
                 type string {
                   pattern "<.*>|$.*";
                 }
                 type uint16 {
                   range "1 .. 32767";
                 }
               }
             }
             container epd-threshold {
               description "Early packet discard threshold for ATM2";
               uses epd_threshold_config;
             }
             leaf cell-bundle-size {
               description "L2 circuit cell bundle size";
               units "cells";
               type union {
                 type string {
                   pattern "<.*>|$.*";
                 }
                 type uint32 {
                   range "1 .. 176";
                 }
               }
             }
             leaf cell-bundle-timeout {
               description "L2 circuit cell bundle timeout";
               units "microseconds";
               type union {
                 type string {
                   pattern "<.*>|$.*";
                 }
                 type uint32 {
                   range "1 .. 512";
                 }
               }
             }
             leaf plp-to-clp {
               description "Enable ATM2 PLP to CLP copy";
               type empty;
             }
             leaf atm-scheduler-map {
               description "Assign ATM2 CoS scheduling map";
               type union {
                 type string {
                   pattern "default";
                 }
                 type string;
               }
             }
             leaf mrru {
               description "Maximum received reconstructed unit";
               units "bytes";
               type union {
                 type string {
                   pattern "<.*>|$.*";
                 }
                 type uint16 {
                   range "1500 .. 4500";
                 }
               }
             }
             leaf short-sequence {
               description "Short sequence number header format (MLPPP only)";
               type empty;
             }
             leaf fragment-threshold {
               description "Fragmentation threshold";
               units "bytes";
               type union {
                 type string {
                   pattern "<.*>|$.*";
                 }
                 type uint32 {
                   range "64 .. 4500";
                 }
               }
             }
             leaf drop-timeout {
               description "Drop timeout";
               units "milliseconds";
               type union {
                 type string {
                   pattern "<.*>|$.*";
                 }
                 type uint16 {
                   range "0 .. 2000";
                 }
               }
             }
             leaf disable-mlppp-inner-ppp-pfc {
               description "Disable compression for inner PPP header in MLPPP payload";
               type empty;
             }
             leaf minimum-links {
               description "Minimum number of links to sustain the bundle";
               type union {
                 type string {
                   pattern "<.*>|$.*";
                 }
                 type uint16;
               }
             }
             leaf multilink-max-classes {
               description "Number of multilink classes";
               type union {
                 type string {
                   pattern "<.*>|$.*";
                 }
                 type uint16;
               }
             }
             container compression {
               presence "enable compression";
               description "Various packet header compressions";
               uses apply-advanced;
               container rtp {
                 presence "enable rtp";
                 description "Compress and decompress RTP";
                 uses apply-advanced;
                 leaf f-max-period {
                   description "Maximum number of compressed packets between transmission of full headers";
                   type union {
                     type string {
                       pattern "<.*>|$.*";
                     }
                     type uint32 {
                       range "1 .. 65535";
                     }
                   }
                 }
                 leaf-list queues {
                   ordered-by user;
                   description "Queue holding RTP packets. Default is queue 1";
                   type enumeration {
                     enum "q0" {
                       description "RTP packets assigned to queue 0";
                     }
                     enum "q1" {
                       description "RTP packets assigned to queue 1";
                     }
                     enum "q2" {
                       description "RTP packets assigned to queue 2";
                     }
                     enum "q3" {
                       description "RTP packets assigned to queue 3";
                     }
                   }
                 }
                 container port {
                   presence "enable port";
                   description "UDP destination ports reserved for RTP packets";
                   leaf minimum {
                     type union {
                       type string {
                         pattern "<.*>|$.*";
                       }
                       type uint32 {
                         range "0 .. 65535";
                       }
                     }
                   }
                   leaf maximum {
                     type union {
                       type string {
                         pattern "<.*>|$.*";
                       }
                       type uint32 {
                         range "0 .. 65535";
                       }
                     }
                   }
                 }
                 container maximum-contexts {
                   description "Maximum number of simultaneous RTP contexts";
                   leaf number {
                     description "Maximum number of simultaneous RTP contexts";
                     type union {
                       type string {
                         pattern "<.*>|$.*";
                       }
                       type uint32 {
                         range "16 .. 2048";
                       }
                     }
                   }
                 }
               }
             }
             leaf interleave-fragments {
               description "Interleave long packets with high priority ones";
               type empty;
             }
             leaf link-layer-overhead {
               description "Link layer bit stuffing overhead (0.0 .. 50.0 percent)";
               type jt:unsigned-float;
             }
             leaf accounting-profile {
               description "Accounting profile name";
               type string;
             }
             leaf peer-unit {
               description "Peer unit number";
               type union {
                 type string {
                   pattern "<.*>|$.*";
                 }
                 type uint32 {
                   range "0 .. 16385";
                 }
               }
             }
             container tunnel {
               description "Tunnel parameters";
               uses apply-advanced;
               container encapsulation {
                 presence "enable encapsulation";
                 description "Encapsulation over tunnel";
                 container vxlan-gpe {
                   presence "enable vxlan-gpe";
                   uses apply-advanced;
                   container source {
                     uses apply-advanced;
                     leaf address {
                       description "Interface address prefix";
                       type jt:ipv4addr;
                     }
                     leaf mac-address {
                       description "Interface source mac address";
                       type jt:mac-addr;
                     }
                     leaf interface {
                       description "Name of the interface";
                       type union {
                         type jt:interface-name;
                         type string {
                           pattern "<.*>|$.*";
                         }
                       }
                     }
                   }
                   container destination {
                     uses apply-advanced;
                     leaf address {
                       description "Interface address prefix";
                       type jt:ipv4addr;
                     }
                     leaf mac-address {
                       description "Interface destination mac address";
                       type jt:mac-addr;
                     }
                   }
                   leaf tunnel-endpoint {
                     description "Tunnel end point type";
                     type enumeration {
                       enum "vxlan" {
                         description "To configure vxlan tunnel-end-point";
                       }
                     }
                   }
                   container source-udp-port-range {
                     description "Value range for source-udp-port";
                     leaf min {
                       description "Minimum range value";
                       type union {
                         type string {
                           pattern "<.*>|$.*";
                         }
                         type uint32 {
                           range "1 .. 65535";
                         }
                       }
                     }
                     leaf max {
                       description "Maximum range value";
                       type union {
                         type string {
                           pattern "<.*>|$.*";
                         }
                         type uint32 {
                           range "1 .. 65535";
                         }
                       }
                     }
                   }
                   leaf destination-udp-port {
                     description "Value to write to the destination-udp-port field";
                     type union {
                       type string {
                         pattern "<.*>|$.*";
                       }
                       type uint32 {
                         range "1 .. 65535";
                       }
                     }
                   }
                   leaf vni {
                     description "Value to write to the vni field";
                     type union {
                       type string {
                         pattern "<.*>|$.*";
                       }
                       type uint32 {
                         range "0 .. 16777214";
                       }
                     }
                   }
                 }
                 container udp {
                   presence "enable udp";
                   description "Family for tunnel encapsulation udp";
                   uses apply-advanced;
                   container source {
                     uses apply-advanced;
                     leaf address {
                       description "Interface address prefix";
                       type jt:ipv4addr;
                     }
                     leaf interface {
                       description "Name of the interface";
                       type union {
                         type jt:interface-name;
                         type string {
                           pattern "<.*>|$.*";
                         }
                       }
                     }
                   }
                   container destination {
                     uses apply-advanced;
                     leaf address {
                       description "Interface address prefix";
                       type jt:ipv4addr;
                     }
                   }
                 }
                 container ipip {
                   presence "enable ipip";
                   description "Family for tunnel encapsulation ipip";
                   uses apply-advanced;
                   container source {
                     uses apply-advanced;
                     leaf address {
                       description "Interface address prefix";
                       type jt:ipv4addr;
                     }
                     leaf interface {
                       description "Name of the interface";
                       type union {
                         type jt:interface-name;
                         type string {
                           pattern "<.*>|$.*";
                         }
                       }
                     }
                   }
                   container destination {
                     uses apply-advanced;
                     leaf address {
                       description "Interface address prefix";
                       type jt:ipv4addr;
                     }
                   }
                 }
               }
               leaf encap-type {
                 description "Tunnel encapsulation type";
                 type enumeration {
                   enum "ipv4" {
                     description "Tunnel IPv4 encapsulation";
                   }
                   enum "ipv6" {
                     description "Tunnel IPv6 encapsulation";
                   }
                 }
               }
               choice source_type {
                 case case_1 {
                   leaf source {
                     description "Tunnel source address";
                     type jt:ipaddr;
                   }
                 }
                 case case_2 {
                   leaf source-hostname {
                     description "Tunnel source hostname";
                     type string;
                   }
                 }
                 case case_3 {
                   leaf source-interface {
                     description "Tunnel source interface";
                     type union {
                       type jt:interface-name;
                       type string {
                         pattern "<.*>|$.*";
                       }
                     }
                   }
                 }
               }
               choice destination_type {
                 case case_1 {
                   leaf destination {
                     description "Tunnel destination address";
                     type jt:ipaddr;
                   }
                 }
                 case case_2 {
                   leaf destination-hostname {
                     description "Tunnel destination hostname";
                     type string;
                   }
                 }
               }
               leaf key {
                 description "Tunnel key";
                 type union {
                   type string {
                     pattern "<.*>|$.*";
                   }
                   type uint32 {
                     range "0 .. 4294967295";
                   }
                 }
               }
               leaf backup-destination {
                 description "Backup tunnel destination";
                 type jt:ipaddr;
               }
               choice fragmentation {
                 case case_1 {
                   leaf allow-fragmentation {
                     description "Do not set DF bit on packets";
                     type empty;
                   }
                 }
                 case case_2 {
                   leaf do-not-fragment {
                     description "Set DF bit on packets";
                     type empty;
                   }
                 }
               }
               leaf ttl {
                 description "Time to live";
                 type union {
                   type string {
                     pattern "<.*>|$.*";
                   }
                   type uint32 {
                     range "1 .. 255";
                   }
                 }
               }
               leaf traffic-class {
                 description "TOS/Traffic class field of IP-header";
                 type union {
                   type string {
                     pattern "<.*>|$.*";
                   }
                   type uint32 {
                     range "0 .. 255";
                   }
                 }
               }
               leaf flow-label {
                 description "Flow label field of IP6-header";
                 type union {
                   type string {
                     pattern "<.*>|$.*";
                   }
                   type uint32 {
                     range "0 .. 1048575";
                   }
                 }
               }
               choice path-mtu-discovery-choice {
                 leaf path-mtu-discovery {
                   description "Enable path MTU discovery for tunnels";
                   type empty;
                 }
                 leaf no-path-mtu-discovery {
                   description "Don't enable path MTU discovery for tunnels";
                   type empty;
                 }
               }
               container routing-instance {
                 description "Routing instance to which tunnel ends belong";
                 uses apply-advanced;
                 leaf destination {
                   description "Routing instance of tunnel destination";
                   type string {
                   }
                 }
               }
             }
             leaf compression-device {
               description "Logical interface used for compression";
               type union {
                 type jt:interface-unit;
                 type string {
                   pattern "<.*>|$.*";
                 }
               }
             }
             container atm-policer {
               description "ATM policing for logical interface";
               uses apply-advanced;
               leaf input-atm-policer {
                 description "Input atm policer";
                 type string;
               }
             }
             container layer2-policer {
               description "Layer2 policing for logical interface";
               uses apply-advanced;
               choice layer2-input-policer-choice {
                 case case_1 {
                   leaf input-policer {
                     description "Two-color policer for received packets";
                     type string;
                   }
                 }
                 case case_2 {
                   leaf input-hierarchical-policer {
                     description "Hierarchical policer for received packets";
                     type string;
                   }
                 }
                 case case_3 {
                   leaf input-three-color {
                     description "Color-blind three-color policer for received packets";
                     type string;
                   }
                 }
               }
               choice layer2-output-policer-choice {
                 case case_1 {
                   leaf output-policer {
                     description "Two-color policer for transmitted packets";
                     type string;
                   }
                 }
                 case case_2 {
                   leaf output-three-color {
                     description "Three-color policer for transmitted packets";
                     type string;
                   }
                 }
               }
             }
             container filter {
               description "Filters to apply to all families configured under this logical interface";
               uses apply-advanced;
               choice chain_choice {
                 case case_1 {
                   leaf-list chain {
                     ordered-by user;
                     description "List of filter modules applied to TAG packets ";
                     type string;
                     max-elements 6;
                   }
                 }
               }
               choice input_choice {
                 case case_1 {
                   container input {
                     description "Name of filter to be applied to received packets";
                     leaf filter-name {
                       description "Name of the filter";
                       type string;
                     }
                     leaf shared-name {
                       description "Filter shared-name of instances of interface-shared filter";
                       type string;
                     }
                     leaf precedence {
                       description "Precedence of the filter";
                       type union {
                         type string {
                           pattern "<.*>|$.*";
                         }
                         type uint32 {
                           range "0 .. 255";
                         }
                       }
                     }
                   }
                 }
               }
               choice output_choice {
                 case case_1 {
                   container output {
                     description "Name of filter to be applied to transmitted packets";
                     leaf filter-name {
                       description "Name of the filter";
                       type string;
                     }
                     leaf shared-name {
                       description "Filter shared-name of instances of interface-shared filter";
                       type string;
                     }
                     leaf precedence {
                       description "Precedence of the filter";
                       type union {
                         type string {
                           pattern "<.*>|$.*";
                         }
                         type uint32 {
                           range "0 .. 255";
                         }
                       }
                     }
                   }
                 }
               }
             }
             list multi-chassis-protection {
               key name;
               description "Inter-Chassis protection configuration";
               uses multi-chassis-protection-group-ifl;
             }
             leaf statistics {
               description "Enable statistics collection in PFE";
               type empty;
             }
             container esi {
               presence "enable esi";
               description "ESI configuration of logical interface";
               uses apply-advanced;
               container auto-derive {
                 description "Auto-derive ESI value for the interface";
                 uses apply-advanced;
                 choice esitype {
                   case case_1 {
                     leaf lacp-pe-system-id-and-admin-key {
                       description "Auto-derive ESI from lacp";
                       type empty;
                     }
                   }
                 }
               }
               leaf identifier {
                 description "ESI value for the interface";
                 type jt:esi;
               }
               choice mode {
                 case case_1 {
                   leaf single-active {
                     description "Single-active mode";
                     type empty;
                   }
                 }
                 case case_2 {
                   leaf all-active {
                     description "All-active mode";
                     type empty;
                   }
                 }
               }
               container df-election-granularity {
                 presence "enable df-election-granularity";
                 description "DF Election Granularity Selection ";
                 uses apply-advanced;
                 choice mode {
                   case case_1 {
                     container per-esi {
                       presence "enable per-esi";
                       description "DF Election Granularity Per Esi";
                       uses apply-advanced;
                       leaf lacp-oos-on-ndf {
                         description "Lacp Oos";
                         type empty;
                       }
                     }
                   }
                   case case_2 {
                     leaf per-esi-vlan {
                       description "Per Esi Vlan";
                       type empty;
                     }
                   }
                 }
               }
               container df-election-type {
                 presence "enable df-election-type";
                 description "DF Election Type";
                 uses apply-advanced;
                 choice pref_choice {
                   case case_1 {
                     container preference {
                       presence "enable preference";
                       description "Preference based DF election";
                       uses apply-advanced;
                       leaf value {
                         description "Preference value for EVPN Multihoming DF election";
                         default "32767";
                         type union {
                           type string {
                             pattern "<.*>|$.*";
                           }
                           type uint32 {
                             range "0 .. 65535";
                           }
                         }
                       }
                     }
                   }
                 }
                 choice mod_choice {
                   case case_1 {
                     container mod {
                       presence "enable mod";
                       description "MOD based DF election";
                     }
                   }
                 }
               }
               leaf source-bmac {
                 description "Unicast Source B-MAC address per ESI for PBB-EVPN";
                 type jt:mac-unicast;
               }
             }
             choice virtual-gateway {
               case case_1 {
                 leaf no-auto-virtual-gateway-esi {
                   description "Disable auto ESI generation for virtual gateway address";
                   type empty;
                 }
               }
               case case_2 {
                 container virtual-gateway-esi {
                   description "ESI configuration of virtual gateway";
                   uses apply-advanced;
                   leaf identifier {
                     description "ESI value for the interface";
                     type jt:esi;
                   }
                   choice mode {
                     case case_1 {
                       leaf single-active {
                         description "Single-active mode";
                         type empty;
                       }
                     }
                     case case_2 {
                       leaf all-active {
                         description "All-active mode";
                         type empty;
                       }
                     }
                   }
                 }
               }
             }
             container service {
               description "Service operations";
               uses apply-advanced;
               list pcef {
                 key name;
                 ordered-by user;
                 description "PCEF configuration";
                 leaf name {
                   description "PCEF Profile name";
                   type string;
                 }
                 uses apply-advanced;
                 leaf activate-all {
                   description "Activate all rules and rulebases in the pcef profile";
                   type empty;
                 }
                 list activate {
                   key name;
                   ordered-by user;
                   description "Name of pcef profile rule or rulebase to activate";
                   leaf name {
                     description "Name of pcef profile rule or rulebase to activate";
                     type string;
                   }
                   uses apply-advanced;
                 }
               }
             }
             choice generate-eui64-choice {
               leaf generate-eui64 {
                 description "To generate Link Local EUI-64 addresses";
                 type empty;
               }
               leaf no-generate-eui64 {
                 description "Don't to generate Link Local EUI-64 addresses";
                 type empty;
               }
             }
             container family {
               description "Protocol family";
               container inet {
                 presence "enable inet";
                 description "IPv4 parameters";
                 uses apply-advanced;
                 container dhcp {
                   description "Dynamic Host Configuration Protocol client configuration";
                   presence "enable dhcp";
                   uses dhcp-client-type;
                 }
                 container targeted-broadcast {
                   presence "enable targeted-broadcast";
                   description "Directed broadcast";
                   uses apply-advanced;
                   choice targeted-bcast-choice {
                     case case_1 {
                       leaf forward-and-send-to-re {
                         description "Allow packets to be forwarded and sent to re";
                         type empty;
                       }
                     }
                     case case_2 {
                       leaf forward-only {
                         description "Allow packets only to be forwarded";
                         type empty;
                       }
                     }
                   }
                 }
                 leaf destination-class-usage {
                   description "Enable destination class usage on this interface";
                   status deprecated;
                   type empty;
                 }
                 leaf transit-options-packets {
                   description "Transit IP options packets (don't send to Routing Engine)";
                   status deprecated;
                   type empty;
                 }
                 leaf transit-ttl-exceeded {
                   description "Transit IP TTL-exceeded packets (don't send to Routing Engine)";
                   status deprecated;
                   type empty;
                 }
                 leaf receive-options-packets {
                   description "Receive IP options packets (don't send to Routing Engine)";
                   type empty;
                 }
                 leaf receive-ttl-exceeded {
                   description "Receive IP TTL-exceeded packets (don't send to Routing Engine)";
                   type empty;
                 }
                 container accounting {
                   description "Configure interface-based accounting options";
                   uses apply-advanced;
                   container source-class-usage {
                     description "Enable source class usage on this interface";
                     uses apply-advanced;
                     leaf input {
                       description "Specify this interface for source-class-usage input";
                       type empty;
                     }
                     leaf output {
                       description "Specify this interface for source-class-usage output";
                       type empty;
                     }
                   }
                   leaf destination-class-usage {
                     description "Enable destination class usage on this interface";
                     type empty;
                   }
                 }
                 leaf mac-validate {
                   description "Validate source MAC address";
                   type enumeration {
                     enum "strict" {
                       description "Strict mac-validation";
                     }
                     enum "loose" {
                       description "Loose mac-validation";
                     }
                   }
                 }
                 container rpf-check {
                   presence "enable rpf-check";
                   description "Enable reverse-path-forwarding checks on this interface";
                   uses apply-advanced;
                   leaf fail-filter {
                     description "Name of filter applied to packets failing RPF check";
                     type string;
                   }
                   container mode {
                     description "Mode for reverse path forwarding";
                     leaf loose {
                       description "Reverse-path-forwarding loose mode";
                       type empty;
                     }
                   }
                 }
                 leaf mtu {
                   description "Protocol family maximum transmission unit";
                   type union {
                     type uint32;
                     type string {
                       pattern "<.*>|$.*";
                     }
                   }
                 }
                 leaf arp-max-cache {
                   description "Max interface ARP nexthop cache size";
                   type union {
                     type string {
                       pattern "<.*>|$.*";
                     }
                     type uint32 {
                       range "1 .. 2000000";
                     }
                   }
                 }
                 leaf arp-new-hold-limit {
                   description "Max no. of new unresolved nexthops";
                   type union {
                     type string {
                       pattern "<.*>|$.*";
                     }
                     type uint32 {
                       range "1 .. 2000000";
                     }
                   }
                 }
                 leaf tcp-mss {
                   description "Protocol family tcp maximum segment size";
                   type union {
                     type string {
                       pattern "<.*>|$.*";
                     }
                     type uint32 {
                       range "1 .. 65535";
                     }
                   }
                 }
                 leaf no-redirects {
                   description "Do not redirect traffic";
                   type empty;
                 }
                 leaf no-neighbor-learn {
                   description "Disable neighbor address learning on interface";
                   type empty;
                 }
                 leaf unconditional-src-learn {
                   description "Glean from arp packets even when source cannot be validated";
                   type empty;
                 }
                 leaf multicast-only {
                   description "Allow only multicast traffic (tunnels only)";
                   type empty;
                 }
                 leaf primary {
                   description "Candidate for primary interface in system";
                   type empty;
                 }
                 leaf ipsec-sa {
                   description "Name of security association";
                   type string {
                     length "1 .. 32";
                   }
                 }
                 leaf allow-filter-on-re {
                   description "Enable kernel filter on network ports";
                   type empty;
                 }
                 list demux-source {
                   key name;
                   ordered-by user;
                   description "Demux based on source prefix";
                   leaf name {
                     type string;
                   }
                   uses apply-advanced;
                 }
                 list demux-destination {
                   key name;
                   ordered-by user;
                   description "Demux based on destination prefix";
                   leaf name {
                     type string;
                   }
                   uses apply-advanced;
                 }
                 container filter {
                   description "Packet filtering";
                   uses apply-advanced;
                   choice input_choice {
                     case case_1 {
                       container input {
                         description "Filter to be applied to received packets";
                         leaf filter-name {
                           description "Name of the filter";
                           type string;
                         }
                         leaf shared-name {
                           description "Filter shared-name of instances of interface-shared filter";
                           type string;
                         }
                         leaf precedence {
                           description "Precedence of the filter";
                           type union {
                             type string {
                               pattern "<.*>|$.*";
                             }
                             type uint32 {
                               range "0 .. 255";
                             }
                           }
                         }
                       }
                     }
                     case case_2 {
                       leaf-list input-list {
                         ordered-by user;
                         description "List of filter modules applied to received packets ";
                         type string;
                       }
                     }
                   }
                   leaf-list input-chain {
                     ordered-by user;
                     description "List of filter modules applied to received packets ";
                     type string;
                   }
                   leaf-list output-chain {
                     ordered-by user;
                     description "List of filter modules applied to transmitted packets ";
                     type string;
                   }
                   choice output_choice {
                     case case_1 {
                       container output {
                         description "Filter to be applied to transmitted packets";
                         leaf filter-name {
                           description "Name of the filter";
                           type string;
                         }
                         leaf shared-name {
                           description "Filter shared-name of instances of interface-shared filter";
                           type string;
                         }
                         leaf precedence {
                           description "Precedence of the filter";
                           type union {
                             type string {
                               pattern "<.*>|$.*";
                             }
                             type uint32 {
                               range "0 .. 255";
                             }
                           }
                         }
                       }
                     }
                     case case_2 {
                       leaf-list output-list {
                         ordered-by user;
                         description "List of filter modules applied to transmitted packets ";
                         type string;
                       }
                     }
                   }
                   container adf {
                     description "Ascend Data Filter definition";
                     uses apply-advanced;
                     list rule {
                       key name;
                       ordered-by user;
                       description "Set of ADF rules";
                       leaf name {
                         description "Value for a single rule";
                         type string;
                       }
                       uses apply-advanced;
                     }
                     leaf counter {
                       description "Add a counter to each rule";
                       type empty;
                     }
                     leaf input-precedence {
                       description "Precedence of the input rules";
                       type union {
                         type string {
                           pattern "<.*>|$.*";
                         }
                         type uint32 {
                           range "0 .. 255";
                         }
                       }
                     }
                     leaf not-mandatory {
                       description "No errors will be reported if no rules are present";
                       type empty;
                     }
                     leaf output-precedence {
                       description "Precedence of the output rules";
                       type union {
                         type string {
                           pattern "<.*>|$.*";
                         }
                         type uint32 {
                           range "0 .. 255";
                         }
                       }
                     }
                   }
                   leaf group {
                     description "Group to which interface belongs";
                     type union {
                       type string {
                         pattern "<.*>|$.*";
                       }
                       type uint32;
                     }
                   }
                   leaf dialer {
                     description "Name of filter applied on dialer";
                     type string;
                   }
                 }
                 container ingress-queuing-filter {
                   description "Protocol family ingress-queuing-filter";
                   leaf filter-name {
                     description "Name of the ingress-queuing-filter";
                     type string;
                   }
                 }
                 container iq-policing-filter {
                   description "Protocol family ingress-queuing-policing-filter";
                   leaf filter-name {
                     description "Name of the ingress-queuing-policing-filter";
                     type string;
                   }
                 }
                 container simple-filter {
                   description "Filter for doing multifield classification";
                   uses apply-advanced;
                   leaf input {
                     description "Name of simple filter applied to received packets";
                     type string;
                   }
                 }
                 leaf input-hierarchical-policer {
                   description "Hierarchical policer for received packets";
                   type string;
                 }
                 container policer {
                   description "Interface policing";
                   uses apply-advanced;
                   leaf disable-arp-policer {
                     description "Disable the arp policer for the interface";
                     type empty;
                   }
                   leaf arp {
                     description "Name of policer applied to received ARP packets";
                     type string;
                   }
                   leaf input {
                     description "Name of policer applied to received packets";
                     type string;
                   }
                   leaf output {
                     description "Name of policer applied to transmitted packets";
                     type string;
                   }
                 }
                 container sampling {
                   description "Interface sampling";
                   uses apply-advanced;
                   leaf input {
                     description "Sample all packets input on this interface";
                     type empty;
                   }
                   leaf output {
                     description "Sample all packets output on this interface";
                     type empty;
                   }
                 }
                 container service {
                   description "Service operations";
                   uses apply-advanced;
                   container input {
                     description "Service sets to consider for received packets";
                     uses apply-advanced;
                     list service-set {
                       key name;
                       ordered-by user;
                       description "Service set to consider for received packets";
                       leaf name {
                         description "Name of service set";
                         type string {
                         }
                       }
                       uses apply-advanced;
                       leaf service-filter {
                         description "Name of service filter";
                         type string;
                       }
                     }
                     leaf post-service-filter {
                       description "Post-service filter to apply to received packets";
                       type string;
                     }
                   }
                   container output {
                     description "Service sets to consider for transmitted packets";
                     uses apply-advanced;
                     list service-set {
                       key name;
                       ordered-by user;
                       description "Service set to consider for transmitted packets";
                       leaf name {
                         description "Name of service set";
                         type string {
                         }
                       }
                       uses apply-advanced;
                       leaf service-filter {
                         description "Name of service filter";
                         type string;
                       }
                     }
                   }
                 }
                 list next-hop-tunnel {
                   key name;
                   ordered-by user;
                   description "One or more next-hop tunnel tables";
                   leaf name {
                     description "Next-hop tunnel gateway address";
                     type string;
                   }
                   uses apply-advanced;
                   leaf ipsec-vpn {
                     description "Name of IPSec VPN";
                     type string;
                   }
                 }
                 choice tunnel-termination-status {
                   case case_1 {
                     leaf tunnel-termination {
                       description "Tunnel termination";
                       type empty;
                     }
                   }
                   case case_2 {
                     leaf no-tunnel-termination {
                       description "No Tunnel termination";
                       type empty;
                     }
                   }
                 }
                 leaf tunnel-loopback {
                   description "Allows tunnel packet processing on IRB underlay using the loopback path";
                   type empty;
                 }
                 list address {
                   key name;
                   ordered-by user;
                   description "Interface address/destination prefix";
                   leaf name {
                     description "Interface address/destination prefix";
                     type jt:ipv4prefix;
                   }
                   uses apply-advanced;
                   leaf destination {
                     description "Destination address";
                     type jt:ipv4addr;
                   }
                   leaf destination-profile {
                     description "Profile to use for destination address";
                     type string;
                   }
                   leaf broadcast {
                     description "Broadcast address";
                     type jt:ipv4addr;
                   }
                   leaf primary {
                     description "Candidate for primary address in system";
                     type empty;
                   }
                   leaf preferred {
                     description "Preferred address on interface";
                     type empty;
                   }
                   leaf master-only {
                     description "Master management IP address for router";
                     type empty;
                   }
                   list multipoint-destination {
                     key name;
                     ordered-by user;
                     description "Multipoint NBMA destination";
                     leaf name {
                       description "Destination address";
                       type jt:ipv4addr;
                     }
                     uses apply-advanced;
                     choice link-address {
                       case case_1 {
                         leaf dlci {
                           description "Frame Relay data-link control identifier";
                           type union {
                             type string {
                               pattern "<.*>|$.*";
                             }
                             type uint32 {
                               range "1 .. 1022";
                             }
                           }
                         }
                       }
                       case case_2 {
                         leaf vci {
                           description "ATM virtual circuit identifier ([vpi.]vci)";
                           type jt:atm-vci;
                         }
                       }
                     }
                     container shaping {
                       description "Virtual circuit traffic-shaping options";
                       uses dcd_shaping_config;
                     }
                     container oam-period {
                       description "OAM cell period";
                       choice oam_period_choices {
                         case case_1 {
                           leaf oam_period {
                             description "OAM cell period";
                             units "seconds";
                             type union {
                               type string {
                                 pattern "<.*>|$.*";
                               }
                               type uint32 {
                                 range "1 .. 900";
                               }
                             }
                           }
                         }
                         case case_2 {
                           container disable {
                             presence "enable disable";
                             description "Disable OAM loopback";
                           }
                         }
                       }
                     }
                     container oam-liveness {
                       description "OAM virtual circuit liveness parameters";
                       uses apply-advanced;
                       leaf up-count {
                         description "Number of OAM cells to consider VC up";
                         type union {
                           type string {
                             pattern "<.*>|$.*";
                           }
                           type uint32 {
                             range "1 .. 255";
                           }
                         }
                       }
                       leaf down-count {
                         description "Number of OAM cells to consider VC down";
                         type union {
                           type string {
                             pattern "<.*>|$.*";
                           }
                           type uint32 {
                             range "1 .. 255";
                           }
                         }
                       }
                     }
                     leaf inverse-arp {
                       description "Enable inverse ARP reply messages";
                       type empty;
                     }
                     leaf transmit-weight {
                       description "ATM2 transmit weight for VC under VP tunnel";
                       type union {
                         type string {
                           pattern "<.*>|$.*";
                         }
                         type uint16 {
                           range "1 .. 32767";
                         }
                       }
                     }
                     container epd-threshold {
                       description "Early packet discard threshold for ATM2";
                       uses epd_threshold_config;
                     }
                   }
                   list arp {
                     key name;
                     ordered-by user;
                     description "Static Address Resolution Protocol entries";
                     leaf name {
                       description "Destination IP address";
                       type jt:ipv4addr;
                     }
                     leaf l2-interface {
                       description "Layer 2 interface name for ARP entry";
                       type union {
                         type jt:interface-name;
                         type string {
                           pattern "<.*>|$.*";
                         }
                       }
                     }
                     choice mac_address_type {
                       case case_1 {
                         leaf mac {
                           description "MAC address";
                           type jt:mac-unicast;
                         }
                       }
                       case case_2 {
                         leaf multicast-mac {
                           description "Multicast MAC address";
                           type jt:mac-multicast;
                         }
                       }
                     }
                     leaf publish {
                       description "Reply to ARP requests for this entry";
                       type empty;
                     }
                     leaf flood-as-unknown-unicast {
                       description "Broadcast the packet with unicast MAC";
                       type empty;
                     }
                   }
                   list host-discovery {
                     key name;
                     ordered-by user;
                     description "Discover servers IP based on subnet range";
                     max-elements 8;
                     leaf name {
                       description "IP address subnet range";
                       type jt:ipv4prefix;
                     }
                     leaf aging-timer {
                       description "ARP aging timer";
                       type union {
                         type string {
                           pattern "<.*>|$.*";
                         }
                         type uint32 {
                           range "10 .. 1200";
                         }
                       }
                     }
                     leaf discovery-interval {
                       description "ARP proactive discovery time";
                       type union {
                         type string {
                           pattern "<.*>|$.*";
                         }
                         type uint32 {
                           range "3 .. 300";
                         }
                       }
                     }
                   }
                   container web-authentication {
                     description "Parameters for web-based firewall-user authentication";
                     uses apply-advanced;
                     leaf http {
                       description "Enable authentication via HTTP";
                       type empty;
                     }
                     leaf https {
                       description "Enable authentication via HTTPS";
                       type empty;
                     }
                     leaf redirect-to-https {
                       description "Web authentication redirect to HTTPS";
                       type empty;
                     }
                   }
                   list vrrp-group {
                     key name;
                     ordered-by user;
                     description "VRRP group";
                     uses vrrp-group;
                   }
                   leaf virtual-gateway-address {
                     description "Virtual Gateway IP address";
                     type jt:ipv4addr;
                   }
                 }
                 container unnumbered-address {
                   description "Unnumbered interface address/destination prefix";
                   leaf source {
                     description "Interface from which to take local address";
                     type union {
                       type jt:interface-unit;
                       type string {
                         pattern "<.*>|$.*";
                       }
                     }
                   }
                   leaf preferred-source-address {
                     description "Preferred address on the donor interface";
                     type string;
                   }
                   leaf destination {
                     description "Destination address";
                     type jt:ipv4addr;
                   }
                   leaf destination-profile {
                     description "Profile to use for destination address";
                     type string;
                   }
                 }
                 container location-pool-address {
                   presence "enable location-pool-address";
                   description "Location-based IP address pool";
                   uses apply-advanced;
                   leaf pool-name {
                     description "Pool name";
                     type string {
                       length "1 .. 64";
                     }
                   }
                 }
                 leaf negotiate-address {
                   description "Negotiate address with remote";
                   type empty;
                 }
                 leaf destination-udp-port {
                   description "Choose destination UDP port number";
                   type union {
                     type string {
                       pattern "<.*>|$.*";
                     }
                     type uint32 {
                       range "10000 .. 10009";
                     }
                   }
                 }
                 container auto-configure {
                   description "Auto configuration";
                   uses dynamic_ipv4_type;
                 }
                 leaf clear-dont-fragment-bit {
                   description "Clear DF bit in packet (AS PIC and J-series only as well as MIF)";
                   type empty;
                 }
               }
               container iso {
                 presence "enable iso";
                 description "OSI ISO protocol parameters";
                 uses apply-advanced;
                 list address {
                   key name;
                   ordered-by user;
                   description "Interface address";
                   leaf name {
                     description "Interface address";
                     type jt:isoaddr;
                   }
                   uses apply-advanced;
                 }
                 leaf mtu {
                   description "Protocol family maximum transmission unit";
                   type union {
                     type uint32;
                     type string {
                       pattern "<.*>|$.*";
                     }
                   }
                 }
                 leaf destination-udp-port {
                   description "Choose destination UDP port number";
                   type union {
                     type string {
                       pattern "<.*>|$.*";
                     }
                     type uint32 {
                       range "10030 .. 10039";
                     }
                   }
                 }
               }
               container inet6 {
                 presence "enable inet6";
                 description "IPv6 protocol parameters";
                 uses apply-advanced;
                 container dhcpv6-client {
                   description "Dynamic Host Configuration Protocol DHCPv6 client configuration";
                   uses apply-advanced;
                   leaf client-type {
                     description "DHCPv6 client type";
                     type enumeration {
                       enum "stateful" {
                         description "Stateful client type for address assignment.";
                       }
                       enum "autoconfig" {
                         description "Autoconfig  client type for router-advertisement";
                       }
                     }
                   }
                   list client-ia-type {
                     key name;
                     ordered-by user;
                     description "DHCPv6 client identity association type";
                     leaf name {
                       type enumeration {
                         enum "ia-na" {
                           description "Identity Association-Non-temporary Address";
                         }
                         enum "ia-pd" {
                           description "Identity Association-Prefix Address";
                         }
                       }
                     }
                     uses apply-advanced;
                   }
                   container rapid-commit {
                     presence "enable rapid-commit";
                     description "Option is used to signal the use of the two message exchange for address assignment";
                   }
                   leaf interface-identifier {
                     description "Identifier for this interface";
                     type jt:ipv6addr;
                   }
                   leaf use-ra-prefix {
                     description "Assign interface IP from RA prefix when ia-na address not received";
                     type empty;
                   }
                   container prefix-delegating {
                     description "Prefix delegating parameters";
                     uses apply-advanced;
                     leaf preferred-prefix-length {
                       description "Client preferred prefix length";
                       type union {
                         type string {
                           pattern "<.*>|$.*";
                         }
                         type uint32 {
                           range "0 .. 64";
                         }
                       }
                     }
                     leaf sub-prefix-length {
                       description "The sub prefix length for LAN interfaces";
                       type union {
                         type string {
                           pattern "<.*>|$.*";
                         }
                         type uint32 {
                           range "1 .. 127";
                         }
                       }
                     }
                   }
                   container client-identifier {
                     description "DHCP Server identifies a client by client-identifier value ";
                     leaf duid-type {
                       description "DUID identifying a client";
                       type enumeration {
                         enum "duid-llt" {
                           description "Link-layer address plus time";
                         }
                         enum "vendor" {
                           description "Vendor-assigned unique ID based on Enterprise Number";
                         }
                         enum "duid-ll" {
                           description "Link-layer address";
                         }
                       }
                     }
                   }
                   leaf vendor-id {
                     description "Vendor class id for the dhcpv6 client";
                     type string {
                       length "1 .. 60";
                     }
                   }
                   list req-option {
                     key name;
                     ordered-by user;
                     description "DHCPV6 client requested option configuration";
                     leaf name {
                       type enumeration {
                         enum "dns-server" {
                           description "Dns-server option";
                         }
                         enum "domain" {
                           description "Dns-server option";
                         }
                         enum "ntp-server" {
                           description "Ntp-server option";
                         }
                         enum "time-zone" {
                           description "Time-zone option";
                         }
                         enum "sip-server" {
                           description "Sip-server option";
                         }
                         enum "sip-domain" {
                           description "Sip-domain option";
                         }
                         enum "nis-server" {
                           description "Nis-server option";
                         }
                         enum "nis-domain" {
                           description "Nis-domain option";
                         }
                         enum "fqdn" {
                           description "Fully-qualified-domain option";
                         }
                         enum "vendor-spec" {
                           description "Vendor-spec option";
                         }
                         enum "zero-touch-redirect" {
                           description "Zero-touch-redirect";
                         }
                         enum "bootfile-url" {
                           description "Bootfile url";
                         }
                         enum "bootfile-param" {
                           description "Bootfile param";
                         }
                       }
                     }
                     uses apply-advanced;
                   }
                   container options {
                     description "DHCP options";
                     uses apply-advanced;
                     list number {
                       key name;
                       description "DHCP option code";
                       leaf name {
                         description "DHCP option identifier code";
                         type union {
                           type string {
                             pattern "<.*>|$.*";
                           }
                           type uint32 {
                             range "1 .. 254";
                           }
                         }
                       }
                       choice option-type-choice {
                         case case_1 {
                           leaf hex-string {
                             description "Hexadecimal string";
                             type string {
                               length "1 .. 510";
                             }
                           }
                         }
                       }
                     }
                   }
                   leaf retransmission-attempt {
                     description "Number of attempts to retransmit the DHCPV6 client protocol packet";
                     default "9";
                     type union {
                       type string {
                         pattern "<.*>|$.*";
                       }
                       type uint32 {
                         range "0 .. 50000";
                       }
                     }
                   }
                   container no-dns-install {
                     presence "enable no-dns-install";
                     description "Not propagate DNS to kernel";
                   }
                   container update-router-advertisement {
                     description "Dhcpv6 client update rpd for prefix delegation";
                     uses apply-advanced;
                     list interface {
                       key name;
                       ordered-by user;
                       description "Interfaces on which to delegate prefix";
                       max-elements 3;
                       leaf name {
                         description "Interfaces-name on which to delegate prefix";
                         type union {
                           type jt:interface-name;
                           type string {
                             pattern "<.*>|$.*";
                           }
                         }
                       }
                       uses apply-advanced;
                       leaf interface-identifier {
                         description "Identifier for this interface";
                         type jt:ipv6addr;
                       }
                       leaf prefix-identifier {
                         description "Prefix identifier for prefix used in this interface";
                         type jt:ipv6addr;
                       }
                       choice managed-configuration-choice {
                         leaf managed-configuration {
                           description "Set managed address configuration";
                           type empty;
                         }
                         leaf no-managed-configuration {
                           description "Don't set managed address configuration";
                           type empty;
                         }
                       }
                       choice other-stateful-configuration-choice {
                         leaf other-stateful-configuration {
                           description "Set other stateful configuration";
                           type empty;
                         }
                         leaf no-other-stateful-configuration {
                           description "Don't set other stateful configuration";
                           type empty;
                         }
                       }
                       leaf max-advertisement-interval {
                         description "Maximum advertisement interval";
                         units "seconds";
                         type union {
                           type string {
                             pattern "<.*>|$.*";
                           }
                           type uint32 {
                             range "4 .. 1800";
                           }
                         }
                       }
                       leaf min-advertisement-interval {
                         description "Minimum advertisement interval";
                         units "seconds";
                         type union {
                           type string {
                             pattern "<.*>|$.*";
                           }
                           type uint32 {
                             range "3 .. 1350";
                           }
                         }
                       }
                       choice enable-recursive-dns-server-option-choice {
                         leaf enable-recursive-dns-server-option {
                           description "Enables the recursive DNS server option";
                           type empty;
                         }
                         leaf no-enable-recursive-dns-server-option {
                           description "Don't enables the recursive DNS server option";
                           type empty;
                         }
                       }
                     }
                   }
                   leaf update-server {
                     description "Propagate TCP/IP settings to DHCP server";
                     type empty;
                   }
                 }
                 container rpf-check {
                   presence "enable rpf-check";
                   description "Enable reverse-path-forwarding checks on this interface";
                   uses apply-advanced;
                   leaf fail-filter {
                     description "Name of filter applied to packets failing RPF check";
                     type string;
                   }
                   container mode {
                     description "Mode for reverse path forwarding";
                     leaf loose {
                       description "Reverse-path-forwarding loose mode";
                       type empty;
                     }
                   }
                 }
                 container accounting {
                   description "Interface-based accounting options";
                   uses apply-advanced;
                   container source-class-usage {
                     uses apply-advanced;
                     leaf input {
                       description "Interface for source-class-usage input";
                       type empty;
                     }
                     leaf output {
                       description "Interface for source-class-usage output";
                       type empty;
                     }
                   }
                   leaf destination-class-usage {
                     description "Enable destination class usage on this interface";
                     type empty;
                   }
                 }
                 leaf mtu {
                   description "Protocol family maximum transmission unit";
                   type union {
                     type uint32;
                     type string {
                       pattern "<.*>|$.*";
                     }
                   }
                 }
                 leaf tcp-mss {
                   description "Protocol family tcp maximum segment size";
                   type union {
                     type string {
                       pattern "<.*>|$.*";
                     }
                     type uint32 {
                       range "1 .. 65535";
                     }
                   }
                 }
                 leaf nd6-stale-time {
                   description "Stale time to reconfirm reachability with inet6 neighbour";
                   units "seconds";
                   type union {
                     type string {
                       pattern "<.*>|$.*";
                     }
                     type uint32 {
                       range "1 .. 18000";
                     }
                   }
                 }
                 leaf no-neighbor-learn {
                   description "Disable neighbor address learning on interface";
                   type empty;
                 }
                 leaf slaac-enable {
                   description "Enable slaac on management interface";
                   type empty;
                 }
                 container ndp-proxy {
                   description "Enable ndp proxy on interface";
                   uses apply-advanced;
                   leaf interface-restricted {
                     description "Enable ndp interface proxy restricted to interface";
                     type empty;
                   }
                   leaf interface-unrestricted {
                     description "Enable ndp interface proxy unrestricted to interface";
                     type empty;
                   }
                 }
                 container dad-proxy {
                   description "DAD proxy on interface";
                   uses apply-advanced;
                   leaf interface-restricted {
                     description "Enable DAD interface proxy restricted to interface";
                     type empty;
                   }
                   leaf interface-unrestricted {
                     description "Enable DAD interface proxy unrestricted to interface";
                     type empty;
                   }
                 }
                 leaf nd6-max-cache {
                   description "Max interface ND nexthop cache size";
                   type union {
                     type string {
                       pattern "<.*>|$.*";
                     }
                     type uint32 {
                       range "1 .. 2000000";
                     }
                   }
                 }
                 leaf nd6-new-hold-limit {
                   description "Max no. of new unresolved nexthops";
                   type union {
                     type string {
                       pattern "<.*>|$.*";
                     }
                     type uint32 {
                       range "1 .. 2000000";
                     }
                   }
                 }
                 leaf no-redirects {
                   description "Do not redirect traffic";
                   type empty;
                 }
                 leaf allow-filter-on-re {
                   description "Enable kernel filter on network ports";
                   type empty;
                 }
                 container filter {
                   description "Packet filtering";
                   uses apply-advanced;
                   choice input_choice {
                     case case_1 {
                       container input {
                         description "Filter to be applied to received packets";
                         leaf filter-name {
                           description "Name of the filter";
                           type string;
                         }
                         leaf shared-name {
                           description "Filter shared-name of instances of interface-shared filter";
                           type string;
                         }
                         leaf precedence {
                           description "Precedence of the filter";
                           type union {
                             type string {
                               pattern "<.*>|$.*";
                             }
                             type uint32 {
                               range "0 .. 255";
                             }
                           }
                         }
                       }
                     }
                     case case_2 {
                       leaf-list input-list {
                         ordered-by user;
                         description "List of filter modules applied to received packets ";
                         type string;
                       }
                     }
                   }
                   choice output_choice {
                     case case_1 {
                       container output {
                         description "Filter to be applied to transmitted packets";
                         leaf filter-name {
                           description "Name of the filter";
                           type string;
                         }
                         leaf shared-name {
                           description "Filter shared-name of instances of interface-shared filter";
                           type string;
                         }
                         leaf precedence {
                           description "Precedence of the filter";
                           type union {
                             type string {
                               pattern "<.*>|$.*";
                             }
                             type uint32 {
                               range "0 .. 255";
                             }
                           }
                         }
                       }
                     }
                     case case_2 {
                       leaf-list output-list {
                         ordered-by user;
                         description "List of filter modules applied to transmitted packets ";
                         type string;
                       }
                     }
                   }
                   leaf-list input-chain {
                     ordered-by user;
                     description "List of filter modules applied to received packets ";
                     type string;
                   }
                   leaf-list output-chain {
                     ordered-by user;
                     description "List of filter modules applied to transmitted packets ";
                     type string;
                   }
                   container adf {
                     description "Ascend Data Filter definition";
                     uses apply-advanced;
                     list rule {
                       key name;
                       ordered-by user;
                       description "Set of ADF rules";
                       leaf name {
                         description "Value for a single rule";
                         type string;
                       }
                       uses apply-advanced;
                     }
                     leaf counter {
                       description "Add a counter to each rule";
                       type empty;
                     }
                     leaf input-precedence {
                       description "Precedence of the input rules";
                       type union {
                         type string {
                           pattern "<.*>|$.*";
                         }
                         type uint32 {
                           range "0 .. 255";
                         }
                       }
                     }
                     leaf not-mandatory {
                       description "No errors will be reported if no rules are present";
                       type empty;
                     }
                     leaf output-precedence {
                       description "Precedence of the output rules";
                       type union {
                         type string {
                           pattern "<.*>|$.*";
                         }
                         type uint32 {
                           range "0 .. 255";
                         }
                       }
                     }
                   }
                   leaf group {
                     description "Group to which interface belongs";
                     type union {
                       type string {
                         pattern "<.*>|$.*";
                       }
                       type uint32;
                     }
                   }
                   leaf dialer {
                     description "Name of filter applied on dialer";
                     type string;
                   }
                 }
                 container ingress-queuing-filter {
                   description "Protocol family ingress-queuing-filter";
                   leaf filter-name {
                     description "Name of the ingress-queuing-filter";
                     type string;
                   }
                 }
                 leaf input-hierarchical-policer {
                   description "Hierarchical policer for received packets";
                   type string;
                 }
                 container policer {
                   description "Interface policing";
                   uses apply-advanced;
                   leaf input {
                     description "Name of policer applied to received packets";
                     type string;
                   }
                   leaf output {
                     description "Name of policer applied to transmitted packets";
                     type string;
                   }
                 }
                 container sampling {
                   description "Interface sampling";
                   uses apply-advanced;
                   leaf input {
                     description "Sample all packets input on this interface";
                     type empty;
                   }
                   leaf output {
                     description "Sample all packets output on this interface";
                     type empty;
                   }
                 }
                 container service {
                   description "Service operations";
                   uses apply-advanced;
                   container input {
                     description "Service sets to consider for received packets";
                     uses apply-advanced;
                     list service-set {
                       key name;
                       ordered-by user;
                       description "Service set to consider for received packets";
                       leaf name {
                         description "Name of service set";
                         type string {
                         }
                       }
                       uses apply-advanced;
                       leaf service-filter {
                         description "Name of service filter";
                         type string;
                       }
                     }
                     leaf post-service-filter {
                       description "Post-service filter to apply to received packets";
                       type string;
                     }
                   }
                   container output {
                     description "Service sets to consider for transmitted packets";
                     uses apply-advanced;
                     list service-set {
                       key name;
                       ordered-by user;
                       description "Service set to consider for transmitted packets";
                       leaf name {
                         description "Name of service set";
                         type string {
                         }
                       }
                       uses apply-advanced;
                       leaf service-filter {
                         description "Name of service filter";
                         type string;
                       }
                     }
                   }
                 }
                 choice tunnel-termination-status {
                   case case_1 {
                     leaf tunnel-termination {
                       description "Tunnel termination";
                       type empty;
                     }
                   }
                   case case_2 {
                     leaf no-tunnel-termination {
                       description "No Tunnel termination";
                       type empty;
                     }
                   }
                 }
                 list address {
                   key name;
                   ordered-by user;
                   description "Interface address or destination prefix";
                   leaf name {
                     description "Interface address or destination prefix";
                     type jt:ipv6prefix;
                   }
                   uses apply-advanced;
                   leaf destination {
                     description "Destination address";
                     type jt:ipv6addr;
                   }
                   leaf eui-64 {
                     description "Generate EUI-64 interface ID";
                     type empty;
                   }
                   leaf primary {
                     description "Candidate for primary address in system";
                     type empty;
                   }
                   leaf preferred {
                     description "Preferred address on interface";
                     type empty;
                   }
                   leaf master-only {
                     description "Master management IP address for router";
                     type empty;
                   }
                   list ndp {
                     key name;
                     ordered-by user;
                     description "Static Neighbor Discovery Protocol  entries";
                     leaf name {
                       description "Destination IP address";
                       type jt:ipv6addr;
                     }
                     leaf l2-interface {
                       description "Layer 2 interface name for NDP entry";
                       type union {
                         type jt:interface-name;
                         type string {
                           pattern "<.*>|$.*";
                         }
                       }
                     }
                     choice mac_address_type {
                       case case_1 {
                         leaf mac {
                           description "MAC address";
                           type jt:mac-unicast;
                         }
                       }
                       case case_2 {
                         leaf multicast-mac {
                           description "Multicast MAC address";
                           type jt:mac-multicast;
                         }
                       }
                     }
                     leaf publish {
                       description "Reply to NDP requests for this entry";
                       type empty;
                     }
                   }
                   list vrrp-inet6-group {
                     key name;
                     ordered-by user;
                     description "VRRP group";
                     uses vrrp-group;
                   }
                   container web-authentication {
                     description "Parameters for web-based firewall-user authentication";
                     uses apply-advanced;
                     leaf http {
                       description "Enable authentication via HTTP";
                       type empty;
                     }
                     leaf https {
                       description "Enable authentication via HTTPS";
                       type empty;
                     }
                     leaf redirect-to-https {
                       description "Web authentication redirect to HTTPS";
                       type empty;
                     }
                   }
                   leaf virtual-gateway-address {
                     description "Virtual Gateway IP address";
                     type jt:ipv6addr;
                   }
                   leaf subnet-router-anycast {
                     description "Create a subnet roter anycast address for this address.";
                     type empty;
                   }
                 }
                 list demux-source {
                   key name;
                   ordered-by user;
                   description "Demux based on source prefix";
                   leaf name {
                     type string;
                   }
                   uses apply-advanced;
                 }
                 list demux-destination {
                   key name;
                   ordered-by user;
                   description "Demux based on destination prefix";
                   leaf name {
                     type string;
                   }
                   uses apply-advanced;
                 }
                 container unnumbered-address {
                   description "Unnumbered interface address/destination prefix";
                   leaf source {
                     description "Interface from which to take local address";
                     type union {
                       type jt:interface-unit;
                       type string {
                         pattern "<.*>|$.*";
                       }
                     }
                   }
                   leaf preferred-source-address {
                     description "Preferred address on the donor interface";
                     type string;
                   }
                 }
                 choice dad-disable-choice {
                   leaf dad-disable {
                     description "Disable duplicate-address-detection";
                     type empty;
                   }
                   leaf no-dad-disable {
                     description "Don't disable duplicate-address-detection";
                     type empty;
                   }
                 }
                 leaf destination-udp-port {
                   description "Choose destination UDP port number";
                   type union {
                     type string {
                       pattern "<.*>|$.*";
                     }
                     type uint32 {
                       range "10010 .. 10019";
                     }
                   }
                 }
                 container auto-configure {
                   description "Auto configuration";
                   uses dynamic_ipv6_type;
                 }
                 leaf negotiate-address {
                   description "Negotiate address with remote";
                   type empty;
                 }
               }
               container mpls {
                 presence "enable mpls";
                 description "MPLS protocol parameters";
                 uses apply-advanced;
                 leaf mtu {
                   description "Protocol family maximum transmission unit";
                   type union {
                     type uint32;
                     type string {
                       pattern "<.*>|$.*";
                     }
                   }
                 }
                 leaf maximum-labels {
                   description "Protocol family maximum number of labels";
                   type union {
                     type string {
                       pattern "<.*>|$.*";
                     }
                     type uint32;
                   }
                 }
                 container filter {
                   description "Packet filtering";
                   uses apply-advanced;
                   choice input_choice {
                     case case_1 {
                       leaf input {
                         description "Name of filter applied to received packets";
                         type string;
                       }
                     }
                     case case_2 {
                       leaf-list input-list {
                         ordered-by user;
                         description "List of filter modules applied to received packets ";
                         type string;
                       }
                     }
                   }
                   leaf-list input-chain {
                     ordered-by user;
                     description "List of filter modules applied to received packets ";
                     type string;
                   }
                   choice output_choice {
                     case case_1 {
                       leaf output {
                         description "Name of filter applied to transmitted packets";
                         type string;
                       }
                     }
                     case case_2 {
                       leaf-list output-list {
                         ordered-by user;
                         description "List of filter modules applied to transmitted packets ";
                         type string;
                       }
                     }
                   }
                   leaf-list output-chain {
                     ordered-by user;
                     description "List of filter modules applied to transmitted packets ";
                     type string;
                   }
                   leaf group {
                     description "Interface group to which interface belongs";
                     type union {
                       type string {
                         pattern "<.*>|$.*";
                       }
                       type uint32 {
                         range "1 .. 255";
                       }
                     }
                   }
                   leaf dialer {
                     description "Name of filter applied on dialer";
                     type string;
                   }
                 }
                 container ingress-queuing-filter {
                   description "Protocol family ingress-queuing-filter";
                   leaf filter-name {
                     description "Name of the ingress-queuing-filter";
                     type string;
                   }
                 }
                 leaf input-hierarchical-policer {
                   description "Hierarchical policer for received packets";
                   type string;
                 }
                 container policer {
                   description "Interface policing";
                   uses apply-advanced;
                   leaf input {
                     description "Name of policer applied to received packets";
                     type string;
                   }
                   leaf output {
                     description "Name of policer applied to transmitted packets";
                     type string;
                   }
                 }
                 leaf destination-udp-port {
                   description "Choose destination UDP port number";
                   type union {
                     type string {
                       pattern "<.*>|$.*";
                     }
                     type uint32 {
                       range "10020 .. 10029";
                     }
                   }
                 }
               }
               container mlppp {
                 description "Multilink PPP protocol parameters";
                 uses apply-advanced;
                 leaf bundle {
                   description "Logical interface name this link will join";
                   type string;
                 }
                 choice anchor-points {
                   case case_1 {
                     leaf service-interface {
                       description "Services interface to use";
                       type union {
                         type jt:interface-device;
                         type string {
                           pattern "<.*>|$.*";
                         }
                       }
                     }
                   }
                   case case_2 {
                     leaf service-device-pool {
                       description "Service interface pool name to use";
                       type string {
                         length "1 .. 63";
                       }
                     }
                   }
                 }
                 leaf dynamic-profile {
                   description " dynamic profile for interface to use";
                   type string {
                     length "1 .. 80";
                   }
                 }
               }
               container mlfr-end-to-end {
                 presence "enable mlfr-end-to-end";
                 description "Multilink Frame Relay end-to-end protocol parameters";
                 uses apply-advanced;
                 leaf bundle {
                   description "Logical interface name this link will join";
                   type union {
                     type jt:interface-unit;
                     type string {
                       pattern "<.*>|$.*";
                     }
                   }
                 }
               }
               container mlfr-uni-nni {
                 presence "enable mlfr-uni-nni";
                 description "Multilink Frame Relay UNI NNI protocol parameters";
                 uses apply-advanced;
                 leaf bundle {
                   description "Logical interface name this link will join";
                   type union {
                     type jt:interface-unit;
                     type string {
                       pattern "<.*>|$.*";
                     }
                   }
                 }
               }
               container ccc {
                 presence "enable ccc";
                 description "Circuit cross-connect parameters";
                 uses apply-advanced;
                 leaf mtu {
                   description "Protocol family maximum transmission unit";
                   type union {
                     type uint32;
                     type string {
                       pattern "<.*>|$.*";
                     }
                   }
                 }
                 container filter {
                   description "Packet filtering";
                   uses apply-advanced;
                   choice input_choice {
                     case case_1 {
                       leaf input {
                         description "Name of filter applied to received packets";
                         type string;
                       }
                     }
                     case case_2 {
                       leaf-list input-list {
                         ordered-by user;
                         description "List of filter modules applied to received packets ";
                         type string;
                       }
                     }
                   }
                   leaf-list input-chain {
                     ordered-by user;
                     description "List of filter modules applied to received packets ";
                     type string;
                   }
                   choice output_choice {
                     case case_1 {
                       leaf output {
                         description "Name of filter applied to transmitted packets";
                         type string;
                       }
                     }
                     case case_2 {
                       leaf-list output-list {
                         ordered-by user;
                         description "List of filter modules applied to transmitted packets ";
                         type string;
                       }
                     }
                   }
                   leaf-list output-chain {
                     ordered-by user;
                     description "List of filter modules applied to transmitted packets ";
                     type string;
                   }
                   leaf group {
                     description "Interface group to which interface belongs";
                     type union {
                       type string {
                         pattern "<.*>|$.*";
                       }
                       type uint32 {
                         range "1 .. 255";
                       }
                     }
                   }
                 }
                 container ingress-queuing-filter {
                   description "Protocol family ingress-queuing-filter";
                   leaf filter-name {
                     description "Name of the ingress-queuing-filter";
                     type string;
                   }
                 }
                 container policer {
                   description "Interface policing";
                   uses apply-advanced;
                   leaf input {
                     description "Name of policer applied to received packets";
                     type string;
                   }
                   leaf output {
                     description "Name of policer applied to transmitted packets";
                     type string;
                   }
                 }
                 leaf translate-fecn-and-becn {
                   description "Translate FECN and BECN bits";
                   type empty;
                 }
                 choice de-or-plp {
                   case case_1 {
                     leaf translate-discard-eligible {
                       description "Translate DE bit";
                       type empty;
                     }
                   }
                   case case_2 {
                     leaf translate-plp-control-word-de {
                       description "Translate PLP to/from Martini Control DE bit";
                       type empty;
                     }
                   }
                 }
                 leaf keep-address-and-control {
                   description "Don't strip PPP address and control bytes";
                   type empty;
                 }
               }
               container tcc {
                 presence "enable tcc";
                 description "Translational cross-connect parameters";
                 uses apply-advanced;
                 container policer {
                   description "Interface policing";
                   uses apply-advanced;
                   leaf input {
                     description "Name of policer applied to received packets";
                     type string;
                   }
                   leaf output {
                     description "Name of policer applied to transmitted packets";
                     type string;
                   }
                 }
                 container proxy {
                   presence "enable proxy";
                   uses apply-advanced;
                   leaf inet-address {
                     description "Remote host address on non-Ethernet side of Ethernet TCC";
                     type jt:ipv4addr;
                   }
                 }
                 container remote {
                   presence "enable remote";
                   uses apply-advanced;
                   leaf inet-address {
                     description "Remote host address on Ethernet side of Ethernet TCC";
                     type jt:ipv4addr;
                   }
                   leaf mac-address {
                     description "Remote host MAC address on Ethernet side of Ethernet TCC";
                     type jt:mac-addr;
                   }
                 }
                 leaf-list protocols {
                   ordered-by user;
                   description "Protocols supported on TCC interface";
                   type enumeration {
                     enum "mpls" {
                       description "Multiprotocol Label Switching";
                     }
                     enum "inet" {
                       description "IP version 4";
                     }
                     enum "iso" {
                       description "International Organization for Standardization";
                     }
                     enum "inet6" {
                       description "IP version 6";
                     }
                   }
                 }
               }
               container vpls {
                 presence "enable vpls";
                 description "Virtual private LAN service parameters";
                 uses apply-advanced;
                 leaf core-facing {
                   description "Interface is core facing";
                   type empty;
                 }
                 container filter {
                   description "Packet filtering";
                   uses apply-advanced;
                   choice input_choice {
                     case case_1 {
                       container input {
                         description "Filter to be applied to received packets";
                         leaf filter-name {
                           description "Name of the filter";
                           type string;
                         }
                         leaf shared-name {
                           description "Filter shared-name of instances of interface-shared filter";
                           type string;
                         }
                         leaf precedence {
                           description "Precedence of the filter";
                           type union {
                             type string {
                               pattern "<.*>|$.*";
                             }
                             type uint32 {
                               range "0 .. 255";
                             }
                           }
                         }
                       }
                     }
                     case case_2 {
                       leaf-list input-list {
                         ordered-by user;
                         description "List of filter modules applied to received packets ";
                         type string;
                       }
                     }
                   }
                   leaf-list input-chain {
                     ordered-by user;
                     description "List of filter modules applied to received packets ";
                     type string;
                   }
                   leaf-list output-chain {
                     ordered-by user;
                     description "List of filter modules applied to transmitted packets ";
                     type string;
                   }
                   choice output_choice {
                     case case_1 {
                       container output {
                         description "Filter to be applied to transmitted packets";
                         leaf filter-name {
                           description "Name of the filter";
                           type string;
                         }
                         leaf shared-name {
                           description "Filter shared-name of instances of interface-shared filter";
                           type string;
                         }
                         leaf precedence {
                           description "Precedence of the filter";
                           type union {
                             type string {
                               pattern "<.*>|$.*";
                             }
                             type uint32 {
                               range "0 .. 255";
                             }
                           }
                         }
                       }
                     }
                     case case_2 {
                       leaf-list output-list {
                         ordered-by user;
                         description "List of filter modules applied to transmitted packets ";
                         type string;
                       }
                     }
                   }
                   container adf {
                     description "Ascend Data Filter definition";
                     uses apply-advanced;
                     list rule {
                       key name;
                       ordered-by user;
                       description "Set of ADF rules";
                       leaf name {
                         description "Value for a single rule";
                         type string;
                       }
                       uses apply-advanced;
                     }
                     leaf counter {
                       description "Add a counter to each rule";
                       type empty;
                     }
                     leaf input-precedence {
                       description "Precedence of the input rules";
                       type union {
                         type string {
                           pattern "<.*>|$.*";
                         }
                         type uint32 {
                           range "0 .. 255";
                         }
                       }
                     }
                     leaf not-mandatory {
                       description "No errors will be reported if no rules are present";
                       type empty;
                     }
                     leaf output-precedence {
                       description "Precedence of the output rules";
                       type union {
                         type string {
                           pattern "<.*>|$.*";
                         }
                         type uint32 {
                           range "0 .. 255";
                         }
                       }
                     }
                   }
                   leaf group {
                     description "Group to which interface belongs";
                     type union {
                       type string {
                         pattern "<.*>|$.*";
                       }
                       type uint32 {
                         range "1 .. 255";
                       }
                     }
                   }
                 }
                 container ingress-queuing-filter {
                   description "Protocol family ingress-queuing-filter";
                   leaf filter-name {
                     description "Name of the ingress-queuing-filter";
                     type string;
                   }
                 }
                 container iq-policing-filter {
                   description "Protocol family ingress-queuing-policing-filter";
                   leaf filter-name {
                     description "Name of the ingress-queuing-policing-filter";
                     type string;
                   }
                 }
                 container policer {
                   description "Interface policing";
                   uses apply-advanced;
                   leaf input {
                     description "Name of policer applied to received packets";
                     type string;
                   }
                   leaf output {
                     description "Name of policer applied to transmitted packets";
                     type string;
                   }
                 }
                 container sampling {
                   description "Interface sampling";
                   uses apply-advanced;
                   leaf input {
                     description "Sample all packets input on this interface";
                     type empty;
                   }
                   leaf output {
                     description "Sample all packets output on this interface";
                     type empty;
                   }
                 }
               }
               container bridge {
                 presence "enable bridge";
                 description "Layer-2 bridging parameters";
                 uses apply-advanced;
                 leaf core-facing {
                   description "Interface is core facing";
                   type empty;
                 }
                 container filter {
                   description "Packet filtering";
                   uses apply-advanced;
                   choice input_choice {
                     case case_1 {
                       container input {
                         description "Filter to be applied to received packets";
                         leaf filter-name {
                           description "Name of the filter";
                           type string;
                         }
                         leaf shared-name {
                           description "Filter shared-name of instances of interface-shared filter";
                           type string;
                         }
                         leaf precedence {
                           description "Precedence of the filter";
                           type union {
                             type string {
                               pattern "<.*>|$.*";
                             }
                             type uint32 {
                               range "0 .. 255";
                             }
                           }
                         }
                       }
                     }
                     case case_2 {
                       leaf-list input-list {
                         ordered-by user;
                         description "List of filter modules applied to received packets ";
                         type string;
                       }
                     }
                   }
                   leaf-list input-chain {
                     ordered-by user;
                     description "List of filter modules applied to received packets ";
                     type string;
                   }
                   leaf-list output-chain {
                     ordered-by user;
                     description "List of filter modules applied to transmitted packets ";
                     type string;
                   }
                   choice output_choice {
                     case case_1 {
                       container output {
                         description "Filter to be applied to transmitted packets";
                         leaf filter-name {
                           description "Name of the filter";
                           type string;
                         }
                         leaf shared-name {
                           description "Filter shared-name of instances of interface-shared filter";
                           type string;
                         }
                         leaf precedence {
                           description "Precedence of the filter";
                           type union {
                             type string {
                               pattern "<.*>|$.*";
                             }
                             type uint32 {
                               range "0 .. 255";
                             }
                           }
                         }
                       }
                     }
                     case case_2 {
                       leaf-list output-list {
                         ordered-by user;
                         description "List of filter modules applied to transmitted packets ";
                         type string;
                       }
                     }
                   }
                   container adf {
                     description "Ascend Data Filter definition";
                     uses apply-advanced;
                     list rule {
                       key name;
                       ordered-by user;
                       description "Set of ADF rules";
                       leaf name {
                         description "Value for a single rule";
                         type string;
                       }
                       uses apply-advanced;
                     }
                     leaf counter {
                       description "Add a counter to each rule";
                       type empty;
                     }
                     leaf input-precedence {
                       description "Precedence of the input rules";
                       type union {
                         type string {
                           pattern "<.*>|$.*";
                         }
                         type uint32 {
                           range "0 .. 255";
                         }
                       }
                     }
                     leaf not-mandatory {
                       description "No errors will be reported if no rules are present";
                       type empty;
                     }
                     leaf output-precedence {
                       description "Precedence of the output rules";
                       type union {
                         type string {
                           pattern "<.*>|$.*";
                         }
                         type uint32 {
                           range "0 .. 255";
                         }
                       }
                     }
                   }
                   leaf group {
                     description "Group to which interface belongs";
                     type union {
                       type string {
                         pattern "<.*>|$.*";
                       }
                       type uint32 {
                         range "1 .. 255";
                       }
                     }
                   }
                 }
                 container ingress-queuing-filter {
                   description "Protocol family ingress-queuing-filter";
                   leaf filter-name {
                     description "Name of the ingress-queuing-filter";
                     type string;
                   }
                 }
                 container iq-policing-filter {
                   description "Protocol family ingress-queuing-policing-filter";
                   leaf filter-name {
                     description "Name of the ingress-queuing-policing-filter";
                     type string;
                   }
                 }
                 container policer {
                   description "Interface policing";
                   uses apply-advanced;
                   leaf input {
                     description "Name of policer applied to received packets";
                     type string;
                   }
                   leaf output {
                     description "Name of policer applied to transmitted packets";
                     type string;
                   }
                 }
                 leaf interface-mode {
                   description "Interface mode (access or trunk)";
                   type enumeration {
                     enum "access" {
                       description "Interface mode is access";
                     }
                     enum "trunk" {
                       description "Interface mode is trunk";
                     }
                   }
                 }
                 leaf vlan-auto-sense {
                   description "Enable VLAN auto sense on this interface";
                   type empty;
                 }
                 leaf bridge-domain-type {
                   description "Bridge domain type (svlan or bvlan)";
                   type enumeration {
                     enum "svlan" {
                       description "Bridge domain type svlan";
                     }
                     enum "bvlan" {
                       description "Bridge domain type bvlan";
                     }
                   }
                 }
                 leaf inter-switch-link {
                   description "PVLAN inter switch link";
                   type empty;
                 }
                 choice vlan_list {
                   case case_1 {
                     leaf vlan-id {
                       description "Access mode and trunk mode VLAN membership";
                       type union {
                         type string {
                           pattern "<.*>|$.*";
                         }
                         type uint32 {
                           range "1 .. 4094";
                         }
                       }
                     }
                   }
                   case case_2 {
                     leaf-list vlan-id-list {
                       description "Trunk mode VLAN membership for this interface";
                       type jt:vlan-range;
                     }
                   }
                   case case_3 {
                     leaf-list inner-vlan-id-list {
                       description "Trunk mode VLAN membership for this interface based on inner VLAN tag";
                       type jt:vlan-range;
                     }
                   }
                 }
                 container vlan-rewrite {
                   description "Specify vlan translation";
                   uses apply-advanced;
                   list translate {
                     key name;
                     ordered-by user;
                     description "Translate incoming VLAN tag";
                     leaf name {
                       description "Specify the incoming VLAN tag";
                       type union {
                         type string {
                           pattern "<.*>|$.*";
                         }
                         type uint32 {
                           range "1 .. 4094";
                         }
                       }
                     }
                     leaf to-vlan-id {
                       description "Specify the bridge-domain VLAN-ID";
                       type union {
                         type string {
                           pattern "<.*>|$.*";
                         }
                         type uint32 {
                           range "1 .. 4094";
                         }
                       }
                     }
                   }
                 }
                 choice isid_list {
                   case case_1 {
                     leaf isid-list {
                       description "Specify the ISID list";
                       type enumeration {
                         enum "all-service-groups" {
                           description "Map all ISIDs specified under the service-groups";
                         }
                         enum "all" {
                           description "Map all ISIDs";
                         }
                       }
                     }
                   }
                 }
                 container storm-control {
                   description "Storm control profile name to bind";
                   uses apply-advanced;
                   leaf profile-name {
                     description "Profile name";
                     type string;
                   }
                 }
                 container recovery-timeout {
                   description "Recovery timeout for this interface";
                   leaf time-in-seconds {
                     units "seconds";
                     type union {
                       type string {
                         pattern "<.*>|$.*";
                       }
                       type uint32 {
                         range "10 .. 3600";
                       }
                     }
                   }
                 }
                 container sampling {
                   description "Interface sampling";
                   uses apply-advanced;
                   leaf input {
                     description "Sample all packets input on this interface";
                     type empty;
                   }
                   leaf output {
                     description "Sample all packets output on this interface";
                     type empty;
                   }
                 }
               }
               container ethernet-switching {
                 description "Ethernet switching parameters";
                 presence "enable ethernet-switching";
                 uses ethernet-switching-type;
               }
               container fibre-channel {
                 description "Fibre channel switching parameters";
                 presence "enable fibre-channel";
                 uses fibre-channel-type;
               }
               container pppoe {
                 description "PPP over Ethernet underlying interface-specific options";
                 presence "enable pppoe";
                 uses pppoe_underlying_options_type;
               }
               container any {
                 presence "enable any";
                 description "Parameters for 'any' family";
                 uses apply-advanced;
                 container filter {
                   description "Layer 2 packet filtering";
                   uses apply-advanced;
                   leaf input {
                     description "Name of filter applied to received packets";
                     type string {
                     }
                   }
                   leaf group {
                     description "Group to which interface belongs";
                     type union {
                       type string {
                         pattern "<.*>|$.*";
                       }
                       type uint32 {
                         range "1 .. 255";
                       }
                     }
                   }
                 }
               }
               uses apply-advanced;
             }
             leaf service-domain {
               description "Service domain to which interface belongs";
               type enumeration {
                 enum "inside" {
                   description "Inside network";
                 }
                 enum "outside" {
                   description "Outside network";
                 }
               }
             }
             leaf copy-tos-to-outer-ip-header {
               description "Copy IP payload header's ToS field to GRE delivery header";
               type empty;
             }
             leaf copy-tos-to-outer-ip-header-transit {
               description "Copy IP ToS field to GRE header for transit packets";
               type empty;
             }
             leaf force-control-packets-on-transit-path {
               description "Force control packets to follow transit path";
               type empty;
             }
             container load-balancing-options {
               description "AMS subunit load balancing options";
               uses apply-advanced;
               leaf preferred-active {
                 description "Preferred active Interface name";
                 type union {
                   type jt:interface-device;
                   type string {
                     pattern "<.*>|$.*";
                   }
                 }
               }
               leaf disable-hash {
                 description "Hash based distribution is not needed for this subunit";
                 type empty;
               }
               leaf modulo-key {
                 description "Modulo based distribution";
                 type enumeration {
                   enum "source-ip" {
                     description "Source Ip Address";
                   }
                   enum "destination-ip" {
                     description "Destination Ip Address";
                   }
                 }
               }
               container hash-keys {
                 uses apply-advanced;
                 leaf-list ingress-key {
                   ordered-by user;
                   description "Hash Key for the ingress direction";
                   type enumeration {
                     enum "source-ip" {
                       description "Source Ip Address";
                     }
                     enum "destination-ip" {
                       description "Destination Ip Address";
                     }
                     enum "protocol" {
                       description "Protocol";
                     }
                     enum "iif" {
                       description "Incoming Interface";
                     }
                   }
                 }
                 leaf-list egress-key {
                   ordered-by user;
                   description "Hash Key for the egress direction";
                   status deprecated;
                   type enumeration {
                     enum "source-ip" {
                       description "Source Ip Address";
                       status deprecated;
                     }
                     enum "destination-ip" {
                       description "Destination Ip Address";
                       status deprecated;
                     }
                     enum "protocol" {
                       description "Protocol";
                       status deprecated;
                     }
                     enum "oif" {
                       description "Outgoing Interface";
                       status deprecated;
                     }
                   }
                 }
                 leaf ipv6-source-prefix-length {
                   description "IPv6 source prefix length for hash computation";
                   type enumeration {
                     enum "56" {
                       description "56 bit IPv6 address prefix";
                     }
                     enum "64" {
                       description "64 bit IPv6 address prefix";
                     }
                     enum "96" {
                       description "96 bit IPv6 address prefix";
                     }
                     enum "128" {
                       description "Complete 128 bit IPv6 address";
                     }
                   }
                 }
               }
             }
             container interface-state {
               description "IRB interface state computation";
               uses apply-advanced;
               choice state {
                 case case_1 {
                   leaf local {
                     description "IRB State computation based on local interface state";
                     type empty;
                   }
                 }
                 case case_2 {
                   leaf remote {
                     description "IRB State computation based on remote reachability";
                     type empty;
                   }
                 }
                 case case_3 {
                   leaf local-remote {
                     description "IRB State computation based on local or remote reachability";
                     type empty;
                   }
                 }
                 case case_4 {
                   leaf local-interface {
                     description "IRB State computation based on loopback AE port state";
                     type union {
                       type jt:interface-name;
                       type string {
                         pattern "<.*>|$.*";
                       }
                     }
                   }
                 }
               }
               leaf local-count {
                 description "Minimum number of local layer2 link in up state to consider IRB up";
                 type union {
                   type uint16;
                   type string {
                     pattern "<.*>|$.*";
                   }
                 }
               }
               leaf vtep-count {
                 description "Minimum number of VTEP link in up state to consider IRB up";
                 type union {
                   type uint16;
                   type string {
                     pattern "<.*>|$.*";
                   }
                 }
               }
               container hold-time {
                 description "Delay before marking interface up or down for defect";
                 uses apply-advanced;
                 leaf up {
                   description "Delay in seconds before marking IRB interface up";
                   units "seconds";
                   type union {
                     type uint32;
                     type string {
                       pattern "<.*>|$.*";
                     }
                   }
                 }
                 leaf down {
                   description "Delay in seconds before marking IRB interface down";
                   units "seconds";
                   type union {
                     type uint32;
                     type string {
                       pattern "<.*>|$.*";
                     }
                   }
                 }
               }
             }
             leaf mac {
               description "Configure logical interface MAC address";
               type jt:mac-unicast;
             }
             leaf virtual-gateway-v4-mac {
               description "Configure virtual gateway IPV4 virtual MAC address";
               type jt:mac-unicast;
             }
             leaf virtual-gateway-v6-mac {
               description "Configure virtual gateway IPV6 virtual MAC address";
               type jt:mac-unicast;
             }
             leaf no-dhcp-flood {
               description "Disable dhcp flooding";
               type empty;
             }
             container forwarding-options {
               description "Aggregated Ethernet interface forwarding-options";
               uses apply-advanced;
               container load-balance-stateful {
                 description "Stateful load balancing";
                 uses apply-advanced;
                 leaf per-flow {
                   description "Enable feature";
                   type empty;
                 }
                 leaf rebalance {
                   description "Rebalancing interval";
                   units "per minute";
                   type union {
                     type string {
                       pattern "<.*>|$.*";
                     }
                     type uint32 {
                       range "1 .. 1000";
                     }
                   }
                 }
                 leaf load-type {
                   description "Load - defines the flows";
                   type enumeration {
                     enum "high" {
                       description "If the no of flows on this aggregate is large(1000-10000 flows) ";
                     }
                     enum "medium" {
                       description "If the no of flows on this aggregate is moderate(100-1000 flows)";
                     }
                     enum "low" {
                       description "If the no of flows on this aggregate is less(1-100)";
                     }
                   }
                 }
               }
             }
             leaf etree-ac-role {
               description "ETREE attachment circuit role";
               type enumeration {
                 enum "root" {
                   description "ETREE root interface";
                 }
                 enum "leaf" {
                   description "ETREE leaf interface";
                 }
               }
             }
             container load-balance {
               description "Load-balance weight per subscriber interface";
               uses apply-advanced;
               leaf weight {
                 description "Load-balance weight";
                 type union {
                   type string {
                     pattern "<.*>|$.*";
                   }
                   type uint32 {
                     range "1 .. 1000";
                   }
                 }
               }
             }
             container explicit-proxy {
               presence "enable explicit-proxy";
               description "Attach explicit proxy profiles";
               uses apply-advanced;
               leaf-list profile {
                 description "Explicit proxy profile name";
                 type string {
                   length "1 .. 63";
                 }
               }
             }
             container dialer-options {
               presence "enable dialer-options";
               description "Dialer options";
               uses apply-advanced;
               leaf pool {
                 description "Dialer pool";
                 type string {
                   length "1 .. 64";
                 }
               }
               leaf-list route {
                 ordered-by user;
                 description "Route on dialer";
                 type jt:ipprefix;
               }
               leaf always-on {
                 description "Always keep on-line";
                 type empty;
               }
               leaf-list dial-string {
                 ordered-by user;
                 description "String to dial out";
                 type string {
                   length "1 .. 63";
                 }
                 max-elements 15;
               }
               container incoming-map {
                 description "Map incoming call to dialer";
                 uses apply-advanced;
                 choice caller-type {
                   case case_1 {
                     list caller {
                       key name;
                       ordered-by user;
                       description "Caller Id to be screened";
                       max-elements 300;
                       leaf name {
                         description "Caller ID (upto 15 digits)";
                         type string {
                         }
                       }
                     }
                   }
                   case case_2 {
                     leaf accept-all {
                       description "Accept all incoming calls";
                       type empty;
                     }
                   }
                 }
               }
               leaf callback {
                 description "Call back on any incoming call to the dialer";
                 type empty;
               }
               leaf callback-wait-period {
                 description "Time to wait before calling back";
                 units "seconds";
                 type union {
                   type string {
                     pattern "<.*>|$.*";
                   }
                   type uint32 {
                     range "2 .. 255";
                   }
                 }
               }
               leaf redial-delay {
                 description "Time to wait before redialing";
                 units "seconds";
                 type union {
                   type string {
                     pattern "<.*>|$.*";
                   }
                   type uint32 {
                     range "2 .. 255";
                   }
                 }
               }
               leaf self-recover-time {
                 description "Sub-interface self-recover time";
                 units "seconds";
                 type union {
                   type string {
                     pattern "<.*>|$.*";
                   }
                   type uint32 {
                     range "2 .. 120";
                   }
                 }
               }
               leaf idle-timeout {
                 description "Delay before taking down the interface";
                 default "120";
                 units "seconds";
                 type union {
                   type string {
                     pattern "<.*>|$.*";
                   }
                   type uint32 {
                     range "0 .. 4294967295";
                   }
                 }
               }
               list watch-list {
                 key name;
                 description "Dialer watch list";
                 leaf name {
                   description "Address prefix";
                   type jt:ipprefix-only;
                 }
                 uses apply-advanced;
               }
               leaf load-threshold {
                 description "Load threshold for adding interfaces";
                 type union {
                   type string {
                     pattern "<.*>|$.*";
                   }
                   type uint32 {
                     range "0 .. 100";
                   }
                 }
               }
               leaf load-interval {
                 description "Interval used to calculate average load";
                 units "seconds";
                 type union {
                   type string {
                     pattern "<.*>|$.*";
                   }
                   type uint32 {
                     range "20 .. 180";
                   }
                 }
               }
               leaf activation-delay {
                 description "Activation delay";
                 units "seconds";
                 type union {
                   type string {
                     pattern "<.*>|$.*";
                   }
                   type uint32 {
                     range "1 .. 4294967295";
                   }
                 }
               }
               leaf deactivation-delay {
                 description "Deactivation delay";
                 units "seconds";
                 type union {
                   type string {
                     pattern "<.*>|$.*";
                   }
                   type uint32 {
                     range "1 .. 4294967295";
                   }
                 }
               }
               leaf initial-route-check {
                 description "Delay to check primary after the router is up";
                 default "120";
                 units "seconds";
                 type union {
                   type string {
                     pattern "<.*>|$.*";
                   }
                   type uint16 {
                     range "1 .. 300";
                   }
                 }
               }
             }
             container backup-options {
               description "Backup interface configuration options";
               uses apply-advanced;
               leaf interface {
                 description "Backup interface";
                 type union {
                   type jt:interface-name;
                   type string {
                     pattern "<.*>|$.*";
                   }
                 }
               }
             }
           }
           container no-partition {
             description "Use channelizable interface as clear channel";
             leaf interface-type {
               description "Interface type";
               type enumeration {
                 enum "e1" {
                   description "E1 interface";
                 }
                 enum "t1" {
                   description "T1 interface";
                 }
                 enum "at" {
                   description "ATM interface";
                 }
                 enum "t3" {
                   description "T3 interface";
                 }
                 enum "e3" {
                   description "E3 interface";
                 }
                 enum "ct3" {
                   description "Channelized T3 interface";
                 }
                 enum "so" {
                   description "SONET interface";
                 }
                 enum "cau4" {
                   description "CAU4 interface";
                 }
               }
             }
           }
           list partition {
             key name;
             ordered-by user;
             description "Channelized interface partition";
             leaf name {
               description "Sublevel interface partition index (for example, 1, 3-4)";
               type string;
             }
             leaf oc-slice {
               description "Range of SONET/SDH slices (for example, 1, 7-9)";
               type string;
             }
             leaf timeslots {
               description "Timeslots [(1..24) for T1, (1..31) for E1]; for example, 1-3,4,9,22-24 (no spaces)";
               type string;
             }
             leaf interface-type {
               description "Sublevel interface type";
               type enumeration {
                 enum "ds" {
                   description "DS0 interface";
                 }
                 enum "e1" {
                   description "E1 interface";
                 }
                 enum "t1" {
                   description "T1 interface";
                 }
                 enum "at" {
                   description "ATM interface";
                 }
                 enum "ct1" {
                   description "Channelized T1 interface";
                 }
                 enum "ce1" {
                   description "Channelized E1 interface";
                 }
                 enum "t3" {
                   description "T3 interface";
                 }
                 enum "ct3" {
                   description "Channelized T3 interface";
                 }
                 enum "e3" {
                   description "E3 interface";
                 }
                 enum "so" {
                   description "SONET interface";
                 }
                 enum "coc1" {
                   description "Channelized OC1 interface";
                 }
                 enum "cau4" {
                   description "Channelized AU4 interface";
                 }
                 enum "dc" {
                   description "D channel interface";
                 }
                 enum "bc" {
                   description "B channel interface";
                 }
               }
             }
           }
           container radius-options {
             description "Interface RADIUS Options";
             uses radius_options_vlan_type;
           }
           leaf rpf-stats {
             description "Enable Reverse path forwarding stats for this interface";
             type empty;
           }
           container redundant-pseudo-interface-options {
             description "Pseudo interface redundancy options";
             uses apply-advanced;
             leaf redundancy-group {
               description "Redundancy group of this interface";
               type union {
                 type string {
                   pattern "<.*>|$.*";
                 }
                 type uint16 {
                   range "0 .. 255";
                 }
               }
             }
           }
           container modem-options {
             description "MODEM interface-specific options";
             uses apply-advanced;
             leaf init-command-string {
               description "AT command string to initialize modem";
               type string {
                 length "1 .. 127";
               }
             }
             leaf dialin {
               default "console";
               type enumeration {
                 enum "console" {
                   description "Management console access";
                 }
                 enum "routable" {
                   description "Routable access";
                 }
               }
             }
           }
           leaf act-sim {
             description "Default SIM slot to connect LTE network";
             type union {
               type string {
                 pattern "<.*>|$.*";
               }
               type uint32;
             }
           }
           container cellular-options {
             presence "enable cellular-options";
             description "Cellular interface specific options";
             uses apply-advanced;
             list sim {
               key name;
               description "SIM slot to connect LTE network";
               leaf name {
                 description "SIM slot number";
                 type union {
                   type string {
                     pattern "<.*>|$.*";
                   }
                   type uint32;
                 }
               }
               uses apply-advanced;
               container select-profile {
                 description "Profile to be applied";
                 leaf profile-id {
                   description "Profile to be used for data calls";
                   type union {
                     type string {
                       pattern "<.*>|$.*";
                     }
                     type uint32 {
                       range "1 .. 16";
                     }
                   }
                 }
               }
               container radio-access {
                 description "Select radio access technology";
                 choice rat-value {
                   case case_1 {
                     leaf automatic {
                       description "Automatically selects radio access type";
                       type empty;
                     }
                   }
                   case case_2 {
                     leaf umts-3g-only {
                       description "3G only";
                       type empty;
                     }
                   }
                   case case_3 {
                     leaf umts-3g-preferred {
                       description "UMTS 3G Preferred";
                       type empty;
                     }
                   }
                   case case_4 {
                     leaf lte-only {
                       description "Only LTE";
                       type empty;
                     }
                   }
                   case case_5 {
                     leaf lte-preferred {
                       description "LTE Preferred";
                       type empty;
                     }
                   }
                 }
               }
               leaf encrypted-sim-unlock-code {
                 description "Encrypted PIN";
                 type jt:unreadable;
               }
               leaf gateway {
                 description "Set customer gateway for LTE network";
                 type jt:ipprefix;
               }
             }
           }
           container isdn-options {
             description "ISDN interface-specific options";
             uses apply-advanced;
             leaf switch-type {
               description "ISDN switch type";
               type enumeration {
                 enum "ni1" {
                   description "NI1 BRI variant";
                 }
                 enum "etsi" {
                   description "ETSI variant";
                 }
                 enum "att5e" {
                   description "ATT5E variant";
                 }
                 enum "ntdms100" {
                   description "NTDMS100 variant";
                 }
                 enum "ntt" {
                   description "INS NET (NTT) PRI/BRI variant";
                 }
                 enum "ni2" {
                   description "NI2 PRI variant";
                 }
               }
             }
             leaf media-type {
               description "IDSN media type - voice, data or both";
               default "data";
               type enumeration {
                 enum "data" {
                   description "Data";
                 }
                 enum "voice" {
                   description "Voice";
                 }
                 enum "combined" {
                   description "Combined";
                 }
               }
             }
             leaf spid1 {
               description "Service profile identifier";
               type string {
                 length "1 .. 20";
               }
             }
             leaf spid2 {
               description "Additional service profile identifier";
               type string {
                 length "1 .. 20";
               }
             }
             leaf calling-number {
               description "Calling number included in outgoing calls";
               type string {
               }
             }
             list incoming-called-number {
               key name;
               ordered-by user;
               description "Incoming called number to be screened";
               max-elements 30;
               leaf name {
                 description "Number called (upto 15 digits)";
                 type string {
                 }
               }
               leaf reject {
                 description "Reject the called number";
                 type empty;
               }
             }
             leaf tei-option {
               description "ISDN terminal endpoint identifier negotiation options";
               type enumeration {
                 enum "first-call" {
                   description "Terminal endpoint identifier negotiation during first call";
                 }
                 enum "power-up" {
                   description "Terminal endpoint identifier negotiation during power-up";
                 }
               }
             }
             leaf static-tei-val {
               description "Static TEI value";
               type union {
                 type string {
                   pattern "<.*>|$.*";
                 }
                 type uint32 {
                   range "0 .. 63";
                 }
               }
             }
             leaf t310 {
               description "Timer T310 value";
               units "seconds";
               type union {
                 type string {
                   pattern "<.*>|$.*";
                 }
                 type uint32 {
                   range "1 .. 65536";
                 }
               }
             }
             leaf bchannel-allocation {
               description "Allocate PRI dialout b-channel in ascending/descending order";
               default "descending";
               type enumeration {
                 enum "ascending" {
                   description "Allocate b-channel in ascending order";
                 }
                 enum "descending" {
                   description "Allocate b-channel in descending order";
                 }
               }
             }
           }
           container dialer-options {
             presence "enable dialer-options";
             description "Dialer options";
             uses apply-advanced;
             list pool {
               key name;
               description "Dialer pool";
               max-elements 30;
               leaf name {
                 description "Dialer pool identifier";
                 type string {
                   length "1 .. 64";
                 }
               }
               leaf priority {
                 description "Dialer pool priority";
                 type union {
                   type string {
                     pattern "<.*>|$.*";
                   }
                   type uint32 {
                     range "1 .. 255";
                   }
                 }
               }
             }
           }
         }
         list interface {
           key name;
           uses interfaces_type;
         }
       }
     }
     container protocols {
       description "Routing protocol configuration";
       uses apply-advanced;
       container igmp {
         presence "enable igmp";
         description "IGMP options";
         uses apply-advanced;
         leaf protocol-instance-name {
           description "Name of protocol instance under routing instance";
           type string;
         }
         container traceoptions {
           description "Trace options for IGMP";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "packets" {
                   description "Trace all IGMP packets";
                 }
                 enum "query" {
                   description "Trace IGMP membership query messages";
                 }
                 enum "report" {
                   description "Trace membership report messages";
                 }
                 enum "leave" {
                   description "Trace leave group messages (IGMPv2 only)";
                 }
                 enum "mtrace" {
                   description "Trace mtrace packets";
                 }
                 enum "group" {
                   description "Trace group operations";
                 }
                 enum "client-notification" {
                   description "Trace notifications";
                 }
                 enum "host-notification" {
                   description "Trace host notifications";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf maximum-transmit-rate {
           description "Maximum transmission rate (packets per second)";
           type union {
             type string {
               pattern "<.*>|$.*";
             }
             type uint32 {
               range "1 .. 10000";
             }
           }
         }
         leaf accounting {
           description "Enable join and leave event notification";
           type empty;
         }
         list interface {
           key name;
           ordered-by user;
           description "Interface options for IGMP";
           leaf name {
             type string;
           }
           uses apply-advanced;
           choice enable-disable {
             case case_1 {
               leaf disable {
                 description "Disable IGMP on this interface";
                 type empty;
               }
             }
           }
           leaf version {
             description "Set IGMP version number on this interface";
             type union {
               type string {
                 pattern "<.*>|$.*";
               }
               type uint8 {
                 range "1 .. 3";
               }
             }
           }
           container static {
             description "Static group or source membership";
             uses apply-advanced;
             list group {
               key name;
               ordered-by user;
               description "IP multicast group address";
               leaf name {
                 description "IP multicast group address";
                 type jt:ipv4addr;
               }
               uses apply-advanced;
               leaf group-increment {
                 description "Mask for the incrementing group IP address";
                 type jt:ipv4addr;
               }
               leaf group-count {
                 description "Number of groups";
                 type union {
                   type string {
                     pattern "<.*>|$.*";
                   }
                   type uint32 {
                     range "1 .. 512";
                   }
                 }
               }
               leaf exclude {
                 description "Exclude sources";
                 type empty;
               }
               list source {
                 key name;
                 ordered-by user;
                 description "IP multicast source address";
                 leaf name {
                   description "Source address of IP multicast data";
                   type jt:ipv4addr;
                 }
                 uses apply-advanced;
                 leaf source-increment {
                   description "Mask for the incrementing source IP address";
                   type jt:ipv4addr;
                 }
                 leaf source-count {
                   description "Number of sources";
                   type union {
                     type string {
                       pattern "<.*>|$.*";
                     }
                     type uint32 {
                       range "1 .. 1024";
                     }
                   }
                 }
               }
             }
           }
           leaf ssm-map {
             description "Map for SSM translation of IGMPv1 or IGMPv2 messages";
             type string;
           }
           leaf-list ssm-map-policy {
             ordered-by user;
             description "SSM map policy name";
             type jt:policy-algebra;
           }
           leaf immediate-leave {
             description "Group removed immediately, last membership query not sent";
             type empty;
           }
           leaf promiscuous-mode {
             description "Accept igmp messages coming from different subnet";
             type empty;
           }
           choice accounting-choice {
             leaf accounting {
               description "Enable join and leave event notification";
               type empty;
             }
             leaf no-accounting {
               description "Don't enable join and leave event notification";
               type empty;
             }
           }
           leaf-list group-policy {
             ordered-by user;
             description "Group filter applied to incoming IGMP report messages";
             type jt:policy-algebra;
           }
           leaf group-limit {
             description "Maximum number of (source,group) per interface";
             type union {
               type string {
                 pattern "<.*>|$.*";
               }
               type uint16 {
                 range "1 .. 32767";
               }
             }
           }
           leaf group-threshold {
             description "Percentage of limit at which to generate warnings";
             type union {
               type string {
                 pattern "<.*>|$.*";
               }
               type uint32 {
                 range "1 .. 100";
               }
             }
           }
           leaf log-interval {
             description "Time between consecutive log messages";
             type union {
               type string {
                 pattern "<.*>|$.*";
               }
               type uint32 {
                 range "6 .. 32767";
               }
             }
           }
           container passive {
             presence "enable passive";
             description "Suppress sending and receiving IGMP messages";
             leaf allow-receive {
               description "Allow receiving IGMP messages";
               type empty;
             }
             leaf send-general-query {
               description "Send IGMP general query messages";
               type empty;
             }
             leaf send-group-query {
               description "Send IGMP group query messages";
               type empty;
             }
           }
           leaf-list oif-map {
             ordered-by user;
             description "Output interface map";
             type jt:policy-algebra;
           }
           leaf distributed {
             description "Distributed IGMP interface";
             type empty;
           }
         }
         container amt {
           description "Automatic Multicast Tunnel options for IGMP";
           uses apply-advanced;
           container relay {
             description "AMT relay options for IGMP";
             uses apply-advanced;
             container defaults {
               presence "enable defaults";
               description "Default AMT relay options for IGMP";
               uses apply-advanced;
               leaf version {
                 description "Set IGMP version number on AMT interfaces";
                 type union {
                   type string {
                     pattern "<.*>|$.*";
                   }
                   type uint8 {
                     range "1 .. 3";
                   }
                 }
               }
               leaf ssm-map {
                 description "Map for SSM translation of IGMPv1 or IGMPv2 messages";
                 type string;
               }
               leaf-list ssm-map-policy {
                 ordered-by user;
                 description "SSM map policy name";
                 type jt:policy-algebra;
               }
               choice accounting-choice {
                 leaf accounting {
                   description "Enable join and leave event notification";
                   type empty;
                 }
                 leaf no-accounting {
                   description "Don't enable join and leave event notification";
                   type empty;
                 }
               }
               leaf-list group-policy {
                 ordered-by user;
                 description "Group filter applied to incoming IGMP report messages";
                 type jt:policy-algebra;
               }
               leaf group-limit {
                 description "Maximum number of (source,group) per interface";
                 type union {
                   type string {
                     pattern "<.*>|$.*";
                   }
                   type uint16 {
                     range "1 .. 32767";
                   }
                 }
               }
               leaf group-threshold {
                 description "Percentage of limit at which to generate warnings";
                 type union {
                   type string {
                     pattern "<.*>|$.*";
                   }
                   type uint32 {
                     range "1 .. 100";
                   }
                 }
               }
               leaf log-interval {
                 description "Time between consecutive log messages";
                 type union {
                   type string {
                     pattern "<.*>|$.*";
                   }
                   type uint32 {
                     range "6 .. 32767";
                   }
                 }
               }
               leaf robust-count {
                 description "Expected packet loss on a subnet";
                 type union {
                   type string {
                     pattern "<.*>|$.*";
                   }
                   type uint32 {
                     range "2 .. 10";
                   }
                 }
               }
               leaf query-interval {
                 description "When to send host query messages";
                 units "seconds";
                 type union {
                   type string {
                     pattern "<.*>|$.*";
                   }
                   type uint32 {
                     range "1 .. 1024";
                   }
                 }
               }
               leaf query-response-interval {
                 description "How long to wait for a host query response";
                 units "seconds";
                 type string {
                 }
               }
             }
           }
         }
       }
       container oam {
         description "Operation, Administration, and Management configuration";
         uses apply-advanced;
         container ethernet {
           description "OAM configuration for Ethernet";
           uses apply-advanced;
           container link-fault-management {
             description "802.3ah Ethernet OAM configuration";
             uses apply-advanced;
             leaf hardware-assisted-keepalives {
               description "Enable delegating keepalives to hardware";
               type empty;
             }
             container traceoptions {
               description "Trace options for link-fault management";
               uses apply-advanced;
               leaf no-remote-trace {
                 description "Disable remote tracing";
                 type empty;
               }
               container file {
                 description "Trace file information";
                 leaf filename {
                   description "Name of file in which to write trace information";
                   type string {
                     length "1 .. 1024";
                   }
                 }
                 leaf size {
                   description "Maximum trace file size";
                   type string;
                 }
                 leaf files {
                   description "Maximum number of trace files";
                   default "3";
                   type union {
                     type string {
                       pattern "<.*>|$.*";
                     }
                     type uint32 {
                       range "2 .. 1000";
                     }
                   }
                 }
                 choice world-readable-choice {
                   leaf world-readable {
                     description "Allow any user to read the log file";
                     type empty;
                   }
                   leaf no-world-readable {
                     description "Don't allow any user to read the log file";
                     type empty;
                   }
                 }
                 leaf match {
                   description "Regular expression for lines to be logged";
                   type jt:regular-expression;
                 }
               }
               list flag {
                 key name;
                 ordered-by user;
                 description "Tracing parameters";
                 leaf name {
                   type enumeration {
                     enum "configuration" {
                       description "Trace configuration events";
                     }
                     enum "routing-socket" {
                       description "Trace routing socket events";
                     }
                     enum "protocol" {
                       description "Trace protocol processing events";
                     }
                     enum "action-profile" {
                       description "Trace action profile invocation events";
                     }
                     enum "all" {
                       description "Trace everything";
                     }
                   }
                 }
               }
             }
             list action-profile {
               key name;
               ordered-by user;
               description "Define an action profile";
               leaf name {
                 description "Name of action profile";
                 type string {
                   length "1 .. 32";
                 }
               }
               uses apply-advanced;
               container event {
                 description "Events this action profile will check";
                 uses apply-advanced;
                 leaf link-adjacency-loss {
                   description "Loss of adjacency with OAM peer";
                   type empty;
                 }
                 leaf protocol-down {
                   description "Upper layer indication on protocol down";
                   type empty;
                 }
                 container link-event-rate {
                   uses apply-advanced;
                   leaf symbol-period {
                     description "Rate of receiving symbol period events";
                     units "error(s) per 100 symbol";
                     type union {
                       type string {
                         pattern "<.*>|$.*";
                       }
                       type int32 {
                         range "1 .. 100";
                       }
                     }
                   }
                   leaf frame-error {
                     description "Rate of receiving frame error events";
                     units "error(s) per 100 milli-second";
                     type union {
                       type string {
                         pattern "<.*>|$.*";
                       }
                       type int32 {
                         range "1 .. 1000";
                       }
                     }
                   }
                   leaf frame-period {
                     description "Rate of receiving frame period events";
                     units "error(s) per 100 frames";
                     type union {
                       type string {
                         pattern "<.*>|$.*";
                       }
                       type int32 {
                         range "1 .. 100";
                       }
                     }
                   }
                   leaf frame-period-summary {
                     description "Rate of receiving frame period summary events";
                     units "error(s) per second";
                     type union {
                       type string {
                         pattern "<.*>|$.*";
                       }
                       type int32 {
                         range "1 .. 1000";
                       }
                     }
                   }
                 }
               }
               container action {
                 description "Action to take on specified events";
                 uses apply-advanced;
                 leaf syslog {
                   description "Generate syslog message";
                   type empty;
                 }
                 leaf link-down {
                   description "Mark the interface down for transit traffic";
                   type empty;
                 }
                 leaf send-critical-event {
                   description "Start sending OAM PDUs with critical event bit set";
                   type empty;
                 }
               }
             }
             list interface {
               key name;
               ordered-by user;
               description "Interface on which to set Ethernet OAM parameters";
               leaf name {
                 description "Interface name";
                 type union {
                   type jt:interface-device;
                   type string {
                     pattern "<.*>|$.*";
                   }
                 }
               }
               uses apply-advanced;
               leaf-list apply-action-profile {
                 ordered-by user;
                 description "Apply the specified action profile on the interface";
                 type string;
               }
               leaf pdu-interval {
                 description "Periodic OAM protocol data unit interval";
                 default "1000";
                 units "milliseconds";
                 type union {
                   type string {
                     pattern "<.*>|$.*";
                   }
                   type int32 {
                     range "100 .. 1000";
                   }
                 }
               }
               leaf loopback-tracking {
                 description "Enable link down on loopback detection";
                 type empty;
               }
               leaf detect-loc {
                 description "Detects initial lack of adjacency formation";
                 type empty;
               }
               leaf link-discovery {
                 description "Mode of discovery";
                 default "active";
                 type enumeration {
                   enum "active" {
                   }
                   enum "passive" {
                   }
                 }
               }
               leaf pdu-threshold {
                 description "Number of PDUs missed before declaring peer lost";
                 default "3";
                 type union {
                   type string {
                     pattern "<.*>|$.*";
                   }
                   type int32;
                 }
               }
               leaf remote-loopback {
                 description "Put remote DTE into remote-loopback mode";
                 type empty;
               }
               container negotiation-options {
                 description "802.3ah features supported on the interface";
                 uses apply-advanced;
                 leaf no-allow-link-events {
                   description "Do not emit periodic PDUs detailing framing and symbol errors";
                   type empty;
                 }
                 leaf allow-remote-loopback {
                   description "Allow local port to be put into loopback mode";
                   type empty;
                 }
               }
               container event-thresholds {
                 description "Thresholds for sending 802.3ah events";
                 uses apply-advanced;
                 leaf symbol-period {
                   description "Threshold for sending symbol period events";
                   default "1";
                   type union {
                     type string {
                       pattern "<.*>|$.*";
                     }
                     type int32 {
                       range "0 .. 100";
                     }
                   }
                 }
                 leaf frame-error {
                   description "Threshold for sending frame error events";
                   default "1";
                   type union {
                     type string {
                       pattern "<.*>|$.*";
                     }
                     type int32 {
                       range "0 .. 100";
                     }
                   }
                 }
                 leaf frame-period {
                   description "Threshold for sending frame period error events";
                   default "1";
                   type union {
                     type string {
                       pattern "<.*>|$.*";
                     }
                     type int32 {
                       range "0 .. 100";
                     }
                   }
                 }
                 leaf frame-period-summary {
                   description "Threshold for sending frame period summary error events";
                   default "1";
                   type union {
                     type string {
                       pattern "<.*>|$.*";
                     }
                     type int32 {
                       range "0 .. 100";
                     }
                   }
                 }
               }
             }
           }
           container connectivity-fault-management {
             description "Configurations related to 802.1ag ethernet oam";
             uses apply-advanced;
             container performance-monitoring {
               description "Configurations related to ethernet performance monitoring";
               uses apply-advanced;
               leaf hardware-assisted-timestamping {
                 description "Enable timestamping feature in hardware";
                 type empty;
               }
               leaf delegate-server-processing {
                 description "Delegate performance measurement request handling to PFE";
                 type empty;
               }
               leaf hardware-assisted-keepalives {
                 description "Enable/Disable delegating keepalives to hardware";
                 type enumeration {
                   enum "enable" {
                     description "Enable delegate keepalives handling to Hardware";
                   }
                   enum "disable" {
                     description "Disable delegate keepalives handling to Hardware (default)";
                   }
                 }
               }
               leaf hardware-assisted-pm {
                 description "Enable inline support for performance monitoring";
                 type empty;
               }
               leaf enhanced-sla-iterator {
                 description "Enable Enhanced SLA Iterator Cycle-time";
                 type empty;
               }
               leaf measurement-interval {
                 description "Enables measurement-interval based PM (MEF 36 mode). Default 15 min in enhanced-cfm-mode";
                 units "minutes";
                 type enumeration {
                   enum "2" {
                     description "2 minutes measurement interval";
                   }
                   enum "5" {
                     description "5 minutes measurement interval";
                   }
                   enum "15" {
                     description "15 minutes measurement interval";
                   }
                   enum "30" {
                     description "30 minutes measurement interval";
                   }
                   enum "60" {
                     description "1 hour measurement interval";
                   }
                 }
               }
               leaf legacy-pm-display {
                 description "Display Legacy PM output (for DM) in MEF mode.";
                 type empty;
               }
               list sla-iterator-profiles {
                 key name;
                 ordered-by user;
                 description "Configuration related to an sla monitoring iterator";
                 leaf name {
                   type string;
                 }
                 uses apply-advanced;
                 leaf disable {
                   description "Disable the iterator profile";
                   type empty;
                 }
                 leaf measurement-type {
                   description "Choice of the type of Y.1731(SLA measurement) frame to be sent";
                   type enumeration {
                     enum "two-way-delay" {
                       description "Y.1731 2-way DM frames are sent for this profile";
                     }
                     enum "loss" {
                       description "Y.1731 LM frames are sent for this profile";
                     }
                     enum "slm" {
                       description "Y.1731 SLM frames are sent for this profile";
                     }
                     enum "statistical-frame-loss" {
                       description "Y.1731 2-way DM frames for statistical frame loss are sent for this profile";
                     }
                   }
                 }
                 leaf flap-trap-monitor {
                   description "Configurable timer value 1-360";
                   units "seconds";
                   type union {
                     type string {
                       pattern "<.*>|$.*";
                     }
                     type uint32 {
                       range "1 .. 360";
                     }
                   }
                 }
                 leaf cycle-time {
                   description "Time period of an iterator profile";
                   default "1000";
                   units "milliseconds";
                   type union {
                     type string {
                       pattern "<.*>|$.*";
                     }
                     type uint32;
                   }
                 }
                 leaf iteration-period {
                   description "Maximum services under this iterator profile";
                   default "2000";
                   units "connections";
                   type union {
                     type string {
                       pattern "<.*>|$.*";
                     }
                     type uint32 {
                       range "1 .. 2000";
                     }
                   }
                 }
                 container calculation-weight {
                   presence "enable calculation-weight";
                   description "Configure delay and delay variation calculation weight";
                   uses apply-advanced;
                   leaf delay {
                     description "Weight used in delay calculation";
                     default "1";
                     type union {
                       type string {
                         pattern "<.*>|$.*";
                       }
                       type uint32 {
                         range "1 .. 65535";
                       }
                     }
                   }
                   leaf delay-variation {
                     description "Weight used in delay-variation calculation";
                     default "1";
                     type union {
                       type string {
                         pattern "<.*>|$.*";
                       }
                       type uint32 {
                         range "1 .. 65535";
                       }
                     }
                   }
                 }
                 container avg-flr-forward-threshold {
                   presence "enable avg-flr-forward-threshold";
                   description "Avg forward flr threshold";
                   uses apply-advanced;
                   leaf avg-flr-forward {
                     description "Avg forward flr threshold value in mili-percent";
                     type union {
                       type string {
                         pattern "<.*>|$.*";
                       }
                       type uint32 {
                         range "1 .. 100000";
                       }
                     }
                   }
                   leaf flap-trap-monitor {
                     description "Configurable timer value 1-360";
                     units "seconds";
                     type union {
                       type string {
                         pattern "<.*>|$.*";
                       }
                       type uint32 {
                         range "1 .. 360";
                       }
                     }
                   }
                 }
                 container avg-flr-backward-threshold {
                   presence "enable avg-flr-backward-threshold";
                   description "Avg backward flr threshold";
                   uses apply-advanced;
                   leaf avg-flr-backward {
                     description "Avg backward flr threshold value in mili-percent";
                     type union {
                       type string {
                         pattern "<.*>|$.*";
                       }
                       type uint32 {
                         range "1 .. 100000";
                       }
                     }
                   }
                   leaf flap-trap-monitor {
                     description "Configurable timer value 1-360";
                     units "seconds";
                     type union {
                       type string {
                         pattern "<.*>|$.*";
                       }
                       type uint32 {
                         range "1 .. 360";
                       }
                     }
                   }
                 }
                 container avg-fd-twoway-threshold {
                   presence "enable avg-fd-twoway-threshold";
                   description "Avg frame delay threshold value";
                   uses apply-advanced;
                   leaf avg-fd-twoway {
                     description "Avg frame delay threshold value in mili-percent";
                     units "microseconds";
                     type union {
                       type string {
                         pattern "<.*>|$.*";
                       }
                       type uint32 {
                         range "1 .. 4294967295";
                       }
                     }
                   }
                   leaf flap-trap-monitor {
                     description "Configurable timer value 1-360";
                     units "seconds";
                     type union {
                       type string {
                         pattern "<.*>|$.*";
                       }
                       type uint32 {
                         range "1 .. 360";
                       }
                     }
                   }
                 }
                 container avg-fdv-twoway-threshold {
                   presence "enable avg-fdv-twoway-threshold";
                   description "Avg frame delay variance threshold";
                   uses apply-advanced;
                   leaf avg-fdv-twoway {
                     description "Avg frame delay variance threshold value in mili-percent";
                     units "microseconds";
                     type union {
                       type string {
                         pattern "<.*>|$.*";
                       }
                       type uint32 {
                         range "1 .. 4294967295";
                       }
                     }
                   }
                   leaf flap-trap-monitor {
                     description "Configurable timer value 1-360";
                     units "seconds";
                     type union {
                       type string {
                         pattern "<.*>|$.*";
                       }
                       type uint32 {
                         range "1 .. 360";
                       }
                     }
                   }
                 }
                 leaf measurement-interval {
                   description "Measurement-interval to be used for this PM session (MEF 36 mode)";
                   units "minutes";
                   type enumeration {
                     enum "2" {
                       description "2 minutes measurement interval";
                     }
                     enum "5" {
                       description "5 minutes measurement interval";
                     }
                     enum "15" {
                       description "15 minutes measurement interval";
                     }
                     enum "30" {
                       description "30 minutes measurement interval";
                     }
                     enum "60" {
                       description "1 hour measurement interval";
                     }
                   }
                 }
                 container frame-delay {
                   description "Bin configuration for frame delay";
                   uses apply-advanced;
                   leaf num-bins {
                     description "Max number of bins";
                     type union {
                       type string {
                         pattern "<.*>|$.*";
                       }
                       type uint32 {
                         range "2 .. 5";
                       }
                     }
                   }
                   container two-way {
                     presence "enable two-way";
                     description "Bin configuration for 2way frame delay";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container forward {
                     presence "enable forward";
                     description "Bin configuration for forward frame delay";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container backward {
                     presence "enable backward";
                     description "Bin configuration for backward frame delay";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                 }
                 container frame-delay-range {
                   description "Bin configuration for frame delay range";
                   uses apply-advanced;
                   leaf num-bins {
                     description "Max number of bins";
                     type union {
                       type string {
                         pattern "<.*>|$.*";
                       }
                       type uint32 {
                         range "2 .. 5";
                       }
                     }
                   }
                   container two-way {
                     presence "enable two-way";
                     description "Bin configuration for 2way frame delay range";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container forward {
                     presence "enable forward";
                     description "Bin configuration for forward frame delay range";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container backward {
                     presence "enable backward";
                     description "Bin configuration for backward frame delay range";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                 }
                 container ifdv {
                   description "Bin configuration for IFDV";
                   uses apply-advanced;
                   leaf num-bins {
                     description "Max number of bins";
                     type union {
                       type string {
                         pattern "<.*>|$.*";
                       }
                       type uint32 {
                         range "2 .. 5";
                       }
                     }
                   }
                   container two-way {
                     presence "enable two-way";
                     description "Bin configuration for 2way IFDV";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container forward {
                     presence "enable forward";
                     description "Bin configuration for forward IFDV";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container backward {
                     presence "enable backward";
                     description "Bin configuration for backward IFDV";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                 }
                 container availability {
                   description "Configuration of availabilty related parameters (MEF 36 mode)";
                   uses apply-advanced;
                   leaf num-consecutive-pdus {
                     description "Number of consecutive LM/SLM PDUs to be used in availability measurement";
                     type union {
                       type string {
                         pattern "<.*>|$.*";
                       }
                       type uint32 {
                         range "1 .. 100";
                       }
                     }
                   }
                   leaf flr-threshold {
                     description "FLR threshold in milli-percent to be used for evaluating availability";
                     type union {
                       type string {
                         pattern "<.*>|$.*";
                       }
                       type uint32 {
                         range "0 .. 100000";
                       }
                     }
                   }
                   leaf num-consecutive-intervals {
                     description "Number of consecutive availability indicators to detect change in availability";
                     type union {
                       type string {
                         pattern "<.*>|$.*";
                       }
                       type uint32 {
                         range "1 .. 10";
                       }
                     }
                   }
                   leaf num-consecutive-highflr {
                     description "Number of consecutive availability indicators to access CHLI";
                     type union {
                       type string {
                         pattern "<.*>|$.*";
                       }
                       type uint32 {
                         range "1 .. 9";
                       }
                     }
                   }
                 }
               }
               list interface {
                 key name;
                 ordered-by user;
                 description "Name of interface for the performance monitoring";
                 leaf name {
                   description "Interface name";
                   type union {
                     type jt:interface-unit;
                     type string {
                       pattern "<.*>|$.*";
                     }
                   }
                 }
                 leaf enable-multiclass-loss-measurement {
                   description "Disable multiclass loss measurement in hardware";
                   type empty;
                 }
                 leaf code-point-based-lm-accounting {
                   description "Enable code point based loss measurement in hardware";
                   type empty;
                 }
                 leaf priority-based-lm-accounting {
                   description "Enable priority based loss measurement in hardware";
                   type empty;
                 }
               }
               leaf enable-multiclass-loss-measurement {
                 description "Disable multiclass loss measurement in hardware";
                 type empty;
               }
               leaf code-point-based-lm-accounting {
                 description "Enable code point based loss measurement in hardware";
                 type empty;
               }
               leaf priority-based-lm-accounting {
                 description "Enable priority based loss measurement in hardware";
                 type empty;
               }
               leaf colorless-loss-measurement {
                 description "Enable colorless loss measurement in hardware";
                 type empty;
               }
             }
             container connection-protection {
               description "Configurations related to Carrier Ethernet Transport Mode";
               uses apply-advanced;
               leaf mark-connection-protection-tlv {
                 description "Enable marking of Connection Protection TLV";
                 type empty;
               }
               leaf uhp-label-lookup {
                 description "Enable lookup for special UHP labels";
                 type empty;
               }
             }
             leaf no-aggregate-delegate-processing {
               description "Do not distribute aggregate session to pfe";
               type empty;
             }
             leaf enhanced-cfm-mode {
               description "Enables Enhanced CFM Mode";
               type empty;
             }
             container expected-defect {
               description "Configure Expected Defect Parameters";
               uses apply-advanced;
               leaf rx-enable {
                 description "Enables Expected Defect PDU processing";
                 type empty;
               }
               leaf rx-max-duration {
                 description "Max duration that is allowed in EDM in secs";
                 type union {
                   type string {
                     pattern "<.*>|$.*";
                   }
                   type uint32 {
                     range "120 .. 3600";
                   }
                 }
               }
               leaf tx-enable {
                 description "Enables Expected Defect PDU transmission";
                 type empty;
               }
               leaf tx-duration {
                 description "Duration value in secs for Peer to suppress alarms";
                 type union {
                   type string {
                     pattern "<.*>|$.*";
                   }
                   type uint32 {
                     range "120 .. 3600";
                   }
                 }
               }
             }
             container traceoptions {
               description "Trace options for connectivity fault management";
               presence "enable traceoptions";
               uses cfm-traceoptions;
             }
             list action-profile {
               key name;
               ordered-by user;
               description "Action profiles to use when one or more remote maintenance association endpoints are down";
               leaf name {
                 description "Name of action profile";
                 type string;
               }
               uses apply-advanced;
               container event {
                 description "Events that need to be monitored";
                 uses apply-advanced;
                 leaf-list interface-status-tlv {
                   ordered-by user;
                   description "Values that need to be monitored in interface status TLV";
                   type enumeration {
                     enum "down" {
                       description "Interface is administratively down";
                     }
                     enum "lower-layer-down" {
                       description "Interface is physically down";
                     }
                   }
                 }
                 leaf-list port-status-tlv {
                   ordered-by user;
                   description "Values that need to be monitored in port status TLV";
                   type enumeration {
                     enum "blocked" {
                       description "Port is blocked";
                     }
                   }
                 }
                 leaf adjacency-loss {
                   description "Connectivity is lost";
                   type empty;
                 }
                 leaf rdi {
                   description "RDI received from some MEP";
                   type empty;
                 }
                 leaf connection-protection-tlv {
                   description "Values that need to be monitored in connection protection TLV";
                   type enumeration {
                     enum "using-working-path" {
                       description "Service traffic is using working path";
                     }
                     enum "using-protection-path" {
                       description "Service traffic is using protection path";
                     }
                   }
                 }
                 leaf server-mep-defects {
                   description "Defects which are monitored by Server MEP";
                   type enumeration {
                     enum "link-loss-defect" {
                       description "Detect link loss defects for the ethernet interface";
                     }
                     enum "l2circuit-defect" {
                       description "Detect l2circuit down defects";
                     }
                     enum "l2vpn-defect" {
                       description "Detect l2vpn down defects";
                     }
                   }
                 }
                 leaf-list ais-trigger-condition {
                   ordered-by user;
                   description "Defect condition that generates alarm indication signal";
                   type enumeration {
                     enum "all-defects" {
                       description "All defects";
                     }
                     enum "adjacency-loss" {
                       description "Loss of connectivity defects";
                     }
                     enum "cross-connect-ccm" {
                       description "Cross connect CCMs";
                     }
                     enum "erroneous-ccm" {
                       description "Erroneous CCMs";
                     }
                     enum "receive-ais" {
                       description "AIS message received";
                     }
                   }
                 }
               }
               container action {
                 uses apply-advanced;
                 leaf interface-down {
                   description "Mark the interface as down";
                   type empty;
                 }
                 leaf revertive-interface-down {
                   description "Wait for CC loss-threshold to bring back the interface up";
                   type empty;
                 }
                 leaf non-revertive-interface-down {
                   description "Interface will not be brought up when CC is received";
                   type empty;
                 }
                 leaf propagate-remote-mac-flush {
                   description "Remote mac-flush";
                   type empty;
                 }
                 leaf interface-group-down {
                   description "Mark the interface group as down";
                   type empty;
                 }
                 leaf asynchronous-notification {
                   description "Generate asynchronous notification (Laser-off for optical phys)";
                   type empty;
                 }
                 container log-and-generate-ais {
                   uses apply-advanced;
                   leaf-list level {
                     description "Server maintenance domain levels range";
                     type union {
                       type string {
                         pattern "<.*>|$.*";
                       }
                       type uint32 {
                         range "1 .. 7";
                       }
                     }
                   }
                   leaf interval {
                     description "Interval between AIS messages";
                     default "1s";
                     type enumeration {
                       enum "1s" {
                       }
                       enum "1m" {
                       }
                     }
                   }
                   leaf priority {
                     description "802.1p priority of AIS packet";
                     default "0";
                     type union {
                       type string {
                         pattern "<.*>|$.*";
                       }
                       type uint32 {
                         range "0 .. 7";
                       }
                     }
                   }
                 }
               }
               container clear-action {
                 uses apply-advanced;
                 container interface-down {
                   description "Mark the interface as down";
                   leaf peer-interface {
                     description "Mark the interface as down";
                     type empty;
                   }
                 }
                 leaf propagate-remote-mac-flush {
                   description "Remote  mac flush";
                   type empty;
                 }
               }
               container default-actions {
                 description "Action that needs to be taken";
                 uses apply-advanced;
                 leaf interface-down {
                   description "Bring the interface down";
                   type empty;
                 }
               }
             }
             list server-mep {
               key name;
               ordered-by user;
               description "Server MEP to use when generation of AIS is required to monitor different services";
               leaf name {
                 description "Identifier for Server MEP";
                 type union {
                   type string {
                     pattern "<.*>|$.*";
                   }
                   type uint16 {
                     range "1 .. 8191";
                   }
                 }
               }
               uses apply-advanced;
               container protocol {
                 presence "enable protocol";
                 description "Protocol that needs to be monitored by Server MEP";
                 uses apply-advanced;
                 choice protocol {
                   case case_1 {
                     container l2circuit {
                       presence "enable l2circuit";
                       description "Protocol that need to be monitored is l2circuit protocol";
                       container interface {
                         presence "enable interface";
                         description "Interface which is participating in l2circuit service";
                         leaf interface-name {
                           description "Interface name";
                           type union {
                             type jt:interface-name;
                             type string {
                               pattern "<.*>|$.*";
                             }
                           }
                         }
                       }
                     }
                   }
                   case case_2 {
                     container l2vpn {
                       presence "enable l2vpn";
                       description "Protocol that need to be monitored is l2vpn protocol";
                       container interface {
                         presence "enable interface";
                         description "Interface which is participating in l2vpn service";
                         leaf interface-name {
                           description "Interface name";
                           type union {
                             type jt:interface-name;
                             type string {
                               pattern "<.*>|$.*";
                             }
                           }
                         }
                       }
                     }
                   }
                   case case_3 {
                     container ethernet {
                       presence "enable ethernet";
                       description "Protocol that need to be monitored is physical ethernet service";
                       container interface {
                         presence "enable interface";
                         description "Interface which is going to be monitored";
                         leaf interface-name {
                           description "Interface name";
                           type union {
                             type jt:interface-device;
                             type string {
                               pattern "<.*>|$.*";
                             }
                           }
                         }
                       }
                     }
                   }
                 }
               }
               container action-profile {
                 presence "enable action-profile";
                 description "Attached action profile for this Server MEP";
                 uses apply-advanced;
                 leaf action-profile-name {
                   description "Name of the action profile";
                   type string;
                 }
               }
             }
             container policer {
               description "Rate limit Ethernet OAM packets for all sessions";
               uses apply-advanced;
               leaf continuity-check {
                 description "Policer to rate limit Continuity Check Ethernet OAM messages";
                 type string;
               }
               leaf other {
                 description "Policer to rate limit non Continuity Check Ethernet OAM messages";
                 type string;
               }
               leaf all {
                 description "Policer to rate limit all Ethernet OAM messages";
                 type string;
               }
             }
             container linktrace {
               presence "enable linktrace";
               description "Linktrace protocol global options";
               uses apply-advanced;
               leaf path-database-size {
                 description "Number of linktrace reply entries to be stored per linktrace request";
                 default "100";
                 type union {
                   type string {
                     pattern "<.*>|$.*";
                   }
                   type uint32 {
                     range "1 .. 255";
                   }
                 }
               }
               leaf age {
                 description "Time after which a stale request-response entry is deleted";
                 default "10m";
                 type enumeration {
                   enum "10s" {
                   }
                   enum "30s" {
                   }
                   enum "1m" {
                   }
                   enum "10m" {
                   }
                   enum "30m" {
                   }
                 }
               }
             }
             list maintenance-domain {
               key name;
               description "Maintenance domain configuration";
               leaf name {
                 type string;
               }
               uses apply-advanced;
               list bridge-domain {
                 key name;
                 ordered-by user;
                 description "Bridge-domain information for the default maintenance domain";
                 leaf name {
                   description "Bridge domain name";
                   type string;
                 }
                 leaf-list vlan-id {
                   ordered-by user;
                   description "VLAN id";
                   type string;
                 }
               }
               list vlan {
                 key name;
                 ordered-by user;
                 description "VLAN information for the default maintenance domain";
                 leaf name {
                   description "VLAN name";
                   type string;
                 }
               }
               list virtual-switch {
                 key name;
                 ordered-by user;
                 description "Virtual switch Bridge-domain information for the default maintenance domain";
                 leaf name {
                   description "Routing instance of type virtual switch";
                   type string;
                 }
                 uses apply-advanced;
                 list bridge-domain {
                   key name;
                   ordered-by user;
                   leaf name {
                     description "Bridge domain name";
                     type string;
                   }
                   leaf-list vlan-id {
                     ordered-by user;
                     description "VLAN id";
                     type string;
                   }
                 }
               }
               list instance {
                 key name;
                 ordered-by user;
                 description "VPLS instance name for the default maintenance domain";
                 leaf name {
                   description "VPLS routing instance name";
                   type string;
                 }
               }
               list interface {
                 key name;
                 ordered-by user;
                 description "Name of interface for the default maintenance domain";
                 leaf name {
                   description "Interface name";
                   type union {
                     type jt:interface-unit;
                     type string {
                       pattern "<.*>|$.*";
                     }
                   }
                 }
               }
               leaf level {
                 description "Level value for maintenance domain";
                 type union {
                   type string {
                     pattern "<.*>|$.*";
                   }
                   type uint8 {
                     range "0 .. 7";
                   }
                 }
               }
               leaf name-format {
                 description "Format of maintenance domain name";
                 type enumeration {
                   enum "none" {
                     description "No format specified";
                   }
                   enum "dns" {
                     description "Character string similar to Domain Name System name";
                   }
                   enum "mac+2oct" {
                     description "MAC address with 2 octet integer (xx:xx:xx:xx:xx:xx.Y format)";
                   }
                   enum "character-string" {
                     description "Character string";
                   }
                 }
               }
               leaf mip-half-function {
                 description "Half function to be implemented by MIP";
                 default "none";
                 type enumeration {
                   enum "none" {
                     description "No MHFs should be created";
                   }
                   enum "default" {
                     description "Create MHF as per IEEE 802.1ag specifications for defMHFDefault";
                   }
                   enum "explicit" {
                     description "Create MHF as per IEEE 802.1ag specifications for defMHFExplicit";
                   }
                 }
               }
               list maintenance-association {
                 key name;
                 description "Maintenance association configuration";
                 leaf name {
                   description "Name of maintenance association in IEEE compliant format";
                   type string {
                     length "1 .. 45";
                   }
                 }
                 uses apply-advanced;
                 leaf debug-session {
                   description "Debug the CFM session";
                   type empty;
                 }
                 leaf short-name-format {
                   description "Format of Maintenance Association Name";
                   type enumeration {
                     enum "2octet" {
                       description "An integer in the range 0..65535";
                     }
                     enum "rfc-2685-vpn-id" {
                       description "VPN identifier that complies with RFC 2685";
                     }
                     enum "vlan" {
                       description "Primary VLAN identifier";
                     }
                     enum "character-string" {
                       description "Character string";
                     }
                     enum "icc" {
                       description "ITU Carrier Code";
                     }
                   }
                 }
                 container protect-maintenance-association {
                   description "Maintenance association used for connection protection";
                   leaf ma-name {
                     description "Name of the protect maintenance association";
                     type string {
                       length "1 .. 45";
                     }
                   }
                   leaf aps-profile {
                     description "Name of the automatic-protection-switching profile";
                     type string;
                   }
                   leaf detect-path-type {
                     description "Enable detection of working and protect paths";
                     type empty;
                   }
                 }
                 leaf primary-vid {
                   description "VLAN id";
                   type string;
                 }
                 container continuity-check {
                   presence "enable continuity-check";
                   description "Continuity check configuration";
                   uses apply-advanced;
                   leaf interval {
                     description "Interval between continuity-check messages";
                     default "1m";
                     type enumeration {
                       enum "10ms" {
                       }
                       enum "100ms" {
                       }
                       enum "1s" {
                       }
                       enum "10s" {
                       }
                       enum "1m" {
                       }
                       enum "10m" {
                       }
                       enum "3.3ms" {
                       }
                     }
                   }
                   leaf loss-threshold {
                     description "Number of continuity-check messages lost before marking endpoint as down";
                     default "3";
                     type union {
                       type string {
                         pattern "<.*>|$.*";
                       }
                       type uint32 {
                         range "3 .. 256";
                       }
                     }
                   }
                   leaf hold-interval {
                     description "Time before flushing MEP database if no updates occur";
                     default "10";
                     units "minutes";
                     type union {
                       type string {
                         pattern "<.*>|$.*";
                       }
                       type uint32 {
                         range "1 .. 30240";
                       }
                     }
                   }
                   leaf port-status-tlv {
                     description "Include port status TLV in CCM";
                     type empty;
                   }
                   leaf interface-status-tlv {
                     description "Include interface status TLV in CCM";
                     type empty;
                   }
                   leaf connection-protection-tlv {
                     description "Include connection protection OUI TLV in CCM";
                     type empty;
                   }
                   leaf convey-loss-threshold {
                     description "Include Loss Threshold OUI TLV in CCM";
                     type empty;
                   }
                   leaf interface-status-send-rdi {
                     description "Send RDI on interface operation status down in CCM";
                     type empty;
                   }
                   container sendid-tlv {
                     description "Include sendid-tlv in CCM/LBM/LTM";
                     uses apply-advanced;
                     leaf send-chassis-tlv {
                       description "Attach Chassis ID & Mgmt Addr to CCM/LBM/LTM";
                       type empty;
                     }
                   }
                 }
                 leaf mip-half-function {
                   description "Half function to be implemented by MIP";
                   default "defer";
                   type enumeration {
                     enum "none" {
                       description "No MHFs should be created";
                     }
                     enum "default" {
                       description "Create MHF as per IEEE 802.1ag specifications for defMHFDefault";
                     }
                     enum "explicit" {
                       description "Create MHF as per IEEE 802.1ag specifications for defMHFExplicit";
                     }
                     enum "defer" {
                       description "Create MHF as per IEEE 802.1ag specifications for defMHFDefer";
                     }
                   }
                 }
                 list mep {
                   key name;
                   ordered-by user;
                   description "Maintenance association endpoint configuration";
                   leaf name {
                     description "Identifier for maintenance association endpoint";
                     type union {
                       type string {
                         pattern "<.*>|$.*";
                       }
                       type uint16 {
                         range "1 .. 8191";
                       }
                     }
                   }
                   uses apply-advanced;
                   container interface {
                     presence "enable interface";
                     description "Name of interface";
                     leaf interface-name {
                       type union {
                         type jt:interface-unit;
                         type string {
                           pattern "<.*>|$.*";
                         }
                       }
                     }
                     leaf vlan {
                       description "Trunk port interface VLAN identifier";
                       type union {
                         type string {
                           pattern "<.*>|$.*";
                         }
                         type uint32 {
                           range "1 .. 4094";
                         }
                       }
                     }
                     choice connection-type {
                       case case_1 {
                         leaf working {
                           description "Monitory the primary path";
                           type empty;
                         }
                       }
                       case case_2 {
                         leaf protect {
                           description "Monitory the protect path";
                           type empty;
                         }
                       }
                     }
                   }
                   leaf direction {
                     description "Direction of maintenance endpoint";
                     default "down";
                     type enumeration {
                       enum "up" {
                       }
                       enum "down" {
                       }
                     }
                   }
                   leaf priority {
                     description "802.1p priority of continuity-check and link-trace packet";
                     default "0";
                     type union {
                       type string {
                         pattern "<.*>|$.*";
                       }
                       type uint32 {
                         range "0 .. 7";
                       }
                     }
                   }
                   leaf auto-discovery {
                     description "Accept continuity-check messages from all remote MEPs";
                     type empty;
                   }
                   leaf action-profile {
                     description "Name of the action profile";
                     type string;
                   }
                   list remote-mep {
                     key name;
                     ordered-by user;
                     description "Remote maintenance association endpoint configuration";
                     leaf name {
                       description "Identifier for remote maintenance association endpoint";
                       type union {
                         type string {
                           pattern "<.*>|$.*";
                         }
                         type uint16 {
                           range "1 .. 8191";
                         }
                       }
                     }
                     uses apply-advanced;
                     leaf action-profile {
                       description "Name of the action profile";
                       type string;
                     }
                     container interface-group {
                       presence "enable interface-group";
                       description "Mark this interface group down Profile configured with action interface-group-down";
                       uses apply-advanced;
                       leaf interface-device-name {
                         description "Interface device name";
                         type union {
                           type jt:interface-device;
                           type string {
                             pattern "<.*>|$.*";
                           }
                         }
                       }
                       leaf-list unit-list {
                         description "One or more logical interface unit numbers";
                         type jt:range;
                       }
                     }
                     list sla-iterator-profile {
                       key name;
                       ordered-by user;
                       description "Name of the iterator profile";
                       leaf name {
                         type string;
                       }
                       uses apply-advanced;
                       leaf iteration-count {
                         description "Iterations to partake for acquiring SLA measurements";
                         units "frames";
                         type union {
                           type string {
                             pattern "<.*>|$.*";
                           }
                           type uint32 {
                             range "1 .. 65535";
                           }
                         }
                       }
                       leaf priority {
                         description "The vlan pcp value to be sent in the Y.1731 frame";
                         type union {
                           type string {
                             pattern "<.*>|$.*";
                           }
                           type uint32 {
                             range "0 .. 7";
                           }
                         }
                       }
                       leaf data-tlv-size {
                         description "Size of the data-tlv portion of Y.1731 frame";
                         units "bytes";
                         type union {
                           type string {
                             pattern "<.*>|$.*";
                           }
                           type uint32 {
                             range "1 .. 1400";
                           }
                         }
                       }
                     }
                     leaf detect-loc {
                       description "Detects initial loss of connectivity with remote mep";
                       type empty;
                     }
                   }
                   leaf lowest-priority-defect {
                     description "Lowest priority defect that is allowed to generate a fault alarm";
                     type enumeration {
                       enum "all-defects" {
                         description "Allows all defects";
                       }
                       enum "mac-rem-err-xcon" {
                         description "Allows only MAC, not receiving CCM, erroneous CCM and cross connect defects";
                       }
                       enum "rem-err-xcon" {
                         description "Allows only not receiving CCM, erroneous CCM and cross connect CCM defects";
                       }
                       enum "err-xcon" {
                         description "Allows only erroneous CCM and cross connect CCM defects";
                       }
                       enum "xcon" {
                         description "Allows only cross connect CCM defect";
                       }
                       enum "no-defect" {
                         description "Allows no defect";
                       }
                     }
                   }
                 }
                 container policer {
                   description "Rate limit Ethernet OAM packets for this session";
                   uses apply-advanced;
                   leaf continuity-check {
                     description "Policer to rate limit Continuity Check Ethernet OAM messages";
                     type string;
                   }
                   leaf other {
                     description "Policer to rate limit non Continuity Check Ethernet OAM messages";
                     type string;
                   }
                   leaf all {
                     description "Policer to rate limit all Ethernet OAM messages";
                     type string;
                   }
                 }
               }
             }
             container sendid-tlv {
               description "Include sendid-tlv in CCM/LBM/LTM";
               uses apply-advanced;
               leaf send-chassis-tlv {
                 description "Attach Chassis ID & Mgmt Addr to CCM/LBM/LTM";
                 type empty;
               }
             }
           }
           list evcs {
             key name;
             description "Ethernet virtual circuits configuration";
             leaf name {
               description "EVC id";
               type string {
                 length "1 .. 100";
               }
             }
             uses apply-advanced;
             container evc-protocol {
               description "Signaling protocol to monitor EVC status";
               choice protocol {
                 case case_1 {
                   container cfm {
                     presence "enable cfm";
                     description "Connectivity fault management";
                     leaf maintenance-domain {
                       description "Maintenance domain name";
                       type string;
                     }
                     leaf maintenance-association {
                       description "Maintenance association name";
                       type string;
                     }
                     leaf mep {
                       description "Identifier for maintenance association endpoint";
                       type union {
                         type string {
                           pattern "<.*>|$.*";
                         }
                         type uint16 {
                           range "1 .. 8191";
                         }
                       }
                     }
                     container faults {
                       description "CFM faults to trigger ELMI";
                       uses apply-advanced;
                       leaf rdi {
                         description "RDI received from some MEP";
                         type empty;
                       }
                     }
                   }
                 }
                 case case_2 {
                   container vpls {
                     presence "enable vpls";
                     description "Virtual private LAN service (BGP/LDP)";
                     leaf routing-instance {
                       description "Routing instance name";
                       type string;
                     }
                   }
                 }
                 case case_3 {
                   container l2circuit {
                     description "L2circuit";
                     uses apply-advanced;
                     container interface {
                       description "Name of interface forming the Layer 2 circuit";
                       leaf interface-name {
                         type union {
                           type jt:interface-name;
                           type string {
                             pattern "<.*>|$.*";
                           }
                         }
                       }
                     }
                   }
                 }
                 case case_4 {
                   container l2vpn {
                     description "L2vpn";
                     uses apply-advanced;
                     container interface {
                       description "Name of interface forming the Layer 2 VPN";
                       leaf interface-name {
                         type union {
                           type jt:interface-name;
                           type string {
                             pattern "<.*>|$.*";
                           }
                         }
                       }
                     }
                   }
                 }
               }
             }
             leaf remote-uni-count {
               description "Number of remote UNIs in the EVC";
               default "1";
               type union {
                 type string {
                   pattern "<.*>|$.*";
                 }
                 type uint8 {
                   range "1 .. 255";
                 }
               }
             }
             leaf async-status-msg-transmit-interval {
               description "Time interval between E-LMI async status messages per EVC";
               default "10";
               units "milliseconds";
               type union {
                 type string {
                   pattern "<.*>|$.*";
                 }
                 type int32 {
                   range "1 .. 10000";
                 }
               }
             }
             leaf multipoint-to-multipoint {
               description "Multipoint to Multipoint EVC";
               type empty;
             }
           }
           container lmi {
             presence "enable lmi";
             description "Ethernet local management interface configuration";
             uses apply-advanced;
             container traceoptions {
               description "Trace options for ethernet local management interface";
               uses apply-advanced;
               leaf no-remote-trace {
                 description "Disable remote tracing";
                 type empty;
               }
               container file {
                 description "Trace file information";
                 leaf filename {
                   description "Name of file in which to write trace information";
                   type string {
                     length "1 .. 1024";
                   }
                 }
                 leaf size {
                   description "Maximum trace file size";
                   type string;
                 }
                 leaf files {
                   description "Maximum number of trace files";
                   default "3";
                   type union {
                     type string {
                       pattern "<.*>|$.*";
                     }
                     type uint32 {
                       range "2 .. 1000";
                     }
                   }
                 }
                 choice world-readable-choice {
                   leaf world-readable {
                     description "Allow any user to read the log file";
                     type empty;
                   }
                   leaf no-world-readable {
                     description "Don't allow any user to read the log file";
                     type empty;
                   }
                 }
                 leaf match {
                   description "Regular expression for lines to be logged";
                   type jt:regular-expression;
                 }
               }
               list flag {
                 key name;
                 ordered-by user;
                 description "Tracing parameters";
                 leaf name {
                   type enumeration {
                     enum "configuration" {
                       description "Trace configuration events";
                     }
                     enum "routing-socket" {
                       description "Trace routing socket events";
                     }
                     enum "protocol" {
                       description "Trace protocol processing events";
                     }
                     enum "init" {
                       description "Trace events related to protocol daemon start-up";
                     }
                     enum "error" {
                       description "Trace events related to catestrophic errors in daemon";
                     }
                     enum "packet" {
                       description "Trace events related to packet flow";
                     }
                     enum "all" {
                       description "Trace everything";
                     }
                   }
                 }
               }
             }
             leaf status-counter {
               description "E-LMI status counter (N393)";
               default "4";
               type union {
                 type string {
                   pattern "<.*>|$.*";
                 }
                 type uint8 {
                   range "2 .. 10";
                 }
               }
             }
             leaf polling-verification-timer {
               description "Polling verification timer (T392)";
               default "15";
               units "seconds";
               type union {
                 type string {
                   pattern "<.*>|$.*";
                 }
                 type uint8 {
                   range "5 .. 30";
                 }
               }
             }
             list interface {
               key name;
               description "Interface options";
               leaf name {
                 type union {
                   type jt:interface-device;
                   type string {
                     pattern "<.*>|$.*";
                   }
                 }
               }
               uses apply-advanced;
               leaf uni-id {
                 description "UNI identifier";
                 type string {
                   length "1 .. 64";
                 }
               }
               leaf status-counter {
                 description "E-LMI status counter (N393)";
                 default "4";
                 type union {
                   type string {
                     pattern "<.*>|$.*";
                   }
                   type uint8 {
                     range "2 .. 10";
                   }
                 }
               }
               leaf polling-verification-timer {
                 description "Polling verification timer (T392)";
                 default "15";
                 units "seconds";
                 type union {
                   type string {
                     pattern "<.*>|$.*";
                   }
                   type uint8 {
                     range "5 .. 30";
                   }
                 }
               }
               leaf evc-map-type {
                 description "CE-VLAN ID/EVC map type";
                 default "bundling";
                 type enumeration {
                   enum "all-to-one-bundling" {
                     description "All to one bundling";
                   }
                   enum "service-multiplexing" {
                     description "Service multiplexing with no bundling";
                   }
                   enum "bundling" {
                     description "Bundling with service multiplexing";
                   }
                 }
               }
               list evc {
                 key name;
                 description "EVC configuration";
                 leaf name {
                   description "EVC identifier";
                   type string {
                     length "1 .. 100";
                   }
                 }
                 uses apply-advanced;
                 leaf default-evc {
                   description "Default EVC";
                   type empty;
                 }
                 leaf-list vlan-list {
                   description "Vlans mapped to this EVC";
                   type jt:vlan-range;
                 }
               }
             }
           }
           container fnp {
             presence "enable fnp";
             description "Failure notification protocol configuration";
             uses apply-advanced;
             container traceoptions {
               description "Tracing options for FNP";
               uses apply-advanced;
               container file {
                 description "Trace file options";
                 leaf filename {
                   description "Name of file in which to write trace information";
                   type string {
                     length "1 .. 1024";
                   }
                 }
                 leaf replace {
                   description "Replace trace file rather than appending to it";
                   status deprecated;
                   type empty;
                 }
                 leaf size {
                   description "Maximum trace file size";
                   type string;
                 }
                 leaf files {
                   description "Maximum number of trace files";
                   default "10";
                   type union {
                     type string {
                       pattern "<.*>|$.*";
                     }
                     type uint32 {
                       range "2 .. 1000";
                     }
                   }
                 }
                 leaf no-stamp {
                   description "Do not timestamp trace file";
                   status deprecated;
                   type empty;
                 }
                 choice world-readable-choice {
                   leaf world-readable {
                     description "Allow any user to read the log file";
                     type empty;
                   }
                   leaf no-world-readable {
                     description "Don't allow any user to read the log file";
                     type empty;
                   }
                 }
               }
               list flag {
                 key name;
                 ordered-by user;
                 description "Tracing parameters";
                 leaf name {
                   type enumeration {
                     enum "events" {
                       description "Trace protocol events";
                     }
                     enum "pdu" {
                       description "Trace PDU reception and transmission";
                     }
                     enum "timers" {
                       description "Trace protocol timers";
                     }
                     enum "error" {
                       description "Trace all failure conditions";
                     }
                     enum "all" {
                       description "Trace all";
                     }
                   }
                 }
               }
             }
             leaf interval {
               description "Interval between FNP messages";
               default "1s";
               type enumeration {
                 enum "100ms" {
                 }
                 enum "1s" {
                 }
                 enum "10s" {
                 }
                 enum "1m" {
                 }
                 enum "10m" {
                 }
               }
             }
             leaf loss-threshold {
               description "Number of FNP messages lost before clearing FNP state";
               default "4";
               type union {
                 type string {
                   pattern "<.*>|$.*";
                 }
                 type uint8 {
                   range "3 .. 255";
                 }
               }
             }
             list interface {
               key name;
               ordered-by user;
               description "Interface configuration";
               leaf name {
                 type union {
                   type jt:interface-name;
                   type string {
                     pattern "<.*>|$.*";
                   }
                 }
               }
               uses apply-advanced;
               leaf domain-id {
                 description "Ethernet domain identifier";
                 default "0";
                 type union {
                   type uint32;
                   type string {
                     pattern "<.*>|$.*";
                   }
                 }
               }
             }
           }
         }
         container gre-tunnel {
           presence "enable gre-tunnel";
           uses apply-advanced;
           container traceoptions {
             description "Trace options for GRE keepalives";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Tracing parameters";
               leaf name {
                 type enumeration {
                   enum "configuration" {
                     description "Trace configuration events";
                   }
                   enum "routing-socket" {
                     description "Trace routing socket events";
                   }
                   enum "protocol" {
                     description "Trace protocol processing events";
                   }
                   enum "snmp" {
                     description "Trace snmp processing events";
                   }
                   enum "all" {
                     description "Trace everything";
                   }
                 }
               }
             }
           }
           list interface {
             key name;
             ordered-by user;
             leaf name {
               description "Interface name";
               type union {
                 type jt:interface-unit;
                 type string {
                   pattern "<.*>|$.*";
                 }
               }
             }
             uses apply-advanced;
             leaf keepalive-time {
               description "Keepalive time";
               default "1";
               units "seconds";
               type union {
                 type string {
                   pattern "<.*>|$.*";
                 }
                 type int32 {
                   range "1 .. 50";
                 }
               }
             }
             leaf hold-time {
               description "Hold time";
               default "5";
               units "seconds";
               type union {
                 type string {
                   pattern "<.*>|$.*";
                 }
                 type int32 {
                   range "5 .. 250";
                 }
               }
             }
             leaf remote-end-source-address {
               description "     Remote end tunnel source address (GRE tunnel with static NAT)";
               type jt:ipv4addr;
             }
             leaf remote-end-destination-address {
               description "Remote end tunnel destination address (GRE tunnel with static NAT)";
               type jt:ipv4addr;
             }
           }
         }
       }
       container mld {
         presence "enable mld";
         description "MLD options";
         uses apply-advanced;
         container traceoptions {
           description "Trace options for MLD";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "packets" {
                   description "Trace all MLD packets";
                 }
                 enum "query" {
                   description "Trace MLD membership query messages";
                 }
                 enum "report" {
                   description "Trace membership report messages";
                 }
                 enum "leave" {
                   description "Trace leave group messages (MLDv2 only)";
                 }
                 enum "mtrace" {
                   description "Trace mtrace packets";
                 }
                 enum "group" {
                   description "Trace group operations";
                 }
                 enum "client-notification" {
                   description "Trace notifications";
                 }
                 enum "host-notification" {
                   description "Trace host notifications";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf maximum-transmit-rate {
           description "Maximum transmission rate (packets per second)";
           type union {
             type string {
               pattern "<.*>|$.*";
             }
             type uint32 {
               range "1 .. 10000";
             }
           }
         }
         leaf accounting {
           description "Enable join and leave event notification";
           type empty;
         }
         list interface {
           key name;
           ordered-by user;
           description "Interface options for MLD";
           leaf name {
             type string;
           }
           uses apply-advanced;
           choice enable-disable {
             case case_1 {
               leaf disable {
                 description "Disable MLD on this interface";
                 type empty;
               }
             }
           }
           leaf version {
             description "Set mld version number on this interface";
             type union {
               type string {
                 pattern "<.*>|$.*";
               }
               type uint8 {
                 range "1 .. 2";
               }
             }
           }
           container static {
             description "Static group or source membership";
             uses apply-advanced;
             list group {
               key name;
               ordered-by user;
               description "IP multicast group address";
               leaf name {
                 description "IP multicast group address";
                 type jt:ipv6addr;
               }
               uses apply-advanced;
               leaf group-increment {
                 description "Mask for the incrementing group IP address";
                 type jt:ipv6addr;
               }
               leaf group-count {
                 description "Number of groups";
                 type union {
                   type string {
                     pattern "<.*>|$.*";
                   }
                   type uint32 {
                     range "1 .. 512";
                   }
                 }
               }
               leaf exclude {
                 description "Exclude sources";
                 type empty;
               }
               list source {
                 key name;
                 ordered-by user;
                 description "IP multicast source address";
                 leaf name {
                   description "Source address of IP multicast data";
                   type jt:ipv6addr;
                 }
                 uses apply-advanced;
                 leaf source-increment {
                   description "Mask for the incrementing source IP address";
                   type jt:ipv6addr;
                 }
                 leaf source-count {
                   description "Number of sources";
                   type union {
                     type string {
                       pattern "<.*>|$.*";
                     }
                     type uint32 {
                       range "1 .. 1024";
                     }
                   }
                 }
               }
             }
           }
           leaf ssm-map {
             description "Map for ssm translation of mld v1 messages";
             type string;
           }
           leaf-list ssm-map-policy {
             ordered-by user;
             description "SSM map policy name";
             type jt:policy-algebra;
           }
           leaf immediate-leave {
             description "Group removed immediately, last membership query not sent";
             type empty;
           }
           leaf-list group-policy {
             ordered-by user;
             description "Group filter applied to incoming mld report messages";
             type jt:policy-algebra;
           }
           leaf group-limit {
             description "Maximum number of (source,group) per interface";
             type union {
               type string {
                 pattern "<.*>|$.*";
               }
               type uint16 {
                 range "1 .. 32767";
               }
             }
           }
           leaf group-threshold {
             description "Percentage of group-limit at which to start generating warnings";
             type union {
               type string {
                 pattern "<.*>|$.*";
               }
               type uint16 {
                 range "1 .. 100";
               }
             }
           }
           leaf log-interval {
             description "Time between consecutive log messages";
             type union {
               type string {
                 pattern "<.*>|$.*";
               }
               type uint32 {
                 range "6 .. 32767";
               }
             }
           }
           choice accounting-choice {
             leaf accounting {
               description "Enable join and leave event notification";
               type empty;
             }
             leaf no-accounting {
               description "Don't enable join and leave event notification";
               type empty;
             }
           }
           container passive {
             presence "enable passive";
             description "Suppress sending and receiving mld messages";
             leaf allow-receive {
               description "Allow receiving mld messages";
               type empty;
             }
             leaf send-general-query {
               description "Send mld general query messages";
               type empty;
             }
             leaf send-group-query {
               description "Send mld group query messages";
               type empty;
             }
           }
           leaf-list oif-map {
             ordered-by user;
             description "Output interface map";
             type jt:policy-algebra;
           }
           leaf distributed {
             description "Distributed MLD interface";
             type empty;
           }
         }
       }
       container pim {
         description "PIM configuration";
         uses juniper-protocols-pim;
       }
       container router-advertisement {
         description "IPv6 router advertisement options";
         uses apply-advanced;
         container traceoptions {
           description "Trace options for router advertisement";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
           }
         }
         list interface {
           key name;
           ordered-by user;
           description "Interfaces on which to configure router advertisement";
           leaf name {
             type string;
           }
           uses apply-advanced;
           leaf preference {
             description "Set the Preference for Router Selection";
             type enumeration {
               enum "medium" {
                 description "Medium / (Default)";
               }
               enum "high" {
                 description "High";
               }
               enum "low" {
                 description "Low";
               }
             }
           }
           leaf max-advertisement-interval {
             description "Maximum advertisement interval";
             units "seconds";
             type union {
               type string {
                 pattern "<.*>|$.*";
               }
               type uint32 {
                 range "4 .. 1800";
               }
             }
           }
           leaf min-advertisement-interval {
             description "Minimum advertisement interval";
             units "seconds";
             type union {
               type string {
                 pattern "<.*>|$.*";
               }
               type uint32 {
                 range "3 .. 1350";
               }
             }
           }
           choice managed-configuration-choice {
             leaf managed-configuration {
               description "Set managed address configuration";
               type empty;
             }
             leaf no-managed-configuration {
               description "Don't set managed address configuration";
               type empty;
             }
           }
           choice other-stateful-configuration-choice {
             leaf other-stateful-configuration {
               description "Set other stateful configuration";
               type empty;
             }
             leaf no-other-stateful-configuration {
               description "Don't set other stateful configuration";
               type empty;
             }
           }
           choice link-mtu-choice {
             leaf link-mtu {
               description "Link MTU";
               type empty;
             }
             leaf no-link-mtu {
               description "Don't link MTU";
               type empty;
             }
           }
           leaf solicit-router-advertisement-unicast {
             description "Enable solicited router advertisement as unicast";
             type empty;
           }
           leaf reachable-time {
             description "Reachable time";
             units "milliseconds";
             type union {
               type string {
                 pattern "<.*>|$.*";
               }
               type uint32 {
                 range "0 .. 3600000";
               }
             }
           }
           leaf retransmit-timer {
             description "Retransmit timer";
             units "milliseconds";
             type union {
               type string {
                 pattern "<.*>|$.*";
               }
               type uint32 {
                 range "0 .. 4294967295";
               }
             }
           }
           leaf virtual-router-only {
             description "Send advertisements only for vrrp-inet6-group";
             type empty;
           }
           leaf current-hop-limit {
             description "Current hop limit";
             type union {
               type string {
                 pattern "<.*>|$.*";
               }
               type uint32 {
                 range "0 .. 255";
               }
             }
           }
           leaf default-lifetime {
             description "Router lifetime";
             units "seconds";
             type union {
               type string {
                 pattern "<.*>|$.*";
               }
               type uint32 {
                 range "0 .. 9000";
               }
             }
           }
           list downstream {
             key name;
             ordered-by user;
             description "Configure the list of downstream interfaces for RA proxy";
             leaf name {
               description "Configure the downstream interface for RA proxy";
               type string;
             }
             uses apply-advanced;
           }
           leaf upstream-mode {
             description "Configure the interface as upstream interface for RA proxy";
             type empty;
           }
           leaf downstream-mode {
             description "Configure the interface as downstream interface for RA proxy";
             type empty;
           }
           leaf parameter-preference {
             description "Preference to select configured or proxied parameters for downstream interface";
             type enumeration {
               enum "proxied" {
                 description "Send proxied parameters on downstream interface";
               }
               enum "configured" {
                 description "Send configured parameters on downstream interface";
               }
             }
           }
           leaf passive-mode {
             description "RA receive only mode";
             type empty;
           }
           list dns-server-address {
             key name;
             ordered-by user;
             description "Recursive DNS address configuration";
             max-elements 3;
             leaf name {
               description "DNS address to be advertised";
               type string;
             }
             uses apply-advanced;
             leaf lifetime {
               description "DNS address lifetime";
               default "1800";
               units "seconds";
               type union {
                 type string {
                   pattern "<.*>|$.*";
                 }
                 type uint32 {
                   range "0 .. 4294967295";
                 }
               }
             }
           }
           list prefix {
             key name;
             ordered-by user;
             description "Prefix configuration";
             leaf name {
               description "Prefix to be advertised";
               type jt:ipv6prefix;
             }
             uses apply-advanced;
             leaf valid-lifetime {
               description "Valid lifetime (fixed)";
               units "seconds";
               type union {
                 type string {
                   pattern "<.*>|$.*";
                 }
                 type uint32 {
                   range "0 .. 4294967295";
                 }
               }
             }
             choice on-link-choice {
               leaf on-link {
                 description "Set on-link flag";
                 type empty;
               }
               leaf no-on-link {
                 description "Don't set on-link flag";
                 type empty;
               }
             }
             leaf preferred-lifetime {
               description "Preferred lifetime (fixed)";
               units "seconds";
               type union {
                 type string {
                   pattern "<.*>|$.*";
                 }
                 type uint32 {
                   range "0 .. 4294967295";
                 }
               }
             }
             choice autonomous-choice {
               leaf autonomous {
                 description "Set autonomous flag";
                 type empty;
               }
               leaf no-autonomous {
                 description "Don't set autonomous flag";
                 type empty;
               }
             }
           }
           list dns-search-list {
             key name;
             ordered-by user;
             description "DNS search list configuration";
             leaf name {
               description "DNS search list name";
               type string;
             }
             uses apply-advanced;
             leaf lifetime {
               description "DNS search list lifetime";
               default "5400";
               units "seconds";
               type union {
                 type string {
                   pattern "<.*>|$.*";
                 }
                 type uint32 {
                   range "0 .. 4294967295";
                 }
               }
             }
           }
           list rio-prefix {
             key name;
             ordered-by user;
             description "Route information option configuration";
             leaf name {
               description "Prefix to be advertised";
               type jt:ipv6prefix;
             }
             uses apply-advanced;
             leaf rio-lifetime {
               description "Route information lifetime";
               units "seconds";
               type union {
                 type string {
                   pattern "<.*>|$.*";
                 }
                 type uint32 {
                   range "0 .. 4294967295";
                 }
               }
             }
             leaf rio-preference {
               description "Set the preference for route information";
               type enumeration {
                 enum "medium" {
                   description "Medium / Default";
                 }
                 enum "high" {
                   description "High";
                 }
                 enum "low" {
                   description "Low";
                 }
               }
             }
           }
           list nat-prefix {
             key name;
             ordered-by user;
             description "NAT prefix";
             leaf name {
               description "NAT prefix to be advertised";
               type jt:ipv6prefix;
             }
             uses apply-advanced;
             leaf lifetime {
               description "NAT prefix lifetime";
               units "seconds";
               type union {
                 type string {
                   pattern "<.*>|$.*";
                 }
                 type uint16 {
                   range "0 .. 65528";
                 }
               }
             }
           }
         }
         container ra-secure {
           description "Protect box against rogue incoming RA messages";
           uses apply-advanced;
           leaf accept-current-hop-limit-min {
             description "Current hop limit acceptable min for incoming RA";
             units "uint";
             type union {
               type string {
                 pattern "<.*>|$.*";
               }
               type uint32 {
                 range "1 .. 255";
               }
             }
           }
           leaf accept-current-hop-limit-max {
             description "Current hop acceptable min for incoming RA";
             units "uint";
             type union {
               type string {
                 pattern "<.*>|$.*";
               }
               type uint32 {
                 range "1 .. 255";
               }
             }
           }
           leaf accept-reachable-time-min {
             description "Reachable Time acceptable min for incoming RA";
             units "milliseconds";
             type union {
               type string {
                 pattern "<.*>|$.*";
               }
               type uint32 {
                 range "1000 .. 3600000";
               }
             }
           }
           leaf accept-reachable-time-max {
             description "Reachable Time acceptable max for incoming RA";
             units "milliseconds";
             type union {
               type string {
                 pattern "<.*>|$.*";
               }
               type uint32 {
                 range "1000 .. 3600000";
               }
             }
           }
           leaf accept-retransmit-time-min {
             description "Retransmit Time acceptable min for incoming RA";
             units "milliseconds";
             type union {
               type string {
                 pattern "<.*>|$.*";
               }
               type uint32 {
                 range "1000 .. 3600000";
               }
             }
           }
           leaf accept-retransmit-time-max {
             description "Retransmit Time acceptable min for incoming RA";
             units "milliseconds";
             type union {
               type string {
                 pattern "<.*>|$.*";
               }
               type uint32 {
                 range "1000 .. 3600000";
               }
             }
           }
         }
       }
     }
     container class-of-service {
       description "Class-of-service configuration";
       uses juniper-class-of-service-options;
     }
     container routing-options {
       description "Protocol-independent routing option configuration";
       uses apply-advanced;
       list rib {
         key name;
         description "Routing table options";
         leaf name {
           description "Routing table name";
           type string;
         }
         uses apply-advanced;
         container static {
           description "Static routes";
           uses apply-advanced;
           leaf rib-group {
             description "Routing table group";
             type string;
           }
           container defaults {
             description "Global route options";
             uses apply-advanced;
             choice retain-choice {
               leaf retain {
                 description "Always keep route in forwarding table";
                 type empty;
               }
               leaf no-retain {
                 description "Don't always keep route in forwarding table";
                 type empty;
               }
             }
             choice install-choice {
               leaf install {
                 description "Install route into forwarding table";
                 type empty;
               }
               leaf no-install {
                 description "Don't install route into forwarding table";
                 type empty;
               }
             }
             choice readvertise-choice {
               leaf readvertise {
                 description "Mark route as eligible to be readvertised";
                 type empty;
               }
               leaf no-readvertise {
                 description "Don't mark route as eligible to be readvertised";
                 type empty;
               }
             }
             choice resolve-choice {
               leaf resolve {
                 description "Allow resolution of indirectly connected next hops";
                 type empty;
               }
               leaf no-resolve {
                 description "Don't allow resolution of indirectly connected next hops";
                 type empty;
               }
             }
             leaf explicit-null {
               description "Allows service label to be popped and will lookup nexthop-table inet6.0";
               type empty;
             }
             choice longest-match-choice {
               leaf longest-match {
                 description "Always use longest prefix match to resolve next hops";
                 type empty;
               }
               leaf no-longest-match {
                 description "Don't always use longest prefix match to resolve next hops";
                 type empty;
               }
             }
             choice passive_flag {
               case case_1 {
                 leaf active {
                   description "Remove inactive route from forwarding table";
                   type empty;
                 }
               }
               case case_2 {
                 leaf passive {
                   description "Retain inactive route in forwarding table";
                   type empty;
                 }
               }
             }
             container metric {
               description "Metric value";
               presence "enable metric";
               uses rib_static_metric_type;
             }
             container metric2 {
               description "Metric value 2";
               presence "enable metric2";
               uses rib_static_metric_type;
             }
             container metric3 {
               description "Metric value 3";
               presence "enable metric3";
               uses rib_static_metric_type;
             }
             container metric4 {
               description "Metric value 4";
               presence "enable metric4";
               uses rib_static_metric_type;
             }
             container tag {
               description "Tag string";
               presence "enable tag";
               uses rib_static_metric_type;
             }
             container tag2 {
               description "Tag string 2";
               presence "enable tag2";
               uses rib_static_metric_type;
             }
             container preference {
               description "Preference value";
               presence "enable preference";
               uses rib_static_metric_type;
             }
             container preference2 {
               description "Preference value 2";
               presence "enable preference2";
               uses rib_static_metric_type;
             }
             container color {
               description "Color (preference) value";
               presence "enable color";
               uses rib_static_metric_type;
             }
             container color2 {
               description "Color (preference) value 2";
               presence "enable color2";
               uses rib_static_metric_type;
             }
             leaf-list community {
               ordered-by user;
               description "BGP community identifier";
               type jt:community;
             }
             container as-path {
               description "Autonomous system path";
               uses apply-advanced;
               leaf path {
                 description "Autonomous system path";
                 type string;
               }
               leaf origin {
                 type enumeration {
                   enum "igp" {
                     description "Path originated in the local IGP";
                   }
                   enum "egp" {
                     description "Path originated in another AS";
                   }
                   enum "incomplete" {
                     description "Path was learned by some other means";
                   }
                 }
               }
               leaf atomic-aggregate {
                 description "Add ATOMIC_AGGREGATE path attribute to route";
                 type empty;
               }
               container aggregator {
                 presence "enable aggregator";
                 description "Add AGGREGATOR path attribute to route";
               }
               leaf as-number {
                 description " Autonomous system number in plain number or 'higher 16bits'.'Lower 16 bits' (asdot notation) format";
                 type string {
                 }
               }
               leaf address {
                 description "Address of BGP system that formed the route";
                 type jt:ipv4addr;
               }
             }
           }
           list route {
             key name;
             description "Static route";
             leaf name {
               type jt:ipprefix;
             }
             uses apply-advanced;
             leaf priority {
               description "Static route priority high/medium/low";
               type enumeration {
                 enum "medium" {
                   description "Static route medium priority";
                 }
                 enum "low" {
                   description "Static route low priority";
                 }
                 enum "high" {
                   description "Static route high priority";
                 }
               }
             }
             choice next_hop {
               case case_1 {
                 leaf-list next-hop {
                   ordered-by user;
                   description "Next hop to destination";
                   type union {
                     type jt:ipaddr-or-interface;
                     type string {
                       pattern "<.*>|$.*";
                     }
                   }
                 }
               }
               case case_2 {
                 leaf reject {
                   description "Drop packets to destination; send ICMP unreachables";
                   type empty;
                 }
               }
               case case_3 {
                 leaf discard {
                   description "Drop packets to destination; send no ICMP unreachables";
                   type empty;
                 }
               }
               case case_4 {
                 leaf receive {
                   description "Install a receive route for the destination";
                   type empty;
                 }
               }
               case case_5 {
                 leaf next-table {
                   description "Next hop to another table";
                   type string {
                   }
                 }
               }
             }
             leaf description {
               description "Static route description";
               type string {
               }
             }
             list qualified-next-hop {
               key name;
               ordered-by user;
               description "Next hop with qualifiers";
               uses qualified_nh_obj;
             }
             leaf backup-pe-group {
               description "Multicast source redundancy group";
               type string;
             }
             container bfd-liveness-detection {
               description "Bidirectional Forwarding Detection (BFD) options";
               uses apply-advanced;
               leaf version {
                 description "BFD protocol version number";
                 default "automatic";
                 type enumeration {
                   enum "0" {
                     description "BFD version 0 (deprecated)";
                   }
                   enum "1" {
                     description "BFD version 1";
                   }
                   enum "automatic" {
                     description "Choose BFD version automatically";
                   }
                 }
               }
               leaf minimum-interval {
                 description "Minimum transmit and receive interval";
                 units "milliseconds";
                 type union {
                   type string {
                     pattern "<.*>|$.*";
                   }
                   type uint32 {
                     range "1 .. 255000";
                   }
                 }
               }
               leaf minimum-transmit-interval {
                 description "Minimum transmit interval";
                 status deprecated;
                 units "milliseconds";
                 type union {
                   type string {
                     pattern "<.*>|$.*";
                   }
                   type uint32 {
                     range "1 .. 255000";
                   }
                 }
               }
               leaf minimum-receive-interval {
                 description "Minimum receive interval";
                 units "milliseconds";
                 type union {
                   type string {
                     pattern "<.*>|$.*";
                   }
                   type uint32 {
                     range "1 .. 255000";
                   }
                 }
               }
               leaf multiplier {
                 description "Detection time multiplier";
                 default "3";
                 type union {
                   type string {
                     pattern "<.*>|$.*";
                   }
                   type uint32 {
                     range "1 .. 255";
                   }
                 }
               }
               leaf inline-disable {
                 description "Disable inline mode for this BFD session";
                 type empty;
               }
               leaf pdu-size {
                 description "BFD transport protocol payload size";
                 default "24";
                 type union {
                   type string {
                     pattern "<.*>|$.*";
                   }
                   type uint32 {
                     range "24 .. 9000";
                   }
                 }
               }
               choice adaptation-choice {
                 case case_1 {
                   leaf no-adaptation {
                     description "Disable adaptation";
                     type empty;
                   }
                 }
               }
               container transmit-interval {
                 description "Transmit-interval options";
                 uses apply-advanced;
                 leaf minimum-interval {
                   description "Minimum transmit interval";
                   units "milliseconds";
                   type union {
                     type string {
                       pattern "<.*>|$.*";
                     }
                     type uint32 {
                       range "1 .. 255000";
                     }
                   }
                 }
                 leaf threshold {
                   description "High transmit interval triggering a trap";
                   units "milliseconds";
                   type union {
                     type uint32;
                     type string {
                       pattern "<.*>|$.*";
                     }
                   }
                 }
               }
               container detection-time {
                 description "Detection-time options";
                 uses apply-advanced;
                 leaf threshold {
                   description "High detection-time triggering a trap";
                   units "milliseconds";
                   type union {
                     type uint32;
                     type string {
                       pattern "<.*>|$.*";
                     }
                   }
                 }
               }
               container authentication {
                 description "Authentication options";
                 uses apply-advanced;
                 leaf key-chain {
                   description "Key chain name";
                   type string;
                 }
                 leaf algorithm {
                   description "Algorithm name";
                   type enumeration {
                     enum "simple-password" {
                       description "Simple password";
                     }
                     enum "keyed-md5" {
                       description "Keyed message Digest 5";
                     }
                     enum "meticulous-keyed-md5" {
                       description "Meticulous keyed message Digest 5";
                     }
                     enum "keyed-sha-1" {
                       description "Keyed secure hash algorithm (SHA1) ";
                     }
                     enum "meticulous-keyed-sha-1" {
                       description "Meticulous keyed secure hash algorithm (SHA1) ";
                     }
                   }
                 }
                 leaf loose-check {
                   description "Verify authentication only if authentication is negotiated";
                   type empty;
                 }
               }
               container echo {
                 description "Echo mode parameters";
                 uses apply-advanced;
                 leaf minimum-interval {
                   description "Minimum transmit and receive interval";
                   units "milliseconds";
                   type union {
                     type string {
                       pattern "<.*>|$.*";
                     }
                     type uint32 {
                       range "100 .. 255000";
                     }
                   }
                 }
               }
               container echo-lite {
                 description "Echo-lite more parameters";
                 uses apply-advanced;
                 leaf minimum-interval {
                   description "Minimum transmit and receive interval";
                   units "milliseconds";
                   type union {
                     type string {
                       pattern "<.*>|$.*";
                     }
                     type uint32 {
                       range "100 .. 255000";
                     }
                   }
                 }
               }
               leaf neighbor {
                 description "BFD neighbor address";
                 type jt:ipaddr;
               }
               leaf local-address {
                 description "BFD local address (for multihop only)";
                 type jt:ipaddr;
               }
               leaf holddown-interval {
                 description "Time to hold the session-UP notification to the client";
                 units "milliseconds";
                 type union {
                   type string {
                     pattern "<.*>|$.*";
                   }
                   type uint32 {
                     range "0 .. 255000";
                   }
                 }
               }
               leaf minimum-receive-ttl {
                 description "Minimum receive TTL below which to drop";
                 type union {
                   type string {
                     pattern "<.*>|$.*";
                   }
                   type uint8 {
                     range "1 .. 255";
                   }
                 }
               }
             }
             choice retain-choice {
               leaf retain {
                 description "Always keep route in forwarding table";
                 type empty;
               }
               leaf no-retain {
                 description "Don't always keep route in forwarding table";
                 type empty;
               }
             }
             choice install-choice {
               leaf install {
                 description "Install route into forwarding table";
                 type empty;
               }
               leaf no-install {
                 description "Don't install route into forwarding table";
                 type empty;
               }
             }
             choice readvertise-choice {
               leaf readvertise {
                 description "Mark route as eligible to be readvertised";
                 type empty;
               }
               leaf no-readvertise {
                 description "Don't mark route as eligible to be readvertised";
                 type empty;
               }
             }
             choice resolve-choice {
               leaf resolve {
                 description "Allow resolution of indirectly connected next hops";
                 type empty;
               }
               leaf no-resolve {
                 description "Don't allow resolution of indirectly connected next hops";
                 type empty;
               }
             }
             leaf explicit-null {
               description "Allows service label to be popped and will lookup nexthop-table inet6.0";
               type empty;
             }
             choice longest-match-choice {
               leaf longest-match {
                 description "Always use longest prefix match to resolve next hops";
                 type empty;
               }
               leaf no-longest-match {
                 description "Don't always use longest prefix match to resolve next hops";
                 type empty;
               }
             }
             choice passive_flag {
               case case_1 {
                 leaf active {
                   description "Remove inactive route from forwarding table";
                   type empty;
                 }
               }
               case case_2 {
                 leaf passive {
                   description "Retain inactive route in forwarding table";
                   type empty;
                 }
               }
             }
             container metric {
               description "Metric value";
               presence "enable metric";
               uses rib_static_metric_type;
             }
             container metric2 {
               description "Metric value 2";
               presence "enable metric2";
               uses rib_static_metric_type;
             }
             container metric3 {
               description "Metric value 3";
               presence "enable metric3";
               uses rib_static_metric_type;
             }
             container metric4 {
               description "Metric value 4";
               presence "enable metric4";
               uses rib_static_metric_type;
             }
             container tag {
               description "Tag string";
               presence "enable tag";
               uses rib_static_metric_type;
             }
             container tag2 {
               description "Tag string 2";
               presence "enable tag2";
               uses rib_static_metric_type;
             }
             container preference {
               description "Preference value";
               presence "enable preference";
               uses rib_static_metric_type;
             }
             container preference2 {
               description "Preference value 2";
               presence "enable preference2";
               uses rib_static_metric_type;
             }
             container color {
               description "Color (preference) value";
               presence "enable color";
               uses rib_static_metric_type;
             }
             container color2 {
               description "Color (preference) value 2";
               presence "enable color2";
               uses rib_static_metric_type;
             }
             leaf-list community {
               ordered-by user;
               description "BGP community identifier";
               type jt:community;
             }
             container as-path {
               description "Autonomous system path";
               uses apply-advanced;
               leaf path {
                 description "Autonomous system path";
                 type string;
               }
               leaf origin {
                 type enumeration {
                   enum "igp" {
                     description "Path originated in the local IGP";
                   }
                   enum "egp" {
                     description "Path originated in another AS";
                   }
                   enum "incomplete" {
                     description "Path was learned by some other means";
                   }
                 }
               }
               leaf atomic-aggregate {
                 description "Add ATOMIC_AGGREGATE path attribute to route";
                 type empty;
               }
               container aggregator {
                 presence "enable aggregator";
                 description "Add AGGREGATOR path attribute to route";
               }
               leaf as-number {
                 description " Autonomous system number in plain number or 'higher 16bits'.'Lower 16 bits' (asdot notation) format";
                 type string {
                 }
               }
               leaf address {
                 description "Address of BGP system that formed the route";
                 type jt:ipv4addr;
               }
             }
             list lsp-next-hop {
               key name;
               ordered-by user;
               description "LSP next hop";
               uses lsp_nh_obj;
             }
             list p2mp-lsp-next-hop {
               key name;
               ordered-by user;
               description "Point-to-multipoint LSP next hop";
               max-elements 1;
               uses lsp_nh_obj;
             }
             container spring-te-lsp-next-hop {
               description "SPRING-TE LSP next hop";
               uses springte_lsp_nh_obj;
             }
             container p2mp-ldp-next-hop {
               description "Point-to-multipoint LDP LSP next hop";
               uses p2mp_ldp_lsp_nh_obj;
             }
             list static-lsp-next-hop {
               key name;
               ordered-by user;
               description "Static LSP next hop";
               uses lsp_nh_obj;
             }
           }
           leaf protocol-instance-name {
             description "Name of protocol instance under routing instance";
             type string;
           }
           container static-route {
             description "Static route Status";
             leaf bfd-admin-down {
               description "Static route State on BFD ADMIN DOWN";
               type enumeration {
                 enum "active" {
                   description "Static route will be inactive on bfd-admin-down";
                 }
                 enum "passive" {
                   description "Static route will remain active on bfd-admin-down";
                 }
               }
             }
           }
           list iso-route {
             key name;
             ordered-by user;
             description "ISO family static route";
             leaf name {
               type jt:isoprefix;
             }
             uses apply-advanced;
             leaf priority {
               description "Static route priority high/medium/low";
               type enumeration {
                 enum "medium" {
                   description "Static route medium priority";
                 }
                 enum "low" {
                   description "Static route low priority";
                 }
                 enum "high" {
                   description "Static route high priority";
                 }
               }
             }
             choice next_hop {
               case case_1 {
                 leaf-list next-hop {
                   ordered-by user;
                   description "Next hop to destination";
                   type union {
                     type jt:ipaddr-or-interface;
                     type string {
                       pattern "<.*>|$.*";
                     }
                   }
                 }
               }
               case case_2 {
                 leaf reject {
                   description "Drop packets to destination; send ICMP unreachables";
                   type empty;
                 }
               }
               case case_3 {
                 leaf discard {
                   description "Drop packets to destination; send no ICMP unreachables";
                   type empty;
                 }
               }
               case case_4 {
                 leaf receive {
                   description "Install a receive route for the destination";
                   type empty;
                 }
               }
               case case_5 {
                 leaf next-table {
                   description "Next hop to another table";
                   type string {
                   }
                 }
               }
             }
             leaf description {
               description "Static route description";
               type string {
               }
             }
             list qualified-next-hop {
               key name;
               ordered-by user;
               description "Next hop with qualifiers";
               uses qualified_nh_obj;
             }
             leaf backup-pe-group {
               description "Multicast source redundancy group";
               type string;
             }
             container bfd-liveness-detection {
               description "Bidirectional Forwarding Detection (BFD) options";
               uses apply-advanced;
               leaf version {
                 description "BFD protocol version number";
                 default "automatic";
                 type enumeration {
                   enum "0" {
                     description "BFD version 0 (deprecated)";
                   }
                   enum "1" {
                     description "BFD version 1";
                   }
                   enum "automatic" {
                     description "Choose BFD version automatically";
                   }
                 }
               }
               leaf minimum-interval {
                 description "Minimum transmit and receive interval";
                 units "milliseconds";
                 type union {
                   type string {
                     pattern "<.*>|$.*";
                   }
                   type uint32 {
                     range "1 .. 255000";
                   }
                 }
               }
               leaf minimum-transmit-interval {
                 description "Minimum transmit interval";
                 status deprecated;
                 units "milliseconds";
                 type union {
                   type string {
                     pattern "<.*>|$.*";
                   }
                   type uint32 {
                     range "1 .. 255000";
                   }
                 }
               }
               leaf minimum-receive-interval {
                 description "Minimum receive interval";
                 units "milliseconds";
                 type union {
                   type string {
                     pattern "<.*>|$.*";
                   }
                   type uint32 {
                     range "1 .. 255000";
                   }
                 }
               }
               leaf multiplier {
                 description "Detection time multiplier";
                 default "3";
                 type union {
                   type string {
                     pattern "<.*>|$.*";
                   }
                   type uint32 {
                     range "1 .. 255";
                   }
                 }
               }
               leaf inline-disable {
                 description "Disable inline mode for this BFD session";
                 type empty;
               }
               leaf pdu-size {
                 description "BFD transport protocol payload size";
                 default "24";
                 type union {
                   type string {
                     pattern "<.*>|$.*";
                   }
                   type uint32 {
                     range "24 .. 9000";
                   }
                 }
               }
               choice adaptation-choice {
                 case case_1 {
                   leaf no-adaptation {
                     description "Disable adaptation";
                     type empty;
                   }
                 }
               }
               container transmit-interval {
                 description "Transmit-interval options";
                 uses apply-advanced;
                 leaf minimum-interval {
                   description "Minimum transmit interval";
                   units "milliseconds";
                   type union {
                     type string {
                       pattern "<.*>|$.*";
                     }
                     type uint32 {
                       range "1 .. 255000";
                     }
                   }
                 }
                 leaf threshold {
                   description "High transmit interval triggering a trap";
                   units "milliseconds";
                   type union {
                     type uint32;
                     type string {
                       pattern "<.*>|$.*";
                     }
                   }
                 }
               }
               container detection-time {
                 description "Detection-time options";
                 uses apply-advanced;
                 leaf threshold {
                   description "High detection-time triggering a trap";
                   units "milliseconds";
                   type union {
                     type uint32;
                     type string {
                       pattern "<.*>|$.*";
                     }
                   }
                 }
               }
               container authentication {
                 description "Authentication options";
                 uses apply-advanced;
                 leaf key-chain {
                   description "Key chain name";
                   type string;
                 }
                 leaf algorithm {
                   description "Algorithm name";
                   type enumeration {
                     enum "simple-password" {
                       description "Simple password";
                     }
                     enum "keyed-md5" {
                       description "Keyed message Digest 5";
                     }
                     enum "meticulous-keyed-md5" {
                       description "Meticulous keyed message Digest 5";
                     }
                     enum "keyed-sha-1" {
                       description "Keyed secure hash algorithm (SHA1) ";
                     }
                     enum "meticulous-keyed-sha-1" {
                       description "Meticulous keyed secure hash algorithm (SHA1) ";
                     }
                   }
                 }
                 leaf loose-check {
                   description "Verify authentication only if authentication is negotiated";
                   type empty;
                 }
               }
               container echo {
                 description "Echo mode parameters";
                 uses apply-advanced;
                 leaf minimum-interval {
                   description "Minimum transmit and receive interval";
                   units "milliseconds";
                   type union {
                     type string {
                       pattern "<.*>|$.*";
                     }
                     type uint32 {
                       range "100 .. 255000";
                     }
                   }
                 }
               }
               container echo-lite {
                 description "Echo-lite more parameters";
                 uses apply-advanced;
                 leaf minimum-interval {
                   description "Minimum transmit and receive interval";
                   units "milliseconds";
                   type union {
                     type string {
                       pattern "<.*>|$.*";
                     }
                     type uint32 {
                       range "100 .. 255000";
                     }
                   }
                 }
               }
               leaf neighbor {
                 description "BFD neighbor address";
                 type jt:ipaddr;
               }
               leaf local-address {
                 description "BFD local address (for multihop only)";
                 type jt:ipaddr;
               }
               leaf holddown-interval {
                 description "Time to hold the session-UP notification to the client";
                 units "milliseconds";
                 type union {
                   type string {
                     pattern "<.*>|$.*";
                   }
                   type uint32 {
                     range "0 .. 255000";
                   }
                 }
               }
               leaf minimum-receive-ttl {
                 description "Minimum receive TTL below which to drop";
                 type union {
                   type string {
                     pattern "<.*>|$.*";
                   }
                   type uint8 {
                     range "1 .. 255";
                   }
                 }
               }
             }
             choice retain-choice {
               leaf retain {
                 description "Always keep route in forwarding table";
                 type empty;
               }
               leaf no-retain {
                 description "Don't always keep route in forwarding table";
                 type empty;
               }
             }
             choice install-choice {
               leaf install {
                 description "Install route into forwarding table";
                 type empty;
               }
               leaf no-install {
                 description "Don't install route into forwarding table";
                 type empty;
               }
             }
             choice readvertise-choice {
               leaf readvertise {
                 description "Mark route as eligible to be readvertised";
                 type empty;
               }
               leaf no-readvertise {
                 description "Don't mark route as eligible to be readvertised";
                 type empty;
               }
             }
             choice resolve-choice {
               leaf resolve {
                 description "Allow resolution of indirectly connected next hops";
                 type empty;
               }
               leaf no-resolve {
                 description "Don't allow resolution of indirectly connected next hops";
                 type empty;
               }
             }
             leaf explicit-null {
               description "Allows service label to be popped and will lookup nexthop-table inet6.0";
               type empty;
             }
             choice longest-match-choice {
               leaf longest-match {
                 description "Always use longest prefix match to resolve next hops";
                 type empty;
               }
               leaf no-longest-match {
                 description "Don't always use longest prefix match to resolve next hops";
                 type empty;
               }
             }
             choice passive_flag {
               case case_1 {
                 leaf active {
                   description "Remove inactive route from forwarding table";
                   type empty;
                 }
               }
               case case_2 {
                 leaf passive {
                   description "Retain inactive route in forwarding table";
                   type empty;
                 }
               }
             }
             container metric {
               description "Metric value";
               presence "enable metric";
               uses rib_static_metric_type;
             }
             container metric2 {
               description "Metric value 2";
               presence "enable metric2";
               uses rib_static_metric_type;
             }
             container metric3 {
               description "Metric value 3";
               presence "enable metric3";
               uses rib_static_metric_type;
             }
             container metric4 {
               description "Metric value 4";
               presence "enable metric4";
               uses rib_static_metric_type;
             }
             container tag {
               description "Tag string";
               presence "enable tag";
               uses rib_static_metric_type;
             }
             container tag2 {
               description "Tag string 2";
               presence "enable tag2";
               uses rib_static_metric_type;
             }
             container preference {
               description "Preference value";
               presence "enable preference";
               uses rib_static_metric_type;
             }
             container preference2 {
               description "Preference value 2";
               presence "enable preference2";
               uses rib_static_metric_type;
             }
             container color {
               description "Color (preference) value";
               presence "enable color";
               uses rib_static_metric_type;
             }
             container color2 {
               description "Color (preference) value 2";
               presence "enable color2";
               uses rib_static_metric_type;
             }
             leaf-list community {
               ordered-by user;
               description "BGP community identifier";
               type jt:community;
             }
             container as-path {
               description "Autonomous system path";
               uses apply-advanced;
               leaf path {
                 description "Autonomous system path";
                 type string;
               }
               leaf origin {
                 type enumeration {
                   enum "igp" {
                     description "Path originated in the local IGP";
                   }
                   enum "egp" {
                     description "Path originated in another AS";
                   }
                   enum "incomplete" {
                     description "Path was learned by some other means";
                   }
                 }
               }
               leaf atomic-aggregate {
                 description "Add ATOMIC_AGGREGATE path attribute to route";
                 type empty;
               }
               container aggregator {
                 presence "enable aggregator";
                 description "Add AGGREGATOR path attribute to route";
               }
               leaf as-number {
                 description " Autonomous system number in plain number or 'higher 16bits'.'Lower 16 bits' (asdot notation) format";
                 type string {
                 }
               }
               leaf address {
                 description "Address of BGP system that formed the route";
                 type jt:ipv4addr;
               }
             }
             list lsp-next-hop {
               key name;
               ordered-by user;
               description "LSP next hop";
               uses lsp_nh_obj;
             }
             list p2mp-lsp-next-hop {
               key name;
               ordered-by user;
               description "Point-to-multipoint LSP next hop";
               max-elements 1;
               uses lsp_nh_obj;
             }
             container spring-te-lsp-next-hop {
               description "SPRING-TE LSP next hop";
               uses springte_lsp_nh_obj;
             }
             container p2mp-ldp-next-hop {
               description "Point-to-multipoint LDP LSP next hop";
               uses p2mp_ldp_lsp_nh_obj;
             }
           }
           list route-target-filter {
             key name;
             ordered-by user;
             description "Route-target-filter route";
             leaf name {
               type string {
                 length "1 .. 47";
               }
             }
             uses apply-advanced;
             leaf-list neighbor {
               ordered-by user;
               description "BGP peers for filter";
               type jt:ipaddr-scoped;
             }
             leaf-list group {
               ordered-by user;
               description "BGP groups for filter";
               type string;
             }
             leaf local {
               description "Locally originated filter";
               type empty;
             }
           }
         }
         list martians {
           key "address choice-ident choice-value";
           ordered-by user;
           description "Invalid routes";
           uses martian_type;
         }
         container aggregate {
           description "Coalesced routes";
           uses rib_aggregate_type;
         }
         container generate {
           description "Route of last resort";
           uses rib_aggregate_type;
         }
         choice maximum-paths-type {
           case case_1 {
             container maximum-routes {
               description "Maximum number of routes";
               status deprecated;
               leaf limit {
                 description "Maximum number of routes";
                 type union {
                   type string {
                     pattern "<.*>|$.*";
                   }
                   type uint32 {
                     range "1 .. 4294967295";
                   }
                 }
               }
               choice log_type {
                 case case_1 {
                   leaf threshold {
                     description "Percentage of limit at which to start generating warnings";
                     type union {
                       type string {
                         pattern "<.*>|$.*";
                       }
                       type uint32 {
                         range "1 .. 100";
                       }
                     }
                   }
                 }
                 case case_2 {
                   leaf log-only {
                     description "Generate warning messages only";
                     type empty;
                   }
                 }
               }
               leaf log-interval {
                 description "Minimum interval between log messages";
                 units "seconds";
                 type union {
                   type string {
                     pattern "<.*>|$.*";
                   }
                   type uint32 {
                     range "5 .. 86400";
                   }
                 }
               }
             }
           }
           case case_2 {
             container maximum-paths {
               description "Maximum number of paths";
               leaf limit {
                 description "Maximum number of paths";
                 type union {
                   type string {
                     pattern "<.*>|$.*";
                   }
                   type uint32 {
                     range "1 .. 4294967295";
                   }
                 }
               }
               choice log_type {
                 case case_1 {
                   leaf threshold {
                     description "Percentage of limit at which to start generating warnings";
                     type union {
                       type string {
                         pattern "<.*>|$.*";
                       }
                       type uint32 {
                         range "1 .. 100";
                       }
                     }
                   }
                 }
                 case case_2 {
                   leaf log-only {
                     description "Generate warning messages only";
                     type empty;
                   }
                 }
               }
               leaf log-interval {
                 description "Minimum interval between log messages";
                 units "seconds";
                 type union {
                   type string {
                     pattern "<.*>|$.*";
                   }
                   type uint32 {
                     range "5 .. 86400";
                   }
                 }
               }
             }
           }
         }
         container maximum-prefixes {
           description "Maximum number of prefixes";
           leaf limit {
             description "Maximum number of prefixes";
             type union {
               type string {
                 pattern "<.*>|$.*";
               }
               type uint32 {
                 range "1 .. 4294967295";
               }
             }
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
         container multipath {
           presence "enable multipath";
           description "Protocol-independent load balancing";
           uses apply-advanced;
           container vpn-unequal-cost {
             presence "enable vpn-unequal-cost";
             description "Include VPN routes with unequal IGP metrics";
             leaf equal-external-internal {
               description "Include external and internal VPN routes";
               type empty;
             }
           }
           leaf as-path-compare {
             description "Compare AS path sequences in addition to AS path length";
             type empty;
           }
           leaf preserve-nexthop-hierarchy {
             description "Force multipath to create List nexthop";
             type empty;
           }
         }
         container policy-multipath {
           description "Policy based multipath";
           uses apply-advanced;
           leaf-list policy {
             ordered-by user;
             description "Import policy to create policy based multipath";
             type jt:policy-algebra;
           }
           container traceoptions {
             description "Trace options";
             uses apply-advanced;
             container file {
               description "Trace file options";
               leaf filename {
                 description "Name of file in which to write trace information";
                 type string {
                   length "1 .. 1024";
                 }
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "route" {
                     description "Policy-multipath route tracing.";
                   }
                 }
               }
               leaf send {
                 description "Trace transmitted packets";
                 type empty;
               }
               leaf receive {
                 description "Trace received packets";
                 type empty;
               }
               leaf detail {
                 description "Trace detailed information";
                 type empty;
               }
               leaf disable {
                 description "Disable this trace flag";
                 type empty;
               }
             }
           }
           leaf preserve-nexthop-hierarchy {
             description "Enable preserved nexthop hierarchy";
             type empty;
           }
         }
         container protect {
           description "Protocol-independent protection";
           leaf core {
             description "Protect against unreachability to service-edge router";
             type empty;
           }
         }
         container access {
           description "Access routes";
           uses apply-advanced;
           list route {
             key name;
             ordered-by user;
             description "Access route";
             leaf name {
               description "IP address of destination";
               type jt:ipprefix;
             }
             uses apply-advanced;
             leaf-list next-hop {
               ordered-by user;
               description "Next hop to destination";
               type union {
                 type jt:ipaddr-or-interface;
                 type string {
                   pattern "<.*>|$.*";
                 }
               }
             }
             list qualified-next-hop {
               key name;
               ordered-by user;
               description "Next hop with qualifiers";
               uses qualified_nh_obj;
             }
             leaf metric {
               description "Metric value";
               type union {
                 type string {
                   pattern "<.*>|$.*";
                 }
                 type uint32 {
                   range "1 .. 255";
                 }
               }
             }
             leaf preference {
               description "Preference value";
               type union {
                 type uint32;
                 type string {
                   pattern "<.*>|$.*";
                 }
               }
             }
             leaf tag {
               description "Tag string";
               type union {
                 type uint32;
                 type string {
                   pattern "<.*>|$.*";
                 }
               }
             }
             leaf tag2 {
               description "Tag2 string";
               type union {
                 type uint32;
                 type string {
                   pattern "<.*>|$.*";
                 }
               }
             }
           }
         }
         container access-internal {
           description "Access-internal routes";
           uses apply-advanced;
           list route {
             key name;
             ordered-by user;
             description "Access-internal route";
             leaf name {
               description "IP address and optional prefix length of destination";
               type jt:ipprefix;
             }
             uses apply-advanced;
             leaf-list next-hop {
               ordered-by user;
               description "Next hop to destination";
               type union {
                 type jt:ipaddr-or-interface;
                 type string {
                   pattern "<.*>|$.*";
                 }
               }
             }
             list qualified-next-hop {
               key name;
               ordered-by user;
               description "Next hop with qualifiers";
               uses qualified_nh_obj;
             }
           }
         }
         container bgp-static {
           description "Routes for BGP static advertisements";
           uses apply-advanced;
           list route {
             key name;
             ordered-by user;
             description "BGP-static route";
             leaf name {
               description "IP address and optional prefix length of destination";
               type jt:ipprefix;
             }
             uses apply-advanced;
             container metric {
               description "Metric value";
               presence "enable metric";
               uses rib_static_metric_type;
             }
             container metric2 {
               description "Metric value 2";
               presence "enable metric2";
               uses rib_static_metric_type;
             }
             container metric3 {
               description "Metric value 3";
               presence "enable metric3";
               uses rib_static_metric_type;
             }
             container metric4 {
               description "Metric value 4";
               presence "enable metric4";
               uses rib_static_metric_type;
             }
             container tag {
               description "Tag string";
               presence "enable tag";
               uses rib_static_metric_type;
             }
             container tag2 {
               description "Tag string 2";
               presence "enable tag2";
               uses rib_static_metric_type;
             }
             container preference {
               description "Preference value";
               presence "enable preference";
               uses rib_static_metric_type;
             }
             container preference2 {
               description "Preference value 2";
               presence "enable preference2";
               uses rib_static_metric_type;
             }
             container color {
               description "Color (preference) value";
               presence "enable color";
               uses rib_static_metric_type;
             }
             container color2 {
               description "Color (preference) value 2";
               presence "enable color2";
               uses rib_static_metric_type;
             }
             leaf-list community {
               ordered-by user;
               description "BGP community identifier";
               type jt:community;
             }
             container as-path {
               description "Autonomous system path";
               uses apply-advanced;
               leaf path {
                 description "Autonomous system path";
                 type string;
               }
               leaf origin {
                 type enumeration {
                   enum "igp" {
                     description "Path originated in the local IGP";
                   }
                   enum "egp" {
                     description "Path originated in another AS";
                   }
                   enum "incomplete" {
                     description "Path was learned by some other means";
                   }
                 }
               }
               leaf atomic-aggregate {
                 description "Add ATOMIC_AGGREGATE path attribute to route";
                 type empty;
               }
               container aggregator {
                 presence "enable aggregator";
                 description "Add AGGREGATOR path attribute to route";
               }
               leaf as-number {
                 description " Autonomous system number in plain number or 'higher 16bits'.'Lower 16 bits' (asdot notation) format";
                 type string {
                 }
               }
               leaf address {
                 description "Address of BGP system that formed the route";
                 type jt:ipv4addr;
               }
             }
           }
         }
         container flow {
           description "Locally defined flow routing information";
           uses apply-advanced;
           container validation {
             description "Flow route validation options";
             presence "enable validation";
             uses flow-validation;
           }
           list route {
             key name;
             ordered-by user;
             description "Flow route";
             uses flow-route-inet6;
           }
           list security-group {
             key name;
             ordered-by user;
             description "Security groups";
             leaf name {
               description "Name of the security group";
               type string {
                 length "1 .. 16";
               }
             }
             uses apply-advanced;
             list rule {
               key name;
               ordered-by user;
               description "Flow route";
               uses flow-rule-inet6;
             }
           }
           container interface-group {
             description "Interface-group for applying flow-spec filter";
             uses flow-interface-group;
           }
           leaf discard-action-for-unresolved-redir-addr {
             description "For action redirect IP if redirect address is unresolved install discard action filter";
             type empty;
           }
           choice per-route-accounting-choice {
             leaf per-route-accounting {
               description "Enable traffic accounting per flowspec route";
               type empty;
             }
             leaf no-per-route-accounting {
               description "Don't enable traffic accounting per flowspec route";
               type empty;
             }
           }
         }
         container label {
           presence "enable label";
           description "Label processing";
           uses apply-advanced;
           leaf-list allocation {
             ordered-by user;
             description "Label allocation policy";
             type jt:policy-algebra;
           }
           leaf-list substitution {
             ordered-by user;
             description "Label substitution policy";
             type jt:policy-algebra;
           }
         }
       }
       container access {
         description "Access routes";
         uses apply-advanced;
         list route {
           key name;
           ordered-by user;
           description "Access route";
           leaf name {
             description "IP address of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
           leaf metric {
             description "Metric value";
             type union {
               type string {
                 pattern "<.*>|$.*";
               }
               type uint32 {
                 range "1 .. 255";
               }
             }
           }
           leaf preference {
             description "Preference value";
             type union {
               type uint32;
               type string {
                 pattern "<.*>|$.*";
               }
             }
           }
           leaf tag {
             description "Tag string";
             type union {
               type uint32;
               type string {
                 pattern "<.*>|$.*";
               }
             }
           }
           leaf tag2 {
             description "Tag2 string";
             type union {
               type uint32;
               type string {
                 pattern "<.*>|$.*";
               }
             }
           }
         }
       }
       container access-internal {
         description "Access-internal routes";
         uses apply-advanced;
         list route {
           key name;
           ordered-by user;
           description "Access-internal route";
           leaf name {
             description "IP address and optional prefix length of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
         }
       }
       container multicast {
         description "Global multicast options";
         uses apply-advanced;
         container traceoptions {
           description "Global multicast trace options";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "parse" {
                   description "Trace configuration parsing";
                 }
                 enum "config-internal" {
                   description "Trace configuration internals";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf disable {
               description "Disable this trace flag";
               type empty;
             }
           }
         }
         leaf rpf {
           status deprecated;
           type string;
         }
         list scope {
           key name;
           ordered-by user;
           description "Multicast address scope";
           leaf name {
             description "Name to identify multicast address scope";
             type string;
           }
           uses apply-advanced;
           leaf prefix {
             description "Administratively scoped address";
             type jt:ipprefix;
           }
           leaf-list interface {
             ordered-by user;
             description "Interface on which to configure scoping";
             type union {
               type jt:interface-name;
               type string {
                 pattern "<.*>|$.*";
               }
             }
           }
         }
         leaf-list scope-policy {
           ordered-by user;
           description "Scoping policy";
           type jt:policy-algebra;
         }
         list flow-map {
           key name;
           ordered-by user;
           description "Multicast flow map configuration";
           leaf name {
             description "Name of the flow map";
             type string;
           }
           uses apply-advanced;
           leaf-list policy {
             ordered-by user;
             description "Policy for matched flows";
             type jt:policy-algebra;
           }
           container bandwidth {
             presence "enable bandwidth";
             description "Bandwidth properties for matched flows";
             leaf bandwidth-value {
               description "Static or default bandwidth for the matched flows";
               units "bps";
               type string;
             }
             leaf adaptive {
               description "Auto-sense bandwidth for matched flows";
               type empty;
             }
           }
           leaf-list redundant-sources {
             ordered-by user;
             description "Redundant source addresses";
             type jt:ipaddr;
           }
           container forwarding-cache {
             description "Forwarding cache properties for matched flows";
             uses apply-advanced;
             container timeout {
               description "Timeout properties for matched flows";
               choice timeout_choice {
                 case case_1 {
                   leaf timeout-value {
                     description "Timeout for forwarding cache entry";
                     units "minutes";
                     type union {
                       type string {
                         pattern "<.*>|$.*";
                       }
                       type uint32 {
                         range "1 .. 720";
                       }
                     }
                   }
                 }
                 case case_2 {
                   container never {
                     presence "enable never";
                     description "Forwarding cache entries never time out";
                     uses apply-advanced;
                     leaf non-discard-entry-only {
                       description "Apply only to non-discard entries";
                       type empty;
                     }
                   }
                 }
               }
             }
           }
         }
         leaf-list resolve-filter {
           ordered-by user;
           description "Multicast resolve policy filter";
           status deprecated;
           type jt:policy-algebra;
         }
         leaf-list ssm-groups {
           ordered-by user;
           description "Source-specific multicast group ranges";
           type jt:ipprefix;
         }
         leaf cont-stats-collection-interval {
           description "IGMP/MLD continuous statistics collection interval";
           default "300";
           type union {
             type string {
               pattern "<.*>|$.*";
             }
             type uint16 {
               range "60 .. 3600";
             }
           }
         }
         leaf asm-override-ssm {
           description "Allow ASM state for SSM group ranges";
           type empty;
         }
         leaf-list rpf-check-policy {
           ordered-by user;
           description "Disable RPF check for a source group pair";
           type jt:policy-algebra;
         }
         container pim-to-igmp-proxy {
           description "PIM-to-IGMP proxy";
           uses apply-advanced;
           leaf-list upstream-interface {
             ordered-by user;
             description "Upstream interface list";
             type union {
               type jt:interface-name;
               type string {
                 pattern "<.*>|$.*";
               }
             }
             max-elements 2;
           }
         }
         container pim-to-mld-proxy {
           description "PIM-to-MLD proxy";
           uses apply-advanced;
           leaf-list upstream-interface {
             ordered-by user;
             description "Upstream interface list";
             type union {
               type jt:interface-name;
               type string {
                 pattern "<.*>|$.*";
               }
             }
             max-elements 2;
           }
         }
         container forwarding-cache {
           description "Multicast forwarding cache";
           uses apply-advanced;
           leaf allow-maximum {
             description "Allow maximum of global and family level threshold values for suppress and reuse";
             type empty;
           }
           list family {
             key name;
             ordered-by user;
             description "Protocol family";
             leaf name {
               description "Protocol family";
               type enumeration {
                 enum "inet" {
                   description "IPv4 family";
                 }
                 enum "inet6" {
                   description "IPv6 family";
                 }
               }
             }
             uses apply-advanced;
             container threshold {
               presence "enable threshold";
               description "Multicast forwarding cache suppress threshold";
               uses apply-advanced;
               leaf suppress {
                 description "Suppress threshold";
                 type union {
                   type string {
                     pattern "<.*>|$.*";
                   }
                   type uint32 {
                     range "1 .. 200000";
                   }
                 }
               }
               leaf reuse {
                 description "Reuse threshold";
                 type union {
                   type string {
                     pattern "<.*>|$.*";
                   }
                   type uint32 {
                     range "1 .. 200000";
                   }
                 }
               }
               leaf mvpn-rpt-suppress {
                 description "MVPN RP tree entry suppress threshold";
                 type union {
                   type string {
                     pattern "<.*>|$.*";
                   }
                   type uint32 {
                     range "1 .. 200000";
                   }
                 }
               }
               leaf mvpn-rpt-reuse {
                 description "MVPN RP tree entry reuse threshold";
                 type union {
                   type string {
                     pattern "<.*>|$.*";
                   }
                   type uint32 {
                     range "1 .. 200000";
                   }
                 }
               }
               leaf log-warning {
                 description "Percentage at which to start generating warnings";
                 type union {
                   type string {
                     pattern "<.*>|$.*";
                   }
                   type uint32 {
                     range "1 .. 100";
                   }
                 }
               }
             }
           }
           container threshold {
             description "Threshold";
             uses apply-advanced;
             leaf suppress {
               description "Suppress threshold";
               type union {
                 type string {
                   pattern "<.*>|$.*";
                 }
                 type uint32 {
                   range "1 .. 200000";
                 }
               }
             }
             leaf reuse {
               description "Reuse threshold";
               type union {
                 type string {
                   pattern "<.*>|$.*";
                 }
                 type uint32 {
                   range "1 .. 200000";
                 }
               }
             }
             leaf mvpn-rpt-suppress {
               description "MVPN RP tree entry suppress threshold";
               type union {
                 type string {
                   pattern "<.*>|$.*";
                 }
                 type uint32 {
                   range "1 .. 200000";
                 }
               }
             }
             leaf mvpn-rpt-reuse {
               description "MVPN RP tree entry reuse threshold";
               type union {
                 type string {
                   pattern "<.*>|$.*";
                 }
                 type uint32 {
                   range "1 .. 200000";
                 }
               }
             }
             leaf log-warning {
               description "Percentage at which to start generating warnings";
               type union {
                 type string {
                   pattern "<.*>|$.*";
                 }
                 type uint32 {
                   range "1 .. 100";
                 }
               }
             }
           }
           leaf timeout {
             description "Forwarding cache entry timeout in minutes";
             type union {
               type string {
                 pattern "<.*>|$.*";
               }
               type uint32 {
                 range "1 .. 720";
               }
             }
           }
         }
         list interface {
           key name;
           ordered-by user;
           description "Multicast interface options";
           uses multicast_interface_options_type;
         }
         list ssm-map {
           key name;
           ordered-by user;
           description "SSM map definitions";
           leaf name {
             description "SSM map name";
             type string;
           }
           uses apply-advanced;
           leaf-list policy {
             ordered-by user;
             description "Policy for matching group";
             type jt:policy-algebra;
           }
           leaf-list source {
             ordered-by user;
             description "One or more source addresses";
             type jt:ipaddr;
           }
         }
         container stream-protection {
           presence "enable stream-protection";
           description "Multicast only Fast Re-Route";
           uses apply-advanced;
           leaf mofrr-primary-path-selection-by-routing {
             description "Multicast only Fast Re-Route primary path by Routing";
             type empty;
           }
           leaf mofrr-disjoint-upstream-only {
             description "Multicast only Fast Re-Route disjoint upstream only";
             type empty;
           }
           leaf mofrr-no-backup-join {
             description "Multicast only Fast Re-Route no backup join";
             type empty;
           }
           leaf mofrr-asm-starg {
             description "Multicast only Fast Re-Route asm (*,G)";
             type empty;
           }
           leaf-list policy {
             ordered-by user;
             description "MoFRR Policy";
             type jt:policy-algebra;
           }
         }
         list backup-pe-group {
           key name;
           ordered-by user;
           description "Backup PE group definitions";
           leaf name {
             description "PE group name";
             type string;
           }
           uses apply-advanced;
           leaf-list backups {
             ordered-by user;
             description "One or more IP addresses";
             type jt:ipaddr;
             max-elements 8;
           }
           leaf local-address {
             description "Address to be used as local-address for this group";
             type jt:ipaddr;
           }
         }
         leaf omit-wildcard-address {
           description "Omit wildcard source/group fields in SPMSI AD NLRI";
           type empty;
         }
         leaf local-address {
           description "Local address for PIM and MVPN sessions";
           type jt:ipv4addr;
         }
       }
     }
     container firewall {
       description "Define a firewall configuration";
       uses apply-advanced;
       container family {
         description "Protocol family";
         container inet {
           description "Protocol family IPv4 for firewall filter";
           uses apply-advanced;
           list dialer-filter {
             key name;
             ordered-by user;
             description "Define an IPv4 dialer filter";
             uses inet_dialer_filter;
           }
           list prefix-action {
             key name;
             ordered-by user;
             description "Define a prefix action";
             uses prefix_action;
           }
           list filter {
             key name;
             description "Define an IPv4 firewall filter";
             uses inet_filter;
           }
           list template {
             key name;
             description "Define an Inet firewall template";
             uses inet_template;
           }
           list simple-filter {
             key name;
             description "Define an IPv4 firewall simple filter";
             uses inet_simple_filter;
           }
           list service-filter {
             key name;
             description "One or more IPv4 service filters";
             uses inet_service_filter;
           }
           list fast-update-filter {
             key name;
             ordered-by user;
             description "One or more fast update filters";
             uses inet_fuf;
           }
         }
         container inet6 {
           description "Protocol family IPv6 for firewall filter";
           uses apply-advanced;
           list dialer-filter {
             key name;
             ordered-by user;
             description "Define an IPv6 dialer filter";
             uses inet6_dialer_filter;
           }
           list filter {
             key name;
             description "Define an IPv6 firewall filter";
             uses inet6_filter;
           }
           list service-filter {
             key name;
             description "One or more IPv6 service filters";
             uses inet6_service_filter;
           }
           list fast-update-filter {
             key name;
             ordered-by user;
             description "One or more fast update filters";
             uses inet6_fuf;
           }
           list template {
             key name;
             description "Define an Inet6 firewall template";
             uses inet6_template;
           }
         }
         container mpls {
           description "Protocol family MPLS for firewall filter";
           uses apply-advanced;
           list dialer-filter {
             key name;
             ordered-by user;
             description "Define an mpls dialer filter";
             uses mpls_dialer_filter;
           }
           list filter {
             key name;
             uses mpls_filter;
           }
           list template {
             key name;
             description "Define an MPLS firewall template";
             uses mpls_template;
           }
         }
         container vpls {
           description "Protocol family VPLS for firewall filter";
           uses apply-advanced;
           list filter {
             key name;
             uses vpls_filter;
           }
         }
         container evpn {
           description "Protocol family EVPN for firewall filter";
           uses apply-advanced;
           list filter {
             key name;
             uses vpls_filter;
           }
         }
         container bridge {
           description "Protocol family BRIDGE for firewall filter";
           uses apply-advanced;
           list filter {
             key name;
             uses bridge_filter;
           }
         }
         container ccc {
           description "Protocol family CCC for firewall filter";
           uses apply-advanced;
           list filter {
             key name;
             uses ccc_filter;
           }
         }
         container any {
           description "Protocol-independent filter";
           uses apply-advanced;
           list filter {
             key name;
             description "Define a protocol independent filter";
             uses any_filter;
           }
           list template {
             key name;
             description "Define Protocol independent filter template";
             uses any_template;
           }
         }
         container ethernet-switching {
           description "Protocol family Ethernet Switching for firewall filter";
           uses apply-advanced;
           list filter {
             key name;
             description "Define an Ethernet Switching firewall filter";
             uses es_filter;
           }
           list template {
             key name;
             description "Define an ethernet switching firewall template";
             uses es_template;
           }
         }
       }
       container no-next-header-to-payload-protocol-mapping {
         presence "enable no-next-header-to-payload-protocol-mapping";
         description "To enable next-header matching first extension header";
       }
       list policer {
         key name;
         description "Policer template definition";
         uses firewall_policer;
       }
       list flexible-match {
         key name;
         description "Flexible packet match template definition";
         uses firewall_flexible_match;
       }
       list tunnel-end-point {
         key name;
         description "Tunnel end-point template definition";
         uses tunnel_end_point;
       }
       list hierarchical-policer {
         key name;
         description "Hierarchical policer template definition";
         uses firewall_hierpolicer;
       }
       list enhanced-hierarchical-policer {
         key name;
         description "Enhanced hierarchical policer template definition";
         uses firewall_enhanced_hierarchical_policer;
       }
       leaf disable-arp-policers {
         description "Disables ARP policers";
         type empty;
       }
       list interface-set {
         key name;
         description "Interface set definition";
         uses interface_set_type;
       }
       list load-balance-group {
         key name;
         ordered-by user;
         description "Load-balance group definition";
         uses firewall_load_balance_group;
       }
       list atm-policer {
         key name;
         description "Atm policer";
         uses atm-policer-type;
       }
       list three-color-policer {
         key name;
         description "Three-color policer";
         uses three-color-policer-type;
       }
       list filter {
         key name;
         description "Define an IPv4 firewall filter";
         uses inet_filter;
       }
     }
     container services {
       description "Service PIC applications settings";
       uses apply-advanced;
       container aacl {
         description "Application Aware Access List services configuration";
         uses apply-advanced;
         list rule {
           key name;
           ordered-by user;
           description "One or more AACL rules";
           uses aacl_rule_object;
         }
         list rule-set {
           key name;
           ordered-by user;
           description "Define a Set of AACL rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         list aacl-dyn-rule-set {
           key name;
           ordered-by user;
           description "Define a set of AACL dynamic rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
       }
       container captive-portal-content-delivery {
         description "Configuration for captive portal and content delivery service";
         uses apply-advanced;
         leaf auto-deactivate {
           description "Deactivate content delivery service";
           type string;
         }
         list rule {
           key name;
           ordered-by user;
           description "Define a captive portal content delivery rule";
           uses cpcd-rule-object-type;
         }
         list rule-set {
           key name;
           ordered-by user;
           description "Define a set of captive portal content delivery rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         list profile {
           key name;
           ordered-by user;
           description "One or more rule/rule set in the profile";
           leaf name {
             description "Profile name";
             type string {
               length "1 .. 63";
             }
           }
           uses apply-advanced;
           choice cpcd_rules_choice {
             case case_1 {
               leaf dynamic {
                 description "Dynamic profile flag";
                 type empty;
               }
             }
             case case_2 {
               list cpcd-rules {
                 key name;
                 ordered-by user;
                 description "List of captive portal content delivery rules";
                 leaf name {
                   type string {
                     length "1 .. 63";
                   }
                 }
                 uses apply-advanced;
               }
             }
             case case_3 {
               list cpcd-rule-sets {
                 key name;
                 ordered-by user;
                 description "List of captive portal content delivery rule sets";
                 leaf name {
                   type string {
                     length "1 .. 63";
                   }
                 }
                 uses apply-advanced;
               }
             }
           }
           container ipda-rewrite-options {
             description "Ipda rewrite options";
             uses apply-advanced;
             leaf destination-address {
               description "Default ipda rewrite IP address";
               type jt:ipaddr;
             }
             leaf destination-port {
               description "Default ipda rewrite port";
               type union {
                 type string {
                   pattern "<.*>|$.*";
                 }
                 type uint16 {
                   range "1 .. 65535";
                 }
               }
             }
           }
           container http-redirect-options {
             description "Http redirect options";
             uses apply-advanced;
             leaf url {
               description "URL of the captive portal file";
               type string {
               }
             }
           }
           leaf auto-deactivate {
             description "Deactivate content delivery service";
             type enumeration {
               enum "never" {
                 description "Deactivate never";
               }
               enum "initial-get" {
                 description "Deactivate on initial http-get";
               }
             }
           }
         }
         container traceoptions {
           description "Captive portal and content delivery trace options";
           uses cpcd-trace-options-type;
         }
       }
     }
     list profile-variable-set {
       key name;
       ordered-by user;
       description "Dynamic profiles variable configuration";
       uses juniper-dynamic-profile-varset-object;
     }
     container policy-options {
       description "Routing policy option configuration";
       uses apply-advanced;
       list prefix-list {
         key name;
         description "Define a named set of address prefixes";
         leaf name {
           description "Prefix list name";
           type string;
         }
         uses apply-advanced;
         list prefix-list-item {
           key name;
           uses prefix_list_items;
         }
         leaf apply-path {
           description "Apply IP prefixes from a configuration statement";
           type string;
         }
       }
     }
     container extensible-subscriber-services {
       presence "enable extensible-subscriber-services";
       description "Extensible subscriber services";
       uses apply-advanced;
       leaf-list vsas {
         ordered-by user;
         description "Service VSAs";
         type string;
       }
     }
     container access-cac {
       description "Access ucac configuration";
       uses apply-advanced;
       list interface {
         key name;
         ordered-by user;
         description "Access ucac interface options";
         uses access_cac_interface_options;
       }
     }
     container profile-type {
       presence "enable profile-type";
       description "Profile type";
       uses apply-advanced;
       leaf remote-device-service {
         description "Service profile to be programmed on a remote device";
         type empty;
       }
     }
   }
   grouping aacl_rule_object {
     leaf name {
       description "Rule name";
       type string {
         length "1 .. 63";
       }
     }
     uses apply-advanced;
     leaf dynamic {
       description "Make rule dynamic";
       type empty;
     }
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "One or more terms in AACL rule";
       leaf name {
         description "Term name";
         type string {
           length "1 .. 63";
         }
       }
       uses apply-advanced;
       container from {
         description "Match criteria";
         presence "enable from";
         uses aacl_match_object;
       }
       container then {
         description "Action to take if the 'from' condition is matched";
         uses apply-advanced;
         leaf forwarding-class {
           description "Forwarding class assigned to outgoing packets";
           type string {
           }
         }
         leaf count {
           description "Count packets by application or Application group";
           type enumeration {
             enum "none" {
               description "Do not count any application or group";
             }
             enum "application" {
               description "Count by application name";
             }
             enum "application-group" {
               description "Count by application group";
             }
             enum "application-group-any" {
               description "Count all application groups as a single total in group 'any'";
             }
             enum "nested-application" {
               description "Count by nested application name";
             }
           }
         }
         leaf log {
           description "Log session information for this application match";
           type enumeration {
             enum "none" {
               description "Do not log session information";
             }
             enum "session-start" {
               description "Log session start information for this match";
             }
             enum "session-start-end" {
               description "Log session start/end information for this match";
             }
             enum "session-start-end-no-stats" {
               description "Log session start/end information with no stats";
             }
             enum "session-start-interim-end" {
               description "Log session start/interim/end information for this match";
             }
             enum "session-interim-end" {
               description "Log session interim/end information for this match";
             }
             enum "session-end" {
               description "Log session end information for this match";
             }
           }
         }
         leaf police {
           description "Policer name";
           type string {
           }
         }
         choice designation {
           case case_1 {
             leaf accept {
               description "Accept the packet";
               type empty;
             }
           }
           case case_2 {
             leaf discard {
               description "Discard the packet";
               type empty;
             }
           }
         }
       }
     }
   }
   grouping aacl_match_object {
     uses apply-advanced;
     list source-address {
       key name;
       ordered-by user;
       description "Match IP source address";
       uses sfw_addr_object;
     }
     list destination-address {
       key name;
       ordered-by user;
       description "Match IP destination address";
       uses sfw_addr_object;
     }
     list source-address-range {
       key "low high";
       ordered-by user;
       description "Match IP source address range";
       leaf low {
         description "Lower limit of address range";
         type jt:ipaddr;
       }
       leaf high {
         description "Upper limit of address range";
         type jt:ipaddr;
       }
       leaf except {
         description "Match address not in this prefix";
         type empty;
       }
     }
     list source-prefix-list {
       key name;
       ordered-by user;
       description "One or more named lists of source prefixes to match";
       leaf name {
         description "Name of prefix list to match against";
         type string;
       }
       leaf except {
         description "Name of prefix list not to match against";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     choice app-rule {
       case case_1 {
         leaf application-group-any {
           description "Use to wildcard or match any application group";
           type empty;
         }
       }
       case case_2 {
         leaf application-unknown {
           description "Use to specify unknown application as the match criteria.";
           type empty;
         }
       }
       case case_3 {
         leaf nested-application-unknown {
           description "Use to specify unknown nested application as the match criteria.";
           type empty;
         }
       }
       case case_4 {
         leaf-list applications {
           ordered-by user;
           description "Match one or more applications";
           type string;
         }
       }
       case case_5 {
         leaf-list nested-applications {
           ordered-by user;
           description "Match one or more nested-applications";
           type string;
         }
       }
       case case_6 {
         leaf-list application-groups {
           ordered-by user;
           description "Match one or more applications";
           type string;
         }
       }
     }
   }
   grouping access_cac_interface_options {
     description "Access ucac interface options";
     leaf name {
       description "Interface name";
       type union {
         type jt:interface-unit;
         type string {
           pattern "<.*>|$.*";
         }
       }
     }
     uses apply-advanced;
     container multicast-video-bandwidth {
       presence "enable multicast-video-bandwidth";
       description "Maximum multicast bandwidth for the interface";
       leaf access-cac-bandwidth {
         description "Bandwidth used in access cac configuration";
         units "bps";
         type string;
       }
     }
     container video-bandwidth {
       presence "enable video-bandwidth";
       description "Maximum video bandwidth for the interface";
       leaf access-cac-bandwidth {
         description "Bandwidth used in access cac configuration";
         units "bps";
         type string;
       }
     }
     choice isqos {
       case case_1 {
         leaf no-qos-adjust {
           description "No qos adjustment";
           type empty;
         }
       }
       case case_2 {
         container qos-adjust-hierarchical {
           description "Ucac interface set configuration";
           uses apply-advanced;
           leaf interface-set {
             description "Enable hierarchical adjust on iflset";
             type empty;
           }
         }
       }
     }
     list multicast-video-policy {
       key name;
       ordered-by user;
       description "Mcast video policy";
       leaf name {
         description "Mcast video policy name";
         type string {
           length "1 .. 64";
         }
       }
       uses apply-advanced;
       container family {
         presence "enable family";
         description "Access cac multicast policy family";
         uses apply-advanced;
         choice family_type {
           case case_1 {
             container inet {
               presence "enable inet";
               description "Family inet";
               uses apply-advanced;
               leaf-list source {
                 description "One or more multicast source addresses";
                 type jt:ipv4addr;
               }
               leaf-list group {
                 ordered-by user;
                 description "One or more multicast group addresses";
                 type jt:ipv4addr;
               }
             }
           }
           case case_2 {
             container inet6 {
               presence "enable inet6";
               description "Family inet6";
               uses apply-advanced;
               leaf-list source {
                 description "One or more multicast source addresses";
                 type jt:ipv6addr;
               }
               leaf-list group {
                 ordered-by user;
                 description "One or more multicast group addresses";
                 type jt:ipv6addr;
               }
             }
           }
         }
       }
       container bandwidth {
         presence "enable bandwidth";
         description "Maximum video bandwidth for the interface";
         uses apply-advanced;
         leaf access-cac-bandwidth {
           description "Bandwidth used in access cac configuration";
           units "bps";
           type string;
         }
       }
       leaf adaptive {
         description "Use multicast real traffic rate";
         type empty;
       }
     }
   }
   grouping advisory_options_type {
     uses apply-advanced;
     leaf upstream-rate {
       description "Recommended upstream shaping rate";
       units "bits per second";
       type string;
     }
     leaf downstream-rate {
       description "Recommended downstream shaping rate";
       units "bits per second";
       type string;
     }
   }
   grouping aggregate-load-balance {
     description "Load balancing parameters";
     uses apply-advanced;
     choice adaptive_option {
       case case_1 {
         leaf per-packet {
           description "Per packet";
           type empty;
         }
       }
       case case_2 {
         leaf no-adaptive {
           description "Disable adaptive";
           type empty;
         }
       }
       case case_3 {
         container adaptive {
           presence "enable adaptive";
           description "Enable adaptive load balancing by re-programming selector table";
           uses apply-advanced;
           leaf tolerance {
             description "Target tolerance in percentage (default 20%)";
             units "percent";
             type union {
               type string {
                 pattern "<.*>|$.*";
               }
               type uint32 {
                 range "1 .. 100";
               }
             }
           }
           leaf pps {
             description "Adaptive load balance based on packet per second (default bps)";
             type empty;
           }
           leaf scan-interval {
             description "Scan interval for multiple of 30 seconds (default 30 seconds)";
             type union {
               type string {
                 pattern "<.*>|$.*";
               }
               type uint32 {
                 range "1 .. 5";
               }
             }
           }
         }
       }
     }
     leaf local-bias {
       description "Local bias in percentage";
       units "percent";
       type union {
         type string {
           pattern "<.*>|$.*";
         }
         type uint32 {
           range "0 .. 100";
         }
       }
     }
   }
   grouping any_filter {
     leaf name {
       description "Filter name";
       type string {
       }
     }
     uses apply-advanced;
     leaf interface-specific {
       description "Defined counters are interface specific";
       type empty;
     }
     leaf instance-shared {
       description "Filter instance shared";
       type empty;
     }
     leaf interface-shared {
       description "Filter is interface-shared";
       type empty;
     }
     leaf micro-segmentation {
       description "Indicates GBP tagging filter";
       type empty;
     }
     leaf scale-mode {
       description "Program the filter in scale mode(programs only one pipeline)";
       type empty;
     }
     leaf fast-lookup-filter {
       description "Configure filter in the fast lookup hardware block";
       type empty;
     }
     list term {
       key name;
       ordered-by user;
       description "Define a firewall term";
       leaf name {
         description "Term name";
         type string {
         }
       }
       uses apply-advanced;
       container from {
         description "Define match criteria";
         uses apply-advanced;
         list interface {
           key name;
           ordered-by user;
           description "Match interface name";
           uses match_interface_object_oam;
         }
         list interface-set {
           key name;
           ordered-by user;
           description "Match interface in set";
           uses match_interface_set_object;
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
           case case_3 {
             leaf-list mpls-forwarding-class {
               ordered-by user;
               description "String name";
               type string {
               }
             }
           }
           case case_4 {
             leaf-list mpls-forwarding-class-except {
               ordered-by user;
               description "String name";
               type string {
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         leaf service-filter-hit {
           description "Match if service-filter-hit is set";
           type empty;
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         list destination-mac-address {
           key name;
           ordered-by user;
           description "Destination MAC address";
           uses firewall_mac_addr_object;
         }
         list source-mac-address {
           key name;
           ordered-by user;
           description "Source MAC address";
           uses firewall_mac_addr_object;
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
         choice learn-vlan-id_choice {
           case case_1 {
             leaf-list learn-vlan-id {
               ordered-by user;
               description "Range of values";
               type string;
             }
           }
           case case_2 {
             leaf-list learn-vlan-id-except {
               ordered-by user;
               description "Range of values";
               type string;
             }
           }
         }
         choice ether-type_choice {
           case case_1 {
             leaf-list ether-type {
               ordered-by user;
               type string;
             }
           }
           case case_2 {
             leaf-list ether-type-except {
               ordered-by user;
               type string;
             }
           }
         }
         leaf mpls-bottom-of-stack {
           description "Match MPLS BottomOfStack bit";
           type empty;
         }
         choice slice_choice {
           case case_1 {
             leaf-list slice {
               ordered-by user;
               description "Slice name";
               type string {
                 length "1 .. 64";
               }
             }
           }
           case case_2 {
             leaf-list slice-except {
               ordered-by user;
               description "Slice name";
               type string {
                 length "1 .. 64";
               }
             }
           }
         }
         choice flex-mask_choice {
           case case_1 {
             container flexible-match-mask {
               description "Match flexible mask";
               presence "enable flexible-match-mask";
               uses match_L3_flexible_mask;
             }
           }
         }
         choice flex-range_choice {
           case case_1 {
             container flexible-match-range {
               description "Match flexible range";
               presence "enable flexible-match-range";
               uses match_L3_flexible_range;
             }
           }
         }
         list egress-interface {
           key name;
           ordered-by user;
           description "Match egress interface name";
           uses match_interface_object;
         }
         list mpls-label {
           key name;
           ordered-by user;
           description "MPLS label bits";
           leaf name {
             description "Range of values between 0 and 1048575 in decimal or hexadecimal";
             type string {
             }
           }
           uses apply-advanced;
         }
         container ip-version {
           description "Define IP version";
           uses apply-advanced;
           container ipv4 {
             description "Define L3/L4 match items to match IPv4 packets";
             uses apply-advanced;
             choice ip-protocol_choice {
               case case_1 {
                 leaf-list ip-protocol {
                   ordered-by user;
                   type string;
                 }
               }
               case case_2 {
                 leaf-list ip-protocol-except {
                   ordered-by user;
                   type string;
                 }
               }
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice ip-precedence_choice {
               case case_1 {
                 leaf-list ip-precedence {
                   ordered-by user;
                   type string;
                 }
               }
               case case_2 {
                 leaf-list ip-precedence-except {
                   ordered-by user;
                   type string;
                 }
               }
             }
             choice dscp_choice {
               case case_1 {
                 leaf-list dscp {
                   ordered-by user;
                   type string;
                 }
               }
               case case_2 {
                 leaf-list dscp-except {
                   ordered-by user;
                   type string;
                 }
               }
             }
             list ip-source-address {
               key name;
               ordered-by user;
               description "Match IP source address";
               uses firewall_addr_object;
             }
             list ip-address {
               key name;
               ordered-by user;
               description "Match IP source or destination address";
               uses firewall_addr_object;
             }
             list address {
               key name;
               ordered-by user;
               description "Match IP source or destination address";
               uses firewall_addr_object;
             }
             list ip-destination-address {
               key name;
               ordered-by user;
               description "Match IP destination address";
               uses firewall_addr_object;
             }
             list source-prefix-list {
               key name;
               ordered-by user;
               description "Match IP source prefixes in named list";
               uses firewall_prefix_list;
             }
             list destination-prefix-list {
               key name;
               ordered-by user;
               description "Match IP destination prefixes in named list";
               uses firewall_prefix_list;
             }
             list prefix-list {
               key name;
               ordered-by user;
               description "Match IP address prefixes in named list";
               uses firewall_prefix_list;
             }
             leaf tcp-flags {
               description "Match TCP flags (in symbolic or hex formats) - (Ingress only)";
               type string;
             }
             leaf tcp-initial {
               description "Match initial packet of a TCP connection - (Ingress only)";
               type empty;
             }
             leaf tcp-established {
               description "Match packet of an established TCP connection";
               type empty;
             }
             leaf is-fragment {
               description "Match if packet is a fragment";
               type empty;
             }
             choice ttl_choice {
               case case_1 {
                 leaf-list ttl {
                   ordered-by user;
                   description "Range of values";
                   type string {
                   }
                 }
               }
               case case_2 {
                 leaf-list ttl-except {
                   ordered-by user;
                   description "Range of values";
                   type string {
                   }
                 }
               }
             }
             leaf fragment-flags {
               description "Match fragment flags (in symbolic or hex formats)";
               type string {
               }
             }
             container vxlan {
               description "Define vxlan match items";
               uses apply-advanced;
               choice vni_choice {
                 case case_1 {
                   leaf-list vni {
                     ordered-by user;
                     description "Range of values";
                     type string {
                     }
                   }
                 }
                 case case_2 {
                   leaf-list vni-except {
                     ordered-by user;
                     description "Range of values";
                     type string {
                     }
                   }
                 }
               }
             }
           }
           container ipv6 {
             description "Define L3/L4 match items to match IPv6 packets";
             uses apply-advanced;
             list ip6-source-address {
               key name;
               ordered-by user;
               description "Match source address";
               uses firewall_addr6_object;
             }
             list ip6-destination-address {
               key name;
               ordered-by user;
               description "Match destination address";
               uses firewall_addr6_object;
             }
             list ip6-address {
               key name;
               ordered-by user;
               description "Match IPv6 source or destination address";
               uses firewall_addr6_object;
             }
             list address {
               key name;
               ordered-by user;
               description "Match IPv6 source or destination address";
               uses firewall_addr6_object;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             list source-prefix-list {
               key name;
               ordered-by user;
               description "Match IP source prefixes in named list";
               uses firewall_prefix_list;
             }
             list destination-prefix-list {
               key name;
               ordered-by user;
               description "Match IP destination prefixes in named list";
               uses firewall_prefix_list;
             }
             list prefix-list {
               key name;
               ordered-by user;
               description "Match IPv6 address prefixes in named list";
               uses firewall_prefix_list;
             }
             choice next-header_choice {
               case case_1 {
                 leaf-list next-header {
                   ordered-by user;
                   type string;
                 }
               }
               case case_2 {
                 leaf-list next-header-except {
                   ordered-by user;
                   type string;
                 }
               }
             }
             choice payload-protocol_choice {
               case case_1 {
                 leaf-list payload-protocol {
                   ordered-by user;
                   type string;
                 }
               }
               case case_2 {
                 leaf-list payload-protocol-except {
                   ordered-by user;
                   type string;
                 }
               }
             }
             choice traffic-class_choice {
               case case_1 {
                 leaf-list traffic-class {
                   ordered-by user;
                   type string;
                 }
               }
               case case_2 {
                 leaf-list traffic-class-except {
                   ordered-by user;
                   type string;
                 }
               }
             }
             leaf tcp-flags {
               description "Match TCP flags (in symbolic or hex formats)";
               type string;
             }
             leaf tcp-initial {
               description "Match initial packet of a TCP connection";
               type empty;
             }
             leaf tcp-established {
               description "Match packet of an established TCP connection";
               type empty;
             }
             choice hop-limit_choice {
               case case_1 {
                 leaf-list hop-limit {
                   ordered-by user;
                   description "Range of values";
                   type string {
                   }
                 }
               }
               case case_2 {
                 leaf-list hop-limit-except {
                   ordered-by user;
                   description "Range of values";
                   type string {
                   }
                 }
               }
             }
             container vxlan {
               description "Define vxlan match items";
               uses apply-advanced;
               choice vni_choice {
                 case case_1 {
                   leaf-list vni {
                     ordered-by user;
                     description "Range of values";
                     type string {
                     }
                   }
                 }
                 case case_2 {
                   leaf-list vni-except {
                     ordered-by user;
                     description "Range of values";
                     type string {
                     }
                   }
                 }
               }
             }
           }
         }
         list mac-address {
           key name;
           ordered-by user;
           description "GBP MAC address";
           uses firewall_mac_addr_object;
         }
         choice vlan-id_choice {
           case case_1 {
             leaf-list vlan-id {
               ordered-by user;
               description "Vlan-id range (0..4095)";
               type string {
               }
             }
           }
           case case_2 {
             leaf-list vlan-id-except {
               ordered-by user;
               description "Vlan-id range (0..4095)";
               type string {
               }
             }
           }
         }
         choice gbp-src-tag_choice {
           case case_1 {
             leaf-list gbp-src-tag {
               ordered-by user;
               description "Range of values";
               type string {
               }
             }
           }
         }
         choice gbp-dst-tag_choice {
           case case_1 {
             leaf-list gbp-dst-tag {
               ordered-by user;
               description "Range of values";
               type string {
               }
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
             leaf hierarchical-policer {
               description "Name of hierarchical policer to use to rate-limit traffic";
               type string {
               }
             }
           }
           case case_4 {
             container enhanced-hierarchical-policer {
               description "Police the packet using enhanced-hierarchical-policer";
               uses apply-advanced;
               leaf enhanced-hierarchical-policer-name {
                 description "Name of enhanced hierarchical policer to use to rate-limit traffic";
                 type string {
                 }
               }
               leaf traffic-priority {
                 description "Traffic priority based on hierarchy level";
                 type enumeration {
                   enum "high" {
                     description "Hierarchical policer high traffic-priority";
                   }
                   enum "medium-high" {
                     description "Hierarchical policer medium-high traffic-priority";
                   }
                   enum "medium-low" {
                     description "Hierarchical policer medium-low traffic-priority";
                   }
                   enum "low" {
                     description "Hierarchical policer low traffic-priority";
                   }
                 }
               }
             }
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         leaf slice {
           description "Set network slice action";
           type string;
         }
         leaf count {
           description "Count the packet in the named counter";
           type string {
           }
         }
         leaf service-accounting {
           description "Count the packets for service accounting";
           type empty;
         }
         leaf service-accounting-deferred {
           description "Count the packets for deferred service accounting";
           type empty;
         }
         leaf service-filter-hit {
           description "Signal subsequent filters in the chain that packet was processed";
           type empty;
         }
         leaf force-premium {
           description "Process packets as premium traffic by subsequent hierarchical policers";
           type empty;
         }
         leaf loss-priority {
           description "Classify packet to loss-priority";
           type enumeration {
             enum "low" {
               description "Loss priority low";
             }
             enum "high" {
               description "Loss priority high";
             }
             enum "medium-low" {
               description "Loss priority medium-low";
             }
             enum "medium-high" {
               description "Loss priority medium-high";
             }
           }
         }
         leaf port-mirror-instance {
           description "Port-mirror the packet to specified instance";
           type string {
           }
         }
         leaf port-mirror {
           description "Port-mirror the packet";
           type empty;
         }
         leaf inline-monitoring-instance {
           description "Inline monitoring to specified instance";
           type string {
           }
         }
         leaf forwarding-class {
           description "Classify packet to forwarding class";
           type string {
           }
         }
         choice designation {
           case case_1 {
             container encapsulate {
               presence "enable encapsulate";
               description "Send to a tunnel";
               leaf tunnel-end-point {
                 description "Name of the tunnel end point";
                 type string {
                 }
               }
             }
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
           case case_5 {
             leaf redirect {
               description "Redirect packets to specified instance";
               type string {
               }
             }
           }
         }
         leaf log {
           description "Log the packet";
           type empty;
         }
         leaf syslog {
           description "System log (syslog) information about the packet";
           type empty;
         }
         container routing-instance {
           description "Packets are directed to specified routing instance";
           leaf routing-instance-name {
             description "Name of routing instance";
             type string {
             }
           }
           leaf topology {
             description "Packets are directed to specified topology";
             type string {
             }
           }
         }
         leaf gbp-tag {
           description "GBP tag to be assigned";
           type union {
             type string {
               pattern "<.*>|$.*";
             }
             type uint32 {
               range "1 .. 65535";
             }
           }
         }
       }
       container template {
         description "Refer a template";
         uses apply-advanced;
         leaf template-name {
           description "Template name";
           type string {
           }
         }
       }
     }
   }
   grouping any_template {
     leaf name {
       description "Template name";
       type string {
       }
     }
     uses apply-advanced;
     container attributes {
       description "Template attributes";
       uses apply-advanced;
       leaf forwarding-class {
         description "Match forwarding class";
         type empty;
       }
       leaf forwarding-class-except {
         description "Do not match forwarding class";
         type empty;
       }
       leaf interface {
         description "Match interface name";
         type empty;
       }
       leaf interface-set {
         description "Match interface in set";
         type empty;
       }
       leaf loss-priority {
         description "Match Loss Priority";
         type empty;
       }
       leaf loss-priority-except {
         description "Do not match Loss Priority";
         type empty;
       }
       leaf packet-length {
         description "Match packet length";
         type empty;
       }
       leaf packet-length-except {
         description "Do not match packet length";
         type empty;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping aps_type {
     uses apply-advanced;
     choice aps_mode {
       case case_1 {
         leaf working-circuit {
           description "Working circuit group name";
           type string;
         }
       }
       case case_2 {
         leaf protect-circuit {
           description "Protect circuit group name";
           type string;
         }
       }
     }
     leaf annex-b {
       description "Annex-b mode";
       type empty;
     }
     leaf wait-to-restore-time {
       description "Circuit wait-to-restore time for annex-b";
       units "seconds";
       type union {
         type string {
           pattern "<.*>|$.*";
         }
         type uint32 {
           range "1 .. 4294967295";
         }
       }
     }
     leaf preserve-interface {
       description "Preserve interface state for fast failover";
       type empty;
     }
     leaf neighbor {
       description "Neighbor address";
       type jt:ipv4addr;
     }
     leaf paired-group {
       description "Name of paired APS group";
       type string;
     }
     container authentication-key {
       presence "enable authentication-key";
       description "Authentication parameters";
       leaf auth_key {
         description "Authentication key";
         type jt:unreadable;
       }
     }
     leaf switching-mode {
       description "APS switching mode";
       type enumeration {
         enum "bidirectional" {
           description "Bidirectional";
         }
         enum "unidirectional" {
           description "Unidirectional";
         }
       }
     }
     leaf advertise-interval {
       description "Advertise interval";
       units "milliseconds";
       type union {
         type string {
           pattern "<.*>|$.*";
         }
         type uint32 {
           range "1 .. 65534";
         }
       }
     }
     leaf hold-time {
       description "Hold time";
       units "milliseconds";
       type union {
         type string {
           pattern "<.*>|$.*";
         }
         type uint32 {
           range "1 .. 65534";
         }
       }
     }
     leaf revert-time {
       description "Circuit revert time";
       units "seconds";
       type union {
         type string {
           pattern "<.*>|$.*";
         }
         type uint32 {
           range "0 .. 65534";
         }
       }
     }
     choice break-before-make-choice {
       leaf break-before-make {
         description "Ensure only one interface is active at a time";
         type empty;
       }
       leaf no-break-before-make {
         description "Don't ensure only one interface is active at a time";
         type empty;
       }
     }
     choice manual_mode {
       case case_1 {
         leaf request {
           description "Request circuit state";
           type enumeration {
             enum "protect" {
               description "Request protect circuit";
             }
             enum "working" {
               description "Request working circuit";
             }
           }
         }
       }
       case case_2 {
         leaf force {
           description "Force circuit state";
           type enumeration {
             enum "protect" {
               description "Force protect circuit";
             }
             enum "working" {
               description "Force working circuit";
             }
           }
         }
       }
       case case_3 {
         leaf lockout {
           description "Lockout protection";
           type empty;
         }
       }
     }
     leaf fast-aps-switch {
       description "Fast aps switch";
       type empty;
     }
   }
   grouping atm-policer-type {
     description "Atm policer";
     leaf name {
       description "Policer name";
       type string {
       }
     }
     uses apply-advanced;
     leaf logical-interface-policer {
       description "Policer is logical interface policer";
       type empty;
     }
     leaf atm-service {
       description "ATM service category";
       type enumeration {
         enum "cbr" {
           description "Constant bit rate";
         }
         enum "rtvbr" {
           description "Real-time variable bit rate";
         }
         enum "nrtvbr" {
           description "Non-real-time variable bit rate";
         }
         enum "ubr" {
           description "Unspecified bit rate";
         }
       }
     }
     leaf peak-rate {
       description "ATM Peak Cell Rate (PCR)";
       units "cps";
       type string;
     }
     leaf sustained-rate {
       description "ATM Sustained Cell Rate (SCR)";
       units "cps";
       type string;
     }
     leaf max-burst-size {
       description "ATM Maximum Burst Size (MBS)";
       units "cells";
       type union {
         type string {
           pattern "<.*>|$.*";
         }
         type uint64 {
           range "1 .. 4000";
         }
       }
     }
     leaf cdvt {
       description "Cell Delay Variation Tolerance";
       units "microseconds";
       type string;
     }
     leaf policing-action {
       description "Policing action";
       type enumeration {
         enum "count" {
           description "Update counters";
         }
         enum "discard" {
           description "Discard non-conforming cells (CBR.1/VBR.1/UBR.1)";
         }
         enum "discard-tag" {
           description "Discard PCR non-conforming and tag SCR non-conforming cells (VBR.3/UBR.2)";
         }
       }
     }
   }
   grouping auto_configure_vlan_type {
     uses apply-advanced;
     container stacked-vlan-ranges {
       presence "enable stacked-vlan-ranges";
       description "Stacked Vlan Range configuration";
       uses apply-advanced;
       list dynamic-profile {
         key name;
         ordered-by user;
         description "Attach dynamic-profile to ranges";
         max-elements 16;
         leaf name {
           description "Profile name";
           type string;
         }
         uses apply-advanced;
         leaf-list accept {
           ordered-by user;
           type enumeration {
             enum "inet" {
               description "Family inet";
             }
             enum "inet6" {
               description "Family inet6";
             }
             enum "pppoe" {
               description "PPPoE PADI only";
             }
             enum "dhcp-v4" {
               description "DHCP v4 Discover only";
             }
             enum "dhcp-v6" {
               description "DHCP v6 Solicit only";
             }
             enum "any" {
               description "Any in-band packet type";
             }
           }
         }
         list ranges {
           key name;
           ordered-by user;
           description "Configure interface based on stacked-vlan range";
           leaf name {
             description "Stacked-vlan range: [any | <low-tag>-<high-tag>],[any | <low-tag>-<high-tag>]";
             type string {
             }
           }
           uses apply-advanced;
         }
         container access-profile {
           description "Auto-configure VLAN access profile for these ranges";
           leaf ap-name {
             description "Access profile name";
             type string {
               length "1 .. 64";
             }
           }
         }
       }
       container override {
         presence "enable override";
         description "SVLAN profile override specification ";
         uses apply-advanced;
         list outer-tag {
           key name;
           ordered-by user;
           description "Specify pair of SVLAN tags for profile override";
           max-elements 8;
           leaf name {
             description "Stacked-vlan outer tag range to be overridden";
             type union {
               type string {
                 pattern "<.*>|$.*";
               }
               type uint32 {
                 range "1 .. 4094";
               }
             }
           }
           uses apply-advanced;
           leaf inner-tag {
             description "Stacked-vlan inner tag to be overridden";
             type union {
               type string {
                 pattern "<.*>|$.*";
               }
               type uint32 {
                 range "1 .. 4094";
               }
             }
           }
           leaf dynamic-profile {
             description "Dynamic profile to override with";
             type string;
           }
         }
       }
       container authentication {
         description "Auto-configure stacked VLAN authentication";
         uses auto_configure_authentication_type;
       }
       container access-profile {
         description "Auto-configure stacked VLAN access profile";
         leaf access-profile-name {
           description "Access profile name";
           type string {
             length "1 .. 64";
           }
         }
       }
     }
     container vlan-ranges {
       description "Vlan Range configuration";
       uses apply-advanced;
       list dynamic-profile {
         key name;
         ordered-by user;
         description "Attach dynamic-profile to ranges";
         max-elements 16;
         leaf name {
           description "Profile name";
           type string;
         }
         uses apply-advanced;
         choice accept_type {
           case case_1 {
             leaf-list accept {
               ordered-by user;
               type enumeration {
                 enum "inet" {
                   description "Family inet";
                 }
                 enum "inet6" {
                   description "Family inet6";
                 }
                 enum "pppoe" {
                   description "PPPoE PADI only";
                 }
                 enum "dhcp-v4" {
                   description "DHCP v4 Discover only";
                 }
                 enum "dhcp-v6" {
                   description "DHCP v6 Solicit only";
                 }
                 enum "any" {
                   description "Any in-band packet type";
                 }
               }
             }
           }
           case case_2 {
             leaf-list accept-out-of-band {
               ordered-by user;
               type enumeration {
                 enum "ancp" {
                   description "ANCP";
                 }
               }
             }
           }
         }
         list ranges {
           key name;
           ordered-by user;
           description "Configure interface based on vlan range";
           leaf name {
             description "Vlan range: [any | <low-tag>-<high-tag>]";
             type string {
             }
           }
           uses apply-advanced;
         }
         container access-profile {
           description "Auto-configure VLAN access profile for these ranges";
           leaf ap-name {
             description "Access profile name";
             type string {
               length "1 .. 64";
             }
           }
         }
       }
       container override {
         presence "enable override";
         description "VLAN profile override specification";
         uses apply-advanced;
         list tag {
           key name;
           ordered-by user;
           description "Specify VLAN tag for profile override";
           max-elements 8;
           leaf name {
             description "Vlan tag to be overridden";
             type union {
               type string {
                 pattern "<.*>|$.*";
               }
               type uint32 {
                 range "1 .. 4094";
               }
             }
           }
           uses apply-advanced;
           leaf dynamic-profile {
             description "Dynamic profile to override with";
             type string;
           }
         }
       }
       container authentication {
         description "Auto-configure VLAN authentication";
         uses auto_configure_authentication_type;
       }
       container access-profile {
         description "Auto-configure VLAN access profile";
         leaf access-profile-name {
           description "Access profile name";
           type string {
             length "1 .. 64";
           }
         }
       }
     }
     container agent-circuit-identifier {
       description "ACI configuration";
       uses apply-advanced;
       leaf dynamic-profile {
         description "Dynamic profile name";
         type string {
           length "1 .. 64";
         }
       }
     }
     container line-identity {
       description "Line-identity configuration";
       uses apply-advanced;
       container includes {
         presence "enable includes";
         description "Agent options configuration";
         uses apply-advanced;
         leaf circuit-id {
           description "Agent Circit id";
           type empty;
         }
         leaf remote-id {
           description "Agent Remote id";
           type empty;
         }
         container accept-no-ids {
           presence "enable accept-no-ids";
           description "Accept packet with no agent options";
           uses apply-advanced;
         }
       }
       leaf dynamic-profile {
         description "Dynamic profile name";
         type string {
           length "1 .. 64";
         }
       }
     }
     leaf remove-when-no-subscribers {
       description "Requests auto-deletion of interface when not in use by subscribers";
       type empty;
     }
   }
   grouping auto_configure_authentication_type {
     description "Autoconf VLAN authentication";
     uses apply-advanced;
     leaf-list packet-types {
       ordered-by user;
       type enumeration {
         enum "inet" {
           description "Family inet";
         }
         enum "inet6" {
           description "Family inet6";
         }
         enum "pppoe" {
           description "PPPoE PADI only";
         }
         enum "dhcp-v4" {
           description "DHCP v4 Discover only";
         }
         enum "dhcp-v6" {
           description "DHCP v6 Solicit only";
         }
         enum "any" {
           description "Any in-band packet type";
         }
       }
     }
     leaf password {
       description "Username password";
       type string {
         length "1 .. 64";
       }
     }
     container username-include {
       description "Username options";
       uses apply-advanced;
       leaf delimiter {
         description "Delimiter/separator character";
         type string {
           length 1;
         }
       }
       leaf domain-name {
         description "Domain name";
         type string {
           length "1 .. 64";
         }
       }
       leaf user-prefix {
         description "User defined prefix";
         type string {
           length "1 .. 64";
         }
       }
       leaf mac-address {
         description "Include MAC address";
         type empty;
       }
       container option-82 {
         presence "enable option-82";
         description "Include option 82";
         leaf circuit-id {
           description "Include option 82 circuit-id (sub option 1)";
           type empty;
         }
         leaf remote-id {
           description "Include option 82 remote-id (sub option 2)";
           type empty;
         }
       }
       leaf option-18 {
         description "Include option 18 for dhcp-v6";
         type empty;
       }
       leaf option-37 {
         description "Include option 37 for dhcp-v6";
         type empty;
       }
       leaf circuit-type {
         description "Include circuit type";
         type empty;
       }
       leaf radius-realm {
         description "Include Radius realm name";
         type string {
           length "1 .. 64";
         }
       }
       leaf interface-name {
         description "Include interface name";
         type empty;
       }
       leaf vlan-tags {
         description "Include vlan tag(s)";
         type empty;
       }
     }
   }
   grouping base-default-variable-object {
     leaf name {
       description "Name of predefined variable";
       type enumeration {
         enum "igmp-enable" {
           description "Default for junos-igmp-enable";
         }
         enum "igmp-access-group-name" {
           description "Default for junos-igmp-access-group-name";
         }
         enum "igmp-access-source-group-name" {
           description "Default for junos-igmp-access-group-name";
         }
         enum "igmp-version" {
           description "Default for junos-igmp-version";
         }
         enum "igmp-immediate-leave" {
           description "Default for junos-igmp-immediate-leave";
         }
         enum "mld-access-group-name" {
           description "Default for junos-mld-access-group-name";
         }
         enum "mld-access-source-group-name" {
           description "Default for junos-mld-access-source-group-name";
         }
         enum "mld-immediate-leave" {
           description "Default for junos-mld-immediate-leave";
         }
         enum "input-filter" {
           description "Default for junos-input-filter";
         }
         enum "output-filter" {
           description "Default for junos-output-filter";
         }
         enum "input-interface-filter" {
           description "Default for junos-input-interface-filter";
         }
         enum "output-interface-filter" {
           description "Default for junos-output-interface-filter";
         }
         enum "input-ipv6-filter" {
           description "Default for junos-input-ipv6-filter";
         }
         enum "output-ipv6-filter" {
           description "Default for junos-output-ipv6-filter";
         }
         enum "adf-rule-v4" {
           description "Default for junos-adf-rule-v4";
         }
         enum "adf-rule-v6" {
           description "Default for junos-adf-rule-v6";
         }
         enum "cos-scheduler-map" {
           description "Default for junos-cos-scheduler-map";
         }
         enum "cos-shaping-rate" {
           description "Default for junos-cos-shaping-rate";
         }
         enum "cos-guaranteed-rate" {
           description "Default for junos-cos-guaranteed-rate";
         }
         enum "cos-delay-buffer-rate" {
           description "Default for junos-cos-delay-buffer-rate";
         }
         enum "cos-traffic-control-profile" {
           description "Default for junos-cos-traffic-control-profile";
         }
         enum "cos-shaping-mode" {
           description "Default for junos-cos-shaping-mode";
         }
         enum "cos-byte-adjust" {
           description "Default for junos-cos-byte-adjust";
         }
         enum "cos-scheduler" {
           description "Default for junos-cos-scheduler";
         }
         enum "cos-scheduler-pri" {
           description "Default for junos-cos-scheduler-pri";
         }
         enum "cos-scheduler-dropfile-low" {
           description "Default for junos-cos-scheduler-dropfile-low";
         }
         enum "cos-scheduler-dropfile-medium-low" {
           description "Default for junos-cos-scheduler-dropfile-medium-low";
         }
         enum "cos-scheduler-dropfile-medium-high" {
           description "Default for junos-cos-scheduler-dropfile-medium-high";
         }
         enum "cos-scheduler-dropfile-high" {
           description "Default for junos-cos-scheduler-dropfile-high";
         }
         enum "cos-scheduler-dropfile-any" {
           description "Default for junos-cos-scheduler-dropfile-any";
         }
         enum "cos-scheduler-excess-rate" {
           description "Default for junos-cos-scheduler-excess-rate";
         }
         enum "cos-scheduler-explicit-congestion-notification" {
           description "Default for junos-cos-scheduler-explicit-congestion-notification";
         }
         enum "cos-scheduler-ecn-rtlog-rate-limit" {
           description "Default for junos-cos-scheduler-ecn-rtlog-rate-limit";
         }
         enum "cos-scheduler-excess-priority" {
           description "Default for junos-cos-scheduler-excess-priority";
         }
         enum "cos-adjust-minimum" {
           description "Default for junos-cos-adjust-minimum";
         }
         enum "cos-excess-rate-high" {
           description "Default for junos-cos-excess-rate-high";
         }
         enum "cos-excess-rate-low" {
           description "Default for junos-cos-excess-rate-low";
         }
         enum "cos-shaping-rate-burst" {
           description "Default for junos-cos-shaping-rate-burst";
         }
         enum "cos-byte-adjust-frame" {
           description "Default for junos-cos-byte-adjust-frame";
         }
         enum "cos-byte-adjust-cell" {
           description "Default for junos-cos-byte-adjust-cell";
         }
         enum "cos-shaping-rate-priority-high" {
           description "Default for junos-cos-shaping-rate-priority-high";
         }
         enum "cos-shaping-rate-priority-high-burst" {
           description "Default for junos-cos-shaping-rate-priority-high-burst";
         }
         enum "cos-shaping-rate-priority-medium" {
           description "Default for junos-cos-shaping-rate-priority-medium";
         }
         enum "cos-shaping-rate-priority-medium-burst" {
           description "Default for junos-cos-shaping-rate-priority-medium-burst";
         }
         enum "cos-shaping-rate-priority-low" {
           description "Default for junos-cos-shaping-rate-priority-low";
         }
         enum "cos-shaping-rate-priority-low-burst" {
           description "Default for junos-cos-shaping-rate-priority-low-burst";
         }
         enum "cos-shaping-rate-excess-high" {
           description "Default for junos-cos-shaping-rate-excess-high";
         }
         enum "cos-shaping-rate-excess-high-burst" {
           description "Default for junos-cos-shaping-rate-excess-high-burst";
         }
         enum "cos-shaping-rate-excess-low" {
           description "Default for junos-cos-shaping-rate-excess-low";
         }
         enum "cos-shaping-rate-excess-low-burst" {
           description "Default for junos-cos-shaping-rate-excess-low-burst";
         }
         enum "cos-guaranteed-rate-burst" {
           description "Default for junos-cos-guaranteed-rate-burst";
         }
         enum "cos-traffic-control-profile-remaining" {
           description "Default for junos-cos-traffic-control-profile-remaining";
         }
         enum "routing-instances" {
           description "Default for junos-routing-instance";
         }
         enum "pim-enable" {
           description "Default for junos-pim-enable";
         }
         enum "interface-mtu" {
           description "Default for junos-interface-mtu";
         }
         enum "inner-vlan-tag-protocol-id" {
           description "Default for junos-inner-vlan-tag-protocol-id";
         }
         enum "routing-services" {
           description "Default for junos-routing-services";
         }
         enum "aggregation-interface-set-name" {
           description "Default for junos-aggregation-interface-set-name";
         }
         enum "interface-set-name" {
           description "Default for junos-interface-set-name";
         }
         enum "default-interface-set-name" {
           description "Default for junos-default-interface-set-name";
         }
         enum "phy-ifd-interface-set-name" {
           description "Default for junos-phy-ifd-interface-set-name";
         }
         enum "phy-ifd-underlying-intf-set-name" {
           description "Default for junos-phy-ifd-underlying-intf-set-name";
         }
       }
     }
     uses apply-advanced;
     leaf default-value {
       description "Default value for predefined variable";
       type string;
     }
   }
   grouping bridge_filter {
     description "Define a BRIDGE firewall filter";
     leaf name {
       description "Filter name";
       type string {
       }
     }
     uses apply-advanced;
     leaf-list accounting-profile {
       ordered-by user;
       description "Accounting profile name";
       type string;
     }
     leaf interface-specific {
       description "Defined counters are interface specific";
       type empty;
     }
     leaf physical-interface-filter {
       description "Filter is physical interface filter";
       type empty;
     }
     leaf instance-shared {
       description "Filter is routing-instance shared";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         choice ether-type_choice {
           case case_1 {
             leaf-list ether-type {
               ordered-by user;
               type string;
             }
           }
           case case_2 {
             leaf-list ether-type-except {
               ordered-by user;
               type string;
             }
           }
         }
         choice vlan-ether-type_choice {
           case case_1 {
             leaf-list vlan-ether-type {
               ordered-by user;
               type string;
             }
           }
           case case_2 {
             leaf-list vlan-ether-type-except {
               ordered-by user;
               type string;
             }
           }
         }
         list destination-mac-address {
           key name;
           ordered-by user;
           description "Destination MAC address";
           uses firewall_mac_addr_object;
         }
         list source-mac-address {
           key name;
           ordered-by user;
           description "Source MAC address";
           uses firewall_mac_addr_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice learn-vlan-id_choice {
           case case_1 {
             leaf-list learn-vlan-id {
               ordered-by user;
               description "Learn-vlan-id range (0..4095)";
               type string {
               }
             }
           }
           case case_2 {
             leaf-list learn-vlan-id-except {
               ordered-by user;
               description "Learn-vlan-id range (0..4095)";
               type string {
               }
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice user-vlan-id_choice {
           case case_1 {
             leaf-list user-vlan-id {
               ordered-by user;
               description "User-vlan-id range (0..4095)";
               type string {
               }
             }
           }
           case case_2 {
             leaf-list user-vlan-id-except {
               ordered-by user;
               description "User-vlan-id range (0..4095)";
               type string {
               }
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         choice learn-vlan-dei_choice {
           case case_1 {
             leaf-list learn-vlan-dei {
               ordered-by user;
               description "DEI value 0-1";
               type union {
                 type string {
                   pattern "<.*>|$.*";
                 }
                 type uint32 {
                   range "0 .. 1";
                 }
               }
             }
           }
           case case_2 {
             leaf-list learn-vlan-dei-except {
               ordered-by user;
               description "DEI value 0-1";
               type union {
                 type string {
                   pattern "<.*>|$.*";
                 }
                 type uint32 {
                   range "0 .. 1";
                 }
               }
             }
           }
         }
         choice traffic-type_choice {
           case case_1 {
             leaf-list traffic-type {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
           case case_2 {
             leaf-list traffic-type-except {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
         }
         list ip-source-address {
           key name;
           ordered-by user;
           description "Match IP source address";
           uses firewall_addr_object;
         }
         list ip-destination-address {
           key name;
           ordered-by user;
           description "Match IP destination address";
           uses firewall_addr_object;
         }
         list ip-address {
           key name;
           ordered-by user;
           description "Match IP source or destination address";
           uses firewall_addr_object;
         }
         choice ip-protocol_choice {
           case case_1 {
             leaf-list ip-protocol {
               ordered-by user;
               type string;
             }
           }
           case case_2 {
             leaf-list ip-protocol-except {
               ordered-by user;
               type string;
             }
           }
         }
         choice dscp_choice {
           case case_1 {
             leaf-list dscp {
               ordered-by user;
               type string;
             }
           }
           case case_2 {
             leaf-list dscp-except {
               ordered-by user;
               type string;
             }
           }
         }
         choice ip-precedence_choice {
           case case_1 {
             leaf-list ip-precedence {
               ordered-by user;
               type string;
             }
           }
           case case_2 {
             leaf-list ip-precedence-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-flags {
           description "Match TCP flags";
           type string;
         }
         choice icmp-code_choice {
           case case_1 {
             leaf-list icmp-code {
               ordered-by user;
               type string;
             }
           }
           case case_2 {
             leaf-list icmp-code-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         list interface {
           key name;
           ordered-by user;
           description "Match interface name";
           uses match_interface_object;
         }
         list interface-set {
           key name;
           ordered-by user;
           description "Match interface in set";
           uses match_interface_set_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         list ipv6-destination-address {
           key name;
           ordered-by user;
           description "Match IPv6 destination address";
           uses firewall_addr6_object;
         }
         list ipv6-source-address {
           key name;
           ordered-by user;
           description "Match IPv6 source address";
           uses firewall_addr6_object;
         }
         list ipv6-address {
           key name;
           ordered-by user;
           description "Match IPv6 address";
           uses firewall_addr6_object;
         }
         choice ipv6-next-header_choice {
           case case_1 {
             leaf-list ipv6-next-header {
               ordered-by user;
               type string;
             }
           }
           case case_2 {
             leaf-list ipv6-next-header-except {
               ordered-by user;
               type string;
             }
           }
         }
         choice ipv6-payload-protocol_choice {
           case case_1 {
             leaf-list ipv6-payload-protocol {
               ordered-by user;
               type string;
             }
           }
           case case_2 {
             leaf-list ipv6-payload-protocol-except {
               ordered-by user;
               type string;
             }
           }
         }
         choice ipv6-traffic-class_choice {
           case case_1 {
             leaf-list ipv6-traffic-class {
               ordered-by user;
               type string;
             }
           }
           case case_2 {
             leaf-list ipv6-traffic-class-except {
               ordered-by user;
               type string;
             }
           }
         }
         list ipv6-source-prefix-list {
           key name;
           ordered-by user;
           description "Match IPV6 source prefixes in named list";
           uses firewall_prefix_list;
         }
         list ipv6-destination-prefix-list {
           key name;
           ordered-by user;
           description "Match IPV6 destination prefixes in named list";
           uses firewall_prefix_list;
         }
         list ipv6-prefix-list {
           key name;
           ordered-by user;
           description "Match IP source or destination prefixes in named list";
           uses firewall_prefix_list;
         }
         choice flex-mask_choice {
           case case_1 {
             container flexible-match-mask {
               description "Match flexible mask";
               presence "enable flexible-match-mask";
               uses match_L2_flexible_mask;
             }
           }
         }
         choice flex-range_choice {
           case case_1 {
             container flexible-match-range {
               description "Match flexible range";
               presence "enable flexible-match-range";
               uses match_L2_flexible_range;
             }
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice isid_choice {
           case case_1 {
             leaf-list isid {
               ordered-by user;
               description "Range of values";
               type string;
             }
           }
           case case_2 {
             leaf-list isid-except {
               ordered-by user;
               description "Range of values";
               type string;
             }
           }
         }
         choice isid-priority-code-point_choice {
           case case_1 {
             leaf-list isid-priority-code-point {
               ordered-by user;
               description "802.1p priority value 0-7";
               type union {
                 type string {
                   pattern "<.*>|$.*";
                 }
                 type uint32 {
                   range "0 .. 7";
                 }
               }
             }
           }
           case case_2 {
             leaf-list isid-priority-code-point-except {
               ordered-by user;
               description "802.1p priority value 0-7";
               type union {
                 type string {
                   pattern "<.*>|$.*";
                 }
                 type uint32 {
                   range "0 .. 7";
                 }
               }
             }
           }
         }
         choice isid-dei_choice {
           case case_1 {
             leaf-list isid-dei {
               ordered-by user;
               description "DEI value 0-1";
               type union {
                 type string {
                   pattern "<.*>|$.*";
                 }
                 type uint32 {
                   range "0 .. 1";
                 }
               }
             }
           }
           case case_2 {
             leaf-list isid-dei-except {
               ordered-by user;
               description "DEI value 0-1";
               type union {
                 type string {
                   pattern "<.*>|$.*";
                 }
                 type uint32 {
                   range "0 .. 1";
                 }
               }
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
             leaf hierarchical-policer {
               description "Name of hierarchical policer to use to rate-limit traffic";
               type string {
               }
             }
           }
           case case_4 {
             container enhanced-hierarchical-policer {
               description "Police the packet using enhanced-hierarchical-policer";
               uses apply-advanced;
               leaf enhanced-hierarchical-policer-name {
                 description "Name of enhanced hierarchical policer to use to rate-limit traffic";
                 type string {
                 }
               }
               leaf traffic-priority {
                 description "Traffic priority based on hierarchy level";
                 type enumeration {
                   enum "high" {
                     description "Hierarchical policer high traffic-priority";
                   }
                   enum "medium-high" {
                     description "Hierarchical policer medium-high traffic-priority";
                   }
                   enum "medium-low" {
                     description "Hierarchical policer medium-low traffic-priority";
                   }
                   enum "low" {
                     description "Hierarchical policer low traffic-priority";
                   }
                 }
               }
             }
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         leaf count {
           description "Count the packet in the named counter";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf port-mirror-instance {
           description "Port-mirror the packet to specified instance";
           type string {
           }
         }
         leaf port-mirror {
           description "Port-mirror the packet";
           type empty;
         }
         leaf inline-monitoring-instance {
           description "Inline monitoring to specified instance";
           type string {
           }
         }
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf next-hop-group {
           description "Use specified next-hop group";
           type string;
         }
         leaf sample {
           description "Sample the packet";
           type empty;
         }
         leaf log {
           description "Log the packet";
           type empty;
         }
         leaf syslog {
           description "System log (syslog) information about the packet";
           type empty;
         }
         container forwarding-policy {
           description "Specify forwarding policy for extended port";
           uses apply-advanced;
           leaf uplink-select {
             description "Specify port group for uplink selection";
             type string;
           }
         }
       }
     }
   }
   grouping ccc_filter {
     description "Define a CCC firewall filter";
     leaf name {
       description "Filter name";
       type string {
       }
     }
     uses apply-advanced;
     leaf-list accounting-profile {
       ordered-by user;
       description "Accounting profile name";
       type string;
     }
     leaf interface-specific {
       description "Any counters defined will be interface specific";
       type empty;
     }
     leaf scale-mode {
       description "Program the filter in scale mode(programs only one pipeline)";
       type empty;
     }
     leaf fast-lookup-filter {
       description "Configure filter in the fast lookup hardware block";
       type empty;
     }
     leaf physical-interface-filter {
       description "Filter is physical interface filter";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         list interface {
           key name;
           ordered-by user;
           description "Match interface name";
           uses match_interface_object;
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
           case case_3 {
             leaf-list mpls-forwarding-class {
               ordered-by user;
               description "String name";
               type string {
               }
             }
           }
           case case_4 {
             leaf-list mpls-forwarding-class-except {
               ordered-by user;
               description "String name";
               type string {
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         list destination-mac-address {
           key name;
           ordered-by user;
           description "Destination MAC address";
           uses firewall_mac_addr_object;
         }
         leaf is-host-packet {
           description "Match if packet is host generated";
           type empty;
         }
         list source-mac-address {
           key name;
           ordered-by user;
           description "Source MAC address";
           uses firewall_mac_addr_object;
         }
         list ip-source-address {
           key name;
           ordered-by user;
           description "Match IP source address";
           uses firewall_addr_object;
         }
         list ip-destination-address {
           key name;
           ordered-by user;
           description "Match IP destination address";
           uses firewall_addr_object;
         }
         choice dscp_choice {
           case case_1 {
             leaf-list dscp {
               ordered-by user;
               type string;
             }
           }
           case case_2 {
             leaf-list dscp-except {
               ordered-by user;
               type string;
             }
           }
         }
         choice ip-precedence_choice {
           case case_1 {
             leaf-list ip-precedence {
               ordered-by user;
               type string;
             }
           }
           case case_2 {
             leaf-list ip-precedence-except {
               ordered-by user;
               type string;
             }
           }
         }
         choice ip-protocol_choice {
           case case_1 {
             leaf-list ip-protocol {
               ordered-by user;
               type string;
             }
           }
           case case_2 {
             leaf-list ip-protocol-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice flex-mask_choice {
           case case_1 {
             container flexible-match-mask {
               description "Match flexible mask";
               presence "enable flexible-match-mask";
               uses match_L2_flexible_mask;
             }
           }
         }
         choice flex-range_choice {
           case case_1 {
             container flexible-match-range {
               description "Match flexible range";
               presence "enable flexible-match-range";
               uses match_L2_flexible_range;
             }
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
         choice ether-type_choice {
           case case_1 {
             leaf-list ether-type {
               ordered-by user;
               type string;
             }
           }
           case case_2 {
             leaf-list ether-type-except {
               ordered-by user;
               type string;
             }
           }
         }
         choice learn-vlan-id_choice {
           case case_1 {
             leaf-list learn-vlan-id {
               ordered-by user;
               description "Range of values";
               type string;
             }
           }
           case case_2 {
             leaf-list learn-vlan-id-except {
               ordered-by user;
               description "Range of values";
               type string;
             }
           }
         }
         leaf mpls-bottom-of-stack {
           description "Match MPLS BottomOfStack bit";
           type empty;
         }
         list mpls-label {
           key name;
           ordered-by user;
           description "MPLS label bits";
           leaf name {
             description "Range of values between 0 and 1048575 in decimal or hexadecimal";
             type string {
             }
           }
           uses apply-advanced;
         }
         container ip-version {
           description "Define IP version";
           uses apply-advanced;
           container ipv4 {
             description "Define L3/L4 match items to match IPv4 packets";
             uses apply-advanced;
             choice ip-protocol_choice {
               case case_1 {
                 leaf-list ip-protocol {
                   ordered-by user;
                   type string;
                 }
               }
               case case_2 {
                 leaf-list ip-protocol-except {
                   ordered-by user;
                   type string;
                 }
               }
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice ip-precedence_choice {
               case case_1 {
                 leaf-list ip-precedence {
                   ordered-by user;
                   type string;
                 }
               }
             }
             choice dscp_choice {
               case case_1 {
                 leaf-list dscp {
                   ordered-by user;
                   type string;
                 }
               }
               case case_2 {
                 leaf-list dscp-except {
                   ordered-by user;
                   type string;
                 }
               }
             }
             choice traffic-class_choice {
               case case_1 {
                 leaf-list traffic-class {
                   ordered-by user;
                   type string;
                 }
               }
               case case_2 {
                 leaf-list traffic-class-except {
                   ordered-by user;
                   type string;
                 }
               }
             }
             list ip-source-address {
               key name;
               ordered-by user;
               description "Match IP source address";
               uses firewall_addr_object;
             }
             list ip-destination-address {
               key name;
               ordered-by user;
               description "Match IP destination address";
               uses firewall_addr_object;
             }
             list source-prefix-list {
               key name;
               ordered-by user;
               description "Match IP source prefixes in named list";
               uses firewall_prefix_list;
             }
             list destination-prefix-list {
               key name;
               ordered-by user;
               description "Match IP destination prefixes in named list";
               uses firewall_prefix_list;
             }
             leaf tcp-flags {
               description "Match TCP flags (in symbolic or hex formats) - (Ingress only)";
               type string;
             }
             leaf tcp-initial {
               description "Match initial packet of a TCP connection - (Ingress only)";
               type empty;
             }
             leaf tcp-established {
               description "Match packet of an established TCP connection";
               type empty;
             }
             leaf is-fragment {
               description "Match if packet is a fragment";
               type empty;
             }
           }
           container ipv6 {
             description "Define L3/L4 match items to match IPv6 packets";
             uses apply-advanced;
             list ip6-source-address {
               key name;
               ordered-by user;
               description "Match source address";
               uses firewall_addr6_object;
             }
             list ip6-destination-address {
               key name;
               ordered-by user;
               description "Match destination address";
               uses firewall_addr6_object;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             list source-prefix-list {
               key name;
               ordered-by user;
               description "Match IP source prefixes in named list";
               uses firewall_prefix_list;
             }
             list destination-prefix-list {
               key name;
               ordered-by user;
               description "Match IP destination prefixes in named list";
               uses firewall_prefix_list;
             }
             choice next-header_choice {
               case case_1 {
                 leaf-list next-header {
                   ordered-by user;
                   type string;
                 }
               }
               case case_2 {
                 leaf-list next-header-except {
                   ordered-by user;
                   type string;
                 }
               }
             }
             choice payload-protocol_choice {
               case case_1 {
                 leaf-list payload-protocol {
                   ordered-by user;
                   type string;
                 }
               }
               case case_2 {
                 leaf-list payload-protocol-except {
                   ordered-by user;
                   type string;
                 }
               }
             }
             choice traffic-class_choice {
               case case_1 {
                 leaf-list traffic-class {
                   ordered-by user;
                   type string;
                 }
               }
               case case_2 {
                 leaf-list traffic-class-except {
                   ordered-by user;
                   type string;
                 }
               }
             }
             leaf tcp-flags {
               description "Match TCP flags (in symbolic or hex formats)";
               type string;
             }
             leaf tcp-initial {
               description "Match initial packet of a TCP connection";
               type empty;
             }
             leaf tcp-established {
               description "Match packet of an established TCP connection";
               type empty;
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
             leaf hierarchical-policer {
               description "Name of hierarchical policer to use to rate-limit traffic";
               type string {
               }
             }
           }
           case case_4 {
             container enhanced-hierarchical-policer {
               description "Police the packet using enhanced-hierarchical-policer";
               uses apply-advanced;
               leaf enhanced-hierarchical-policer-name {
                 description "Name of enhanced hierarchical policer to use to rate-limit traffic";
                 type string {
                 }
               }
               leaf traffic-priority {
                 description "Traffic priority based on hierarchy level";
                 type enumeration {
                   enum "high" {
                     description "Hierarchical policer high traffic-priority";
                   }
                   enum "medium-high" {
                     description "Hierarchical policer medium-high traffic-priority";
                   }
                   enum "medium-low" {
                     description "Hierarchical policer medium-low traffic-priority";
                   }
                   enum "low" {
                     description "Hierarchical policer low traffic-priority";
                   }
                 }
               }
             }
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         leaf count {
           description "Count the packet in the named counter";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf port-mirror-instance {
           description "Port-mirror the packet to the specified instance";
           type string {
           }
         }
         leaf next-hop-group {
           description "Use specified next-hop group";
           type string;
         }
         leaf port-mirror {
           description "Port-mirror the packet";
           type empty;
         }
         leaf inline-monitoring-instance {
           description "Inline monitoring to specified instance";
           type string {
           }
         }
         leaf packet-mode {
           description "Bypass flow mode for the packet";
           type empty;
         }
         leaf force-premium {
           description "Convert traffic-class to premium";
           type empty;
         }
         leaf log {
           description "Log the packet";
           type empty;
         }
         leaf syslog {
           description "System log (syslog) information about the packet";
           type empty;
         }
         choice designation {
           case case_1 {
             container encapsulate {
               presence "enable encapsulate";
               description "Send to a tunnel";
               leaf tunnel-end-point {
                 description "Name of the tunnel end point";
                 type string {
                 }
               }
             }
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
         }
       }
     }
   }
   grouping cfm-traceoptions {
     description "Trace options for connectivity fault management";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Tracing parameters";
       leaf name {
         type enumeration {
           enum "configuration" {
             description "Trace configuration events";
           }
           enum "routing-socket" {
             description "Trace routing socket events";
           }
           enum "protocol" {
             description "Trace protocol processing events";
           }
           enum "init" {
             description "Trace events related to protocol daemon start-up";
           }
           enum "error" {
             description "Trace events related to catestrophic errors in daemon";
           }
           enum "issu" {
             description "Trace ISSU related events";
           }
           enum "all" {
             description "Trace everything";
           }
         }
       }
     }
   }
   grouping cos_policer {
     description "Define a CoS based policer";
     leaf name {
       description "Policer name";
       type string {
       }
     }
     uses apply-advanced;
     container premium {
       description "Policer to apply to premium traffic";
       presence "enable premium";
       uses ethernet_policer;
     }
     container aggregate {
       description "Policer to apply to aggregate traffic";
       presence "enable aggregate";
       uses ethernet_policer;
     }
   }
   grouping cos_policer_input_priority_map {
     description "Input policer priority map";
     uses apply-advanced;
     container ieee-802.1p {
       description "Use IEEE 802.1p to determine policer priority map";
       uses apply-advanced;
       leaf-list premium {
         ordered-by user;
         description "Input traffic's IEEE 802.1p value to which premium policer is applied";
         type union {
           type string {
             pattern "<.*>|$.*";
           }
           type uint32 {
             range "0 .. 7";
           }
         }
       }
     }
   }
   grouping cos_policer_output_priority_map {
     description "Output policer priority map";
     uses apply-advanced;
     container classifier {
       description "Use classifier as policer priority map";
       uses apply-advanced;
       container premium {
         description "Output traffic classifier to which premium policer is applied";
         uses apply-advanced;
         list forwarding-class {
           key name;
           ordered-by user;
           description "Select a classification for this priority map";
           leaf name {
             description "Forwarding class name";
             type string {
             }
           }
           uses apply-advanced;
           list loss-priority {
             key name;
             ordered-by user;
             description "Select a loss priority";
             leaf name {
               type enumeration {
                 enum "low" {
                   description "Select low loss priority as premium policer";
                 }
                 enum "high" {
                   description "Select high loss priority as premium policer";
                 }
               }
             }
           }
         }
       }
     }
   }
   grouping cpcd-rule-object-type {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "Define a captive portal content delivery term";
       leaf name {
         description "Term name";
         type string {
           length "1 .. 63";
         }
       }
       uses apply-advanced;
       container from {
         description "Define match criteria";
         uses cpcd-match-object-type;
       }
       container then {
         description "Action to take if the 'from' condition is matched";
         uses cpcd-action-object-type;
       }
     }
   }
   grouping cpcd-action-object-type {
     uses apply-advanced;
     choice designation {
       case case_1 {
         leaf accept {
           description "Accept the packet";
           type empty;
         }
       }
       case case_2 {
         container rewrite {
           presence "enable rewrite";
           description "Rewrite the IP-DA of the packet";
           uses apply-advanced;
           leaf destination-address {
             description "The destination IP address";
             type jt:ipaddr;
           }
           leaf destination-port {
             description "The destination port";
             type union {
               type string {
                 pattern "<.*>|$.*";
               }
               type uint16 {
                 range "1 .. 65535";
               }
             }
           }
         }
       }
       case case_3 {
         container redirect {
           presence "enable redirect";
           description "Redirect the http packet";
           leaf url {
             description "URL of the captive portal file";
             type string {
             }
           }
         }
       }
       case case_4 {
         container insert {
           description "Insert tag into the http packet";
           uses apply-advanced;
           list tag {
             key name;
             ordered-by user;
             description "Tag name to be inserted";
             leaf name {
               description "Tag name";
               type string {
                 length "1 .. 127";
               }
             }
             uses apply-advanced;
             leaf tag-value {
               description "Tag value to be inserted";
               type string;
             }
           }
         }
       }
     }
     leaf syslog {
       description "System log information about the packet";
       type empty;
     }
   }
   grouping cpcd-match-object-type {
     uses apply-advanced;
     list destination-address {
       key name;
       ordered-by user;
       description "Match IP destination address";
       leaf name {
         description "Match IP address";
         type string;
       }
       leaf except {
         description "Match address not in this prefix";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     list applications {
       key name;
       ordered-by user;
       description "Match one or more applications";
       leaf name {
         type string {
           length "1 .. 63";
         }
       }
       uses apply-advanced;
       leaf application-protocol {
         description "Application protocol type";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf protocol {
         description "Match IP protocol type";
         type string;
       }
       leaf source-port {
         description "Match TCP/UDP source port";
         type string;
       }
       leaf destination-port {
         description "Match TCP/UDP destination port";
         type string;
       }
     }
   }
   grouping cpcd-trace-options-type {
     description "Trace options for captive portal and content delivery service";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Captive portal operations to include in debugging trace";
       leaf name {
         type enumeration {
           enum "configuration" {
             description "Configuration operations";
           }
           enum "clicommand" {
             description "Cli command operations";
           }
           enum "general" {
             description "Miscellaneous operations";
           }
           enum "rtsock" {
             description "Routing socket operations";
           }
           enum "statistics" {
             description "Statistics operations";
           }
           enum "rules" {
             description "Rules operations";
           }
           enum "ssets" {
             description "Service sets operations";
           }
           enum "ipc" {
             description "RE-PIC operations";
           }
           enum "gres" {
             description "GRES operations";
           }
           enum "re-services" {
             description "RE Service Operations";
           }
           enum "re-svc-debug-stat" {
             description "RE Service debug stats";
           }
           enum "all" {
             description "All operations";
           }
         }
       }
     }
   }
   grouping dcd_rx_bucket_config {
     uses apply-advanced;
     leaf overflow {
       description "Overflow behavior";
       type enumeration {
         enum "tag" {
           description "Tag and count overflow packets";
         }
         enum "discard" {
           description "Discard overflow packets";
         }
       }
     }
     leaf rate {
       description "Bucket rate";
       type union {
         type string {
           pattern "<.*>|$.*";
         }
         type uint32 {
           range "0 .. 100";
         }
       }
     }
     leaf threshold {
       description "Bucket threshold";
       type union {
         type string {
           pattern "<.*>|$.*";
         }
         type uint32 {
           range "0 .. 65535";
         }
       }
     }
   }
   grouping dcd_shaping_config {
     description "Traffic-shaping profile";
     uses apply-advanced;
     choice useless_shaping_choice {
       case case_1 {
         container cbr {
           presence "enable cbr";
           description "Constant bandwidth utilization";
           leaf cbr-value {
             description "Constant bandwidth utilization";
             type string;
           }
           leaf cdvt {
             description "Cell Delay Variation Tolerance";
             units "microseconds";
             type union {
               type string {
                 pattern "<.*>|$.*";
               }
               type uint32 {
                 range "1 .. 9999";
               }
             }
           }
         }
       }
       case case_2 {
         container vbr {
           description "Variable bandwidth utilization";
           leaf peak {
             description "Peak rate";
             type string;
           }
           leaf sustained {
             description "Sustained rate";
             type string;
           }
           leaf burst {
             description "Burst size";
             type string;
           }
           leaf cdvt {
             description "Cell Delay Variation Tolerance";
             units "microseconds";
             type union {
               type string {
                 pattern "<.*>|$.*";
               }
               type uint32 {
                 range "1 .. 9999";
               }
             }
           }
         }
       }
       case case_3 {
         container rtvbr {
           description "ATM2 real-time variable bandwidth utilization";
           leaf peak {
             description "Peak rate";
             type string;
           }
           leaf sustained {
             description "Sustained rate";
             type string;
           }
           leaf burst {
             description "Burst size";
             type string;
           }
           leaf cdvt {
             description "Cell Delay Variation Tolerance";
             units "microseconds";
             type union {
               type string {
                 pattern "<.*>|$.*";
               }
               type uint32 {
                 range "1 .. 9999";
               }
             }
           }
         }
       }
     }
     leaf queue-length {
       description "Queue length";
       type union {
         type string {
           pattern "<.*>|$.*";
         }
         type uint32 {
           range "1 .. 16383";
         }
       }
     }
   }
   grouping dcd_tx_bucket_config {
     uses apply-advanced;
     leaf overflow {
       description "Overflow behavior";
       type enumeration {
         enum "discard" {
           description "Discard overflow packets";
         }
       }
     }
     leaf rate {
       description "Bucket rate";
       type union {
         type string {
           pattern "<.*>|$.*";
         }
         type uint32 {
           range "0 .. 100";
         }
       }
     }
     leaf threshold {
       description "Bucket threshold";
       type union {
         type string {
           pattern "<.*>|$.*";
         }
         type uint32 {
           range "0 .. 65535";
         }
       }
     }
   }
   grouping demux_options_table {
     leaf name {
       type enumeration {
         enum "inet" {
           description "Family inet";
         }
         enum "inet6" {
           description "Family inet6";
         }
       }
     }
   }
   grouping demux_options_type {
     uses apply-advanced;
     leaf underlying-interface {
       description "Underlying interface name";
       type string;
     }
   }
   grouping dhcp-client-type {
     description "Dynamic Host Configuration Protocol client configuration";
     uses apply-advanced;
     container client-identifier {
       description "DHCP server identifies a client by client-identifier value ";
       uses apply-advanced;
       choice client-identifier-choice {
         case case_1 {
           leaf ascii {
             description "Client identifier as an ASCII string";
             type string;
           }
         }
         case case_2 {
           leaf hexadecimal {
             description "Client identifier as a hexadecimal string";
             type string {
             }
           }
         }
       }
       container user-id {
         description "Add user id to client-id option ";
         choice user-id-choice {
           case case_1 {
             leaf ascii {
               description "Client identifier as an ASCII string";
               type string;
             }
           }
           case case_2 {
             leaf hexadecimal {
               description "Client identifier as a hexadecimal string";
               type string {
               }
             }
           }
         }
       }
       container prefix {
         description "Add prefix to client-id option";
         uses apply-advanced;
         leaf host-name {
           description "Add router host name to client-id option";
           type empty;
         }
         leaf logical-system-name {
           description "Add logical system name to client-id option";
           type empty;
         }
         leaf routing-instance-name {
           description "Add routing instance name to client-id option";
           type empty;
         }
       }
       leaf use-interface-description {
         description "Use the interface description";
         type enumeration {
           enum "logical" {
             description "Use the logical interface description";
           }
           enum "device" {
             description "Use the device interface description";
           }
         }
       }
       leaf hardware-type {
         description "Hardware type";
         default "0";
         type union {
           type string {
             pattern "<.*>|$.*";
           }
           type uint8 {
             range "0 .. 255";
           }
         }
       }
     }
     container no-dns-install {
       presence "enable no-dns-install";
       description "Do not install DNS information learned from DHCP server";
     }
     leaf lease-time {
       description "Lease time in seconds requested in DHCP client protocol packet";
       units "seconds";
       type string;
     }
     leaf retransmission-attempt {
       description "Number of attempts to retransmit the DHCP client protocol packet";
       default "4";
       type union {
         type string {
           pattern "<.*>|$.*";
         }
         type uint32 {
           range "0 .. 50000";
         }
       }
     }
     leaf retransmission-interval {
       description "Number of seconds between successive retransmission";
       default "4";
       units "seconds";
       type union {
         type string {
           pattern "<.*>|$.*";
         }
         type uint32 {
           range "4 .. 64";
         }
       }
     }
     leaf metric {
       description "Client initiated default-route metric";
       default "0";
       type union {
         type string {
           pattern "<.*>|$.*";
         }
         type uint32 {
           range "0 .. 255";
         }
       }
     }
     leaf server-address {
       description "DHCP Server-address";
       type jt:ipv4addr;
     }
     leaf update-server {
       description "Propagate TCP/IP settings to DHCP server";
       type empty;
     }
     leaf vendor-id {
       description "Vendor class id for the DHCP Client";
       type string {
         length "1 .. 60";
       }
     }
     leaf force-discover {
       description "Send DHCPDISCOVER after DHCPREQUEST retransmission failure";
       type empty;
     }
     container options {
       description "DHCP options";
       uses apply-advanced;
       list number {
         key name;
         description "DHCP option code";
         leaf name {
           description "DHCP option identifier code";
           type union {
             type string {
               pattern "<.*>|$.*";
             }
             type uint32 {
               range "1 .. 254";
             }
           }
         }
         choice option-type-choice {
           case case_1 {
             leaf hex-string {
               description "Hexadecimal string";
               type string {
                 length "1 .. 510";
               }
             }
           }
         }
       }
       leaf no-hostname {
         description "Do not carry hostname (RFC option code is 12) in packet";
         type empty;
       }
     }
     list requested-options {
       key name;
       description "DHCP options";
       leaf name {
         description "DHCP option identifier code";
         type union {
           type string {
             pattern "<.*>|$.*";
           }
           type uint32 {
             range "1 .. 254";
           }
         }
       }
     }
   }
   grouping dynamic_ifbw_parms_type {
     uses apply-advanced;
     leaf capacity {
       description "Weight of current (vs. maximum) data rate";
       status deprecated;
       units "percent";
       type union {
         type string {
           pattern "<.*>|$.*";
         }
         type uint32 {
           range "0 .. 100";
         }
       }
     }
     leaf margin {
       description "Maximum reduction in bandwidth due to low link quality";
       status deprecated;
       units "percent";
       type union {
         type string {
           pattern "<.*>|$.*";
         }
         type uint32 {
           range "0 .. 100";
         }
       }
     }
     leaf delay {
       description "Bandwidth reduction when delay is announced as 1 second";
       status deprecated;
       units "bits per second";
       type string;
     }
     leaf bandwidth {
       description "Weight of current (vs. maximum) data rate";
       type union {
         type string {
           pattern "<.*>|$.*";
         }
         type uint32 {
           range "0 .. 100";
         }
       }
     }
     leaf resource {
       description "Resource weight";
       type union {
         type string {
           pattern "<.*>|$.*";
         }
         type uint32 {
           range "0 .. 100";
         }
       }
     }
     leaf latency {
       description "Latency weight";
       type union {
         type string {
           pattern "<.*>|$.*";
         }
         type uint32 {
           range "0 .. 100";
         }
       }
     }
     leaf quality {
       description "Relative Link Quality weight";
       type union {
         type string {
           pattern "<.*>|$.*";
         }
         type uint32 {
           range "0 .. 100";
         }
       }
     }
     leaf data-rate {
       description "Data rate weight";
       type union {
         type string {
           pattern "<.*>|$.*";
         }
         type uint32 {
           range "0 .. 100";
         }
       }
     }
     leaf threshold {
       description "Percentage bandwidth change required for routing updates";
       units "percent";
       type union {
         type string {
           pattern "<.*>|$.*";
         }
         type uint32 {
           range "0 .. 100";
         }
       }
     }
     container credit {
       presence "enable credit";
       description "Credit-based scheduling parameters";
       uses apply-advanced;
       leaf interval {
         description "Grant rate interval in 100mS steps";
         type union {
           type string {
             pattern "<.*>|$.*";
           }
           type uint16 {
             range "1 .. 60";
           }
         }
       }
     }
   }
   grouping dynamic_ipv4_type {
     description "Packet triggered subscribers";
     uses apply-advanced;
     container address-ranges {
       description "Packet triggered subscribers configuration";
       uses apply-advanced;
       list dynamic-profile {
         key name;
         ordered-by user;
         description "Attach dynamic-profile to packet triggered subscriber ranges";
         max-elements 16;
         leaf name {
           description "Profile name";
           type string;
         }
         uses apply-advanced;
         list network {
           key name;
           ordered-by user;
           description "IPv4 Network address";
           max-elements 16;
           leaf name {
             description "Specify the network address";
             type jt:ipv4prefix;
           }
           uses apply-advanced;
           list range {
             key name;
             ordered-by user;
             description "Configure demux interface based on source IP address range";
             max-elements 16;
             leaf name {
               description "Name of range";
               type string;
             }
             uses apply-advanced;
             leaf low {
               description "Lower limit of address range";
               type jt:ipv4prefix;
             }
             leaf high {
               description "Upper limit of address range";
               type jt:ipv4prefix;
             }
           }
         }
       }
       container authentication {
         description "Auto-configure packet triggered subscriber authentication";
         uses dynamic_ip_authentication_type;
       }
       leaf session-timeout {
         description "Self destruct or auto clear timeout in seconds";
         type union {
           type string {
             pattern "<.*>|$.*";
           }
           type uint32 {
             range "600 .. 6000";
           }
         }
       }
     }
   }
   grouping dynamic_ip_authentication_type {
     description "Autoconf packet trigger subscriber authentication";
     uses apply-advanced;
     leaf password {
       description "Username password";
       type string {
         length "1 .. 64";
       }
     }
     container username-include {
       description "Username options";
       uses apply-advanced;
       leaf delimiter {
         description "Delimiter/separator character";
         type string {
           length 1;
         }
       }
       leaf domain-name {
         description "Domain name";
         type string {
           length "1 .. 64";
         }
       }
       leaf user-prefix {
         description "User defined prefix";
         type string {
           length "1 .. 64";
         }
       }
       leaf auth-server-realm {
         description "Authentication server realm name";
         type string {
           length "1 .. 64";
         }
       }
       leaf interface-name {
         description "Interface name";
         type empty;
       }
       leaf source-address {
         description "Source address";
         type empty;
       }
     }
   }
   grouping dynamic_ipv6_type {
     description "Packet triggered subscribers";
     uses apply-advanced;
     container prefix-ranges {
       description "Packet triggered subscribers configuration";
       uses apply-advanced;
       list dynamic-profile {
         key name;
         ordered-by user;
         description "Attach dynamic-profile to packet triggered subscriber ranges";
         max-elements 16;
         leaf name {
           description "Profile name";
           type string;
         }
         uses apply-advanced;
         list prefix {
           key name;
           ordered-by user;
           description "IPv6 Network prefix ";
           max-elements 16;
           leaf name {
             description "Specify the network prefix";
             type jt:ipv6prefix;
           }
           uses apply-advanced;
           list range {
             key name;
             ordered-by user;
             description "Configure demux interface based on source IP address range";
             max-elements 16;
             leaf name {
               description "Name of range";
               type string;
             }
             uses apply-advanced;
             leaf low {
               description "Lower limit of prefix range";
               type jt:ipv6prefix;
             }
             leaf high {
               description "Upper limit of prefix range";
               type jt:ipv6prefix;
             }
           }
         }
       }
       container authentication {
         description "Auto-configure packet triggered subscriber authentication";
         uses dynamic_ip_authentication_type;
       }
       leaf session-timeout {
         description "Self destruct or auto clear timeout in seconds";
         type union {
           type string {
             pattern "<.*>|$.*";
           }
           type uint32 {
             range "600 .. 6000";
           }
         }
       }
     }
   }
   grouping epd_threshold_config {
     uses apply-advanced;
     leaf epd-threshold-plp0 {
       description "Early packet discard threshold value";
       units "cells";
       type string;
     }
     leaf plp1 {
       description "Early packet drop threshold value for PLP 1";
       units "cells";
       type string;
     }
   }
   grouping es_filter {
     leaf name {
       description "Filter name";
       type string {
       }
     }
     uses apply-advanced;
     leaf interface-specific {
       description "Defined counters are interface specific";
       type empty;
     }
     leaf scale-mode {
       description "Program the filter in scale mode(programs only one pipeline)";
       type empty;
     }
     leaf physical-interface-filter {
       description "Filter is physical interface filter";
       type empty;
     }
     leaf instance-specific {
       description "Filter is instance specific";
       type empty;
     }
     leaf fast-lookup-filter {
       description "Configure filter in the fast lookup hardware block";
       type empty;
     }
     list term {
       key name;
       ordered-by user;
       description "Define a firewall term";
       leaf name {
         description "Term name";
         type string {
         }
       }
       uses apply-advanced;
       container from {
         description "Define match criteria";
         uses apply-advanced;
         list interface {
           key name;
           ordered-by user;
           description "Match interface name";
           uses match_interface_object;
         }
         list source-mac-address {
           key name;
           ordered-by user;
           description "Match MAC source address";
           uses firewall_mac_addr_object;
         }
         list destination-mac-address {
           key name;
           ordered-by user;
           description "Match MAC destination address";
           uses firewall_mac_addr_object;
         }
         choice ether-type_choice {
           case case_1 {
             leaf-list ether-type {
               ordered-by user;
               type string;
             }
           }
           case case_2 {
             leaf-list ether-type-except {
               ordered-by user;
               type string;
             }
           }
         }
         choice l2-encap-type_choice {
           case case_1 {
             leaf-list l2-encap-type {
               ordered-by user;
               type string;
             }
           }
           case case_2 {
             leaf-list l2-encap-type-except {
               ordered-by user;
               type string;
             }
           }
         }
         choice vlan_choice {
           case case_1 {
             leaf-list vlan {
               ordered-by user;
               description "VLAN name or ID";
               type string;
             }
           }
           case case_2 {
             leaf-list vlan-except {
               ordered-by user;
               description "VLAN name or ID";
               type string;
             }
           }
         }
         choice dot1q-tag_choice {
           case case_1 {
             leaf-list dot1q-tag {
               ordered-by user;
               description "Range of values";
               type string {
               }
             }
           }
           case case_2 {
             leaf-list dot1q-tag-except {
               ordered-by user;
               description "Range of values";
               type string {
               }
             }
           }
         }
         choice dot1q-user-priority_choice {
           case case_1 {
             leaf-list dot1q-user-priority {
               ordered-by user;
               type string;
             }
           }
           case case_2 {
             leaf-list dot1q-user-priority-except {
               ordered-by user;
               type string;
             }
           }
         }
         list address {
           key name;
           ordered-by user;
           description "Match IP source or destination address";
           uses firewall_addr_object;
         }
         list source-address {
           key name;
           ordered-by user;
           description "Match IP source address";
           uses firewall_addr_object;
         }
         list destination-address {
           key name;
           ordered-by user;
           description "Match IP destination address";
           uses firewall_addr_object;
         }
         choice dscp_choice {
           case case_1 {
             leaf-list dscp {
               ordered-by user;
               type string;
             }
           }
           case case_2 {
             leaf-list dscp-except {
               ordered-by user;
               type string;
             }
           }
         }
         choice precedence_choice {
           case case_1 {
             leaf-list precedence {
               ordered-by user;
               type string;
             }
           }
           case case_2 {
             leaf-list precedence-except {
               ordered-by user;
               type string;
             }
           }
         }
         choice ip-options_choice {
           case case_1 {
             leaf-list ip-options {
               ordered-by user;
               type enumeration {
                 enum "any" {
                   description "Any IP option";
                 }
               }
             }
           }
           case case_2 {
             leaf-list ip-options-except {
               ordered-by user;
               type enumeration {
                 enum "any" {
                   description "Any IP option";
                 }
               }
             }
           }
         }
         leaf fragment-flags {
           description "Match fragment flags (in symbolic or hex formats) - (Ingress only)";
           type string {
           }
         }
         leaf is-fragment {
           description "Match if packet is a fragment";
           type empty;
         }
         choice protocol_choice {
           case case_1 {
             leaf-list protocol {
               ordered-by user;
               type string;
             }
           }
           case case_2 {
             leaf-list protocol-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-flags {
           description "Match TCP flags (in symbolic or hex formats)";
           type string;
         }
         leaf tcp-initial {
           description "Match initial packet of a TCP connection";
           type empty;
         }
         leaf tcp-established {
           description "Match packet of an established TCP connection";
           type empty;
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list ip-source-address {
           key name;
           ordered-by user;
           description "Match IP source address";
           uses firewall_addr_object;
         }
         list ip-destination-address {
           key name;
           ordered-by user;
           description "Match IP destination address";
           uses firewall_addr_object;
         }
         choice ip-protocol_choice {
           case case_1 {
             leaf-list ip-protocol {
               ordered-by user;
               type string;
             }
           }
           case case_2 {
             leaf-list ip-protocol-except {
               ordered-by user;
               type string;
             }
           }
         }
         choice ip-precedence_choice {
           case case_1 {
             leaf-list ip-precedence {
               ordered-by user;
               type string;
             }
           }
           case case_2 {
             leaf-list ip-precedence-except {
               ordered-by user;
               type string;
             }
           }
         }
         list ipv6-destination-address {
           key name;
           ordered-by user;
           description "Match IPv6 destination address";
           uses firewall_addr6_object;
         }
         list ipv6-source-address {
           key name;
           ordered-by user;
           description "Match IPv6 source address";
           uses firewall_addr6_object;
         }
         list ipv6-address {
           key name;
           ordered-by user;
           description "Match IPv6 address";
           uses firewall_addr6_object;
         }
         choice ipv6-next-header_choice {
           case case_1 {
             leaf-list ipv6-next-header {
               ordered-by user;
               type string;
             }
           }
           case case_2 {
             leaf-list ipv6-next-header-except {
               ordered-by user;
               type string;
             }
           }
         }
         choice ipv6-payload-protocol_choice {
           case case_1 {
             leaf-list ipv6-payload-protocol {
               ordered-by user;
               type string;
             }
           }
           case case_2 {
             leaf-list ipv6-payload-protocol-except {
               ordered-by user;
               type string;
             }
           }
         }
         choice ipv6-traffic-class_choice {
           case case_1 {
             leaf-list ipv6-traffic-class {
               ordered-by user;
               type string;
             }
           }
           case case_2 {
             leaf-list ipv6-traffic-class-except {
               ordered-by user;
               type string;
             }
           }
         }
         list ipv6-source-prefix-list {
           key name;
           ordered-by user;
           description "Match IPV6 source prefixes in named list";
           uses firewall_prefix_list;
         }
         list ipv6-destination-prefix-list {
           key name;
           ordered-by user;
           description "Match IPV6 destination prefixes in named list";
           uses firewall_prefix_list;
         }
         list ipv6-prefix-list {
           key name;
           ordered-by user;
           description "Match IP source or destination prefixes in named list";
           uses firewall_prefix_list;
         }
         choice interface-group_choice {
           case case_1 {
             leaf-list interface-group {
               ordered-by user;
               description "Range of values";
               type string;
             }
           }
           case case_2 {
             leaf-list interface-group-except {
               ordered-by user;
               description "Range of values";
               type string;
             }
           }
         }
         choice vlan-ether-type_choice {
           case case_1 {
             leaf-list vlan-ether-type {
               ordered-by user;
               type string;
             }
           }
           case case_2 {
             leaf-list vlan-ether-type-except {
               ordered-by user;
               type string;
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice learn-vlan-id_choice {
           case case_1 {
             leaf-list learn-vlan-id {
               ordered-by user;
               description "Range of values";
               type string;
             }
           }
           case case_2 {
             leaf-list learn-vlan-id-except {
               ordered-by user;
               description "Range of values";
               type string;
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice learn-vlan-dei_choice {
           case case_1 {
             leaf-list learn-vlan-dei {
               ordered-by user;
               description "DEI value 0-1";
               type union {
                 type string {
                   pattern "<.*>|$.*";
                 }
                 type uint32 {
                   range "0 .. 1";
                 }
               }
             }
           }
           case case_2 {
             leaf-list learn-vlan-dei-except {
               ordered-by user;
               description "DEI value 0-1";
               type union {
                 type string {
                   pattern "<.*>|$.*";
                 }
                 type uint32 {
                   range "0 .. 1";
                 }
               }
             }
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         choice traffic-type_choice {
           case case_1 {
             leaf-list traffic-type {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
           case case_2 {
             leaf-list traffic-type-except {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
         }
         list ip-address {
           key name;
           ordered-by user;
           description "Match IP source or destination address";
           uses firewall_addr_object;
         }
         list interface-set {
           key name;
           ordered-by user;
           description "Match interface in set";
           uses match_interface_set_object;
         }
         list prefix-list {
           key name;
           ordered-by user;
           description "Match IP source or destination prefixes in named list";
           uses firewall_prefix_list;
         }
         choice isid_choice {
           case case_1 {
             leaf-list isid {
               ordered-by user;
               description "Range of values";
               type string;
             }
           }
           case case_2 {
             leaf-list isid-except {
               ordered-by user;
               description "Range of values";
               type string;
             }
           }
         }
         choice isid-priority-code-point_choice {
           case case_1 {
             leaf-list isid-priority-code-point {
               ordered-by user;
               description "802.1p priority value 0-7";
               type union {
                 type string {
                   pattern "<.*>|$.*";
                 }
                 type uint32 {
                   range "0 .. 7";
                 }
               }
             }
           }
           case case_2 {
             leaf-list isid-priority-code-point-except {
               ordered-by user;
               description "802.1p priority value 0-7";
               type union {
                 type string {
                   pattern "<.*>|$.*";
                 }
                 type uint32 {
                   range "0 .. 7";
                 }
               }
             }
           }
         }
         choice isid-dei_choice {
           case case_1 {
             leaf-list isid-dei {
               ordered-by user;
               description "DEI value 0-1";
               type union {
                 type string {
                   pattern "<.*>|$.*";
                 }
                 type uint32 {
                   range "0 .. 1";
                 }
               }
             }
           }
           case case_2 {
             leaf-list isid-dei-except {
               ordered-by user;
               description "DEI value 0-1";
               type union {
                 type string {
                   pattern "<.*>|$.*";
                 }
                 type uint32 {
                   range "0 .. 1";
                 }
               }
             }
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         container to-fabric {
           description "Match packets going to fabric";
           presence "enable to-fabric";
           uses to_fabric_object;
         }
         leaf from-fabric {
           description "Match packets coming from fabric";
           type empty;
         }
         leaf source-port-range-optimize {
           description "Optimize the source port range";
           type empty;
         }
         leaf destination-port-range-optimize {
           description "Optimize the destination port range";
           type empty;
         }
         choice arp-type_choice {
           case case_1 {
             leaf-list arp-type {
               ordered-by user;
               type string;
             }
           }
         }
         choice flex-mask_choice {
           case case_1 {
             container flexible-match-mask {
               description "Match flexible mask";
               presence "enable flexible-match-mask";
               uses match_L2_flexible_mask;
             }
           }
         }
         choice flex-range_choice {
           case case_1 {
             container flexible-match-range {
               description "Match flexible range";
               presence "enable flexible-match-range";
               uses match_L2_flexible_range;
             }
           }
         }
         container ip-version {
           description "Define IP version";
           uses apply-advanced;
           container ipv4 {
             description "Define L3/L4 match items to match IPv4 packets";
             uses apply-advanced;
             list address {
               key name;
               ordered-by user;
               description "Match IP source or destination address";
               uses firewall_addr_object;
             }
             list source-address {
               key name;
               ordered-by user;
               description "Match IP source address";
               uses firewall_addr_object;
             }
             list destination-address {
               key name;
               ordered-by user;
               description "Match IP destination address";
               uses firewall_addr_object;
             }
             choice dscp_choice {
               case case_1 {
                 leaf-list dscp {
                   ordered-by user;
                   type string;
                 }
               }
               case case_2 {
                 leaf-list dscp-except {
                   ordered-by user;
                   type string;
                 }
               }
             }
             choice precedence_choice {
               case case_1 {
                 leaf-list precedence {
                   ordered-by user;
                   type string;
                 }
               }
               case case_2 {
                 leaf-list precedence-except {
                   ordered-by user;
                   type string;
                 }
               }
             }
             choice ip-options_choice {
               case case_1 {
                 leaf-list ip-options {
                   ordered-by user;
                   type enumeration {
                     enum "any" {
                       description "Any IP option";
                     }
                   }
                 }
               }
               case case_2 {
                 leaf-list ip-options-except {
                   ordered-by user;
                   type enumeration {
                     enum "any" {
                       description "Any IP option";
                     }
                   }
                 }
               }
             }
             leaf fragment-flags {
               description "Match fragment flags (in symbolic or hex formats) - (Ingress only)";
               type string;
             }
             leaf is-fragment {
               description "Match if packet is a fragment";
               type empty;
             }
             choice protocol_choice {
               case case_1 {
                 leaf-list protocol {
                   ordered-by user;
                   type string;
                 }
               }
               case case_2 {
                 leaf-list protocol-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
                 leaf-list port {
                   ordered-by user;
                   type string;
                 }
               }
               case case_2 {
                 leaf-list port-except {
                   ordered-by user;
                   type string;
                 }
               }
             }
             leaf tcp-flags {
               description "Match TCP flags (in symbolic or hex formats) - (Ingress only)";
               type string;
             }
             leaf tcp-initial {
               description "Match initial packet of a TCP connection - (Ingress only)";
               type empty;
             }
             leaf tcp-established {
               description "Match packet of an established TCP connection";
               type empty;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             list source-prefix-list {
               key name;
               ordered-by user;
               description "Match IP source prefixes in named list";
               uses firewall_prefix_list;
             }
             list destination-prefix-list {
               key name;
               ordered-by user;
               description "Match IP destination prefixes in named list";
               uses firewall_prefix_list;
             }
             list ip-source-address {
               key name;
               ordered-by user;
               description "Match IP source address";
               uses firewall_addr_object;
             }
             list ip-destination-address {
               key name;
               ordered-by user;
               description "Match IP destination address";
               uses firewall_addr_object;
             }
             choice ip-protocol_choice {
               case case_1 {
                 leaf-list ip-protocol {
                   ordered-by user;
                   type string;
                 }
               }
               case case_2 {
                 leaf-list ip-protocol-except {
                   ordered-by user;
                   type string;
                 }
               }
             }
             choice ip-precedence_choice {
               case case_1 {
                 leaf-list ip-precedence {
                   ordered-by user;
                   type string;
                 }
               }
               case case_2 {
                 leaf-list ip-precedence-except {
                   ordered-by user;
                   type string;
                 }
               }
             }
           }
           container ipv6 {
             description "Define L3/L4 match items to match IPv6 packets";
             uses apply-advanced;
             list source-address {
               key name;
               ordered-by user;
               description "Match source address";
               uses firewall_addr6_object;
             }
             list destination-address {
               key name;
               ordered-by user;
               description "Match destination address";
               uses firewall_addr6_object;
             }
             choice traffic-class_choice {
               case case_1 {
                 leaf-list traffic-class {
                   ordered-by user;
                   type string;
                 }
               }
               case case_2 {
                 leaf-list traffic-class-except {
                   ordered-by user;
                   type string;
                 }
               }
             }
             choice next-header_choice {
               case case_1 {
                 leaf-list next-header {
                   ordered-by user;
                   type string;
                 }
               }
               case case_2 {
                 leaf-list next-header-except {
                   ordered-by user;
                   type string;
                 }
               }
             }
             choice payload-protocol_choice {
               case case_1 {
                 leaf-list payload-protocol {
                   ordered-by user;
                   type string;
                 }
               }
               case case_2 {
                 leaf-list payload-protocol-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
                 leaf-list port {
                   ordered-by user;
                   type string;
                 }
               }
               case case_2 {
                 leaf-list port-except {
                   ordered-by user;
                   type string;
                 }
               }
             }
             choice extension-header_choice {
               case case_1 {
                 leaf-list extension-header {
                   ordered-by user;
                   type string;
                 }
               }
               case case_2 {
                 leaf-list extension-header-except {
                   ordered-by user;
                   type string;
                 }
               }
             }
             leaf tcp-flags {
               description "Match TCP flags (in symbolic or hex formats)";
               type string;
             }
             leaf tcp-initial {
               description "Match initial packet of a TCP connection";
               type empty;
             }
             leaf tcp-established {
               description "Match packet of an established TCP connection";
               type empty;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             list source-prefix-list {
               key name;
               ordered-by user;
               description "Match IP source prefixes in named list";
               uses firewall_prefix_list;
             }
             list destination-prefix-list {
               key name;
               ordered-by user;
               description "Match IP destination prefixes in named list";
               uses firewall_prefix_list;
             }
             list ip6-source-address {
               key name;
               ordered-by user;
               description "Match source address";
               uses firewall_addr6_object;
             }
             list ip6-destination-address {
               key name;
               ordered-by user;
               description "Match destination address";
               uses firewall_addr6_object;
             }
           }
         }
         container vxlan {
           description "Define vxlan match items";
           uses apply-advanced;
           choice vni_choice {
             case case_1 {
               leaf-list vni {
                 ordered-by user;
                 description "Range of values";
                 type string {
                 }
               }
             }
             case case_2 {
               leaf-list vni-except {
                 ordered-by user;
                 description "Range of values";
                 type string {
                 }
               }
             }
           }
           choice rsvd1_choice {
             case case_1 {
               leaf-list rsvd1 {
                 ordered-by user;
                 description "Range of values";
                 type string {
                 }
               }
             }
             case case_2 {
               leaf-list rsvd1-except {
                 ordered-by user;
                 description "Range of values";
                 type string {
                 }
               }
             }
           }
           choice rsvd2_choice {
             case case_1 {
               leaf-list rsvd2 {
                 ordered-by user;
                 description "Range of values";
                 type string {
                 }
               }
             }
             case case_2 {
               leaf-list rsvd2-except {
                 ordered-by user;
                 description "Range of values";
                 type string {
                 }
               }
             }
           }
           container flags {
             description "Match VXlan flag field";
             uses match_flags_value;
           }
         }
         choice gbp-src-tag_choice {
           case case_1 {
             leaf-list gbp-src-tag {
               ordered-by user;
               description "Range of values";
               type string {
               }
             }
           }
         }
         choice gbp-dst-tag_choice {
           case case_1 {
             leaf-list gbp-dst-tag {
               ordered-by user;
               description "Range of values";
               type string {
               }
             }
           }
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
       }
       container then {
         description "Action to take if the 'from' condition is matched";
         uses apply-advanced;
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf log {
           description "Log the packet";
           type empty;
         }
         choice policy-map-choice {
           case case_1 {
             leaf clear-policy-map {
               description "Clear the policy marking";
               type empty;
             }
           }
           case case_2 {
             leaf policy-map {
               description "Policy map action";
               type string {
               }
             }
           }
         }
         leaf pkt-trace {
           description "Trace the packet";
           type empty;
         }
         leaf flood {
           description "Flood the packet";
           type empty;
         }
         leaf syslog {
           description "System log (syslog) information about the packet";
           type empty;
         }
         leaf packet-capture {
           description "Enable packet capture for telemetry";
           type empty;
         }
         leaf forwarding-class {
           description "Classify packet to forwarding class";
           type string {
           }
         }
         leaf analyzer {
           description "Name of analyzer - (Ingress only)";
           type string {
           }
         }
         leaf port-mirror-instance {
           description "Port-mirror the packet to specified instance";
           type string {
           }
         }
         leaf port-mirror {
           description "Port-mirror the packet";
           type empty;
         }
         leaf inline-monitoring-instance {
           description "Inline monitoring to specified instance";
           type string {
           }
         }
         leaf inband-flow-telemetry-init {
           description "Initiate inband telemetry for a flow";
           type string;
         }
         leaf inband-flow-telemetry-terminate {
           description "Terminate inband telemetry for a flow";
           type string;
         }
         leaf next-hop-group {
           description "Use specified next-hop group";
           type string;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf count {
           description "Count the packet in the named counter";
           type string {
           }
         }
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
             leaf hierarchical-policer {
               description "Name of hierarchical policer to use to rate-limit traffic";
               type string {
               }
             }
           }
           case case_4 {
             container enhanced-hierarchical-policer {
               description "Police the packet using enhanced-hierarchical-policer";
               uses apply-advanced;
               leaf enhanced-hierarchical-policer-name {
                 description "Name of enhanced hierarchical policer to use to rate-limit traffic";
                 type string {
                 }
               }
               leaf traffic-priority {
                 description "Traffic priority based on hierarchy level";
                 type enumeration {
                   enum "high" {
                     description "Hierarchical policer high traffic-priority";
                   }
                   enum "medium-high" {
                     description "Hierarchical policer medium-high traffic-priority";
                   }
                   enum "medium-low" {
                     description "Hierarchical policer medium-low traffic-priority";
                   }
                   enum "low" {
                     description "Hierarchical policer low traffic-priority";
                   }
                 }
               }
             }
           }
           case case_5 {
             leaf policer-charge {
               description "Name of policer-charge used to charge the policer";
               type string {
               }
             }
           }
         }
         leaf vlan {
           description "Name of VLAN - (Ingress only)";
           type string;
         }
         leaf interface {
           description "Switch traffic to the specified interface by-passing switching lookup - (Ingress only)";
           type union {
             type jt:interface-unit;
             type string {
               pattern "<.*>|$.*";
             }
           }
         }
         container vxlan {
           description "Vxlan related data";
           uses apply-advanced;
           leaf flags {
             description "Set vxlan flags value (8..255 or 0x08..0xFF)";
             type string {
             }
           }
           leaf rsvd1 {
             description "Set vxlan reserved-1 value";
             type string {
             }
           }
           leaf rsvd2 {
             description "Set vxlan reserved-2 value";
             type string {
             }
           }
         }
         leaf gbp-src-tag {
           description "Set GBP source tag";
           type union {
             type string {
               pattern "<.*>|$.*";
             }
             type uint32 {
               range "0 .. 65535";
             }
           }
         }
       }
       container template {
         description "Refer a template";
         uses apply-advanced;
         leaf template-name {
           description "Template name";
           type string {
           }
         }
       }
     }
   }
   grouping es_template {
     leaf name {
       description "Template name";
       type string {
       }
     }
     uses apply-advanced;
     container attributes {
       description "Template attributes";
       uses apply-advanced;
       container ip-version {
         description "Define IP version";
         uses apply-advanced;
         container ipv4 {
           description "Define L3/L4 match items to match IPv4 packets";
           uses apply-advanced;
           leaf destination-port {
             description "Match TCP/UDP destination port";
             type empty;
           }
           leaf destination-prefix-list {
             description "Match IP destination prefixes in named list";
             type empty;
           }
           leaf dscp {
             description "Match Differentiated Services (DiffServ) code point";
             type empty;
           }
           leaf fragment-flags {
             description "Match fragment flags";
             type empty;
           }
           leaf icmp-code {
             description "Match ICMP message code";
             type empty;
           }
           leaf icmp-type {
             description "Match ICMP message type";
             type empty;
           }
           leaf ip-destination-address {
             description "Match IP destination address";
             type empty;
           }
           leaf ip-precedence {
             description "Match IP precedence value";
             type empty;
           }
           leaf ip-protocol {
             description "Match IP protocol type";
             type empty;
           }
           leaf ip-source-address {
             description "Match IP source address";
             type empty;
           }
           leaf is-fragment {
             description "Match if packet is a fragment";
             type empty;
           }
           leaf source-port {
             description "Match TCP/UDP source port";
             type empty;
           }
           leaf source-prefix-list {
             description "Match IP source prefixes in named list";
             type empty;
           }
           leaf tcp-established {
             description "Match packet of an established TCP connection";
             type empty;
           }
           leaf tcp-flags {
             description "Match TCP flags";
             type empty;
           }
           leaf tcp-initial {
             description "Match initial packet of a TCP connection";
             type empty;
           }
         }
         container ipv6 {
           description "Define L3/L4 match items to match IPv6 packets";
           uses apply-advanced;
           leaf destination-port {
             description "Match TCP/UDP destination port";
             type empty;
           }
           leaf destination-prefix-list {
             description "Match IP destination prefixes in named list";
             type empty;
           }
           leaf icmp-code {
             description "Match ICMP message code";
             type empty;
           }
           leaf icmp-type {
             description "Match ICMP message type";
             type empty;
           }
           leaf ip6-destination-address {
             description "Match destination address";
             type empty;
           }
           leaf ip6-source-address {
             description "Match source address";
             type empty;
           }
           leaf next-header {
             description "Match next header protocol type";
             type empty;
           }
           leaf source-port {
             description "Match TCP/UDP source port";
             type empty;
           }
           leaf source-prefix-list {
             description "Match IP source prefixes in named list";
             type empty;
           }
           leaf tcp-established {
             description "Match packet of an established TCP connection";
             type empty;
           }
           leaf tcp-flags {
             description "Match TCP flags";
             type empty;
           }
           leaf tcp-initial {
             description "Match initial packet of a TCP connection";
             type empty;
           }
           leaf traffic-class {
             description " Match Differentiated Services (DiffServ) code point";
             type empty;
           }
         }
       }
       leaf arp-type {
         description "Match ARP type";
         type empty;
       }
       leaf destination-mac-address {
         description "Match MAC destination address";
         type empty;
       }
       leaf destination-port {
         description "Match TCP/UDP destination port";
         type empty;
       }
       leaf destination-port-range-optimize {
         description "Optimize the destination port range";
         type empty;
       }
       leaf destination-prefix-list {
         description "Match IP destination prefixes in named list";
         type empty;
       }
       leaf dscp {
         description "Match Differentiated Services (DiffServ) code point";
         type empty;
       }
       leaf ether-type {
         description "Match Ethernet Type";
         type empty;
       }
       leaf fragment-flags {
         description "Match fragment flags";
         type empty;
       }
       leaf icmp-code {
         description "Match ICMP message code";
         type empty;
       }
       leaf icmp-type {
         description "Match ICMP message type";
         type empty;
       }
       leaf interface {
         description "Match interface name";
         type empty;
       }
       leaf ip-destination-address {
         description "Match IP destination address";
         type empty;
       }
       leaf ip-precedence {
         description "Match IP precedence value";
         type empty;
       }
       leaf ip-protocol {
         description "Match IP protocol type";
         type empty;
       }
       leaf ip-source-address {
         description "Match IP source address";
         type empty;
       }
       leaf is-fragment {
         description "Match if packet is a fragment";
         type empty;
       }
       leaf l2-encap-type {
         description "Match Ethernet Encapsulation Type";
         type empty;
       }
       leaf learn-vlan-id {
         description "Match Learnt VLAN ID";
         type empty;
       }
       leaf source-mac-address {
         description "Match MAC source address";
         type empty;
       }
       leaf source-port {
         description "Match TCP/UDP source port";
         type empty;
       }
       leaf source-port-range-optimize {
         description "Optimize the source port range";
         type empty;
       }
       leaf source-prefix-list {
         description "Match IP source prefixes in named list";
         type empty;
       }
       leaf tcp-established {
         description "Match packet of an established TCP connection";
         type empty;
       }
       leaf tcp-flags {
         description "Match TCP flags";
         type empty;
       }
       leaf tcp-initial {
         description "Match initial packet of a TCP connection";
         type empty;
       }
       leaf user-vlan-1p-priority {
         description "Match User 802.1p VLAN priority";
         type empty;
       }
       leaf user-vlan-id {
         description "Match User VLAN ID";
         type empty;
       }
     }
   }
   grouping ethernet-switching-type {
     description "Ethernet switching family";
     uses apply-advanced;
     leaf port-mode {
       description "Type of port mode";
       type enumeration {
         enum "access" {
           description "Interface mode is access";
         }
         enum "tagged-access" {
           description "Interface mode is tagged-access";
         }
         enum "trunk" {
           description "Interface mode is trunk";
         }
       }
     }
     leaf interface-mode {
       description "Type of interface mode";
       default "access";
       type enumeration {
         enum "access" {
           description "Interface mode is access";
         }
         enum "trunk" {
           description "Interface mode is trunk";
         }
       }
     }
     leaf inter-switch-link {
       description "PVLAN inter switch link";
       type empty;
     }
     leaf reflective-relay {
       description "Reflective-relay mode for this interface";
       type empty;
     }
     choice vlan_choice_list {
       case case_1 {
         container vlan {
           description "Virtual LAN parameters";
           uses apply-advanced;
           leaf-list members {
             ordered-by user;
             description "Membership for this interface (name or id)";
             type string;
           }
         }
       }
       case case_2 {
         container inner-vlan {
           description "Trunk mode vlan membership for this interface";
           uses apply-advanced;
           leaf-list members {
             ordered-by user;
             description "Membership for this interface (name or id)";
             type string;
           }
         }
       }
       case case_3 {
         leaf-list inner-vlan-id-list {
           description "Trunk mode VLAN membership for this interface based on inner VLAN tag";
           type jt:vlan-range;
         }
       }
     }
     leaf vlan-auto-sense {
       description "Enable VLAN auto sense on this interface";
       type empty;
     }
     leaf bridge-domain-type {
       description "Bridge domain type";
       type enumeration {
         enum "svlan" {
           description "Bridge domain type SVLAN";
         }
         enum "bvlan" {
           description "Bridge domain type BVLAN";
         }
       }
     }
     container vlan-rewrite {
       description "Specify VLAN translation";
       uses apply-advanced;
       list translate {
         key name;
         ordered-by user;
         description "Translate incoming VLAN tag";
         leaf name {
           description "Specify the incoming VLAN tag";
           type union {
             type string {
               pattern "<.*>|$.*";
             }
             type uint32 {
               range "1 .. 4094";
             }
           }
         }
         leaf to-vlan-id {
           description "Specify the bridge-domain VLAN-ID";
           type union {
             type string {
               pattern "<.*>|$.*";
             }
             type uint32 {
               range "1 .. 4094";
             }
           }
         }
       }
     }
     leaf native-vlan-id {
       description "Untagged packets on a trunk/tagged-access interface belong to this vlan";
       type string {
       }
     }
     choice isid_list {
       case case_1 {
         leaf isid-list {
           description "Specify the ISID list";
           type enumeration {
             enum "all-service-groups" {
               description "Map all ISIDs specified under the service-groups";
             }
             enum "all" {
               description "Map all ISIDs";
             }
           }
         }
       }
     }
     leaf core-facing {
       description "Interface is core facing";
       type empty;
     }
     container filter {
       description "Packet filtering";
       uses apply-advanced;
       leaf input {
         description "Name of filter applied to received packets";
         type string;
       }
       leaf input-precedence {
         description "Precedence of the filter";
         type union {
           type string {
             pattern "<.*>|$.*";
           }
           type uint32 {
             range "0 .. 255";
           }
         }
       }
       leaf-list input-list {
         ordered-by user;
         description "List of filter modules applied to received packets ";
         type string;
       }
       leaf output {
         description "Name of filter applied to transmitted packets";
         type string;
       }
       leaf output-precedence {
         description "Precedence of the filter";
         type union {
           type string {
             pattern "<.*>|$.*";
           }
           type uint32 {
             range "0 .. 255";
           }
         }
       }
       leaf-list output-list {
         ordered-by user;
         description "List of filter modules applied to transmitted packets ";
         type string;
       }
       leaf-list input-chain {
         ordered-by user;
         description "List of filter modules applied to received packets ";
         type string;
       }
       leaf-list output-chain {
         ordered-by user;
         description "List of filter modules applied to transmitted packets ";
         type string;
       }
       container adf {
         description "Ascend Data Filter definition";
         uses apply-advanced;
         list rule {
           key name;
           ordered-by user;
           description "Set of ADF rules";
           leaf name {
             description "Value for a single rule";
             type string;
           }
           uses apply-advanced;
         }
         leaf counter {
           description "Add a counter to each rule";
           type empty;
         }
         leaf input-precedence {
           description "Precedence of the input rules";
           type union {
             type string {
               pattern "<.*>|$.*";
             }
             type uint32 {
               range "0 .. 255";
             }
           }
         }
         leaf not-mandatory {
           description "No errors will be reported if no rules are present";
           type empty;
         }
         leaf output-precedence {
           description "Precedence of the output rules";
           type union {
             type string {
               pattern "<.*>|$.*";
             }
             type uint32 {
               range "0 .. 255";
             }
           }
         }
       }
       leaf group {
         description "Group to which interface belongs";
         type union {
           type string {
             pattern "<.*>|$.*";
           }
           type uint32 {
             range "1 .. 255";
           }
         }
       }
     }
     container policer {
       description "Interface policing";
       uses apply-advanced;
       leaf input {
         description "Name of policer applied to received packets";
         type string;
       }
       leaf output {
         description "Name of policer applied to transmitted packets";
         type string;
       }
     }
     container storm-control {
       description "Storm control profile name to bind";
       uses apply-advanced;
       leaf profile-name {
         description "Profile name";
         type string;
       }
     }
     container recovery-timeout {
       description "Recovery timeout for this interface";
       leaf time-in-seconds {
         units "seconds";
         type union {
           type string {
             pattern "<.*>|$.*";
           }
           type uint32 {
             range "10 .. 3600";
           }
         }
       }
     }
   }
   grouping ethernet_policer {
     description "Define a policer";
     uses apply-advanced;
     choice bandwidth {
       case case_1 {
         leaf bandwidth-limit {
           description "Bandwidth limit";
           units "bits per second";
           type string;
         }
       }
     }
     leaf burst-size-limit {
       description "Burst size limit";
       units "bytes";
       type string;
     }
   }
   grouping ett-attributes {
     description "Transport ethernet configuration attributes";
     uses apply-advanced;
     leaf rate {
       description "Ethernet client signal rate";
       type enumeration {
         enum "100ge" {
           description "100 gigabit ethernet";
         }
       }
     }
   }
   grouping fibre-channel-type {
     description "Fibre Channel switching family";
     uses apply-advanced;
     leaf port-mode {
       description "Port mode";
       type enumeration {
         enum "f-port" {
           description "Fabric port";
         }
         enum "e-port" {
           description "Inter-switch port";
         }
         enum "np-port" {
           description "Proxy node port";
         }
         enum "auto" {
           description "Interface mode (F/E) is determined at runtime";
         }
       }
     }
     leaf no-npiv {
       description "Disable NPIV";
       type empty;
     }
     container fc-fabric {
       description "Virtual fabric parameters";
       uses apply-advanced;
       leaf-list members {
         ordered-by user;
         description "Virtual Fabric Membership for this interface (name or id)";
         type string;
       }
     }
     leaf native-fabric {
       description "FC frames with no virtual fabric header on a interface belong to this fabric";
       type string {
       }
     }
   }
   grouping firewall_addr6_object {
     leaf name {
       description "Prefix to match";
       type jt:ipv6prefix;
     }
     leaf except {
       description "Match address not in this prefix";
       type empty;
     }
   }
   grouping firewall_addr_object {
     leaf name {
       description "Prefix to match";
       type jt:ipv4prefix;
     }
     leaf except {
       description "Match address not in this prefix";
       type empty;
     }
   }
   grouping firewall_enhanced_hierarchical_policer {
     description "Define a enhanced hierarchical policer";
     leaf name {
       description "Enhanced hierarchical policer name";
       type string {
       }
     }
     uses apply-advanced;
     leaf filter-specific {
       description "Enhanced hierarchical policer is filter-specific";
       type empty;
     }
     container high {
       description "Enhanced hierarchical policer high level";
       presence "enable high";
       uses enhanced-hierarchical-policer-level;
     }
     container medium-high {
       description "Enhanced hierarchical policer medium-high level";
       presence "enable medium-high";
       uses enhanced-hierarchical-policer-level;
     }
     container medium-low {
       description "Enhanced hierarchical policer medium-low level";
       presence "enable medium-low";
       uses enhanced-hierarchical-policer-level;
     }
     container low {
       description "Enhanced hierarchical policer low level";
       presence "enable low";
       uses enhanced-hierarchical-policer-level;
     }
   }
   grouping enhanced-hierarchical-policer-level {
     description "Define a enhanced hierarchical policer level";
     uses apply-advanced;
     leaf committed-burst-size {
       description "Burst size allowed for committed traffic";
       units "bytes";
       type string;
     }
     leaf committed-information-rate {
       description "Bandwidth allowed for committed traffic";
       units "bits per second";
       type string;
     }
     leaf max-committed-information-rate {
       description "Maximum bandwidth allowed for committed traffic";
       units "bits per second";
       type string;
     }
     container then {
       description "Action to take if the rate limits are exceeded";
       uses apply-advanced;
       leaf discard {
         description "Discard the packet";
         type empty;
       }
     }
   }
   grouping firewall_flexible_match {
     description "Define a flexible match";
     leaf name {
       description "Flex match template name";
       type string {
       }
     }
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of integer input (1..32 bits), Optional length of string input (1..128 bits)";
       type union {
         type uint32;
         type string {
           pattern "<.*>|$.*";
         }
       }
     }
   }
   grouping firewall_hierpolicer {
     description "Define a hierarchical policer";
     leaf name {
       description "Hierarchical Policer name";
       type string {
       }
     }
     choice sharing {
       case case_1 {
         leaf logical-interface-policer {
           description "Hierarchical policer is a logical interface policer";
           type empty;
         }
       }
       case case_2 {
         leaf physical-interface-policer {
           description "Hierarchical policer is a physical interface policer";
           type empty;
         }
       }
     }
     leaf shared-bandwidth-policer {
       description "Share policer bandwidth among bundle links";
       type empty;
     }
     leaf filter-specific {
       description "Hierarchical policer is filter-specific";
       type empty;
     }
     container aggregate {
       description "Aggregate definition";
       presence "enable aggregate";
       uses hierarchical-policer-aggregate-bucket;
     }
     container premium {
       description "Premium definition";
       presence "enable premium";
       uses hierarchical-policer-premium-bucket;
     }
   }
   grouping firewall_load_balance_group {
     description "Define group of destinations for load balancing";
     leaf name {
       description "Load balance group name";
       type string {
       }
     }
     uses apply-advanced;
     leaf-list next-hop-group {
       ordered-by user;
       description "Use specified next-hop group";
       type string;
     }
   }
   grouping firewall_mac_addr_object {
     leaf name {
       description "MAC address to match";
       type jt:mac-addr-prefix;
     }
     leaf except {
       description "Match MAC address not in this range";
       type empty;
     }
   }
   grouping firewall_policer {
     description "Define a policer";
     leaf name {
       description "Policer name";
       type string {
       }
     }
     uses apply-advanced;
     leaf filter-specific {
       description "Policer is filter-specific";
       type empty;
     }
     leaf logical-interface-policer {
       description "Policer is logical interface policer";
       type empty;
     }
     leaf physical-interface-policer {
       description "Policer is physical interface policer";
       type empty;
     }
     leaf logical-bandwidth-policer {
       description "Policer uses logical interface bandwidth";
       type empty;
     }
     leaf shared-bandwidth-policer {
       description "Share policer bandwidth among bundle links";
       type empty;
     }
     leaf loss-priority-rewrite {
       description "Perform loss-priority rewrite on policer result";
       type empty;
     }
     choice exceeding {
       case case_1 {
         container if-exceeding {
           presence "enable if-exceeding";
           description "Define rate limits";
           uses apply-advanced;
           choice bandwidth {
             case case_1 {
               leaf bandwidth-limit {
                 description "Bandwidth limit";
                 units "bits per second";
                 type string;
               }
             }
             case case_2 {
               leaf bandwidth-percent {
                 description "Bandwidth limit in percentage";
                 units "percent";
                 type union {
                   type string {
                     pattern "<.*>|$.*";
                   }
                   type uint32 {
                     range "1 .. 100";
                   }
                 }
               }
             }
           }
           leaf burst-size-limit {
             description "Burst size limit";
             units "bytes";
             type string;
           }
           container aggregate-policing {
             presence "enable aggregate-policing";
             description "Configure Aggregate Policer";
             uses apply-advanced;
             list policer {
               key name;
               ordered-by user;
               description "Two-color policer to be used as aggregate";
               max-elements 1;
               leaf name {
                 description "Name of two-color policer to use to aggregate police";
                 type string;
               }
               uses apply-advanced;
               leaf aggregate-sharing-mode {
                 description "Hierarchical Metering model";
                 type enumeration {
                   enum "guarantee" {
                     description "Child policer rates are guaranteed rates for member flow";
                   }
                   enum "peak" {
                     description "Child policer rates are peak rates for member flow";
                   }
                 }
               }
             }
           }
         }
       }
       case case_2 {
         container if-exceeding-pps {
           presence "enable if-exceeding-pps";
           description "Define pps limits";
           uses apply-advanced;
           choice pps {
             case case_1 {
               leaf pps-limit {
                 description "PPS limit";
                 units "packets per second";
                 type string;
               }
             }
           }
           leaf packet-burst {
             description "PPS burst size limit";
             units "packets";
             type string;
           }
         }
       }
     }
     container counter {
       description "Define policer counter configuration";
       uses apply-advanced;
       leaf counter-id {
         description "Counter Index";
         type union {
           type string {
             pattern "<.*>|$.*";
           }
           type uint32 {
             range "0 .. 2";
           }
         }
       }
     }
     container then {
       description "Action to take if the rate limits are exceeded";
       uses apply-advanced;
       leaf discard {
         description "Discard the packet";
         type empty;
       }
       leaf loss-priority {
         description "Packet's loss priority";
         type enumeration {
           enum "low" {
             description "Loss priority low";
           }
           enum "high" {
             description "Loss priority high";
           }
           enum "medium-low" {
             description "Loss priority medium-low";
           }
           enum "medium-high" {
             description "Loss priority medium-high";
           }
         }
       }
       leaf forwarding-class {
         description "Classify packet to forwarding class";
         type string {
         }
       }
       leaf out-of-profile {
         description "Discard packets only if both congested and over threshold";
         type empty;
       }
     }
     container aggregate {
       presence "enable aggregate";
       description "Aggregate policer used in Extended Hierarchical Policers";
       uses apply-advanced;
       leaf instantiation {
         description "Specify instantiation semantics of aggregate policer";
         type enumeration {
           enum "global" {
             description "Single global instance of aggregate policer";
           }
         }
       }
     }
   }
   grouping firewall_prefix_list {
     leaf name {
       description "Prefix list to match";
       type string;
     }
     leaf except {
       description "Match addresses not in this prefix list";
       type empty;
     }
   }
   grouping flow-interface-group {
     leaf group {
       description "Interface group ID to match traffic";
       type union {
         type string {
           pattern "<.*>|$.*";
         }
         type uint32;
       }
     }
     leaf exclude {
       description "Don't apply flow-spec filter to traffic on this group";
       type empty;
     }
   }
   grouping flow-route-inet6 {
     leaf name {
       type string;
     }
     uses apply-advanced;
     leaf no-install {
       description "Don't install firewall filter in forwarding";
       type empty;
     }
     container match {
       description "Flow definition";
       uses flow-route-qualifier-inet6;
     }
     container then {
       description "Actions to take for this flow";
       uses flow-route-op;
     }
   }
   grouping flow-route-op {
     uses apply-advanced;
     leaf community {
       description "Name of BGP community";
       type string;
     }
     choice flow_op_action {
       case case_1 {
         leaf accept {
           description "Allow traffic through";
           type empty;
         }
       }
       case case_2 {
         leaf discard {
           description "Discard all traffic for this flow";
           type empty;
         }
       }
       case case_3 {
         leaf rate-limit {
           description "Rate in bits/sec to limit the flow traffic";
           type string;
         }
       }
     }
     leaf routing-instance {
       description "Redirect to instance identified via Route Target community";
       type string {
       }
     }
     leaf sample {
       description "Sample traffic that matches this flow";
       type empty;
     }
     leaf mark {
       description "Set DSCP value for traffic that matches this flow";
       type union {
         type string {
           pattern "<.*>|$.*";
         }
         type uint32 {
           range "0 .. 63";
         }
       }
     }
     leaf next-term {
       description "Continue the filter evaluation after matching this flow";
       type empty;
     }
     choice redirect_op_action {
       case case_1 {
         leaf-list redirect {
           ordered-by user;
           description "Redirect(Tunnel) this flow's traffic to given next-hop address";
           type jt:ipaddr;
         }
       }
     }
   }
   grouping flow-route-qualifier-inet6 {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     container destination {
       description "Destination prefix for this traffic flow";
       presence "enable destination";
       uses flow-prefix-with-offset;
     }
     container source {
       description "Source prefix for this traffic flow";
       presence "enable source";
       uses flow-prefix-with-offset;
     }
     leaf-list icmp6-type {
       ordered-by user;
       description "ICMP message type";
       type string;
     }
     leaf-list icmp6-code {
       ordered-by user;
       description "ICMP message code";
       type string;
     }
     leaf-list flow-label {
       ordered-by user;
       description "Flow-label (0-1048575)";
       type jt:policy-algebra;
     }
   }
   grouping flow-prefix-with-offset {
     leaf prefix {
       type jt:ipv6prefix;
     }
     leaf prefix-offset {
       description "Offset from where prefix match will start";
       type union {
         type uint32;
         type string {
           pattern "<.*>|$.*";
         }
       }
     }
   }
   grouping flow-rule-inet6 {
     leaf name {
       type string;
     }
     uses apply-advanced;
     leaf no-install {
       description "Don't install firewall filter in forwarding";
       type empty;
     }
     container match {
       description "Flow definition";
       uses flow-rule-qualifier-inet6;
     }
     container then {
       description "Actions to take for this flow";
       uses flow-rule-op;
     }
   }
   grouping flow-rule-op {
     uses apply-advanced;
     choice flow_op_action {
       case case_1 {
         leaf accept {
           description "Allow traffic through";
           type empty;
         }
       }
       case case_2 {
         leaf discard {
           description "Discard all traffic for this flow";
           type empty;
         }
       }
       case case_3 {
         leaf rate-limit {
           description "Rate in bits/sec to limit the flow traffic";
           type string;
         }
       }
     }
   }
   grouping flow-rule-qualifier-inet6 {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     container destination {
       description "Destination prefix for this traffic flow";
       presence "enable destination";
       uses flow-prefix-with-offset;
     }
     container source {
       description "Source prefix for this traffic flow";
       presence "enable source";
       uses flow-prefix-with-offset;
     }
   }
   grouping flow-traceoptions-object {
     description "Trace options for flow services";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events and other information to include in trace output";
       leaf name {
         type enumeration {
           enum "all" {
             description "All events";
           }
           enum "basic-datapath" {
             description "Basic packet flow";
           }
           enum "high-availability" {
             description "Flow high-availability information";
           }
           enum "host-traffic" {
             description "Flow host-traffic information";
           }
           enum "fragmentation" {
             description "Ip fragmentation and reassembly events";
           }
           enum "multicast" {
             description "Multicast flow information";
           }
           enum "route" {
             description "Route lookup information";
           }
           enum "session" {
             description "Session creation and deletion events";
           }
           enum "session-scan" {
             description "Session scan information";
           }
           enum "tcp-basic" {
             description "TCP packet flow";
           }
           enum "tunnel" {
             description "Tunnel information";
           }
           enum "jexec" {
             description "Junos forwarding module";
           }
         }
       }
     }
     leaf rate-limit {
       description "Limit the incoming rate of trace messages";
       default "0";
       type union {
         type string {
           pattern "<.*>|$.*";
         }
         type uint32 {
           range "0 .. 4294967295";
         }
       }
     }
     list packet-filter {
       key name;
       ordered-by user;
       description "Flow packet debug filters";
       max-elements 64;
       uses flow-filter-type;
     }
     container trace-level {
       description "FLow trace level";
       uses apply-advanced;
       choice level {
         case case_1 {
           leaf minimal {
             description "Significant messages including warning, error, criticality, alert and emergency.";
             type empty;
           }
         }
         case case_2 {
           leaf brief {
             description "Brief messages including notice, in addition to minimal messages";
             type empty;
           }
         }
         case case_3 {
           leaf detail {
             description "Detail messages including info and debug, in addition to brief messages";
             type empty;
           }
         }
       }
     }
     leaf root-override {
       description "Allow collect flow trace in root from all logical-systems and tenants";
       type empty;
     }
   }
   grouping flow-filter-type {
     description "Flow filter settings";
     leaf name {
       description "Name of the filter";
       type string {
         length "1 .. 63";
       }
     }
     uses apply-advanced;
     leaf protocol {
       description "Match IP protocol type";
       type string;
     }
     leaf source-prefix {
       description "Source IP address prefix";
       type jt:ipprefix;
     }
     leaf destination-prefix {
       description "Destination IP address prefix";
       type jt:ipprefix;
     }
     leaf conn-tag {
       description "Session connection tag";
       type union {
         type string {
           pattern "<.*>|$.*";
         }
         type uint32 {
           range "0 .. 4294967295";
         }
       }
     }
     leaf logical-system {
       description "Logical system";
       status deprecated;
       type string {
         length "1 .. 63";
       }
     }
     leaf source-port {
       description "Match TCP/UDP source port";
       type string;
     }
     leaf destination-port {
       description "Match TCP/UDP destination port";
       type string;
     }
     leaf interface {
       description "Source logical interface";
       type union {
         type jt:interface-name;
         type string {
           pattern "<.*>|$.*";
         }
       }
     }
   }
   grouping flow-validation {
     uses apply-advanced;
     container traceoptions {
       description "Trace options";
       uses flow-dep-traceoptions;
     }
   }
   grouping flow-dep-traceoptions {
     uses apply-advanced;
     container file {
       description "Trace file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "resolution" {
             description "Trace flow to unicast route resolution";
           }
           enum "flash" {
             description "Trace flash processing";
           }
           enum "route" {
             description "Trace routing information";
           }
           enum "normal" {
             description "Trace normal events";
           }
           enum "general" {
             description "Trace general events";
           }
           enum "state" {
             description "Trace state transitions";
           }
           enum "policy" {
             description "Trace policy processing";
           }
           enum "task" {
             description "Trace routing protocol task processing";
           }
           enum "timer" {
             description "Trace routing protocol timer processing";
           }
           enum "all" {
             description "Trace everything";
           }
         }
       }
       leaf send {
         description "Trace transmitted packets";
         type empty;
       }
       leaf receive {
         description "Trace received packets";
         type empty;
       }
       leaf detail {
         description "Trace detailed information";
         type empty;
       }
       leaf disable {
         description "Disable this trace flag";
         type empty;
       }
       container filter {
         presence "enable filter";
         description "Filter to apply to tracing";
         leaf match-on {
           description "Argument on which to match";
           type enumeration {
             enum "prefix" {
               description "Filter based on prefix";
             }
             enum "route-attribute" {
               description "Filter based on route attributes";
             }
           }
         }
         leaf-list policy {
           ordered-by user;
           description "Filter policy";
           type jt:policy-algebra;
         }
       }
     }
   }
   grouping hierarchical-policer-aggregate-bucket {
     uses apply-advanced;
     choice hp-aggregate-exceeding {
       case case_1 {
         container if-exceeding {
           presence "enable if-exceeding";
           description "Define rate limits";
           uses apply-advanced;
           choice bandwidth {
             case case_1 {
               leaf bandwidth-limit {
                 description "Bandwidth limit";
                 units "bits per second";
                 type string;
               }
             }
           }
           leaf burst-size-limit {
             description "Burst size limit";
             units "bytes";
             type string;
           }
         }
       }
       case case_2 {
         container if-exceeding-pps {
           presence "enable if-exceeding-pps";
           description "Define pps limits";
           uses apply-advanced;
           choice pps {
             case case_1 {
               leaf pps-limit {
                 description "PPS limit";
                 units "packets per second";
                 type string;
               }
             }
           }
           leaf packet-burst {
             description "PPS burst size limit";
             units "packets";
             type string;
           }
         }
       }
     }
     container then {
       description "Action to take if the rate limits are exceeded";
       uses apply-advanced;
       choice hierarchical-policer-action {
         case case_1 {
           leaf discard {
             description "Discard the packet";
             type empty;
           }
         }
         case case_2 {
           leaf loss-priority {
             description "Packet's loss priority";
             type enumeration {
               enum "low" {
                 description "Loss priority low";
               }
               enum "high" {
                 description "Loss priority high";
               }
               enum "medium-low" {
                 description "Loss priority medium-low";
               }
               enum "medium-high" {
                 description "Loss priority medium-high";
               }
             }
           }
         }
         case case_3 {
           leaf forwarding-class {
             description "Classify packet to forwarding class";
             type string {
             }
           }
         }
       }
     }
   }
   grouping hierarchical-policer-premium-bucket {
     uses apply-advanced;
     choice hp-premium-exceeding {
       case case_1 {
         container if-exceeding {
           presence "enable if-exceeding";
           description "Define rate limits";
           uses apply-advanced;
           choice bandwidth {
             case case_1 {
               leaf bandwidth-limit {
                 description "Bandwidth limit";
                 units "bits per second";
                 type string;
               }
             }
           }
           leaf burst-size-limit {
             description "Burst size limit";
             units "bytes";
             type string;
           }
         }
       }
       case case_2 {
         container if-exceeding-pps {
           presence "enable if-exceeding-pps";
           description "Define pps limits";
           uses apply-advanced;
           choice pps {
             case case_1 {
               leaf pps-limit {
                 description "PPS limit";
                 units "packets per second";
                 type string;
               }
             }
           }
           leaf packet-burst {
             description "PPS burst size limit";
             units "packets";
             type string;
           }
         }
       }
     }
     container then {
       description "Action to take if the rate limits are exceeded";
       uses apply-advanced;
       choice hierarchical-policer-action {
         case case_1 {
           leaf discard {
             description "Discard the packet";
             type empty;
           }
         }
       }
     }
   }
   grouping inet6_dialer_filter {
     description "Define an IPv6 dialer filter";
     leaf name {
       description "Filter name";
       type string {
       }
     }
     uses apply-advanced;
     leaf-list accounting-profile {
       ordered-by user;
       description "Accounting profile name";
       type string;
     }
     list term {
       key name;
       ordered-by user;
       description "Define a firewall term";
       leaf name {
         description "Term name";
         type string {
         }
       }
       uses apply-advanced;
       container from {
         description "Define match criteria";
         uses apply-advanced;
         list source-address {
           key name;
           ordered-by user;
           description "Match source address";
           uses firewall_addr6_object;
         }
         list destination-address {
           key name;
           ordered-by user;
           description "Match destination address";
           uses firewall_addr6_object;
         }
         list address {
           key name;
           ordered-by user;
           description "Match source or destination address";
           uses firewall_addr6_object;
         }
         list source-prefix-list {
           key name;
           ordered-by user;
           description "Match source prefixes in named list";
           uses firewall_prefix_list;
         }
         list destination-prefix-list {
           key name;
           ordered-by user;
           description "Match destination prefixes in named list";
           uses firewall_prefix_list;
         }
         list prefix-list {
           key name;
           ordered-by user;
           description "Match source or destination prefixes in named list";
           uses firewall_prefix_list;
         }
         choice packet-length_choice {
           case case_1 {
             leaf-list packet-length {
               ordered-by user;
               description "Range of values";
               type string;
             }
           }
           case case_2 {
             leaf-list packet-length-except {
               ordered-by user;
               description "Range of values";
               type string;
             }
           }
         }
         choice next-header_choice {
           case case_1 {
             leaf-list next-header {
               ordered-by user;
               type string;
             }
           }
           case case_2 {
             leaf-list next-header-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
       }
       container then {
         description "Action to take if the 'from' condition is matched";
         uses apply-advanced;
         leaf log {
           description "Log the packet";
           type empty;
         }
         leaf syslog {
           description "System log (syslog) information about the packet";
           type empty;
         }
         leaf sample {
           description "Sample the packet";
           type empty;
         }
         choice designation {
           case case_1 {
             leaf note {
               description "Interested ISDN packet";
               type empty;
             }
           }
           case case_2 {
             leaf ignore {
               description "Non-interested ISDN packet";
               type empty;
             }
           }
         }
       }
     }
   }
   grouping inet6_filter {
     description "Define an IPv6 firewall filter";
     leaf name {
       description "Filter name";
       type string {
       }
     }
     uses apply-advanced;
     leaf promote {
       description "Promote a firewall match to PFM";
       type enumeration {
         enum "gre-key" {
           description "Promote GRE Key to PFM";
         }
         enum "traffic-class" {
           description "Promote traffic-class to PFM";
         }
         enum "vni" {
           description "Promote VNI to PFM";
         }
       }
     }
     leaf-list accounting-profile {
       ordered-by user;
       description "Accounting profile name";
       type string;
     }
     leaf interface-specific {
       description "Defined counters are interface specific";
       type empty;
     }
     leaf scale-optimized {
       description "Improve filter prefix scale";
       type empty;
     }
     leaf enhanced-mode {
       description "Define filter for chassis network-services enhanced mode";
       type empty;
     }
     leaf interface-shared {
       description "Filter is interface-shared";
       type empty;
     }
     leaf enhanced-mode-override {
       description "Override the default chassis network-services enhanced mode for dynamic filter";
       type empty;
     }
     leaf physical-interface-filter {
       description "Filter is physical interface filter";
       type empty;
     }
     leaf fast-lookup-filter {
       description "Configure filter in the fast lookup hardware block";
       type empty;
     }
     leaf instance-shared {
       description "Filter is routing-instance shared";
       type empty;
     }
     leaf instance-specific {
       description "Filter is instance specific";
       type empty;
     }
     leaf scale-mode {
       description "Program the filter in scale mode(programs only one pipeline)";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice destination-class_choice {
           case case_1 {
             leaf-list destination-class {
               ordered-by user;
               description "String name";
               type string;
             }
           }
           case case_2 {
             leaf-list destination-class-except {
               ordered-by user;
               description "String name";
               type string;
             }
           }
         }
         choice source-class_choice {
           case case_1 {
             leaf-list source-class {
               ordered-by user;
               description "String name";
               type string;
             }
           }
           case case_2 {
             leaf-list source-class-except {
               ordered-by user;
               description "String name";
               type string;
             }
           }
         }
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match  source address";
           uses firewall_addr6_object;
         }
         list destination-address {
           key name;
           ordered-by user;
           description "Match destination address";
           uses firewall_addr6_object;
         }
         list address {
           key name;
           ordered-by user;
           description "Match source or destination address";
           uses firewall_addr6_object;
         }
         list source-prefix-list {
           key name;
           ordered-by user;
           description "Match source prefixes in named list";
           uses firewall_prefix_list;
         }
         list destination-prefix-list {
           key name;
           ordered-by user;
           description "Match destination prefixes in named list";
           uses firewall_prefix_list;
         }
         list prefix-list {
           key name;
           ordered-by user;
           description "Match source or destination prefixes in named list";
           uses firewall_prefix_list;
         }
         choice next-header_choice {
           case case_1 {
             leaf-list next-header {
               ordered-by user;
               type string;
             }
           }
           case case_2 {
             leaf-list next-header-except {
               ordered-by user;
               type string;
             }
           }
         }
         choice payload-protocol_choice {
           case case_1 {
             leaf-list payload-protocol {
               ordered-by user;
               type string;
             }
           }
           case case_2 {
             leaf-list payload-protocol-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice extension-header_choice {
           case case_1 {
             leaf-list extension-header {
               ordered-by user;
               type string;
             }
           }
           case case_2 {
             leaf-list extension-header-except {
               ordered-by user;
               type string;
             }
           }
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
         choice traffic-class_choice {
           case case_1 {
             leaf-list traffic-class {
               ordered-by user;
               type string;
             }
           }
           case case_2 {
             leaf-list traffic-class-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         leaf tcp-initial {
           description "Match initial packet of a TCP connection";
           type empty;
         }
         leaf tcp-established {
           description "Match packet of an established TCP connection";
           type empty;
         }
         leaf tcp-flags {
           description "Match TCP flags (in symbolic or hex formats)";
           type string;
         }
         list interface {
           key name;
           ordered-by user;
           description "Match interface name";
           uses match_interface_object;
         }
         list interface-set {
           key name;
           ordered-by user;
           description "Match interface in set";
           uses match_interface_set_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         leaf service-filter-hit {
           description "Match if service-filter-hit is set";
           type empty;
         }
         choice hop-limit_choice {
           case case_1 {
             leaf-list hop-limit {
               ordered-by user;
               description "Range of values";
               type string {
               }
             }
           }
           case case_2 {
             leaf-list hop-limit-except {
               ordered-by user;
               description "Range of values";
               type string {
               }
             }
           }
         }
         leaf is-fragment {
           description "Match if packet is a fragment";
           type empty;
         }
         leaf egress-to-ingress {
           description "Match egress fields in ingress";
           type empty;
         }
         leaf first-fragment {
           description "Match if packet is first fragment";
           type empty;
         }
         leaf last-fragment {
           description "Match if packet is last fragment";
           type empty;
         }
         choice flex-mask_choice {
           case case_1 {
             container flexible-match-mask {
               description "Match flexible mask";
               presence "enable flexible-match-mask";
               uses match_L3_flexible_mask;
             }
           }
         }
         choice flex-range_choice {
           case case_1 {
             container flexible-match-range {
               description "Match flexible range";
               presence "enable flexible-match-range";
               uses match_L3_flexible_range;
             }
           }
         }
         choice gre-key_choice {
           case case_1 {
             leaf-list gre-key {
               ordered-by user;
               description "Range of values";
               type string;
             }
           }
           case case_2 {
             leaf-list gre-key-except {
               ordered-by user;
               description "Range of values";
               type string;
             }
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice slice_choice {
           case case_1 {
             leaf-list slice {
               ordered-by user;
               description "Slice name";
               type string {
                 length "1 .. 64";
               }
             }
           }
           case case_2 {
             leaf-list slice-except {
               ordered-by user;
               description "Slice name";
               type string {
                 length "1 .. 64";
               }
             }
           }
         }
         container vxlan {
           description "Define vxlan match items";
           uses apply-advanced;
           choice vni_choice {
             case case_1 {
               leaf-list vni {
                 ordered-by user;
                 description "Range of values";
                 type string {
                 }
               }
             }
             case case_2 {
               leaf-list vni-except {
                 ordered-by user;
                 description "Range of values";
                 type string {
                 }
               }
             }
           }
           choice rsvd1_choice {
             case case_1 {
               leaf-list rsvd1 {
                 ordered-by user;
                 description "Range of values";
                 type string {
                 }
               }
             }
             case case_2 {
               leaf-list rsvd1-except {
                 ordered-by user;
                 description "Range of values";
                 type string {
                 }
               }
             }
           }
           choice rsvd2_choice {
             case case_1 {
               leaf-list rsvd2 {
                 ordered-by user;
                 description "Range of values";
                 type string {
                 }
               }
             }
             case case_2 {
               leaf-list rsvd2-except {
                 ordered-by user;
                 description "Range of values";
                 type string {
                 }
               }
             }
           }
           container flags {
             description "Match VXlan flag field";
             uses match_flags_value;
           }
         }
         container gtp-header {
           description "Define gtp header match items";
           uses apply-advanced;
           leaf-list gtp-teid {
             ordered-by user;
             type string;
           }
           container ipv4 {
             presence "enable ipv4";
             description "Define GTP match items to match IPv4 packets";
             uses apply-advanced;
             choice protocol_choice {
               case case_1 {
                 leaf-list protocol {
                   ordered-by user;
                   type string;
                 }
               }
               case case_2 {
                 leaf-list protocol-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             list source-address {
               key name;
               ordered-by user;
               description "Match IPv4 source address";
               uses firewall_addr_object;
             }
             list destination-address {
               key name;
               ordered-by user;
               description "Match IPv4 destination address";
               uses firewall_addr_object;
             }
             list source-prefix-list {
               key name;
               ordered-by user;
               description "Match IPv4 source prefixes in named list";
               uses firewall_prefix_list;
             }
             list destination-prefix-list {
               key name;
               ordered-by user;
               description "Match IPv4 destination prefixes in named list";
               uses firewall_prefix_list;
             }
           }
           container ipv6 {
             presence "enable ipv6";
             description "Define GTP match items to match IPv6 packets";
             uses apply-advanced;
             choice next-header_choice {
               case case_1 {
                 leaf-list next-header {
                   ordered-by user;
                   type string;
                 }
               }
               case case_2 {
                 leaf-list next-header-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             list source-address {
               key name;
               ordered-by user;
               description "Match IPv6 source address";
               uses firewall_addr6_object;
             }
             list destination-address {
               key name;
               ordered-by user;
               description "Match IPv6 destination address";
               uses firewall_addr6_object;
             }
             list source-prefix-list {
               key name;
               ordered-by user;
               description "Match IPv6 source prefixes in named list";
               uses firewall_prefix_list;
             }
             list destination-prefix-list {
               key name;
               ordered-by user;
               description "Match IPv6 destination prefixes in named list";
               uses firewall_prefix_list;
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
             leaf hierarchical-policer {
               description "Name of hierarchical policer to use to rate-limit traffic";
               type string {
               }
             }
           }
           case case_4 {
             container enhanced-hierarchical-policer {
               description "Police the packet using enhanced-hierarchical-policer";
               uses apply-advanced;
               leaf enhanced-hierarchical-policer-name {
                 description "Name of enhanced hierarchical policer to use to rate-limit traffic";
                 type string {
                 }
               }
               leaf traffic-priority {
                 description "Traffic priority based on hierarchy level";
                 type enumeration {
                   enum "high" {
                     description "Hierarchical policer high traffic-priority";
                   }
                   enum "medium-high" {
                     description "Hierarchical policer medium-high traffic-priority";
                   }
                   enum "medium-low" {
                     description "Hierarchical policer medium-low traffic-priority";
                   }
                   enum "low" {
                     description "Hierarchical policer low traffic-priority";
                   }
                 }
               }
             }
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         leaf slice {
           description "Set network slice action";
           type string;
         }
         choice inet6cnt {
           case case_1 {
             leaf traffic-class-count {
               description "Count the packet in the named traffic-class counter";
               type string {
               }
             }
           }
           case case_2 {
             leaf count {
               description "Count the packet in the named counter";
               type string {
               }
             }
           }
         }
         leaf service-accounting {
           description "Count the packets for service accounting";
           type empty;
         }
         leaf service-accounting-deferred {
           description "Count the packets for deferred service accounting";
           type empty;
         }
         leaf log {
           description "Log the packet";
           type empty;
         }
         leaf pkt-trace {
           description "Trace packet forwarding ";
           type empty;
         }
         leaf packet-mode {
           description "Bypass flow mode for the packet";
           type empty;
         }
         leaf syslog {
           description "System log (syslog) information about the packet";
           type empty;
         }
         leaf packet-capture {
           description "Enable packet capture for telemetry";
           type empty;
         }
         leaf sample {
           description "Sample the packet";
           type empty;
         }
         leaf port-mirror-instance {
           description "Port-mirror the packet to specified instance";
           type string {
           }
         }
         leaf port-mirror {
           description "Port-mirror the packet";
           type empty;
         }
         leaf inline-monitoring-instance {
           description "Inline monitoring to specified instance";
           type string {
           }
         }
         leaf inband-flow-telemetry-init {
           description "Initiate inband telemetry for a flow";
           type string;
         }
         leaf inband-flow-telemetry-terminate {
           description "Terminate inband telemetry for a flow";
           type string;
         }
         leaf l2-mirror {
           description "L2 mirror the packet";
           type empty;
         }
         leaf analyzer {
           description "Name of analyzer";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf traffic-class {
           description "Set traffic-class code point";
           type string;
         }
         leaf skip-services {
           description "Skip the services";
           type empty;
         }
         leaf service-filter-hit {
           description "Marked when packet processing by the current type of chained filters is done, the packet is directed to the next type of filters";
           type empty;
         }
         leaf force-premium {
           description "When this bit is marked, traffic is considered as premium by the following hierarchical policer";
           type empty;
         }
         leaf exclude-accounting {
           description "When this is marked, traffic is excluded from accurate accounting";
           type empty;
         }
         choice designation {
           case case_1 {
             container decapsulate {
               presence "enable decapsulate";
               description "Terminate a tunnel";
               uses apply-advanced;
               choice tunnel-protocol {
                 case case_1 {
                   container gre {
                     presence "enable gre";
                     description "GRE protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
                 case case_2 {
                   container gre-in-udp {
                     presence "enable gre-in-udp";
                     description "GRE-in-UDP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
                 case case_3 {
                   container mpls-in-udp {
                     presence "enable mpls-in-udp";
                     description "MPLS-in-UDP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
                 case case_4 {
                   container inet-in-udp {
                     presence "enable inet-in-udp";
                     description "IPv4-in-UDP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
                 case case_5 {
                   container inet6-in-udp {
                     presence "enable inet6-in-udp";
                     description "IPv6-in-UDP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
                 case case_6 {
                   container l2tp {
                     description "L2TP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     leaf-list cookie {
                       ordered-by user;
                       description "L2TPv3 cookie";
                       type string {
                         length "1 .. 32";
                       }
                     }
                     choice destination {
                       case case_1 {
                         leaf output-interface {
                           description "Interface name";
                           type union {
                             type jt:interface-unit;
                             type string {
                               pattern "<.*>|$.*";
                             }
                           }
                         }
                       }
                     }
                   }
                 }
                 case case_7 {
                   container ipip {
                     presence "enable ipip";
                     description "IPIP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
               }
             }
           }
           case case_2 {
             container encapsulate {
               presence "enable encapsulate";
               description "Send to a tunnel";
               leaf tunnel-end-point {
                 description "Name of the tunnel end point";
                 type string {
                 }
               }
             }
           }
           case case_3 {
             leaf accept {
               description "Accept the packet";
               type empty;
             }
           }
           case case_4 {
             leaf discard {
               description "Discard the packet";
               type empty;
             }
           }
           case case_5 {
             leaf next {
               description "Continue to next term in a filter";
               type enumeration {
                 enum "term" {
                   description "Continue to next term in a filter";
                 }
               }
             }
           }
           case case_6 {
             leaf next-hop-group {
               description "Use specified next-hop group";
               type string;
             }
           }
           case case_7 {
             list logical-system {
               key logical-system-name;
               ordered-by user;
               description "Packets are directed to specified logical system";
               max-elements 1;
               leaf logical-system-name {
                 description "Name of logical system";
                 type string {
                 }
               }
               container routing-instance {
                 description "Packets are directed to specified routing instance";
                 leaf routing-instance-name {
                   description "Name of routing instance";
                   type string {
                   }
                 }
                 leaf topology {
                   description "Packets are directed to specified topology";
                   type string {
                   }
                 }
               }
               leaf topology {
                 description "Packets are directed to specified topology";
                 type string {
                 }
               }
             }
           }
           case case_8 {
             leaf redirect {
               description "Redirect packets to specified instance";
               type string {
               }
             }
           }
           case case_9 {
             container routing-instance {
               description "Packets are directed to specified routing instance";
               leaf routing-instance-name {
                 description "Name of routing instance";
                 type string {
                 }
               }
               leaf topology {
                 description "Packets are directed to specified topology";
                 type string {
                 }
               }
             }
           }
           case case_10 {
             leaf topology {
               description "Packets are directed to specified topology";
               type string {
               }
             }
           }
           case case_11 {
             container next-ip6 {
               description "Packets are directed to the specified ipv6 address";
               leaf address {
                 description "Address to route";
                 type jt:ipv6prefix;
               }
               container routing-instance {
                 description "Packets are directed to specified routing instance";
                 leaf routing-instance-name {
                   description "Name of routing instance";
                   type string {
                   }
                 }
                 leaf topology {
                   description "Packets are directed to specified topology";
                   type string {
                   }
                 }
               }
             }
           }
           case case_12 {
             container next-interface {
               presence "enable next-interface";
               description "Packets are to be routed through the specified interface";
               uses apply-advanced;
               leaf interface-name {
                 description "Interface name";
                 type string {
                   length "1 .. 127";
                 }
               }
               container routing-instance {
                 description "Packets are directed to specified routing instance";
                 leaf routing-instance-name {
                   description "Name of routing instance";
                   type string {
                   }
                 }
                 leaf topology {
                   description "Packets are directed to specified topology";
                   type string {
                   }
                 }
               }
               choice designation {
                 case case_1 {
                   leaf accept {
                     description "Accept the packet";
                     type empty;
                   }
                 }
                 case case_2 {
                   leaf next {
                     description "Continue to next term in a filter";
                     type enumeration {
                       enum "term" {
                         description "Continue to next term in a filter";
                       }
                     }
                   }
                 }
               }
             }
           }
           case case_13 {
             container reject {
               presence "enable reject";
               description "Reject the packet";
               choice style {
                 case case_1 {
                   leaf no-route {
                     description "Send ICMPv6 No Route message";
                     type empty;
                   }
                 }
                 case case_2 {
                   leaf administratively-prohibited {
                     description "Send ICMPv6 Administratively Prohibited message";
                     type empty;
                   }
                 }
                 case case_3 {
                   leaf beyond-scope {
                     description "Send ICMPv6 Beyond Scope of Source Address message";
                     type empty;
                   }
                 }
                 case case_4 {
                   leaf address-unreachable {
                     description "Send ICMPv6 Address Unreachable message";
                     type empty;
                   }
                 }
                 case case_5 {
                   leaf port-unreachable {
                     description "Send ICMPv6 Port Unreachable message";
                     type empty;
                   }
                 }
                 case case_6 {
                   leaf policy-failed {
                     description "Source address failed ingress/egress policy";
                     type empty;
                   }
                 }
                 case case_7 {
                   leaf reject-route {
                     description "Reject route to destination";
                     type empty;
                   }
                 }
                 case case_8 {
                   leaf tcp-reset {
                     description "Send TCP Reset message";
                     type empty;
                   }
                 }
                 case case_9 {
                   leaf network-unreachable {
                     description "Send ICMPv4 Network Unreachable message";
                     status deprecated;
                     type empty;
                   }
                 }
                 case case_10 {
                   leaf host-unreachable {
                     description "Send ICMPv4 Host Unreachable message";
                     status deprecated;
                     type empty;
                   }
                 }
                 case case_11 {
                   leaf protocol-unreachable {
                     description "Send ICMPv4 Protocol Unreachable message";
                     status deprecated;
                     type empty;
                   }
                 }
                 case case_12 {
                   leaf source-route-failed {
                     description "Send ICMPv4 Source Route Failed message";
                     status deprecated;
                     type empty;
                   }
                 }
                 case case_13 {
                   leaf network-unknown {
                     description "Send ICMPv4 Network Unknown message";
                     status deprecated;
                     type empty;
                   }
                 }
                 case case_14 {
                   leaf host-unknown {
                     description "Send ICMPv4 Host Unknown message";
                     status deprecated;
                     type empty;
                   }
                 }
                 case case_15 {
                   leaf source-host-isolated {
                     description "Send ICMPv4 Source Host Isolated message";
                     status deprecated;
                     type empty;
                   }
                 }
                 case case_16 {
                   leaf network-prohibited {
                     description "Send ICMPv4 Network Prohibited message";
                     status deprecated;
                     type empty;
                   }
                 }
                 case case_17 {
                   leaf host-prohibited {
                     description "Send ICMPv4 Host Prohibited message";
                     status deprecated;
                     type empty;
                   }
                 }
                 case case_18 {
                   leaf bad-network-tos {
                     description "Send ICMPv4 Bad Network ToS message";
                     status deprecated;
                     type empty;
                   }
                 }
                 case case_19 {
                   leaf bad-host-tos {
                     description "Send ICMPv4 Bad Host ToS message";
                     status deprecated;
                     type empty;
                   }
                 }
                 case case_20 {
                   leaf precedence-violation {
                     description "Send ICMPv4 Precedence Violation message";
                     status deprecated;
                     type empty;
                   }
                 }
                 case case_21 {
                   leaf precedence-cutoff {
                     description "Send ICMPv4 Precedence Cutoff message";
                     status deprecated;
                     type empty;
                   }
                 }
               }
             }
           }
         }
       }
       container template {
         description "Refer a template";
         uses apply-advanced;
         leaf template-name {
           description "Template name";
           type string {
           }
         }
       }
     }
   }
   grouping inet6_fuf {
     leaf name {
       description "Name of fast update filter";
       type string {
       }
     }
     uses apply-advanced;
     leaf interface-specific {
       description "Defined counters are interface specific";
       type empty;
     }
     leaf-list match-order {
       ordered-by user;
       type enumeration {
         enum "next-header" {
           description "Include next header protocol in match set";
         }
         enum "payload-protocol" {
           description "Include payload protocol in match set";
         }
         enum "source-address" {
           description "Include source-address in match set";
         }
         enum "destination-address" {
           description "Include destination-address in match set";
         }
         enum "source-port" {
           description "Include source-port in match set";
         }
         enum "destination-port" {
           description "Include destination-port in match set";
         }
         enum "traffic-class" {
           description "Include traffic-class (DSCP) in match set";
         }
       }
     }
     list term {
       key name;
       ordered-by user;
       description "One or more firewall terms";
       leaf name {
         description "Term name";
         type string {
         }
       }
       uses apply-advanced;
       leaf only-at-create {
         description "Add term only when filter is first created.";
         type empty;
       }
       container from {
         description "Match criteria";
         uses apply-advanced;
         container source-address {
           description "Match source IP address";
           uses firewall_addr6_simple_object;
         }
         container destination-address {
           description "Match destination IP address";
           uses firewall_addr6_simple_object;
         }
         choice source-port_choice {
           case case_1 {
             container source-port {
               description "Match TCP/UDP source port";
               uses match_simple_port_value;
             }
           }
         }
         choice destination-port_choice {
           case case_1 {
             container destination-port {
               description "Match TCP/UDP destination port";
               uses match_simple_port_value;
             }
           }
         }
         choice next-header_choice {
           case case_1 {
             container next-header {
               description "Match next header protocol type";
               uses match_simple_protocol_value;
             }
           }
         }
         choice payload-protocol_choice {
           case case_1 {
             container payload-protocol {
               description "Match payload protocol type";
               uses match_simple_payload_protocol_value;
             }
           }
         }
         choice traffic-class_choice {
           case case_1 {
             container traffic-class {
               description "Match Differentiated Services (DiffServ) code point";
               uses match_simple_dscp_value;
             }
           }
         }
         leaf match-terms {
           description "Dynamically supplied list of match criteria";
           type string;
         }
       }
       container then {
         description "Action to take if the 'from' condition is matched";
         uses apply-advanced;
         choice policer-choice {
           case case_1 {
             leaf policer {
               description "Name of policer to use to rate-limit traffic";
               type string {
               }
             }
           }
         }
         leaf count {
           description "Count the packet in the named counter";
           type string {
           }
         }
         leaf service-accounting {
           description "Count the packets for service accounting";
           type empty;
         }
         leaf log {
           description "Log the packet";
           type empty;
         }
         leaf port-mirror {
           description "Port-mirror the packet";
           type empty;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf action-terms {
           description "Dynamically supplied list of actions";
           type string;
         }
         choice designation {
           case case_1 {
             leaf accept {
               description "Accept the packet";
               type empty;
             }
           }
           case case_2 {
             leaf discard {
               description "Discard the packet";
               type empty;
             }
           }
           case case_3 {
             container routing-instance {
               description "Packets are directed to specified routing instance";
               leaf routing-instance-name {
                 description "Name of routing instance";
                 type string {
                 }
               }
               leaf topology {
                 description "Packets are directed to specified topology";
                 type string {
                 }
               }
             }
           }
         }
       }
     }
   }
   grouping firewall_addr6_simple_object {
     uses apply-advanced;
     leaf address {
       description "Prefix to match";
       type jt:ipv6prefix;
     }
   }
   grouping inet6_service_filter {
     leaf name {
       description "Filter name";
       type string {
       }
     }
     uses apply-advanced;
     list term {
       key name;
       ordered-by user;
       description "Service filter term";
       leaf name {
         description "Term name";
         type string {
         }
       }
       uses apply-advanced;
       container from {
         description "Match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match  source address";
           uses firewall_addr6_object;
         }
         list destination-address {
           key name;
           ordered-by user;
           description "Match destination address";
           uses firewall_addr6_object;
         }
         list address {
           key name;
           ordered-by user;
           description "Match source or destination address";
           uses firewall_addr6_object;
         }
         list source-prefix-list {
           key name;
           ordered-by user;
           description "Match source prefixes in named list";
           uses firewall_prefix_list;
         }
         list destination-prefix-list {
           key name;
           ordered-by user;
           description "Match destination prefixes in named list";
           uses firewall_prefix_list;
         }
         list prefix-list {
           key name;
           ordered-by user;
           description "Match source or destination prefixes in named list";
           uses firewall_prefix_list;
         }
         choice next-header_choice {
           case case_1 {
             leaf-list next-header {
               ordered-by user;
               type string;
             }
           }
           case case_2 {
             leaf-list next-header-except {
               ordered-by user;
               type string;
             }
           }
         }
         choice payload-protocol_choice {
           case case_1 {
             leaf-list payload-protocol {
               ordered-by user;
               type string;
             }
           }
           case case_2 {
             leaf-list payload-protocol-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice extension-header_choice {
           case case_1 {
             leaf-list extension-header {
               ordered-by user;
               type string;
             }
           }
           case case_2 {
             leaf-list extension-header-except {
               ordered-by user;
               type string;
             }
           }
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
             leaf-list ah-spi {
               ordered-by user;
               description "Range of values";
               type string;
             }
           }
           case case_2 {
             leaf-list ah-spi-except {
               ordered-by user;
               description "Range of values";
               type string;
             }
           }
         }
         leaf tcp-flags {
           description "Match TCP flags (in symbolic or hex formats)";
           type string;
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
       }
       container then {
         description "Action to take if the 'from' condition is matched";
         uses apply-advanced;
         leaf count {
           description "Count the packet in the named counter";
           type string {
           }
         }
         leaf log {
           description "Log the packet";
           type empty;
         }
         leaf pkt-trace {
           description "Pkt-Trace the packet";
           type empty;
         }
         leaf sample {
           description "Sample the packet";
           type empty;
         }
         leaf port-mirror {
           description "Port-mirror the packet";
           type empty;
         }
         choice designation {
           case case_1 {
             leaf service {
               description "Forward packets to service processing";
               type empty;
             }
           }
           case case_2 {
             leaf skip {
               description "Skip service processing";
               type empty;
             }
           }
           case case_3 {
             leaf accept {
               description "Accept the packet";
               type empty;
             }
           }
         }
       }
     }
   }
   grouping inet6_template {
     leaf name {
       description "Template name";
       type string {
       }
     }
     uses apply-advanced;
     container attributes {
       description "Template attributes";
       uses apply-advanced;
       leaf destination-address {
         description "Match destination address";
         type empty;
       }
       leaf destination-port {
         description "Match TCP/UDP destination port";
         type empty;
       }
       leaf destination-prefix-list {
         description "Match destination prefixes in named list";
         type empty;
       }
       leaf flexible-match-mask {
         description "Match flexible mask";
         type empty;
       }
       leaf flexible-match-range {
         description "Match ICMP message code";
         type empty;
       }
       leaf hop-limit {
         description "Match Hop Limit";
         type empty;
       }
       leaf icmp-code {
         description "Match ICMP message code";
         type empty;
       }
       leaf icmp-type {
         description "Match ICMP message code";
         type empty;
       }
       leaf interface {
         description "Match interface name";
         type empty;
       }
       leaf next-header {
         description "Match next header protocol type";
         type empty;
       }
       leaf source-address {
         description "Match  source address";
         type empty;
       }
       leaf source-port {
         description "Match TCP/UDP source port";
         type empty;
       }
       leaf source-prefix-list {
         description "Match source prefixes in named list";
         type empty;
       }
       leaf tcp-established {
         description "Match packet of an established TCP connection";
         type empty;
       }
       leaf tcp-flags {
         description "Match TCP flags";
         type empty;
       }
       leaf tcp-initial {
         description "Match initial packet of a TCP connection";
         type empty;
       }
       leaf traffic-class {
         description "Match Differentiated Services (DiffServ) code point";
         type empty;
       }
       leaf egress-to-ingress {
         description "Match egress fields in ingress";
         type empty;
       }
     }
   }
   grouping inet_dialer_filter {
     leaf name {
       description "Filter name";
       type string {
       }
     }
     uses apply-advanced;
     leaf-list accounting-profile {
       ordered-by user;
       description "Accounting profile name";
       type string;
     }
     list term {
       key name;
       ordered-by user;
       description "Define a firewall term";
       leaf name {
         description "Term name";
         type string {
         }
       }
       uses apply-advanced;
       container from {
         description "Define match criteria";
         uses apply-advanced;
         list source-address {
           key name;
           ordered-by user;
           description "Match IP source address";
           uses firewall_addr_object;
         }
         list destination-address {
           key name;
           ordered-by user;
           description "Match IP destination address";
           uses firewall_addr_object;
         }
         list address {
           key name;
           ordered-by user;
           description "Match IP source or destination address";
           uses firewall_addr_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
         choice precedence_choice {
           case case_1 {
             leaf-list precedence {
               ordered-by user;
               type string;
             }
           }
           case case_2 {
             leaf-list precedence-except {
               ordered-by user;
               type string;
             }
           }
         }
         choice dscp_choice {
           case case_1 {
             leaf-list dscp {
               ordered-by user;
               type string;
             }
           }
           case case_2 {
             leaf-list dscp-except {
               ordered-by user;
               type string;
             }
           }
         }
         choice ip-options_choice {
           case case_1 {
             leaf-list ip-options {
               ordered-by user;
               type string;
             }
           }
           case case_2 {
             leaf-list ip-options-except {
               ordered-by user;
               type string;
             }
           }
         }
         leaf is-fragment {
           description "Match if packet is a fragment";
           type empty;
         }
         leaf first-fragment {
           description "Match if packet is the first fragment";
           type empty;
         }
         choice fragment-offset_choice {
           case case_1 {
             leaf-list fragment-offset {
               ordered-by user;
               description "Range of values";
               type string {
               }
             }
           }
           case case_2 {
             leaf-list fragment-offset-except {
               ordered-by user;
               description "Range of values";
               type string {
               }
             }
           }
         }
         leaf fragment-flags {
           description "Match fragment flags";
           type string;
         }
         choice protocol_choice {
           case case_1 {
             leaf-list protocol {
               ordered-by user;
               type string;
             }
           }
           case case_2 {
             leaf-list protocol-except {
               ordered-by user;
               type string;
             }
           }
         }
         choice ttl_choice {
           case case_1 {
             leaf-list ttl {
               ordered-by user;
               description "Range of values";
               type string {
               }
             }
           }
           case case_2 {
             leaf-list ttl-except {
               ordered-by user;
               description "Range of values";
               type string {
               }
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-initial {
           description "Match initial packet of a TCP connection";
           type empty;
         }
         leaf tcp-established {
           description "Match packet of an established TCP connection";
           type empty;
         }
         leaf tcp-flags {
           description "Match TCP flags (in symbolic or hex formats)";
           type string;
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
             leaf-list ah-spi {
               ordered-by user;
               description "Range of values";
               type string;
             }
           }
           case case_2 {
             leaf-list ah-spi-except {
               ordered-by user;
               description "Range of values";
               type string;
             }
           }
         }
       }
       container then {
         description "Action to take if the 'from' condition is matched";
         uses apply-advanced;
         leaf log {
           description "Log the packet";
           type empty;
         }
         leaf syslog {
           description "System log (syslog) information about the packet";
           type empty;
         }
         leaf sample {
           description "Sample the packet";
           type empty;
         }
         choice designation {
           case case_1 {
             leaf note {
               description "Interested ISDN packet";
               type empty;
             }
           }
           case case_2 {
             leaf ignore {
               description "Non-interested ISDN packet";
               type empty;
             }
           }
         }
       }
     }
   }
   grouping inet_filter {
     leaf name {
       description "Filter name";
       type string {
       }
     }
     uses apply-advanced;
     leaf promote {
       description "Promote a firewall match to PFM";
       type enumeration {
         enum "gre-key" {
           description "Promote GRE Key to PFM";
         }
         enum "dscp" {
           description "Promote DSCP to PFM";
         }
         enum "vni" {
           description "Promote VNI to PFM";
         }
       }
     }
     leaf-list accounting-profile {
       ordered-by user;
       description "Accounting profile name";
       type string;
     }
     leaf interface-specific {
       description "Defined counters are interface specific";
       type empty;
     }
     leaf scale-optimized {
       description "Improve filter prefix scale";
       type empty;
     }
     leaf physical-interface-filter {
       description "Filter is physical interface filter";
       type empty;
     }
     leaf enhanced-mode {
       description "Define filter for chassis network-services enhanced mode";
       type empty;
     }
     leaf interface-shared {
       description "Filter is interface-shared";
       type empty;
     }
     leaf enhanced-mode-override {
       description "Override the default chassis network-services enhanced mode for dynamic filter";
       type empty;
     }
     leaf instance-shared {
       description "Filter is routing-instance shared";
       type empty;
     }
     leaf instance-specific {
       description "Filter is instance specific";
       type empty;
     }
     leaf fast-lookup-filter {
       description "Configure filter in the fast lookup hardware block";
       type empty;
     }
     leaf scale-mode {
       description "Program the filter in scale mode(programs only one pipeline)";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice destination-class_choice {
           case case_1 {
             leaf-list destination-class {
               ordered-by user;
               description "String name";
               type string;
             }
           }
           case case_2 {
             leaf-list destination-class-except {
               ordered-by user;
               description "String name";
               type string;
             }
           }
         }
         choice source-class_choice {
           case case_1 {
             leaf-list source-class {
               ordered-by user;
               description "String name";
               type string;
             }
           }
           case case_2 {
             leaf-list source-class-except {
               ordered-by user;
               description "String name";
               type string;
             }
           }
         }
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match IP source address";
           uses firewall_addr_object;
         }
         list destination-address {
           key name;
           ordered-by user;
           description "Match IP destination address";
           uses firewall_addr_object;
         }
         list address {
           key name;
           ordered-by user;
           description "Match IP source or destination address";
           uses firewall_addr_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
         choice dscp_choice {
           case case_1 {
             leaf-list dscp {
               ordered-by user;
               type string;
             }
           }
           case case_2 {
             leaf-list dscp-except {
               ordered-by user;
               type string;
             }
           }
         }
         choice precedence_choice {
           case case_1 {
             leaf-list precedence {
               ordered-by user;
               type string;
             }
           }
           case case_2 {
             leaf-list precedence-except {
               ordered-by user;
               type string;
             }
           }
         }
         choice ip-options_choice {
           case case_1 {
             leaf-list ip-options {
               ordered-by user;
               type string;
             }
           }
           case case_2 {
             leaf-list ip-options-except {
               ordered-by user;
               type string;
             }
           }
         }
         leaf is-fragment {
           description "Match if packet is a fragment";
           type empty;
         }
         leaf egress-to-ingress {
           description "Match egress fields in ingress";
           type empty;
         }
         leaf first-fragment {
           description "Match if packet is the first fragment";
           type empty;
         }
         leaf service-filter-hit {
           description "Match if service-filter-hit is set";
           type empty;
         }
         choice fragment-offset_choice {
           case case_1 {
             leaf-list fragment-offset {
               ordered-by user;
               description "Range of values";
               type string {
               }
             }
           }
           case case_2 {
             leaf-list fragment-offset-except {
               ordered-by user;
               description "Range of values";
               type string {
               }
             }
           }
         }
         leaf fragment-flags {
           description "Match fragment flags (in symbolic or hex formats) - (Ingress only)";
           type string {
           }
         }
         choice protocol_choice {
           case case_1 {
             leaf-list protocol {
               ordered-by user;
               type string;
             }
           }
           case case_2 {
             leaf-list protocol-except {
               ordered-by user;
               type string;
             }
           }
         }
         choice ttl_choice {
           case case_1 {
             leaf-list ttl {
               ordered-by user;
               description "Range of values";
               type string {
               }
             }
           }
           case case_2 {
             leaf-list ttl-except {
               ordered-by user;
               description "Range of values";
               type string {
               }
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-initial {
           description "Match initial packet of a TCP connection";
           type empty;
         }
         leaf tcp-established {
           description "Match packet of an established TCP connection";
           type empty;
         }
         leaf tcp-flags {
           description "Match TCP flags (in symbolic or hex formats)";
           type string;
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
             leaf-list ah-spi {
               ordered-by user;
               description "Range of values";
               type string;
             }
           }
           case case_2 {
             leaf-list ah-spi-except {
               ordered-by user;
               description "Range of values";
               type string;
             }
           }
         }
         list interface {
           key name;
           ordered-by user;
           description "Match interface name";
           uses match_interface_object;
         }
         list interface-set {
           key name;
           ordered-by user;
           description "Match interface in set";
           uses match_interface_set_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         leaf source-port-range-optimize {
           description "Optimize the source port range";
           type empty;
         }
         leaf destination-port-range-optimize {
           description "Optimize the destination port range";
           type empty;
         }
         choice rat-type_choice {
           case case_1 {
             leaf-list rat-type {
               ordered-by user;
               type string;
             }
           }
           case case_2 {
             leaf-list rat-type-except {
               ordered-by user;
               type string;
             }
           }
         }
         choice redirect-reason_choice {
           case case_1 {
             leaf-list redirect-reason {
               ordered-by user;
               type enumeration {
                 enum "aoc" {
                   description "Advice of Charge";
                 }
                 enum "aolb" {
                   description "Advice of Low Balance";
                 }
                 enum "dpi" {
                   description "Layer7 match required";
                 }
               }
             }
           }
           case case_2 {
             leaf-list redirect-reason-except {
               ordered-by user;
               type enumeration {
                 enum "aoc" {
                   description "Advice of Charge";
                 }
                 enum "aolb" {
                   description "Advice of Low Balance";
                 }
                 enum "dpi" {
                   description "Layer7 match required";
                 }
               }
             }
           }
         }
         choice gre-key_choice {
           case case_1 {
             leaf-list gre-key {
               ordered-by user;
               description "Range of values";
               type string;
             }
           }
           case case_2 {
             leaf-list gre-key-except {
               ordered-by user;
               description "Range of values";
               type string;
             }
           }
         }
         choice flex-mask_choice {
           case case_1 {
             container flexible-match-mask {
               description "Match flexible mask";
               presence "enable flexible-match-mask";
               uses match_L3_flexible_mask;
             }
           }
         }
         choice flex-range_choice {
           case case_1 {
             container flexible-match-range {
               description "Match flexible range";
               presence "enable flexible-match-range";
               uses match_L3_flexible_range;
             }
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice slice_choice {
           case case_1 {
             leaf-list slice {
               ordered-by user;
               description "Slice name";
               type string {
                 length "1 .. 64";
               }
             }
           }
           case case_2 {
             leaf-list slice-except {
               ordered-by user;
               description "Slice name";
               type string {
                 length "1 .. 64";
               }
             }
           }
         }
         container vxlan {
           description "Define vxlan match items";
           uses apply-advanced;
           choice vni_choice {
             case case_1 {
               leaf-list vni {
                 ordered-by user;
                 description "Range of values";
                 type string {
                 }
               }
             }
             case case_2 {
               leaf-list vni-except {
                 ordered-by user;
                 description "Range of values";
                 type string {
                 }
               }
             }
           }
           choice rsvd1_choice {
             case case_1 {
               leaf-list rsvd1 {
                 ordered-by user;
                 description "Range of values";
                 type string {
                 }
               }
             }
             case case_2 {
               leaf-list rsvd1-except {
                 ordered-by user;
                 description "Range of values";
                 type string {
                 }
               }
             }
           }
           choice rsvd2_choice {
             case case_1 {
               leaf-list rsvd2 {
                 ordered-by user;
                 description "Range of values";
                 type string {
                 }
               }
             }
             case case_2 {
               leaf-list rsvd2-except {
                 ordered-by user;
                 description "Range of values";
                 type string {
                 }
               }
             }
           }
           container flags {
             description "Match VXlan flag field";
             uses match_flags_value;
           }
         }
         container gtp-header {
           description "Define gtp header match items";
           uses apply-advanced;
           leaf-list gtp-teid {
             ordered-by user;
             type union {
               type uint32;
               type string {
                 pattern "<.*>|$.*";
               }
             }
           }
           container ipv4 {
             presence "enable ipv4";
             description "Define GTP match items to match IPv4 packets";
             uses apply-advanced;
             choice protocol_choice {
               case case_1 {
                 leaf-list protocol {
                   ordered-by user;
                   type string;
                 }
               }
               case case_2 {
                 leaf-list protocol-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             list source-address {
               key name;
               ordered-by user;
               description "Match IPv4 source address";
               uses firewall_addr_object;
             }
             list destination-address {
               key name;
               ordered-by user;
               description "Match IPv4 destination address";
               uses firewall_addr_object;
             }
             list source-prefix-list {
               key name;
               ordered-by user;
               description "Match IPv4 source prefixes in named list";
               uses firewall_prefix_list;
             }
             list destination-prefix-list {
               key name;
               ordered-by user;
               description "Match IPv4 destination prefixes in named list";
               uses firewall_prefix_list;
             }
           }
           container ipv6 {
             presence "enable ipv6";
             description "Define GTP match items to match IPv6 packets";
             uses apply-advanced;
             choice next-header_choice {
               case case_1 {
                 leaf-list next-header {
                   ordered-by user;
                   type string;
                 }
               }
               case case_2 {
                 leaf-list next-header-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             list source-address {
               key name;
               ordered-by user;
               description "Match IPv6 source address";
               uses firewall_addr6_object;
             }
             list destination-address {
               key name;
               ordered-by user;
               description "Match IPv6 destination address";
               uses firewall_addr6_object;
             }
             list source-prefix-list {
               key name;
               ordered-by user;
               description "Match IPv6 source prefixes in named list";
               uses firewall_prefix_list;
             }
             list destination-prefix-list {
               key name;
               ordered-by user;
               description "Match IPv6 destination prefixes in named list";
               uses firewall_prefix_list;
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
             leaf hierarchical-policer {
               description "Name of hierarchical policer to use to rate-limit traffic";
               type string {
               }
             }
           }
           case case_4 {
             container enhanced-hierarchical-policer {
               description "Police the packet using enhanced-hierarchical-policer";
               uses apply-advanced;
               leaf enhanced-hierarchical-policer-name {
                 description "Name of enhanced hierarchical policer to use to rate-limit traffic";
                 type string {
                 }
               }
               leaf traffic-priority {
                 description "Traffic priority based on hierarchy level";
                 type enumeration {
                   enum "high" {
                     description "Hierarchical policer high traffic-priority";
                   }
                   enum "medium-high" {
                     description "Hierarchical policer medium-high traffic-priority";
                   }
                   enum "medium-low" {
                     description "Hierarchical policer medium-low traffic-priority";
                   }
                   enum "low" {
                     description "Hierarchical policer low traffic-priority";
                   }
                 }
               }
             }
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         leaf slice {
           description "Set network slice action";
           type string;
         }
         choice inetcnt {
           case case_1 {
             leaf traffic-class-count {
               description "Count the packet in the named traffic-class counter";
               type string {
               }
             }
           }
           case case_2 {
             leaf count {
               description "Count the packet in the named counter";
               type string {
               }
             }
           }
         }
         leaf service-accounting {
           description "Count the packets for service accounting";
           type empty;
         }
         leaf skip-services {
           description "Skip the services";
           type empty;
         }
         leaf service-accounting-deferred {
           description "Count the packets for deferred service accounting";
           type empty;
         }
         leaf log {
           description "Log the packet";
           type empty;
         }
         leaf pkt-trace {
           description "Trace the packet";
           type empty;
         }
         leaf packet-mode {
           description "Bypass flow mode for the packet";
           type empty;
         }
         leaf syslog {
           description "System log (syslog) information about the packet";
           type empty;
         }
         leaf packet-capture {
           description "Enable packet capture for telemetry";
           type empty;
         }
         leaf sample {
           description "Sample the packet";
           type empty;
         }
         leaf port-mirror-instance {
           description "Port-mirror the packet to specified instance";
           type string {
           }
         }
         leaf port-mirror {
           description "Port-mirror the packet";
           type empty;
         }
         leaf inline-monitoring-instance {
           description "Inline monitoring to specified instance";
           type string {
           }
         }
         leaf inband-flow-telemetry-init {
           description "Initiate inband telemetry for a flow";
           type string;
         }
         leaf inband-flow-telemetry-terminate {
           description "Terminate inband telemetry for a flow";
           type string;
         }
         leaf l2-mirror {
           description "L2 mirror the packet";
           type empty;
         }
         leaf analyzer {
           description "Name of analyzer - (Ingress only)";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf service-filter-hit {
           description "Marked when packet processing by the current type of chained filters is done, the packet is directed to the next type of filters";
           type empty;
         }
         leaf force-premium {
           description "When this bit is marked, traffic is considered as premium by the following hierarchical policer";
           type empty;
         }
         leaf exclude-accounting {
           description "When this is marked, traffic is excluded from accurate accounting";
           type empty;
         }
         leaf virtual-channel {
           description "Set the output interface virtual channel";
           type string {
           }
         }
         choice designation {
           case case_1 {
             leaf accept {
               description "Accept the packet";
               type empty;
             }
           }
           case case_2 {
             container discard {
               presence "enable discard";
               description "Discard the packet";
               uses apply-advanced;
               leaf accounting {
                 description "Named discard collector for packet";
                 type string;
               }
             }
           }
           case case_3 {
             leaf next {
               description "Continue to next term in a filter";
               type enumeration {
                 enum "term" {
                   description "Continue to next term in a filter";
                 }
               }
             }
           }
           case case_4 {
             list logical-system {
               key logical-system-name;
               ordered-by user;
               description "Packets are directed to specified logical system";
               max-elements 1;
               leaf logical-system-name {
                 description "Name of logical system";
                 type string {
                 }
               }
               container routing-instance {
                 description "Packets are directed to specified routing instance";
                 leaf routing-instance-name {
                   description "Name of routing instance";
                   type string {
                   }
                 }
                 leaf topology {
                   description "Packets are directed to specified topology";
                   type string {
                   }
                 }
               }
               leaf topology {
                 description "Packets are directed to specified topology";
                 type string {
                 }
               }
             }
           }
           case case_5 {
             leaf redirect {
               description "Redirect packets to specified instance";
               type string {
               }
             }
           }
           case case_6 {
             container routing-instance {
               description "Packets are directed to specified routing instance";
               leaf routing-instance-name {
                 description "Name of routing instance";
                 type string {
                 }
               }
               leaf topology {
                 description "Packets are directed to specified topology";
                 type string {
                 }
               }
             }
           }
           case case_7 {
             leaf topology {
               description "Packets are directed to specified topology";
               type string {
               }
             }
           }
           case case_8 {
             container next-ip {
               description "Packets are directed to the specified ipv4 address";
               leaf address {
                 description "Address to route";
                 type jt:ipv4prefix;
               }
               container routing-instance {
                 description "Packets are directed to specified routing instance";
                 leaf routing-instance-name {
                   description "Name of routing instance";
                   type string {
                   }
                 }
                 leaf topology {
                   description "Packets are directed to specified topology";
                   type string {
                   }
                 }
               }
             }
           }
           case case_9 {
             container next-interface {
               presence "enable next-interface";
               description "Packets are to be routed through the specified interface";
               uses apply-advanced;
               leaf interface-name {
                 description "Interface name";
                 type string {
                   length "1 .. 127";
                 }
               }
               container routing-instance {
                 description "Packets are directed to specified routing instance";
                 leaf routing-instance-name {
                   description "Name of routing instance";
                   type string {
                   }
                 }
                 leaf topology {
                   description "Packets are directed to specified topology";
                   type string {
                   }
                 }
               }
               choice designation {
                 case case_1 {
                   leaf accept {
                     description "Accept the packet";
                     type empty;
                   }
                 }
                 case case_2 {
                   leaf next {
                     description "Continue to next term in a filter";
                     type enumeration {
                       enum "term" {
                         description "Continue to next term in a filter";
                       }
                     }
                   }
                 }
               }
             }
           }
           case case_10 {
             leaf ipsec-sa {
               description "Use specified IPSec security association";
               type string;
             }
           }
           case case_11 {
             leaf next-hop-group {
               description "Use specified next-hop group";
               type string;
             }
           }
           case case_12 {
             container decapsulate {
               presence "enable decapsulate";
               description "Terminate a tunnel";
               uses apply-advanced;
               choice tunnel-protocol {
                 case case_1 {
                   container gre {
                     presence "enable gre";
                     description "GRE protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
                 case case_2 {
                   container gre-in-udp {
                     presence "enable gre-in-udp";
                     description "GRE-in-UDP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
                 case case_3 {
                   container mpls-in-udp {
                     presence "enable mpls-in-udp";
                     description "MPLS-in-UDP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
                 case case_4 {
                   container inet-in-udp {
                     presence "enable inet-in-udp";
                     description "IPv4-in-UDP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
                 case case_5 {
                   container inet6-in-udp {
                     presence "enable inet6-in-udp";
                     description "IPv6-in-UDP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
                 case case_6 {
                   container l2tp {
                     description "L2TP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     leaf-list cookie {
                       ordered-by user;
                       description "L2TPv3 cookie";
                       type string {
                         length "1 .. 32";
                       }
                     }
                     choice destination {
                       case case_1 {
                         leaf output-interface {
                           description "Interface name";
                           type union {
                             type jt:interface-unit;
                             type string {
                               pattern "<.*>|$.*";
                             }
                           }
                         }
                       }
                     }
                   }
                 }
                 case case_7 {
                   container ipip {
                     presence "enable ipip";
                     description "IPIP protocol";
                     uses apply-advanced;
                     leaf-list sample {
                       ordered-by user;
                       description "Sample the packet";
                       type enumeration {
                         enum "inet" {
                           description "IPV4 protocol";
                         }
                         enum "inet6" {
                           description "IPV6 protocol";
                         }
                         enum "mpls" {
                           description "MPLS protocol";
                         }
                       }
                     }
                     leaf no-decrement-ttl {
                       description "Do not decrement TTL";
                       type empty;
                     }
                     leaf forwarding-class {
                       description "Classify packet to forwarding class";
                       type string {
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             type string {
                             }
                           }
                         }
                       }
                     }
                   }
                 }
               }
             }
           }
           case case_13 {
             container encapsulate {
               presence "enable encapsulate";
               description "Send to a tunnel";
               leaf tunnel-end-point {
                 description "Name of the tunnel end point";
                 type string {
                 }
               }
             }
           }
           case case_14 {
             container reject {
               presence "enable reject";
               description "Reject the packet";
               choice style {
                 case case_1 {
                   leaf network-unreachable {
                     description "Send ICMP Network Unreachable message";
                     type empty;
                   }
                 }
                 case case_2 {
                   leaf host-unreachable {
                     description "Send ICMP Host Unreachable message";
                     type empty;
                   }
                 }
                 case case_3 {
                   leaf protocol-unreachable {
                     description "Send ICMP Protocol Unreachable message";
                     type empty;
                   }
                 }
                 case case_4 {
                   leaf port-unreachable {
                     description "Send ICMP Port Unreachable message";
                     type empty;
                   }
                 }
                 case case_5 {
                   leaf fragmentation-needed {
                     description "Send ICMP Fragmentation Needed message";
                     type empty;
                   }
                 }
                 case case_6 {
                   leaf source-route-failed {
                     description "Send ICMP Source Route Failed message";
                     type empty;
                   }
                 }
                 case case_7 {
                   leaf network-unknown {
                     description "Send ICMP Network Unknown message";
                     type empty;
                   }
                 }
                 case case_8 {
                   leaf host-unknown {
                     description "Send ICMP Host Unknown message";
                     type empty;
                   }
                 }
                 case case_9 {
                   leaf source-host-isolated {
                     description "Send ICMP Source Host Isolated message";
                     type empty;
                   }
                 }
                 case case_10 {
                   leaf network-prohibited {
                     description "Send ICMP Network Prohibited message";
                     type empty;
                   }
                 }
                 case case_11 {
                   leaf host-prohibited {
                     description "Send ICMP Host Prohibited message";
                     type empty;
                   }
                 }
                 case case_12 {
                   leaf bad-network-tos {
                     description "Send ICMP Bad Network ToS message";
                     type empty;
                   }
                 }
                 case case_13 {
                   leaf bad-host-tos {
                     description "Send ICMP Bad Host ToS message";
                     type empty;
                   }
                 }
                 case case_14 {
                   leaf administratively-prohibited {
                     description "Send ICMP Administratively Prohibited message";
                     type empty;
                   }
                 }
                 case case_15 {
                   leaf precedence-violation {
                     description "Send ICMP Precedence Violation message";
                     type empty;
                   }
                 }
                 case case_16 {
                   leaf precedence-cutoff {
                     description "Send ICMP Precedence Cutoff message";
                     type empty;
                   }
                 }
                 case case_17 {
                   leaf tcp-reset {
                     description "Send TCP Reset message";
                     type empty;
                   }
                 }
               }
             }
           }
           case case_15 {
             leaf load-balance {
               description "Use specified load balancing group";
               type string {
               }
             }
           }
         }
         leaf dscp {
           description "Set Differentiated Services (DiffServ) code point";
           type string;
         }
         leaf outer-dscp {
           description "Set differentiated services code point for outer header";
           type string;
         }
         leaf qfi {
           description "Set QFI for N3 interface";
           type string;
         }
         leaf tos-reflect {
           description "Set or clear the tos-reflect bit flag of the IP header";
           type enumeration {
             enum "clear" {
               description "Clear TOS-R bit flag";
             }
             enum "set" {
               description "Set TOS-R bit flag";
             }
           }
         }
         leaf dont-fragment {
           description "Set or clear the DF bit flag of the IP header (ingress only)";
           type enumeration {
             enum "clear" {
               description "Clear DF bit flag";
             }
             enum "set" {
               description "Set DF bit flag";
             }
           }
         }
         leaf prefix-action {
           description "Police or count packets using named prefix action";
           type string {
           }
         }
       }
       container template {
         description "Refer a template";
         uses apply-advanced;
         leaf template-name {
           description "Template name";
           type string {
           }
         }
       }
     }
   }
   grouping inet_fuf {
     leaf name {
       description "Name of fast update filter";
       type string {
       }
     }
     uses apply-advanced;
     leaf interface-specific {
       description "Defined counters are interface specific";
       type empty;
     }
     leaf-list match-order {
       ordered-by user;
       type enumeration {
         enum "protocol" {
           description "Include IP protocol in match set";
         }
         enum "source-address" {
           description "Include source-address in match set";
         }
         enum "destination-address" {
           description "Include destination-address in match set";
         }
         enum "source-port" {
           description "Include source-port in match set";
         }
         enum "destination-port" {
           description "Include destination-port in match set";
         }
         enum "dscp" {
           description "Include Differentiated Services (DiffServ) code point in match set";
         }
       }
     }
     list term {
       key name;
       ordered-by user;
       description "One or more firewall terms";
       leaf name {
         description "Term name";
         type string {
         }
       }
       uses apply-advanced;
       leaf only-at-create {
         description "Add term only when filter is first created.";
         type empty;
       }
       container from {
         description "Match criteria";
         uses apply-advanced;
         container source-address {
           description "Match source IP address";
           uses firewall_addr_simple_object;
         }
         container destination-address {
           description "Match destination IP address";
           uses firewall_addr_simple_object;
         }
         choice source-port_choice {
           case case_1 {
             container source-port {
               description "Match TCP/UDP source port";
               uses match_simple_port_value;
             }
           }
         }
         choice destination-port_choice {
           case case_1 {
             container destination-port {
               description "Match TCP/UDP destination port";
               uses match_simple_port_value;
             }
           }
         }
         choice protocol_choice {
           case case_1 {
             container protocol {
               description "Match IP protocol type";
               uses match_simple_protocol_value;
             }
           }
         }
         choice dscp_choice {
           case case_1 {
             container dscp {
               description "Match Differentiated Services (DiffServ) code point";
               uses match_simple_dscp_value;
             }
           }
         }
         leaf match-terms {
           description "Dynamically supplied list of match criteria";
           type string;
         }
       }
       container then {
         description "Action to take if the 'from' condition is matched";
         uses apply-advanced;
         choice policer-choice {
           case case_1 {
             leaf policer {
               description "Name of policer to use to rate-limit traffic";
               type string {
               }
             }
           }
         }
         leaf count {
           description "Count the packet in the named counter";
           type string {
           }
         }
         leaf service-accounting {
           description "Count the packets for service accounting";
           type empty;
         }
         leaf log {
           description "Log the packet";
           type empty;
         }
         leaf port-mirror {
           description "Port-mirror the packet";
           type empty;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf action-terms {
           description "Dynamically supplied list of actions";
           type string;
         }
         choice designation {
           case case_1 {
             leaf accept {
               description "Accept the packet";
               type empty;
             }
           }
           case case_2 {
             leaf discard {
               description "Discard the packet";
               type empty;
             }
           }
           case case_3 {
             container routing-instance {
               description "Packets are directed to specified routing instance";
               leaf routing-instance-name {
                 description "Name of routing instance";
                 type string {
                 }
               }
               leaf topology {
                 description "Packets are directed to specified topology";
                 type string {
                 }
               }
             }
           }
         }
       }
     }
   }
   grouping firewall_addr_simple_object {
     uses apply-advanced;
     leaf address {
       description "Prefix to match";
       type jt:ipv4prefix;
     }
   }
   grouping inet_service_filter {
     leaf name {
       description "Filter name";
       type string {
       }
     }
     uses apply-advanced;
     list term {
       key name;
       ordered-by user;
       description "Service filter term";
       leaf name {
         description "Term name";
         type string {
         }
       }
       uses apply-advanced;
       container from {
         description "Match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match IP source address";
           uses firewall_addr_object;
         }
         list destination-address {
           key name;
           ordered-by user;
           description "Match IP destination address";
           uses firewall_addr_object;
         }
         list address {
           key name;
           ordered-by user;
           description "Match IP source or destination address";
           uses firewall_addr_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         choice protocol_choice {
           case case_1 {
             leaf-list protocol {
               ordered-by user;
               type string;
             }
           }
           case case_2 {
             leaf-list protocol-except {
               ordered-by user;
               type string;
             }
           }
         }
         choice ip-options_choice {
           case case_1 {
             leaf-list ip-options {
               ordered-by user;
               type enumeration {
                 enum "any" {
                   description "Any IP option";
                 }
               }
             }
           }
           case case_2 {
             leaf-list ip-options-except {
               ordered-by user;
               type enumeration {
                 enum "any" {
                   description "Any IP option";
                 }
               }
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice esp-spi_choice {
           case case_1 {
             leaf-list esp-spi {
               ordered-by user;
               description "Range of values";
               type string;
             }
           }
           case case_2 {
             leaf-list esp-spi-except {
               ordered-by user;
               description "Range of values";
               type string;
             }
           }
         }
         leaf is-fragment {
           description "Match if packet is a fragment";
           type empty;
         }
         leaf first-fragment {
           description "Match if packet is the first fragment";
           type empty;
         }
         choice fragment-offset_choice {
           case case_1 {
             leaf-list fragment-offset {
               ordered-by user;
               description "Range of values";
               type string {
               }
             }
           }
           case case_2 {
             leaf-list fragment-offset-except {
               ordered-by user;
               description "Range of values";
               type string {
               }
             }
           }
         }
         leaf fragment-flags {
           description "Match fragment flags";
           type string;
         }
         leaf tcp-flags {
           description "Match TCP flags (in symbolic or hex formats)";
           type string;
         }
         choice ah-spi_choice {
           case case_1 {
             leaf-list ah-spi {
               ordered-by user;
               description "Range of values";
               type string;
             }
           }
           case case_2 {
             leaf-list ah-spi-except {
               ordered-by user;
               description "Range of values";
               type string;
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice redirect-reason_choice {
           case case_1 {
             leaf-list redirect-reason {
               ordered-by user;
               type enumeration {
                 enum "aoc" {
                   description "Advice of Charge";
                 }
                 enum "aolb" {
                   description "Advice of Low Balance";
                 }
                 enum "dpi" {
                   description "Layer7 match required";
                 }
               }
             }
           }
           case case_2 {
             leaf-list redirect-reason-except {
               ordered-by user;
               type enumeration {
                 enum "aoc" {
                   description "Advice of Charge";
                 }
                 enum "aolb" {
                   description "Advice of Low Balance";
                 }
                 enum "dpi" {
                   description "Layer7 match required";
                 }
               }
             }
           }
         }
       }
       container then {
         description "Action to take if the 'from' condition is matched";
         uses apply-advanced;
         leaf count {
           description "Count the packet in the named counter";
           type string {
           }
         }
         leaf log {
           description "Log the packet";
           type empty;
         }
         leaf pkt-trace {
           description "Pkt-Trace the packet";
           type empty;
         }
         leaf sample {
           description "Sample the packet";
           type empty;
         }
         leaf port-mirror {
           description "Port-mirror the packet";
           type empty;
         }
         choice designation {
           case case_1 {
             leaf service {
               description "Forward packets to service processing";
               type empty;
             }
           }
           case case_2 {
             leaf skip {
               description "Skip service processing";
               type empty;
             }
           }
           case case_3 {
             leaf accept {
               description "Accept the packet";
               type empty;
             }
           }
         }
       }
     }
   }
   grouping inet_simple_filter {
     leaf name {
       description "Name of simple filter";
       type string {
       }
     }
     uses apply-advanced;
     leaf interface-specific {
       description "Defined counters are interface specific";
       status deprecated;
       type empty;
     }
     list term {
       key name;
       ordered-by user;
       description "One or more firewall terms";
       leaf name {
         description "Term name";
         type string {
         }
       }
       uses apply-advanced;
       container from {
         description "Match criteria";
         uses apply-advanced;
         container source-address {
           description "Source IP address";
           uses firewall_addr_simple_object;
         }
         container destination-address {
           description "Destination IP address";
           uses firewall_addr_simple_object;
         }
         choice protocol_choice {
           case case_1 {
             container protocol {
               description "Match IP protocol type";
               uses match_simple_protocol_value;
             }
           }
         }
         choice source-port_choice {
           case case_1 {
             container source-port {
               description "Match TCP/UDP source port";
               uses match_simple_port_value;
             }
           }
         }
         choice destination-port_choice {
           case case_1 {
             container destination-port {
               description "Match TCP/UDP destination port";
               uses match_simple_port_value;
             }
           }
         }
         choice forwarding-class_choice {
           case case_1 {
             leaf-list forwarding-class {
               ordered-by user;
               description "String name";
               type string {
               }
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf two-rate {
                     description "Name of two-rate three-color policer to use to rate-limit traffic";
                     type string {
                     }
                   }
                 }
               }
             }
           }
         }
         leaf loss-priority {
           description "Packet's loss priority";
           type enumeration {
             enum "low" {
               description "Low loss priority";
             }
             enum "medium-high" {
               description "Medium-high loss priority";
             }
             enum "medium-low" {
               description "Medium-low loss priority";
             }
             enum "high" {
               description "High loss priority";
             }
           }
         }
         leaf forwarding-class {
           description "Classify packet to forwarding class";
           type string {
           }
         }
         leaf discard {
           description "Discard the packet";
           type empty;
         }
         leaf accept {
           description "Accept the packet";
           type empty;
         }
       }
     }
   }
   grouping inet_template {
     leaf name {
       description "Template name";
       type string {
       }
     }
     uses apply-advanced;
     container attributes {
       description "Template attributes";
       uses apply-advanced;
       leaf destination-address {
         description "Match IP destination address";
         type empty;
       }
       leaf destination-port {
         description "Match TCP/UDP destination port";
         type empty;
       }
       leaf destination-port-range-optimize {
         description "Optimize the destination port range";
         type empty;
       }
       leaf destination-prefix-list {
         description "Match IP destination prefixes in named list";
         type empty;
       }
       leaf dscp {
         description "Match Differentiated Services (DiffServ) code point";
         type empty;
       }
       leaf flexible-match-mask {
         description "Match flexible mask";
         type empty;
       }
       leaf flexible-match-range {
         description "Match flexible range";
         type empty;
       }
       leaf fragment-flags {
         description "Match fragment flags";
         type empty;
       }
       leaf icmp-code {
         description "Match ICMP message code";
         type empty;
       }
       leaf icmp-type {
         description "Match ICMP message type";
         type empty;
       }
       leaf interface {
         description "Match interface name";
         type empty;
       }
       leaf ip-options {
         description "Match IP options";
         type empty;
       }
       leaf is-fragment {
         description "Match if packet is a fragment";
         type empty;
       }
       leaf packet-length {
         description "Match packet length";
         type empty;
       }
       leaf precedence {
         description "Match IP precedence value";
         type empty;
       }
       leaf protocol {
         description "Match IP protocol type";
         type empty;
       }
       leaf rat-type {
         description "Match RAT Type";
         type empty;
       }
       leaf redirect-reason {
         description "Match Redirect Reason";
         type empty;
       }
       leaf source-address {
         description "Match IP source address";
         type empty;
       }
       leaf source-port {
         description "Match TCP/UDP source port";
         type empty;
       }
       leaf source-port-range-optimize {
         description "Optimize the source port range";
         type empty;
       }
       leaf source-prefix-list {
         description "Match IP source prefixes in named list";
         type empty;
       }
       leaf tcp-established {
         description "Match packet of an established TCP connection";
         type empty;
       }
       leaf tcp-flags {
         description "Match TCP flags";
         type empty;
       }
       leaf tcp-initial {
         description "Match initial packet of a TCP connection";
         type empty;
       }
       leaf ttl {
         description "Match IP ttl type";
         type empty;
       }
       leaf egress-to-ingress {
         description "Match egress fields in ingress";
         type empty;
       }
     }
   }
   grouping interface_set_type {
     leaf name {
       description "Interface set name";
       type string {
       }
     }
     uses apply-advanced;
     list interface-list {
       key name;
       ordered-by user;
       description "Interface list";
       leaf name {
         description "Interface name";
         type union {
           type jt:interface-wildcard;
           type string {
             pattern "<.*>|$.*";
           }
         }
       }
       uses apply-advanced;
     }
   }
   grouping interfaces_type {
     description "Physical interface";
     leaf name {
       type string;
     }
     uses apply-advanced;
     leaf description {
       description "Text description of interface";
       type string;
     }
     leaf external-model-name {
       description "Name for interface as configured using 3rd-party model";
       type string;
     }
     container management-ethernet-redundancy {
       presence "enable management-ethernet-redundancy";
       description "Management Interface Redundancy";
       uses apply-advanced;
       choice enable_choice {
         case case_1 {
           leaf redundancy-enable {
             description "Enable Managment Ethernet Redundancy";
             type empty;
           }
         }
         case case_2 {
           leaf redundancy-disable {
             description "Disable  Managment Ethernet Redundancy";
             type empty;
           }
         }
       }
       leaf connectivity-test-interval {
         description "Connectivity test interval";
         default "5";
         units "seconds";
         type union {
           type string {
             pattern "<.*>|$.*";
           }
           type uint32 {
             range "1 .. 10";
           }
         }
       }
       leaf connectivity-test-response-interval {
         description "Connectivity test response wait time";
         default "5";
         units "seconds";
         type union {
           type string {
             pattern "<.*>|$.*";
           }
           type uint32 {
             range "1 .. 10";
           }
         }
       }
       leaf remote-ipv4-address {
         description "Destination IPV4 address to reach remote ";
         default "nil";
         type jt:ipv4addr;
       }
       leaf remote-ipv6-address {
         description "Destination IPV6 address to reach remote";
         default "nil";
         type jt:ipv6addr;
       }
       leaf number-of-connectivity-retries {
         description "Number of Connectivity retries ";
         default "2";
         type union {
           type string {
             pattern "<.*>|$.*";
           }
           type uint32 {
             range "1 .. 8";
           }
         }
       }
     }
     leaf metadata {
       description "Text metadata attached to interface";
       type string;
     }
     choice enable-disable {
       case case_1 {
         leaf disable {
           description "Disable this interface";
           type empty;
         }
       }
     }
     leaf promiscuous-mode {
       description "Enable promiscuous mode for L3 interface";
       type empty;
     }
     leaf port-mirror-instance {
       description "Port-mirror the packet to specified instance";
       type string {
         length "1 .. 64";
       }
     }
     leaf multicast-statistics {
       description "Enable multicast statistics";
       type empty;
     }
     leaf oam-on-svlan {
       description "Propagate SVLAN OAM state to CVLANs";
       type empty;
     }
     container fabric-options {
       description "Fabric interface specific options";
       uses apply-advanced;
       list member-interfaces {
         key name;
         description "Member interface for the fabric interface";
         leaf name {
           description "Interface name of member";
           type union {
             type jt:interface-device;
             type string {
               pattern "<.*>|$.*";
             }
           }
         }
         uses apply-advanced;
       }
       container remote-chassis {
         presence "enable remote-chassis";
         description "Remote chassis reachability";
         uses apply-advanced;
         leaf destination {
           description "Destination IP address to reach remote chassis";
           type jt:ipv4addr;
         }
       }
     }
     container traceoptions {
       presence "enable traceoptions";
       description "Interface trace options";
       uses apply-advanced;
       list flag {
         key name;
         ordered-by user;
         description "Tracing parameters";
         leaf name {
           type enumeration {
             enum "ipc" {
               description "Trace interface IPC messages";
             }
             enum "event" {
               description "Trace interface events";
             }
             enum "media" {
               description "Trace interface media changes";
             }
             enum "all" {
               description "Enable all interface trace flags";
             }
             enum "q921" {
               description "Trace ISDN Q.921 frames";
             }
             enum "q931" {
               description "Trace ISDN Q.931 frames";
             }
           }
         }
       }
       container file {
         presence "enable file";
         description "Trace file information for ISDN decoded frames";
         uses apply-advanced;
         leaf filename {
           description "Name of file in which to write trace information";
           type string {
             length "1 .. 1024";
           }
         }
         leaf size {
           description "Maximum trace file size";
           default "128k";
           type string;
         }
         leaf files {
           description "Maximum number of trace files";
           default "10";
           type union {
             type uint32;
             type string {
               pattern "<.*>|$.*";
             }
           }
         }
         choice world-readable-choice {
           leaf world-readable {
             description "Allow any user to read the log file";
             type empty;
           }
           leaf no-world-readable {
             description "Don't allow any user to read the log file";
             type empty;
           }
         }
       }
     }
     leaf passive-monitor-mode {
       description "Use interface to tap packets from another router";
       type empty;
     }
     choice keepalive_choices {
       case case_1 {
         container keepalives {
           description "Send or demand keepalive messages";
           presence "enable keepalives";
           uses keepalives_type;
         }
       }
       case case_2 {
         leaf no-keepalives {
           description "Do not send keepalive messages";
           type empty;
         }
       }
     }
     choice traps-choice {
       leaf traps {
         description "Enable SNMP notifications on state changes";
         type empty;
       }
       leaf no-traps {
         description "Don't enable SNMP notifications on state changes";
         type empty;
       }
     }
     choice interface-mib-choice {
       leaf interface-mib {
         description "Enable interface-related MIBs";
         type empty;
       }
       leaf no-interface-mib {
         description "Don't enable interface-related MIBs";
         type empty;
       }
     }
     leaf accounting-profile {
       description "Accounting profile name";
       type string;
     }
     container anchor-point {
       description "Anchor point";
       uses apply-advanced;
       leaf interface-name {
         description "Interface name";
         type union {
           type jt:interface-device;
           type string {
             pattern "<.*>|$.*";
           }
         }
       }
     }
     container targeted-options {
       description "Targeting specific options for PS/RLT active-active mode";
       uses apply-advanced;
       leaf type {
         description "Targeting type of PS";
         type enumeration {
           enum "manual" {
             description "Targeting type is Manual";
           }
         }
       }
       choice redundancy_choice {
         case case_1 {
           leaf logical-interface-fpc-redundancy {
             description "Enable FPC redundancy for logical interfaces";
             type empty;
           }
         }
         case case_2 {
           leaf logical-interface-chassis-redundancy {
             description "Enable CHASSIS redundancy for logical interfaces";
             type empty;
           }
         }
       }
       container rebalance-periodic {
         presence "enable rebalance-periodic";
         uses apply-advanced;
         leaf start-time {
           description "Start time of the rebalance operation ( Wall clock time )";
           type jt:time-of-day;
         }
         leaf interval {
           description "Interval of the rebalance operation in hrs";
           type union {
             type string {
               pattern "<.*>|$.*";
             }
             type uint32 {
               range "1 .. 24";
             }
           }
         }
       }
       leaf rebalance-subscriber-granularity {
         description "Max subscriber aggregate weight";
         type union {
           type string {
             pattern "<.*>|$.*";
           }
           type uint32 {
             range "1 .. 65535";
           }
         }
       }
     }
     choice bypass-queueing-chip-choice {
       leaf bypass-queueing-chip {
         description "Enable to bypass queueing chip";
         type empty;
       }
       leaf no-bypass-queueing-chip {
         description "Don't enable to bypass queueing chip";
         type empty;
       }
     }
     choice scheduler_type {
       case case_1 {
         choice per-unit-scheduler-choice {
           leaf per-unit-scheduler {
             description "Enable subunit queuing on Frame Relay or VLAN IQ interface";
             type empty;
           }
           leaf no-per-unit-scheduler {
             description "Don't enable subunit queuing on Frame Relay or VLAN IQ interface";
             type empty;
           }
         }
       }
       case case_2 {
         leaf shared-scheduler {
           description "Enabled shared queuing on an IQ2 interface";
           type empty;
         }
       }
       case case_3 {
         container hierarchical-scheduler {
           presence "enable hierarchical-scheduler";
           description "Enable hierarchical scheduling";
           leaf maximum-hierarchy-levels {
             description "Maximum hierarchy levels";
             type union {
               type string {
                 pattern "<.*>|$.*";
               }
               type uint32;
             }
           }
           leaf maximum-l2-nodes {
             description "Maximum l2 nodes, allowed numbers are power of 2 between 1 and 16k (needs FPC reboot)";
             default "1";
             type union {
               type string {
                 pattern "<.*>|$.*";
               }
               type uint32 {
                 range "1 .. 16384";
               }
             }
           }
           leaf maximum-l3-nodes {
             description "Maximum l3 nodes, allowed numbers are power of 2 between 2 and 32k (needs FPC reboot)";
             default "16384";
             type union {
               type string {
                 pattern "<.*>|$.*";
               }
               type uint32 {
                 range "2 .. 32768";
               }
             }
           }
           leaf implicit-hierarchy {
             description "Implicit hierarchy (follows interface hierarchy)";
             type empty;
           }
         }
       }
     }
     leaf l2tp-maximum-session {
       description "Maximum L2TP session";
       type union {
         type string {
           pattern "<.*>|$.*";
         }
         type uint32 {
           range "0 .. 64000";
         }
       }
     }
     leaf schedulers {
       description "Number of schedulers to allocate for interface";
       type union {
         type uint32;
         type string {
           pattern "<.*>|$.*";
         }
       }
     }
     leaf interface-transmit-statistics {
       description "Interface statistics based on the transmitted packets";
       type empty;
     }
     leaf cascade-port {
       description "Cascade port";
       type empty;
     }
     leaf dce {
       description "Respond to Frame Relay status enquiry messages";
       type empty;
     }
     choice vlan_tag_mode {
       case case_1 {
         leaf vlan-tagging {
           description "802.1q VLAN tagging support";
           type empty;
         }
       }
       case case_2 {
         leaf stacked-vlan-tagging {
           description "Stacked 802.1q VLAN tagging support";
           type empty;
         }
       }
       case case_3 {
         leaf flexible-vlan-tagging {
           description "Support for no tagging, or single and double 802.1q VLAN tagging";
           type empty;
         }
       }
       case case_4 {
         leaf vlan-vci-tagging {
           description "CCC for VLAN Q-in-Q and ATM VPI/VCI interworking";
           type empty;
         }
       }
     }
     leaf native-vlan-id {
       description "Virtual LAN identifier for untagged frames";
       type union {
         type string {
           pattern "<.*>|$.*";
         }
         type uint32 {
           range "0 .. 4094";
         }
       }
     }
     leaf no-native-vlan-insert {
       description "Disable native-vlan-id insertion to untagged frames";
       type empty;
     }
     leaf vlan-offload {
       description "Offload VLAN filtering to NIC HW";
       type empty;
     }
     leaf input-native-vlan-push {
       description "Control native-vlan-id insertion to untagged frames when input-vlan-map push is configured";
       type enumeration {
         enum "disable" {
           description "Disable input-native-vlan-push";
         }
         enum "enable" {
           description "Enable input-native-vlan-push";
         }
       }
     }
     leaf no-pseudowire-down-on-core-isolation {
       description "Do not bring the pseudowire down in the event of EVPN Core isolation";
       type empty;
     }
     leaf number-of-sub-ports {
       description "Number of channels to create for a port";
       type union {
         type string {
           pattern "<.*>|$.*";
         }
         type uint32 {
           range "1 .. 8";
         }
       }
     }
     leaf unused {
       description "Disable physical port";
       type empty;
     }
     leaf speed {
       description "Link speed";
       type enumeration {
         enum "auto" {
           description "Enable auto negotiation of interface speed";
         }
         enum "auto-10m-100m" {
           description "Enable auto negotiation of limiting interface speed to 10m/100m";
         }
         enum "10m" {
         }
         enum "100m" {
         }
         enum "1g" {
         }
         enum "2.5g" {
         }
         enum "5g" {
         }
         enum "10g" {
         }
         enum "25g" {
         }
         enum "40g" {
         }
         enum "50g" {
         }
         enum "100g" {
         }
         enum "200g" {
         }
         enum "400g" {
         }
         enum "800g" {
         }
         enum "oc3" {
         }
         enum "oc12" {
         }
         enum "oc48" {
         }
       }
     }
     container forwarding-class-accounting {
       presence "enable forwarding-class-accounting";
       description "Configure Forwarding-class-accounting parameters";
       uses apply-advanced;
       leaf direction {
         description "Direction of the traffic to be accounted for IFD";
         type enumeration {
           enum "ingress" {
             description "Enable forwarding-class-accounting for ingress traffic";
           }
           enum "egress" {
             description "Enable forwarding-class-accounting for egress traffic";
           }
           enum "both" {
             description "Enable forwarding-class-accounting for both directions";
           }
         }
       }
       container enhanced {
         presence "enable enhanced";
         uses apply-advanced;
         leaf traffic-type {
           description "Traffic-type to be accounted for forwarding-class-accounting";
           type enumeration {
             enum "unicast-statistics" {
               description "Count only unicast traffic for forwarding-class-accounting";
             }
             enum "multicast-statistics" {
               description "Count only multicast traffic for forwarding-class-accounting";
             }
           }
         }
         leaf family {
           description "Protocol traffic to be accounted for forwarding-class-accounting";
           type enumeration {
             enum "inet" {
               description "Enable forwarding-class-accounting for IPv4 family only";
             }
             enum "inet6" {
               description "Enable forwarding-class-accounting for IPv6 family only";
             }
             enum "both" {
               description "Enable forwarding-class-accounting for both IPv4 and IPv6 family only";
             }
           }
         }
         leaf direction {
           description "Direction of the traffic to be accounted for forwarding-class-accounting";
           type enumeration {
             enum "ingress" {
               description "Enable forwarding-class-accounting for ingress traffic";
             }
             enum "egress" {
               description "Enable forwarding-class-accounting for egress traffic";
             }
             enum "both" {
               description "Enable forwarding-class-accounting for both ingress and egress traffic";
             }
           }
         }
         leaf overhead-bytes {
           description "Per octet overhead bytes to be accounted for forwarding-class-accounting";
           default "0";
           type union {
             type string {
               pattern "<.*>|$.*";
             }
             type uint32 {
               range "0 .. 255";
             }
           }
         }
       }
     }
     container auto-configure {
       description "Auto configuration";
       uses auto_configure_vlan_type;
     }
     leaf mtu {
       description "Maximum transmit packet size";
       type union {
         type string {
           pattern "<.*>|$.*";
         }
         type uint32;
       }
     }
     container hold-time {
       description "Hold time for link up and link down";
       leaf up {
         description "Link up hold time";
         units "milliseconds";
         type union {
           type uint32;
           type string {
             pattern "<.*>|$.*";
           }
         }
       }
       leaf down {
         description "Link down hold time";
         units "milliseconds";
         type union {
           type uint32;
           type string {
             pattern "<.*>|$.*";
           }
         }
       }
     }
     container damping {
       description "Interface damping parameters";
       uses apply-advanced;
       leaf half-life {
         description "Damping half life time";
         default "5";
         units "seconds";
         type union {
           type string {
             pattern "<.*>|$.*";
           }
           type uint32 {
             range "1 .. 30";
           }
         }
       }
       leaf max-suppress {
         description "Maximum suppress time";
         default "20";
         units "seconds";
         type union {
           type string {
             pattern "<.*>|$.*";
           }
           type uint32 {
             range "1 .. 20000";
           }
         }
       }
       leaf reuse {
         description "Reuse threshold";
         default "1000";
         type union {
           type string {
             pattern "<.*>|$.*";
           }
           type uint32 {
             range "1 .. 20000";
           }
         }
       }
       leaf suppress {
         description "Suppress threshold";
         default "2000";
         type union {
           type string {
             pattern "<.*>|$.*";
           }
           type uint32 {
             range "1 .. 20000";
           }
         }
       }
       leaf enable {
         description "Enable interface damping";
         type empty;
       }
     }
     container link-degrade-monitor {
       presence "enable link-degrade-monitor";
       description "Enable link degrade monitoring";
       uses apply-advanced;
       choice enable_choice {
         case case_1 {
           leaf link-degrade-monitor-enable {
             description "Enable Link Degrade Monitoring";
             type empty;
           }
         }
         case case_2 {
           leaf no-link-degrade-monitor-enable {
             description "Disable Link Degrade Monitoring";
             type empty;
           }
         }
       }
       container actions {
         description "Action upon link degrade event";
         uses apply-advanced;
         choice action_choice {
           case case_1 {
             leaf media-based {
               description "Media based";
               type empty;
             }
           }
         }
       }
       container recovery {
         description "Link degrade recovery mechanism";
         uses apply-advanced;
         leaf timer {
           description "Auto recovery timer in seconds";
           default "1800";
           type union {
             type uint32;
             type string {
               pattern "<.*>|$.*";
             }
           }
         }
         choice receovery_choice {
           case case_1 {
             leaf auto {
               description "Automatic recovery";
               type empty;
             }
           }
           case case_2 {
             leaf manual {
               description "Manual recovery";
               type empty;
             }
           }
         }
       }
       container thresholds {
         description "Link degrade threshold parameters";
         uses apply-advanced;
         leaf set {
           description "BER at which link considered degraded(1..16)";
           default "1e-7";
           type string {
           }
         }
         leaf clear {
           description "BER at which link considered improved(1..16)";
           default "1e-12";
           type string {
           }
         }
         leaf warning-set {
           description "BER at which link degrade warning raised(1..16)";
           default "1e-9";
           type string {
           }
         }
         leaf warning-clear {
           description "BER at which link degrade warning cleared(1..16)";
           default "1e-11";
           type string {
           }
         }
         leaf interval {
           description "Consecutive link degrade events";
           default "10";
           type union {
             type string {
               pattern "<.*>|$.*";
             }
             type uint32 {
               range "1 .. 256";
             }
           }
         }
       }
     }
     container satop-options {
       description "Structure-Agnostic TDM over Packet protocol options";
       uses apply-advanced;
       leaf idle-pattern {
         description "An 8-bit hexadecimal pattern to replace TDM data in a lost packet";
         type union {
           type string {
             pattern "<.*>|$.*";
           }
           type uint32 {
             range "0 .. 255";
           }
         }
       }
       leaf payload-size {
         description "Number of payload bytes per packet";
         type union {
           type string {
             pattern "<.*>|$.*";
           }
           type uint32 {
             range "64 .. 1024";
           }
         }
       }
       container excessive-packet-loss-rate {
         description "Packet loss options";
         uses apply-advanced;
         leaf threshold {
           description "Percentile designating the threshold of excessive packet loss rate";
           type union {
             type string {
               pattern "<.*>|$.*";
             }
             type uint8 {
               range "1 .. 100";
             }
           }
         }
         leaf sample-period {
           description "Number of milliseconds over which excessive packet loss rate is calculated";
           type union {
             type string {
               pattern "<.*>|$.*";
             }
             type uint32 {
               range "1000 .. 65535";
             }
           }
         }
       }
       choice jitter-buffer-size {
         case case_1 {
           leaf jitter-buffer-packets {
             description "Number of packets in jitter buffer before packet data is played out in the line";
             type union {
               type string {
                 pattern "<.*>|$.*";
               }
               type uint32 {
                 range "1 .. 64";
               }
             }
           }
         }
         case case_2 {
           leaf jitter-buffer-latency {
             description "Number of milliseconds delay in jitter buffer before packet data is played out in the line";
             units "milliseconds";
             type union {
               type string {
                 pattern "<.*>|$.*";
               }
               type uint32 {
                 range "1 .. 1000";
               }
             }
           }
         }
         case case_3 {
           leaf jitter-buffer-auto-adjust {
             description "Automatically adjust jitter buffer";
             type empty;
           }
         }
       }
       leaf bit-rate {
         description "In multiples of DS0";
         type union {
           type string {
             pattern "<.*>|$.*";
           }
           type uint32 {
             range "1 .. 10240";
           }
         }
       }
     }
     container cesopsn-options {
       description "Structure-Aware TDM over Packet protocol options";
       uses apply-advanced;
       leaf idle-pattern {
         description "An 8-bit hexadecimal pattern to replace TDM data in a lost packet";
         type union {
           type string {
             pattern "<.*>|$.*";
           }
           type uint32 {
             range "0 .. 255";
           }
         }
       }
       leaf packetization-latency {
         description "Number of microseconds to create packets";
         units "microseconds";
         type union {
           type string {
             pattern "<.*>|$.*";
           }
           type uint32 {
             range "1000 .. 8000";
           }
         }
       }
       leaf payload-size {
         description "Number of payload bytes per packet";
         type union {
           type string {
             pattern "<.*>|$.*";
           }
           type uint32 {
             range "64 .. 1024";
           }
         }
       }
       container excessive-packet-loss-rate {
         description "Packet loss options";
         uses apply-advanced;
         leaf threshold {
           description "Percentile designating the threshold of excessive packet loss rate";
           type union {
             type string {
               pattern "<.*>|$.*";
             }
             type uint8 {
               range "1 .. 100";
             }
           }
         }
         leaf sample-period {
           description "Number of milliseconds over which excessive packet loss rate is calculated";
           type union {
             type string {
               pattern "<.*>|$.*";
             }
             type uint32 {
               range "1000 .. 65535";
             }
           }
         }
       }
       choice jitter-buffer-size {
         case case_1 {
           leaf jitter-buffer-packets {
             description "Number of packets in jitter buffer before packet data is played out in the line";
             type union {
               type string {
                 pattern "<.*>|$.*";
               }
               type uint32 {
                 range "1 .. 64";
               }
             }
           }
         }
         case case_2 {
           leaf jitter-buffer-latency {
             description "Number of milliseconds delay in jitter buffer before packet data is played out in the line";
             units "milliseconds";
             type union {
               type string {
                 pattern "<.*>|$.*";
               }
               type uint32 {
                 range "1 .. 1000";
               }
             }
           }
         }
         case case_3 {
           leaf jitter-buffer-auto-adjust {
             description "Automatically adjust jitter buffer";
             type empty;
           }
         }
       }
       leaf bit-rate {
         description "In multiples of DS0";
         type union {
           type string {
             pattern "<.*>|$.*";
           }
           type uint32 {
             range "1 .. 10240";
           }
         }
       }
     }
     container ima-group-options {
       description "IMA group options";
       uses apply-advanced;
       leaf frame-length {
         description "Frame length (cells)";
         type enumeration {
           enum "32" {
           }
           enum "64" {
           }
           enum "128" {
           }
           enum "256" {
           }
         }
       }
       leaf symmetry {
         description "Symmetry of IMA group";
         default "symmetrical-config-and-operation";
         type enumeration {
           enum "symmetrical-config-and-operation" {
           }
           enum "symmetrical-config-asymmetrical-operation" {
           }
         }
       }
       leaf transmit-clock {
         description "Transmit clock";
         type enumeration {
           enum "common" {
             description "Common transmit clock";
           }
           enum "independent" {
             description "Independent transmit clock";
           }
         }
       }
       leaf version {
         description "IMA specification version";
         type enumeration {
           enum "1.0" {
             description "Version 1.0";
           }
           enum "1.1" {
             description "Version 1.1";
           }
         }
       }
       container minimum-links {
         description "IMA group minimum active links";
         choice minimum_links_type {
           case case_1 {
             leaf symmetrical {
               description "Minimum active receive and transmit links";
               type union {
                 type string {
                   pattern "<.*>|$.*";
                 }
                 type uint32 {
                   range "1 .. 32";
                 }
               }
             }
           }
         }
       }
       container frame-synchronization {
         description "IMA group frame synchronization state parameters";
         uses apply-advanced;
         leaf alpha {
           description "Consecutive invalid ICP cells";
           type union {
             type string {
               pattern "<.*>|$.*";
             }
             type uint32 {
               range "1 .. 2";
             }
           }
         }
         leaf beta {
           description "Consecutive errored ICP cells";
           type union {
             type string {
               pattern "<.*>|$.*";
             }
             type uint32 {
               range "1 .. 5";
             }
           }
         }
         leaf gamma {
           description "Consecutive valid ICP cells";
           type union {
             type string {
               pattern "<.*>|$.*";
             }
             type uint32 {
               range "1 .. 5";
             }
           }
         }
       }
       container test-procedure {
         description "IMA group test pattern procedure";
         uses apply-advanced;
         leaf period {
           description "Length of IMA pattern test";
           units "seconds";
           type union {
             type string {
               pattern "<.*>|$.*";
             }
             type uint32 {
               range "1 .. 4294967294";
             }
           }
         }
         leaf interface {
           description "Interface name of the IMA link to test";
           type union {
             type jt:interface-device;
             type string {
               pattern "<.*>|$.*";
             }
           }
         }
         leaf pattern {
           description "IMA test pattern";
           type union {
             type string {
               pattern "<.*>|$.*";
             }
             type uint32 {
               range "1 .. 254";
             }
           }
         }
       }
       leaf differential-delay {
         description "Maximum differential delay among links in the IMA group";
         units "milliseconds";
         type union {
           type string {
             pattern "<.*>|$.*";
           }
           type uint32 {
             range "1 .. 56";
           }
         }
       }
     }
     container ima-link-options {
       description "IMA link options";
       uses apply-advanced;
       leaf group-id {
         description "IMA group ID this IMA link belongs to";
         type union {
           type string {
             pattern "<.*>|$.*";
           }
           type uint32;
         }
       }
     }
     list multi-chassis-protection {
       key name;
       description "Inter-Chassis protection configuration";
       uses multi-chassis-protection-group;
     }
     container clocking {
       description "Interface clock source";
       choice clocking_choices {
         case case_1 {
           leaf internal {
             description "Clocking provided by local system";
             type empty;
           }
         }
         case case_2 {
           container external {
             presence "enable external";
             description "Clocking provided by DCE (loop timing)";
             uses apply-advanced;
             leaf interface {
               description "Interface that acts as clock source";
               type union {
                 type jt:interface-device;
                 type string {
                   pattern "<.*>|$.*";
                 }
               }
             }
           }
         }
       }
       uses apply-advanced;
     }
     leaf link-mode {
       description "Link operational mode";
       type enumeration {
         enum "automatic" {
           description "Automatically negotiate duplex";
         }
         enum "half-duplex" {
           description "Half-duplex operation";
         }
         enum "full-duplex" {
           description "Full-duplex operation";
         }
       }
     }
     leaf media-type {
       description "Interface media type (copper or fiber)";
       type enumeration {
         enum "copper" {
           description "Copper as media";
         }
         enum "fiber" {
           description "Fiber as media";
         }
       }
     }
     leaf encapsulation {
       description "Physical link-layer encapsulation";
       type enumeration {
         enum "ethernet" {
           description "Ethernet physical media";
         }
         enum "fddi" {
           description "FDDI physical media";
         }
         enum "token-ring" {
           description "Token Ring physical media";
         }
         enum "ppp" {
           description "Serial PPP device";
         }
         enum "ppp-ccc" {
           description "Serial PPP device for a cross-connect";
         }
         enum "ppp-tcc" {
           description "Serial PPP device for a translational cross-connect";
         }
         enum "ether-vpls-ppp" {
           description "Ethernet VPLS over PPP (bridging) device";
         }
         enum "frame-relay" {
           description "Frame Relay encapsulation";
         }
         enum "frame-relay-ccc" {
           description "Frame Relay for cross-connect";
         }
         enum "frame-relay-tcc" {
           description "Frame Relay for translational cross-connect";
         }
         enum "extended-frame-relay-ccc" {
           description "Any Frame Relay DLCI for cross-connect";
         }
         enum "extended-frame-relay-tcc" {
           description "Any Frame Relay DLCI for translational cross-connect";
         }
         enum "flexible-frame-relay" {
           description "Multiple Frame Relay encapsulations";
         }
         enum "frame-relay-port-ccc" {
           description "Frame Relay port encapsulation for a cross-connect";
         }
         enum "frame-relay-ether-type" {
           description "Cisco-compatible Frame Relay encapsulation";
         }
         enum "frame-relay-ether-type-tcc" {
           description "Cisco-compatible Frame Relay encapsulation for translational cross-connect";
         }
         enum "extended-frame-relay-ether-type-tcc" {
           description "Cisco-compatible Frame Relay encapsulation any DLCI for translational cross-connect";
         }
         enum "cisco-hdlc" {
           description "Cisco-compatible HDLC framing";
         }
         enum "cisco-hdlc-ccc" {
           description "Cisco-compatible HDLC framing for a cross-connect";
         }
         enum "cisco-hdlc-tcc" {
           description "Cisco-compatible HDLC framing for a translational cross-connect";
         }
         enum "vlan-ccc" {
           description "802.1q tagging for a cross-connect";
         }
         enum "extended-vlan-ccc" {
           description "Nonstandard TPID tagging for a cross-connect";
         }
         enum "ethernet-ccc" {
           description "Ethernet cross-connect";
         }
         enum "flexible-ethernet-services" {
           description "Allows per-unit Ethernet encapsulation configuration";
         }
         enum "smds-dxi" {
           description "SMDS DXI framing";
         }
         enum "atm-pvc" {
           description "ATM permanent virtual circuits";
         }
         enum "atm-ccc-cell-relay" {
           description "ATM cell relay encapsulation for cross-connect";
         }
         enum "ethernet-over-atm" {
           description "Ethernet over ATM encapsulation";
         }
         enum "ethernet-tcc" {
           description "Ethernet translational cross-connect";
         }
         enum "extended-vlan-tcc" {
           description "802.1q tagging for a translational cross-connect";
         }
         enum "multilink-frame-relay-uni-nni" {
           description "Multilink Frame Relay UNI NNI (FRF.16) encapsulation";
         }
         enum "satop" {
           description "Structure-Agnostic TDM over Packet encapsulation";
         }
         enum "cesopsn" {
           description "Structure-Agnostic TDM over Packet encapsulation";
         }
         enum "ima" {
           description "Inverse Multiplexing for ATM";
         }
         enum "ethernet-vpls" {
           description "Ethernet virtual private LAN service";
         }
         enum "ethernet-bridge" {
           description "Ethernet layer-2 bridging";
         }
         enum "vlan-vpls" {
           description "VLAN virtual private LAN service";
         }
         enum "vlan-vci-ccc" {
           description "CCC for VLAN Q-in-Q and ATM VPI/VCI interworking";
         }
         enum "extended-vlan-vpls" {
           description "Extended VLAN virtual private LAN service";
         }
         enum "extended-vlan-bridge" {
           description "VLAN layer-2 bridging";
         }
         enum "multilink-ppp" {
           description "Multilink PPP";
         }
         enum "generic-services" {
           description "Generic services";
         }
       }
     }
     leaf network-isolation-profile {
       description "Attach a network isolation profile on this interface";
       type string;
     }
     container esi {
       description "ESI configuration of multi-homed interface";
       uses apply-advanced;
       container auto-derive {
         description "Auto-derive ESI value for the interface";
         uses apply-advanced;
         choice esitype {
           case case_1 {
             leaf lacp-pe-system-id-and-admin-key {
               description "Auto-derive ESI from lacp pe system-id and admin key";
               type empty;
             }
           }
           case case_2 {
             leaf type-1-lacp {
               description "Auto-generate Type1 ESI LACP";
               type empty;
             }
           }
           case case_3 {
             container type-3-system-mac {
               description "Auto-generate Type3 ESI System-mac";
               uses apply-advanced;
               leaf mac {
                 description "System mac";
                 type jt:mac-unicast;
               }
               leaf local-discriminator {
                 description "Local-discriminator";
                 type union {
                   type string {
                     pattern "<.*>|$.*";
                   }
                   type int32 {
                     range "0 .. 16777215";
                   }
                 }
               }
             }
           }
         }
       }
       leaf identifier {
         description "ESI value for the interface";
         type jt:esi;
       }
       choice mode {
         case case_1 {
           leaf single-active {
             description "Single-active mode";
             type empty;
           }
         }
         case case_2 {
           leaf all-active {
             description "All-active mode";
             type empty;
           }
         }
       }
       container df-election-granularity {
         presence "enable df-election-granularity";
         description "DF Election Granularity Selection ";
         uses apply-advanced;
         choice mode {
           case case_1 {
             container per-esi {
               presence "enable per-esi";
               description "DF Election Granularity Per Esi";
               uses apply-advanced;
               leaf lacp-oos-on-ndf {
                 description "Lacp Oos";
                 type empty;
               }
             }
           }
           case case_2 {
             leaf per-esi-vlan {
               description "Per Esi Vlan";
               type empty;
             }
           }
         }
       }
       container df-election-type {
         presence "enable df-election-type";
         description "DF Election Type";
         uses apply-advanced;
         choice pref_choice {
           case case_1 {
             container preference {
               presence "enable preference";
               description "Preference based DF election";
               uses apply-advanced;
               leaf value {
                 description "Preference value for EVPN Multihoming DF election";
                 default "32767";
                 type union {
                   type string {
                     pattern "<.*>|$.*";
                   }
                   type uint32 {
                     range "0 .. 65535";
                   }
                 }
               }
             }
           }
         }
         choice mod_choice {
           case case_1 {
             container mod {
               presence "enable mod";
               description "MOD based DF election";
             }
           }
         }
       }
       leaf source-bmac {
         description "Unicast Source B-MAC address per ESI for PBB-EVPN";
         type jt:mac-unicast;
       }
     }
     container framing {
       description "Frame type";
       uses apply-advanced;
       choice frame {
         case case_1 {
           leaf lan-phy {
             description "802.3ae 10-Gbps LAN-mode interface";
             type empty;
           }
         }
         case case_2 {
           leaf wan-phy {
             description "802.3ae 10-Gbps WAN-mode interface";
             type empty;
           }
         }
         case case_3 {
           leaf sonet {
             description "SONET framing";
             type empty;
           }
         }
         case case_4 {
           leaf sdh {
             description "SDH framing";
             type empty;
           }
         }
       }
       leaf precise-bandwidth {
         description "Use precise bandwidth for 10G wan-phy interface";
         type empty;
       }
     }
     leaf unidirectional {
       description "Unidirectional Mode";
       type empty;
     }
     container lmi {
       description "Local Management Interface settings";
       uses apply-advanced;
       leaf n391dte {
         description "DTE full status polling interval";
         type union {
           type string {
             pattern "<.*>|$.*";
           }
           type uint16 {
             range "1 .. 255";
           }
         }
       }
       leaf n392dce {
         description "DCE error threshold";
         type union {
           type string {
             pattern "<.*>|$.*";
           }
           type uint16 {
             range "1 .. 10";
           }
         }
       }
       leaf n392dte {
         description "DTE error threshold";
         type union {
           type string {
             pattern "<.*>|$.*";
           }
           type uint16 {
             range "1 .. 10";
           }
         }
       }
       leaf n393dce {
         description "DCE monitored event count";
         type union {
           type string {
             pattern "<.*>|$.*";
           }
           type uint16 {
             range "1 .. 10";
           }
         }
       }
       leaf n393dte {
         description "DTE monitored event count";
         type union {
           type string {
             pattern "<.*>|$.*";
           }
           type uint16 {
             range "1 .. 10";
           }
         }
       }
       leaf t391dte {
         description "DTE polling timer";
         units "seconds";
         type union {
           type string {
             pattern "<.*>|$.*";
           }
           type uint16 {
             range "5 .. 30";
           }
         }
       }
       leaf t392dce {
         description "DCE polling verification timer";
         units "seconds";
         type union {
           type string {
             pattern "<.*>|$.*";
           }
           type uint16 {
             range "5 .. 30";
           }
         }
       }
       leaf lmi-type {
         description "Specify the Frame Relay LMI type";
         type enumeration {
           enum "ansi" {
             description "Use ANSI Annex D LMI";
           }
           enum "itu" {
             description "Use ITU Q933a Annex A LMI";
           }
           enum "c-lmi" {
             description "Use Consortium LMI";
           }
         }
       }
     }
     container mlfr-uni-nni-bundle-options {
       description "Multilink Frame Relay UNI NNI (FRF.16) management settings";
       uses apply-advanced;
       container cisco-interoperability {
         description "FRF.16 Cisco interoperability settings";
         uses apply-advanced;
         leaf send-lip-remove-link-for-link-reject {
           description "Send Link Integrity Protocol remove link on receiving add-link rejection";
           type empty;
         }
       }
       leaf mrru {
         description "Maximum received reconstructed unit";
         units "bytes";
         type union {
           type string {
             pattern "<.*>|$.*";
           }
           type uint16 {
             range "1500 .. 4500";
           }
         }
       }
       leaf yellow-differential-delay {
         description "Yellow differential delay among bundle links to give warning";
         units "milliseconds";
         type union {
           type string {
             pattern "<.*>|$.*";
           }
           type uint16 {
             range "3 .. 2000";
           }
         }
       }
       leaf red-differential-delay {
         description "Red differential delay among bundle links to take action";
         units "milliseconds";
         type union {
           type string {
             pattern "<.*>|$.*";
           }
           type uint16 {
             range "5 .. 2000";
           }
         }
       }
       leaf action-red-differential-delay {
         description "Type of actions when differential delay exceeds red limit";
         type enumeration {
           enum "remove-link" {
             description "Remove bundle link from service when exceeding red limit";
           }
           enum "disable-tx" {
             description "Disable transfer of bundle link when exceeding red limit";
           }
         }
       }
       leaf fragment-threshold {
         description "Fragmentation threshold";
         units "bytes";
         type union {
           type string {
             pattern "<.*>|$.*";
           }
           type uint32 {
             range "64 .. 16320";
           }
         }
       }
       leaf drop-timeout {
         description "Drop timeout";
         units "milliseconds";
         type union {
           type string {
             pattern "<.*>|$.*";
           }
           type uint16 {
             range "0 .. 2000";
           }
         }
       }
       leaf link-layer-overhead {
         description "Link layer bit stuffing overhead (0.0 .. 50.0 percent)";
         type jt:unsigned-float;
       }
       leaf lmi-type {
         description "Specify the multilink Frame Relay UNI NNI LMI type";
         type enumeration {
           enum "ansi" {
             description "Use ANSI Annex D LMI";
           }
           enum "itu" {
             description "Use ITU Q933a Annex A LMI";
           }
           enum "c-lmi" {
             description "Use Consortium LMI";
           }
         }
       }
       leaf minimum-links {
         description "Minimum number of links to sustain the bundle";
         type union {
           type string {
             pattern "<.*>|$.*";
           }
           type uint16 {
             range "1 .. 8";
           }
         }
       }
       leaf hello-timer {
         description "LIP hello timer";
         type union {
           type string {
             pattern "<.*>|$.*";
           }
           type uint16 {
             range "5 .. 180";
           }
         }
       }
       leaf acknowledge-timer {
         description "LIP ack timer";
         type union {
           type string {
             pattern "<.*>|$.*";
           }
           type uint16 {
             range "1 .. 10";
           }
         }
       }
       leaf acknowledge-retries {
         description "LIP ack retry times";
         type union {
           type string {
             pattern "<.*>|$.*";
           }
           type uint16 {
             range "1 .. 5";
           }
         }
       }
       leaf n391 {
         description "Multilink Frame Relay UNI NNI full status polling counter";
         type union {
           type string {
             pattern "<.*>|$.*";
           }
           type uint16 {
             range "1 .. 255";
           }
         }
       }
       leaf n392 {
         description "Multilink Frame Relay UNI NNI LMI error threshold";
         type union {
           type string {
             pattern "<.*>|$.*";
           }
           type uint16 {
             range "1 .. 10";
           }
         }
       }
       leaf n393 {
         description "Multilink Frame Relay UNI NNI LMI monitored event count";
         type union {
           type string {
             pattern "<.*>|$.*";
           }
           type uint16 {
             range "1 .. 10";
           }
         }
       }
       leaf t391 {
         description "Multilink Frame Relay UNI NNI link integrity verify polling timer";
         type union {
           type string {
             pattern "<.*>|$.*";
           }
           type uint16 {
             range "5 .. 30";
           }
         }
       }
       leaf t392 {
         description "Multilink Frame Relay UNI NNI polling verification timer";
         type union {
           type string {
             pattern "<.*>|$.*";
           }
           type uint16 {
             range "5 .. 30";
           }
         }
       }
     }
     leaf mac {
       description "Hardware MAC address";
       type jt:mac-unicast;
     }
     leaf no-forwarding-viable {
       description "Disable forwarding";
       type empty;
     }
     container p4rt {
       description "P4-runtime interfaces";
       uses apply-advanced;
       leaf id {
         description "Port number";
         type union {
           type string {
             pattern "<.*>|$.*";
           }
           type uint64 {
             range "1 .. 4294967296";
           }
         }
       }
       leaf node-id {
         description "Device Id";
         type union {
           type string {
             pattern "<.*>|$.*";
           }
           type uint64 {
             range "1 .. 18446744073709551615";
           }
         }
       }
     }
     container receive-bucket {
       description "Set receive bucket parameters";
       uses dcd_rx_bucket_config;
     }
     container transmit-bucket {
       description "Set transmit bucket parameters";
       uses dcd_tx_bucket_config;
     }
     leaf shared-interface {
       description "Enable shared interface on the interface";
       type empty;
     }
     container sonet-options {
       description "SONET interface-specific options";
       uses sonet_options_type;
     }
     container logical-tunnel-options {
       description "Logical Tunnel interface-specific options";
       uses apply-advanced;
       container link-protection {
         presence "enable link-protection";
         description "Enable link protection mode";
         uses apply-advanced;
         leaf revertive {
           description "Revert back (Default mode) from active backup link to primary, if primary is UP";
           type empty;
         }
         leaf non-revertive {
           description "Do not revert back from active backup link to primary, if primary is UP";
           type empty;
         }
       }
       leaf per-unit-mac-disable {
         description "Disable the creation of per unit mac address on LT IFLs for VPLS/CCC encaps";
         type empty;
       }
       container load-balance {
         uses aggregate-load-balance;
       }
       leaf distribution-list {
         description "Distribution list to which interface belongs";
         type string {
           length "1 .. 20";
         }
       }
     }
     container aggregated-sonet-options {
       description "Aggregated SONET interface-specific options";
       uses apply-advanced;
       leaf minimum-links {
         description "Minimum number of aggregated links";
         type union {
           type string {
             pattern "<.*>|$.*";
           }
           type uint16;
         }
       }
       leaf link-speed {
         description "Aggregated links speed";
         type enumeration {
           enum "oc3" {
             description "Links are OC-3c or STM-1c";
           }
           enum "oc12" {
             description "Links are OC-12c or STM-4c";
           }
           enum "oc48" {
             description "Links are OC-48c or STM-16c";
           }
           enum "oc192" {
             description "Links are OC-192c or STM-64c";
           }
           enum "oc768" {
             description "Links are OC-768c or STM-256c";
           }
           enum "mixed" {
             description "Links are various speeds";
           }
         }
       }
       leaf minimum-bandwidth {
         description "Minimum bandwidth necessary to sustain bundle";
         units "bps";
         type union {
           type string {
             pattern "<.*>|$.*";
           }
           type uint64 {
             range "0 .. 159232000000";
           }
         }
       }
     }
     container atm-options {
       description "ATM interface-specific options";
       uses apply-advanced;
       leaf pic-type {
         description "Type of ATM PIC (ATM I, ATM II or ATM CE)";
         type enumeration {
           enum "atm-ce" {
             description "CE PIC";
           }
           enum "atm2" {
             description "ATM II IQ PIC";
           }
           enum "atm1" {
             description "ATM I PIC";
           }
         }
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf use-null-cw {
         description "Always insert/strip null control words with cell-relay";
         type empty;
       }
       container promiscuous-mode {
         presence "enable promiscuous-mode";
         description "Set ATM interface to promiscuous mode";
         uses apply-advanced;
         list vpi {
           key name;
           ordered-by user;
           description "Open this VPI in promiscuous mode";
           leaf name {
             description "Virtual path index";
             type union {
               type string {
                 pattern "<.*>|$.*";
               }
               type uint32 {
                 range "0 .. 255";
               }
             }
           }
         }
       }
       list vpi {
         key name;
         ordered-by user;
         description "Define a virtual path";
         leaf name {
           description "Virtual path index";
           type union {
             type string {
               pattern "<.*>|$.*";
             }
             type uint32 {
               range "0 .. 255";
             }
           }
         }
         uses apply-advanced;
         leaf maximum-vcs {
           description "Maximum number of virtual circuits on this VP";
           type union {
             type uint32;
             type string {
               pattern "<.*>|$.*";
             }
           }
         }
         container shaping {
           description "Virtual path traffic-shaping options";
           uses dcd_shaping_config;
         }
         container oam-period {
           description "F4 OAM cell period";
           choice oam_period_choices {
             case case_1 {
               leaf oam-period {
                 description "F4 OAM cell period";
                 units "seconds";
                 type union {
                   type string {
                     pattern "<.*>|$.*";
                   }
                   type uint32 {
                     range "1 .. 900";
                   }
                 }
               }
             }
             case case_2 {
               container disable {
                 presence "enable disable";
                 description "Disable F4 OAM loopback";
               }
             }
           }
         }
         container oam-liveness {
           description "F4 OAM virtual path liveness parameters";
           uses apply-advanced;
           leaf up-count {
             description "Number of F4 OAM cells to consider VP up";
             type union {
               type string {
                 pattern "<.*>|$.*";
               }
               type uint32 {
                 range "1 .. 255";
               }
             }
           }
           leaf down-count {
             description "Number of F4 OAM cells to consider VP down";
             type union {
               type string {
                 pattern "<.*>|$.*";
               }
               type uint32 {
                 range "1 .. 255";
               }
             }
           }
         }
       }
       container ilmi {
         presence "enable ilmi";
         description "Enable Interim Local Management Interface";
         uses apply-advanced;
       }
       list linear-red-profiles {
         key name;
         ordered-by user;
         description "ATM2 CoS virtual circuit drop profiles";
         leaf name {
           description "Linear RED profile name";
           type string {
           }
         }
         leaf queue-depth {
           description "Maximum queue depth";
           units "cells";
           type string;
         }
         leaf high-plp-threshold {
           description "Fill level percentage when linear RED is applied for high PLP";
           type union {
             type string {
               pattern "<.*>|$.*";
             }
             type uint32 {
               range "0 .. 100";
             }
           }
         }
         leaf low-plp-threshold {
           description "Fill level percentage when linear RED is applied for low PLP";
           type union {
             type string {
               pattern "<.*>|$.*";
             }
             type uint32 {
               range "0 .. 100";
             }
           }
         }
         leaf high-plp-max-threshold {
           description "Fill level percentage with 100 percent packet drop for high PLP";
           type union {
             type string {
               pattern "<.*>|$.*";
             }
             type uint32 {
               range "0 .. 100";
             }
           }
         }
         leaf low-plp-max-threshold {
           description "Fill level percentage with 100 percent packet drop for low PLP";
           type union {
             type string {
               pattern "<.*>|$.*";
             }
             type uint32 {
               range "0 .. 100";
             }
           }
         }
       }
       list scheduler-maps {
         key name;
         ordered-by user;
         description "ATM2 CoS parameters assigned to forwarding classes";
         leaf name {
           description "ATM2 CoS scheduler map name";
           type string {
           }
         }
         uses apply-advanced;
         leaf vc-cos-mode {
           description "ATM2 virtual circuit CoS mode";
           type enumeration {
             enum "strict" {
               description "Always schedule high priority queue first";
             }
             enum "alternate" {
               description "Every other packet from high priority queue (default)";
             }
           }
         }
         list forwarding-class {
           key name;
           ordered-by user;
           description "Scheduling parameters associated with forwarding class";
           leaf name {
             description "Forwarding class name";
             type string {
             }
           }
           uses apply-advanced;
           leaf priority {
             description "Queuing priority assigned to forwarding class";
             type enumeration {
               enum "low" {
                 description "Low priority queuing";
               }
               enum "high" {
                 description "High priority queuing";
               }
             }
           }
           container transmit-weight {
             description "Transmit weight";
             choice weight-method {
               case case_1 {
                 leaf percent {
                   description "Transmit weight as percentage";
                   type union {
                     type string {
                       pattern "<.*>|$.*";
                     }
                     type uint32 {
                       range "5 .. 100";
                     }
                   }
                 }
               }
               case case_2 {
                 leaf cells {
                   description "Transmit weight by cells count";
                   type string;
                 }
               }
             }
           }
           choice drop-profile-method {
             case case_1 {
               container epd-threshold {
                 description "Early packet discard threshold for ATM2";
                 uses epd_threshold_config;
               }
             }
             case case_2 {
               leaf linear-red-profile {
                 description "Linear RED profile profile name";
                 type string;
               }
             }
           }
         }
       }
       container mpls {
         description "MPLS options";
         uses mpls_ifd_options;
       }
       choice payload-scrambler-choice {
         leaf payload-scrambler {
           description "Enable payload scrambling";
           type empty;
         }
         leaf no-payload-scrambler {
           description "Don't enable payload scrambling";
           type empty;
         }
       }
     }
     container multiservice-options {
       description "Multiservice interface-specific options";
       uses apply-advanced;
       choice syslog-choice {
         leaf syslog {
           description "Enable system logging on this interface";
           type empty;
         }
         leaf no-syslog {
           description "Don't enable system logging on this interface";
           type empty;
         }
       }
       choice core-dump-choice {
         leaf core-dump {
           description "Enable core dumping on this interface";
           type empty;
         }
         leaf no-core-dump {
           description "Don't enable core dumping on this interface";
           type empty;
         }
       }
       choice dump-on-flow-control-choice {
         leaf dump-on-flow-control {
           description "Enable dumping for this interface on prolonged flow-control";
           status deprecated;
           type empty;
         }
         leaf no-dump-on-flow-control {
           description "Don't enable dumping for this interface on prolonged flow-control";
           status deprecated;
           type empty;
         }
       }
       choice reset-on-flow-control-choice {
         leaf reset-on-flow-control {
           description "Enable resetting this interface on prolonged flow-control";
           status deprecated;
           type empty;
         }
         leaf no-reset-on-flow-control {
           description "Don't enable resetting this interface on prolonged flow-control";
           status deprecated;
           type empty;
         }
       }
       container flow-control-options {
         description "Flow control configuration";
         uses apply-advanced;
         leaf dump-on-flow-control {
           description "Cause core dump during prolonged flow-control";
           type empty;
         }
         leaf reset-on-flow-control {
           description "Reset interface during prolonged flow-control";
           type empty;
         }
         leaf down-on-flow-control {
           description "Bring interface down during prolonged flow-control";
           type empty;
         }
         leaf up-on-flow-control {
           description "Keep interface up during prolonged flow-control";
           type empty;
         }
       }
     }
     container ggsn-options {
       description "GGSN interface-specific options";
       uses apply-advanced;
       choice syslog-choice {
         leaf syslog {
           description "Enable system logging on this interface";
           type empty;
         }
         leaf no-syslog {
           description "Don't enable system logging on this interface";
           type empty;
         }
       }
       choice core-dump-choice {
         leaf core-dump {
           description "Enable core dumping on this interface";
           type empty;
         }
         leaf no-core-dump {
           description "Don't enable core dumping on this interface";
           type empty;
         }
       }
     }
     container ppp-options {
       description "Point-to-Point Protocol (PPP) interface-specific options";
       uses ppp_options_type;
     }
     container redundancy-options {
       description "Redundancy options";
       uses apply-advanced;
       leaf primary {
         description "Specify the primary interface";
         type union {
           type jt:interface-device;
           type string {
             pattern "<.*>|$.*";
           }
         }
       }
       leaf secondary {
         description "Specify the secondary interface";
         type union {
           type jt:interface-device;
           type string {
             pattern "<.*>|$.*";
           }
         }
       }
       container redundancy-peer {
         description "Specify information for peer";
         uses apply-advanced;
         leaf ipaddress {
           description "Specify the IP address";
           type jt:ipv4addr;
         }
       }
       container redundancy-local {
         description "Specify information for the local peer";
         uses apply-advanced;
         leaf data-address {
           description "Specify the HA local data IP address";
           type jt:ipv4addr;
         }
       }
       leaf routing-instance {
         description "Specify routing-instance for the HA traffic";
         type string;
       }
       leaf replication-threshold {
         description "Duration for which flow should remain active for replication";
         default "180";
         units "seconds";
         type union {
           type string {
             pattern "<.*>|$.*";
           }
           type uint32 {
             range "60 .. 3600";
           }
         }
       }
       container replication-options {
         description "Specify state replication attributes";
         uses apply-advanced;
         leaf mtu {
           description "Specify the maximal packet size for replicated data";
           default "1500";
           type union {
             type string {
               pattern "<.*>|$.*";
             }
             type uint32 {
               range "1500 .. 8000";
             }
           }
         }
       }
       container replicate-services {
         description "Replicate services state from active to backup";
         uses apply-advanced;
         leaf pgcp {
           description "Replicate the PGCP service state";
           type empty;
         }
       }
     }
     container load-balancing-options {
       description "Load-balancing on services pics";
       uses apply-advanced;
       list member-interface {
         key name;
         max-elements 36;
         leaf name {
           description "Interface name";
           type union {
             type jt:interface-device;
             type string {
               pattern "<.*>|$.*";
             }
           }
         }
         uses apply-advanced;
         container redundancy-group {
           description "Group id to represent a pair of active-backup mams";
           leaf description {
             description "Text description mapping the redundancy group id";
             type string;
           }
           leaf group-id {
             description "Value for Redundancy-group";
             type union {
               type string {
                 pattern "<.*>|$.*";
               }
               type uint32 {
                 range "1 .. 18";
               }
             }
           }
         }
       }
       container member-failure-options {
         description "Load balancing member failure handling options";
         uses apply-advanced;
         choice member-failure {
           case case_1 {
             container redistribute-all-traffic {
               presence "enable redistribute-all-traffic";
               description "On a member failure, redistribute traffic to ams";
               uses apply-advanced;
               leaf enable-rejoin {
                 description "Failed member can rejoin after recovery";
                 type empty;
               }
             }
           }
           case case_2 {
             container drop-member-traffic {
               presence "enable drop-member-traffic";
               description "On a member failure, drop its traffic";
               uses apply-advanced;
               leaf rejoin-timeout {
                 description "Wait time(in seconds) for failed member to rejoin";
                 default "120";
                 type union {
                   type string {
                     pattern "<.*>|$.*";
                   }
                   type uint32 {
                     range "0 .. 1000";
                   }
                 }
               }
               leaf enable-rejoin {
                 description "Failed member can join after recovery";
                 type empty;
               }
             }
           }
         }
       }
       leaf no-bundle-flap {
         description "No bundle flap on member addition - recommended only with IPSec services";
         type empty;
       }
       container high-availability-options {
         description "High Availability options for Load-balancing";
         uses apply-advanced;
         choice ha-type {
           case case_1 {
             container many-to-one {
               description "N:1 High Availability model";
               uses apply-advanced;
               leaf preferred-backup {
                 description "Preferred backup Interface name";
                 type union {
                   type jt:interface-device;
                   type string {
                     pattern "<.*>|$.*";
                   }
                 }
               }
             }
           }
           case case_2 {
             container one-to-one {
               description "1:1 High Availability model";
               uses apply-advanced;
               list redundancy-group {
                 key name;
                 ordered-by user;
                 description "Group number for linking HA member for intra-chassis";
                 leaf name {
                   description "Value for HA Redundancy-group";
                   type union {
                     type string {
                       pattern "<.*>|$.*";
                     }
                     type uint32 {
                       range "1 .. 18";
                     }
                   }
                 }
                 leaf preferred-backup {
                   description "Preferred backup Interface name for Redundancy group";
                   type union {
                     type jt:interface-device;
                     type string {
                       pattern "<.*>|$.*";
                     }
                   }
                 }
               }
               leaf preferred-backup {
                 description "Preferred backup Interface name";
                 type union {
                   type jt:interface-device;
                   type string {
                     pattern "<.*>|$.*";
                   }
                 }
               }
             }
           }
         }
       }
     }
     container aggregated-inline-services-options {
       description "Aggregated Inline Service interface specific options";
       uses apply-advanced;
       leaf primary-interface {
         description "Specify the primary interface";
         type union {
           type jt:interface-device;
           type string {
             pattern "<.*>|$.*";
           }
         }
       }
       leaf secondary-interface {
         description "Specify the secondary interface";
         type union {
           type jt:interface-device;
           type string {
             pattern "<.*>|$.*";
           }
         }
       }
     }
     container anchoring-options {
       description "Groups anchoring PFEs or FPCs together.";
       uses apply-advanced;
       leaf apfe-group-set {
         description "Ties up different anchoring groups to share similar fate";
         type string {
           length "1 .. 32";
         }
       }
       list primary-list {
         key name;
         description "Primary anchoring PFE name.";
         leaf name {
           description "Anchoring PFE name.";
           type string {
           }
         }
         uses apply-advanced;
       }
       container secondary {
         presence "enable secondary";
         description "Secondary anchoring PFE name.";
         uses apply-advanced;
         leaf anchoring-device-name {
           description "Anchoring PFE name.";
           type string {
           }
         }
       }
       choice mode {
         case case_1 {
           leaf warm-standby {
             description "Delayed failover to secondary when primary fails";
             type empty;
           }
         }
       }
     }
     container lsq-failure-options {
       description "Link services queuing failure options";
       uses apply-advanced;
       list trigger-link-failure {
         key name;
         ordered-by user;
         description "Link on which to trigger failure";
         leaf name {
           description "Interface name";
           type union {
             type jt:interface-device;
             type string {
               pattern "<.*>|$.*";
             }
           }
         }
         uses apply-advanced;
       }
       choice no-termination-request-choice {
         leaf no-termination-request {
           description "Do not send PPP termination requests";
           type empty;
         }
         leaf no-no-termination-request {
           description "Don't do not send PPP termination requests";
           type empty;
         }
       }
     }
     container redundancy-group {
       description "Redundancy group configuration";
       uses apply-advanced;
       list member-interface {
         key name;
         description "Member interface for the redundancy group";
         leaf name {
           description "Interface name of member";
           type union {
             type jt:interface-device;
             type string {
               pattern "<.*>|$.*";
             }
           }
         }
         uses apply-advanced;
         choice redundancy {
           case case_1 {
             leaf active {
               description "Active interface";
               type empty;
             }
           }
           case case_2 {
             leaf backup {
               description "Backup interface";
               type empty;
             }
           }
         }
       }
       leaf maximum-links {
         type union {
           type string {
             pattern "<.*>|$.*";
           }
           type uint32 {
             range "2 .. 32";
           }
         }
       }
     }
     container services-options {
       description "Services interface-specific options";
       uses apply-advanced;
       container syslog {
         description "Define system log parameters";
         uses log-object;
       }
       container jflow-log {
         description "Define Jflow-log parameters.";
         uses apply-advanced;
         leaf message-rate-limit {
           description "Maximum jflow-log NAT error events allowed per second from this interface";
           units "messages per second";
           type union {
             type string {
               pattern "<.*>|$.*";
             }
             type uint32 {
               range "1 .. 2147483647";
             }
           }
         }
       }
       container deterministic-nat-configuration-log-interval {
         presence "enable deterministic-nat-configuration-log-interval";
         description "Define Deterministic NAT parameters";
         uses apply-advanced;
         leaf interval {
           description "Interval in which deterministic NAT logs are generated";
           units "seconds";
           type union {
             type string {
               pattern "<.*>|$.*";
             }
             type uint32 {
               range "1800 .. 86400";
             }
           }
         }
       }
       leaf open-timeout {
         description "Timeout period for TCP session establishment";
         units "seconds";
         type union {
           type string {
             pattern "<.*>|$.*";
           }
           type uint32 {
             range "4 .. 300";
           }
         }
       }
       leaf close-timeout {
         description "Timeout period for TCP session tear-down";
         units "seconds";
         type union {
           type string {
             pattern "<.*>|$.*";
           }
           type uint32 {
             range "2 .. 300";
           }
         }
       }
       leaf inactivity-timeout {
         description "Inactivity timeout period for established sessions (4..86400)";
         units "seconds";
         type union {
           type uint32;
           type string {
             pattern "<.*>|$.*";
           }
         }
       }
       leaf inactivity-tcp-timeout {
         description "Inactivity timeout period for TCP established sessions";
         units "seconds";
         type union {
           type string {
             pattern "<.*>|$.*";
           }
           type uint32 {
             range "4 .. 86400";
           }
         }
       }
       leaf inactivity-asymm-tcp-timeout {
         description "Inactivity timeout period for asymmetric TCP established sessions";
         units "seconds";
         type union {
           type string {
             pattern "<.*>|$.*";
           }
           type uint32 {
             range "4 .. 86400";
           }
         }
       }
       leaf inactivity-non-tcp-timeout {
         description "Inactivity timeout period for non-TCP established sessions";
         units "seconds";
         type union {
           type string {
             pattern "<.*>|$.*";
           }
           type uint32 {
             range "4 .. 86400";
           }
         }
       }
       leaf session-timeout {
         description "Session timeout period for established sessions";
         units "seconds";
         type union {
           type string {
             pattern "<.*>|$.*";
           }
           type uint32 {
             range "4 .. 86400";
           }
         }
       }
       leaf disable-global-timeout-override {
         description "Disallow overriding  global inactivity or session timeout";
         type empty;
       }
       leaf tcp-tickles {
         description "Number of TCP keep-alive packets to be sent for bi-directional TCP flows";
         default "4";
         type union {
           type string {
             pattern "<.*>|$.*";
           }
           type uint8 {
             range "0 .. 30";
           }
         }
       }
       container trio-flow-offload {
         presence "enable trio-flow-offload";
         description "Allow PIC to offload flows to Trio-based PFE";
         uses apply-advanced;
         leaf minimum-bytes {
           description "Attempt flow offload after minimum bytes are seen on the flow";
           type union {
             type uint32;
             type string {
               pattern "<.*>|$.*";
             }
           }
         }
       }
       leaf fragment-limit {
         description "Maximum number of fragments allowed for a packet";
         default "64";
         type union {
           type string {
             pattern "<.*>|$.*";
           }
           type uint8 {
             range "1 .. 250";
           }
         }
       }
       leaf reassembly-timeout {
         description "Re-assembly timeout (seconds) for fragments of a packet";
         default "4";
         units "seconds";
         type union {
           type string {
             pattern "<.*>|$.*";
           }
           type uint8 {
             range "1 .. 60";
           }
         }
       }
       leaf cgn-pic {
         description "PIC will be used for Carrier Grade NAT configuration only";
         type empty;
       }
       leaf pba-interim-logging-interval {
         description "Interim logging interval in seconds";
         default "0";
         units "seconds";
         type union {
           type string {
             pattern "<.*>|$.*";
           }
           type uint32 {
             range "0 .. 86400";
           }
         }
       }
       container session-limit {
         presence "enable session-limit";
         description "Session limit";
         uses apply-advanced;
         leaf maximum {
           description "Maximum number of sessions allowed simultaneously";
           type string;
         }
         leaf rate {
           description "Maximum number of new sessions allowed per second";
           type string;
         }
         leaf cpu-load-threshold {
           description "CPU limit in percentage for auto-tuning of session rate";
           units "percent";
           type union {
             type string {
               pattern "<.*>|$.*";
             }
             type uint8 {
               range "1 .. 100";
             }
           }
         }
       }
       leaf enable-subscriber-analysis {
         description "Enable subscriber analysis on the interface";
         type empty;
       }
       leaf disable-subscriber-analysis {
         description "Disable subscriber analysis on the interface";
         type empty;
       }
       leaf disable-usp-tracing {
         description "Disable usp tracing on this pic";
         type empty;
       }
       leaf disable-drop-flows {
         description "Disable drop flows on this pic";
         type empty;
       }
       container ignore-errors {
         presence "enable ignore-errors";
         description "Ignore anomalies or errors";
         leaf tcp {
           description "TCP protocol errors";
           type empty;
         }
         leaf alg {
           description "ALG anomalies or errors";
           type empty;
         }
       }
       container capture {
         description "Packet capture for SFW and NAT on the Services PIC";
         uses apply-advanced;
         leaf capture-size {
           description "The number of packets to store";
           type union {
             type string {
               pattern "<.*>|$.*";
             }
             type uint32 {
               range "1 .. 344000";
             }
           }
         }
         leaf pkt-size {
           description "Number of bytes to be saved from each packet";
           type union {
             type string {
               pattern "<.*>|$.*";
             }
             type uint16 {
               range "64 .. 15000";
             }
           }
         }
         leaf logs-per-packet {
           description "The number of trace messages stored for each packet";
           type union {
             type string {
               pattern "<.*>|$.*";
             }
             type uint16 {
               range "0 .. 500";
             }
           }
         }
         leaf max-log-line-size {
           description "The maximum length of a stored trace message";
           type union {
             type uint8;
             type string {
               pattern "<.*>|$.*";
             }
           }
         }
         container filter {
           presence "enable filter";
           description "Filtering options for the packet capture";
           uses apply-advanced;
           container source-ip {
             description "Filter based on source-ip (and wildcard)";
             leaf ip {
               description "Source IP";
               type jt:ipaddr;
             }
             leaf wildcard {
               description "Source IP wildcard";
               type jt:ipaddr;
             }
           }
           container dest-ip {
             description "Filter based on dest-ip (and wildcard)";
             leaf ip {
               description "Dest IP";
               type jt:ipaddr;
             }
             leaf wildcard {
               description "Dest IP wildcard";
               type jt:ipaddr;
             }
           }
           container sw-sip {
             description "Filter based on source softwire ip (and wildcard)";
             leaf ip {
               description "Source softwire IP";
               type jt:ipv6addr;
             }
             leaf wildcard {
               description "Source IP wildcard";
               type jt:ipv6addr;
             }
           }
           container sw-dip {
             description "Filter based on destination softwire ip (and wildcard)";
             leaf ip {
               description "Destination softwire IP";
               type jt:ipaddr;
             }
             leaf wildcard {
               description "Destination IP wildcard";
               type jt:ipaddr;
             }
           }
           container sport-range {
             description "Filter based on source port";
             leaf low {
               description "Source port range start";
               type union {
                 type uint16;
                 type string {
                   pattern "<.*>|$.*";
                 }
               }
             }
             leaf high {
               description "Source port range end";
               type union {
                 type uint16;
                 type string {
                   pattern "<.*>|$.*";
                 }
               }
             }
           }
           container dport-range {
             description "Filter based on destination port";
             leaf low {
               description "Destination port range start";
               type union {
                 type uint16;
                 type string {
                   pattern "<.*>|$.*";
                 }
               }
             }
             leaf high {
               description "Destination port range end";
               type union {
                 type uint16;
                 type string {
                   pattern "<.*>|$.*";
                 }
               }
             }
           }
           leaf proto {
             description "Filter based on L4 protocol";
             type enumeration {
               enum "icmp" {
               }
               enum "tcp" {
               }
               enum "udp" {
               }
             }
           }
         }
       }
       container flow {
         description "Define flow parameters";
         uses apply-advanced;
         container traceoptions {
           description "Trace options for flow services";
           uses flow-traceoptions-object;
         }
       }
       leaf fpc-pic-information {
         description "Include FPC and PIC slot number in the syslogs";
         type empty;
       }
       leaf utc-timestamp {
         description "Use UTC time for security log timestamps";
         type empty;
       }
       leaf syslog-local-system-timestamp {
         description "Use local system time for services syslog timestamp";
         type empty;
       }
     }
     container t3-options {
       description "T3 interface-specific options";
       uses apply-advanced;
       leaf loopback {
         description "Loopback mode";
         type enumeration {
           enum "local" {
             description "Local loopback";
           }
           enum "remote" {
             description "Remote loopback";
           }
           enum "payload" {
             description "Payload loopback";
           }
         }
       }
       choice long-buildout-choice {
         leaf long-buildout {
           description "Set hardware to drive line longer than 255 feet";
           type empty;
         }
         leaf no-long-buildout {
           description "Don't set hardware to drive line longer than 255 feet";
           type empty;
         }
       }
       choice loop-timing-choice {
         leaf loop-timing {
           description "Set loop timing for T3";
           type empty;
         }
         leaf no-loop-timing {
           description "Don't set loop timing for T3";
           type empty;
         }
       }
       choice unframed-choice {
         leaf unframed {
           description "Enable unframed mode";
           type empty;
         }
         leaf no-unframed {
           description "Don't enable unframed mode";
           type empty;
         }
       }
       container compatibility-mode {
         description "Set CSU compatibility mode";
         choice vendor {
           case case_1 {
             container larscom {
               presence "enable larscom";
               description "Compatible with Larscom CSU";
               leaf subrate {
                 description "Set subrate value";
                 type union {
                   type string {
                     pattern "<.*>|$.*";
                   }
                   type uint32 {
                     range "1 .. 14";
                   }
                 }
               }
             }
           }
           case case_2 {
             container verilink {
               presence "enable verilink";
               description "Compatible with Verilink CSU (not on 2/4-port T3 PIC)";
               leaf subrate {
                 description "Set subrate value";
                 type union {
                   type string {
                     pattern "<.*>|$.*";
                   }
                   type uint32 {
                     range "1 .. 28";
                   }
                 }
               }
             }
           }
           case case_3 {
             container adtran {
               presence "enable adtran";
               description "Compatible with Adtran CSU (not on 2/4-port T3 PIC)";
               leaf subrate {
                 description "Set subrate value";
                 type union {
                   type string {
                     pattern "<.*>|$.*";
                   }
                   type uint32 {
                     range "1 .. 588";
                   }
                 }
               }
             }
           }
           case case_4 {
             container kentrox {
               presence "enable kentrox";
               description "Compatible with Kentrox CSU";
               leaf subrate {
                 description "Set subrate value (not on 2/4-port T3 PIC)";
                 type union {
                   type string {
                     pattern "<.*>|$.*";
                   }
                   type uint32 {
                     range "1 .. 69";
                   }
                 }
               }
             }
           }
           case case_5 {
             container digital-link {
               presence "enable digital-link";
               description "Compatible with Digital Link CSU";
               leaf subrate {
                 description "Set subrate value";
                 type enumeration {
                   enum "301Kb" {
                     description "301 Kbps";
                   }
                   enum "601Kb" {
                     description "601 Kbps";
                   }
                   enum "902Kb" {
                     description "902 Kbps";
                   }
                   enum "1.2Mb" {
                     description "1.2 Mbps";
                   }
                   enum "1.5Mb" {
                     description "1.5 Mbps";
                   }
                   enum "1.8Mb" {
                     description "1.8 Mbps";
                   }
                   enum "2.1Mb" {
                     description "2.1 Mbps";
                   }
                   enum "2.4Mb" {
                     description "2.4 Mbps";
                   }
                   enum "2.7Mb" {
                     description "2.7 Mbps";
                   }
                   enum "3.0Mb" {
                     description "3.0 Mbps";
                   }
                   enum "3.3Mb" {
                     description "3.3 Mbps";
                   }
                   enum "3.6Mb" {
                     description "3.6 Mbps";
                   }
                   enum "3.9Mb" {
                     description "3.9 Mbps";
                   }
                   enum "4.2Mb" {
                     description "4.2 Mbps";
                   }
                   enum "4.5Mb" {
                     description "4.5 Mbps";
                   }
                   enum "4.8Mb" {
                     description "4.8 Mbps";
                   }
                   enum "5.1Mb" {
                     description "5.1 Mbps";
                   }
                   enum "5.4Mb" {
                     description "5.4 Mbps";
                   }
                   enum "5.7Mb" {
                     description "5.7 Mbps";
                   }
                   enum "6.0Mb" {
                     description "6.0 Mbps";
                   }
                   enum "6.3Mb" {
                     description "6.3 Mbps";
                   }
                   enum "6.6Mb" {
                     description "6.6 Mbps";
                   }
                   enum "6.9Mb" {
                     description "6.9 Mbps";
                   }
                   enum "7.2Mb" {
                     description "7.2 Mbps";
                   }
                   enum "7.5Mb" {
                     description "7.5 Mbps";
                   }
                   enum "7.8Mb" {
                     description "7.8 Mbps";
                   }
                   enum "8.1Mb" {
                     description "8.1 Mbps";
                   }
                   enum "8.4Mb" {
                     description "8.4 Mbps";
                   }
                   enum "8.7Mb" {
                     description "8.7 Mbps";
                   }
                   enum "9.0Mb" {
                     description "9.0 Mbps";
                   }
                   enum "9.3Mb" {
                     description "9.3 Mbps";
                   }
                   enum "9.6Mb" {
                     description "9.6 Mbps";
                   }
                   enum "9.9Mb" {
                     description "9.9 Mbps";
                   }
                   enum "10.2Mb" {
                     description "10.2 Mbps";
                   }
                   enum "10.5Mb" {
                     description "10.5 Mbps";
                   }
                   enum "10.8Mb" {
                     description "10.8 Mbps";
                   }
                   enum "11.1Mb" {
                     description "11.1 Mbps";
                   }
                   enum "11.4Mb" {
                     description "11.4 Mbps";
                   }
                   enum "11.7Mb" {
                     description "11.7 Mbps";
                   }
                   enum "12.0Mb" {
                     description "12.0 Mbps";
                   }
                   enum "12.3Mb" {
                     description "12.3 Mbps";
                   }
                   enum "12.6Mb" {
                     description "12.6 Mbps";
                   }
                   enum "12.9Mb" {
                     description "12.9 Mbps";
                   }
                   enum "13.2Mb" {
                     description "13.2 Mbps";
                   }
                   enum "13.5Mb" {
                     description "13.5 Mbps";
                   }
                   enum "13.8Mb" {
                     description "13.8 Mbps";
                   }
                   enum "14.1Mb" {
                     description "14.1 Mbps";
                   }
                   enum "14.4Mb" {
                     description "14.4 Mbps";
                   }
                   enum "14.7Mb" {
                     description "14.7 Mbps";
                   }
                   enum "15.0Mb" {
                     description "15.0 Mbps";
                   }
                   enum "15.3Mb" {
                     description "15.3 Mbps";
                   }
                   enum "15.6Mb" {
                     description "15.6 Mbps";
                   }
                   enum "15.9Mb" {
                     description "15.9 Mbps";
                   }
                   enum "16.2Mb" {
                     description "16.2 Mbps";
                   }
                   enum "16.5Mb" {
                     description "16.5 Mbps";
                   }
                   enum "16.8Mb" {
                     description "16.8 Mbps";
                   }
                   enum "17.1Mb" {
                     description "17.1 Mbps";
                   }
                   enum "17.4Mb" {
                     description "17.4 Mbps";
                   }
                   enum "17.7Mb" {
                     description "17.7 Mbps";
                   }
                   enum "18.0Mb" {
                     description "18.0 Mbps";
                   }
                   enum "18.3Mb" {
                     description "18.3 Mbps";
                   }
                   enum "18.6Mb" {
                     description "18.6 Mbps";
                   }
                   enum "18.9Mb" {
                     description "18.9 Mbps";
                   }
                   enum "19.2Mb" {
                     description "19.2 Mbps";
                   }
                   enum "19.5Mb" {
                     description "19.5 Mbps";
                   }
                   enum "19.8Mb" {
                     description "19.8 Mbps";
                   }
                   enum "20.1Mb" {
                     description "20.1 Mbps";
                   }
                   enum "20.5Mb" {
                     description "20.5 Mbps";
                   }
                   enum "20.8Mb" {
                     description "20.8 Mbps";
                   }
                   enum "21.1Mb" {
                     description "21.1 Mbps";
                   }
                   enum "21.4Mb" {
                     description "21.4 Mbps";
                   }
                   enum "21.7Mb" {
                     description "21.7 Mbps";
                   }
                   enum "22.0Mb" {
                     description "22.0 Mbps";
                   }
                   enum "22.3Mb" {
                     description "22.3 Mbps";
                   }
                   enum "22.6Mb" {
                     description "22.6 Mbps";
                   }
                   enum "22.9Mb" {
                     description "22.9 Mbps";
                   }
                   enum "23.2Mb" {
                     description "23.2 Mbps";
                   }
                   enum "23.5Mb" {
                     description "23.5 Mbps";
                   }
                   enum "23.8Mb" {
                     description "23.8 Mbps";
                   }
                   enum "24.1Mb" {
                     description "24.1 Mbps";
                   }
                   enum "24.4Mb" {
                     description "24.4 Mbps";
                   }
                   enum "24.7Mb" {
                     description "24.7 Mbps";
                   }
                   enum "25.0Mb" {
                     description "25.0 Mbps";
                   }
                   enum "25.3Mb" {
                     description "25.3 Mbps";
                   }
                   enum "25.6Mb" {
                     description "25.6 Mbps";
                   }
                   enum "25.9Mb" {
                     description "25.9 Mbps";
                   }
                   enum "26.2Mb" {
                     description "26.2 Mbps";
                   }
                   enum "26.5Mb" {
                     description "26.5 Mbps";
                   }
                   enum "26.8Mb" {
                     description "26.8 Mbps";
                   }
                   enum "27.1Mb" {
                     description "27.1 Mbps";
                   }
                   enum "27.4Mb" {
                     description "27.4 Mbps";
                   }
                   enum "27.7Mb" {
                     description "27.7 Mbps";
                   }
                   enum "28.0Mb" {
                     description "28.0 Mbps";
                   }
                   enum "28.3Mb" {
                     description "28.3 Mbps";
                   }
                   enum "28.6Mb" {
                     description "28.6 Mbps";
                   }
                   enum "28.9Mb" {
                     description "28.9 Mbps";
                   }
                   enum "29.2Mb" {
                     description "29.2 Mbps";
                   }
                   enum "29.5Mb" {
                     description "29.5 Mbps";
                   }
                   enum "29.8Mb" {
                     description "29.8 Mbps";
                   }
                   enum "30.1Mb" {
                     description "30.1 Mbps";
                   }
                   enum "30.4Mb" {
                     description "30.4 Mbps";
                   }
                   enum "30.7Mb" {
                     description "30.7 Mbps";
                   }
                   enum "31.0Mb" {
                     description "31.0 Mbps";
                   }
                   enum "31.3Mb" {
                     description "31.3 Mbps";
                   }
                   enum "31.6Mb" {
                     description "31.6 Mbps";
                   }
                   enum "31.9Mb" {
                     description "31.9 Mbps";
                   }
                   enum "32.2Mb" {
                     description "32.2 Mbps";
                   }
                   enum "32.5Mb" {
                     description "32.5 Mbps";
                   }
                   enum "32.8Mb" {
                     description "32.8 Mbps";
                   }
                   enum "33.1Mb" {
                     description "33.1 Mbps";
                   }
                   enum "33.4Mb" {
                     description "33.4 Mbps";
                   }
                   enum "33.7Mb" {
                     description "33.7 Mbps";
                   }
                   enum "34.0Mb" {
                     description "34.0 Mbps";
                   }
                   enum "34.3Mb" {
                     description "34.3 Mbps";
                   }
                   enum "34.6Mb" {
                     description "34.6 Mbps";
                   }
                   enum "34.9Mb" {
                     description "34.9 Mbps";
                   }
                   enum "35.2Mb" {
                     description "35.2 Mbps";
                   }
                   enum "35.5Mb" {
                     description "35.5 Mbps";
                   }
                   enum "35.8Mb" {
                     description "35.8 Mbps";
                   }
                   enum "36.1Mb" {
                     description "36.1 Mbps";
                   }
                   enum "36.4Mb" {
                     description "36.4 Mbps";
                   }
                   enum "36.7Mb" {
                     description "36.7 Mbps";
                   }
                   enum "37.0Mb" {
                     description "37.0 Mbps";
                   }
                   enum "37.3Mb" {
                     description "37.3 Mbps";
                   }
                   enum "37.6Mb" {
                     description "37.6 Mbps";
                   }
                   enum "37.9Mb" {
                     description "37.9 Mbps";
                   }
                   enum "38.2Mb" {
                     description "38.2 Mbps";
                   }
                   enum "38.5Mb" {
                     description "38.5 Mbps";
                   }
                   enum "38.8Mb" {
                     description "38.8 Mbps";
                   }
                   enum "39.1Mb" {
                     description "39.1 Mbps";
                   }
                   enum "39.4Mb" {
                     description "39.4 Mbps";
                   }
                   enum "39.7Mb" {
                     description "39.7 Mbps";
                   }
                   enum "40.0Mb" {
                     description "40.0 Mbps";
                   }
                   enum "40.3Mb" {
                     description "40.3 Mbps";
                   }
                   enum "40.6Mb" {
                     description "40.6 Mbps";
                   }
                   enum "40.9Mb" {
                     description "40.9 Mbps";
                   }
                   enum "41.2Mb" {
                     description "41.2 Mbps";
                   }
                   enum "41.5Mb" {
                     description "41.5 Mbps";
                   }
                   enum "41.8Mb" {
                     description "41.8 Mbps";
                   }
                   enum "42.1Mb" {
                     description "42.1 Mbps";
                   }
                   enum "42.4Mb" {
                     description "42.4 Mbps";
                   }
                   enum "42.7Mb" {
                     description "42.7 Mbps";
                   }
                   enum "43.0Mb" {
                     description "43.0 Mbps";
                   }
                   enum "43.3Mb" {
                     description "43.3 Mbps";
                   }
                   enum "43.6Mb" {
                     description "43.6 Mbps";
                   }
                   enum "43.9Mb" {
                     description "43.9 Mbps";
                   }
                   enum "44.2Mb" {
                     description "44.2 Mbps";
                   }
                 }
               }
             }
           }
         }
       }
       choice payload-scrambler-choice {
         leaf payload-scrambler {
           description "Enable payload scrambling";
           type empty;
         }
         leaf no-payload-scrambler {
           description "Don't enable payload scrambling";
           type empty;
         }
       }
       choice cbit-parity-choice {
         leaf cbit-parity {
           description "Enable C-bit parity mode";
           type empty;
         }
         leaf no-cbit-parity {
           description "Don't enable C-bit parity mode";
           type empty;
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       choice feac-loop-respond-choice {
         leaf feac-loop-respond {
           description "Respond to FEAC loop requests";
           type empty;
         }
         leaf no-feac-loop-respond {
           description "Don't respond to FEAC loop requests";
           type empty;
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
       leaf buildout {
         description "Line buildout";
         units "feet";
         type union {
           type string {
             pattern "<.*>|$.*";
           }
           type uint32 {
             range "0 .. 450";
           }
         }
       }
       leaf atm-encapsulation {
         description "DS-3 interface encapsulation";
         type enumeration {
           enum "plcp" {
             description "PLCP encapsulation";
           }
           enum "direct" {
             description "ATM direct mapping";
           }
         }
       }
     }
     container e3-options {
       description "E3 interface-specific options";
       uses apply-advanced;
       leaf loopback {
         description "Loopback mode";
         type enumeration {
           enum "local" {
             description "Local loopback";
           }
           enum "remote" {
             description "Remote loopback";
           }
         }
       }
       choice unframed-choice {
         leaf unframed {
           description "Enable unframed mode";
           type empty;
         }
         leaf no-unframed {
           description "Don't enable unframed mode";
           type empty;
         }
       }
       container compatibility-mode {
         description "Set CSU compatibility mode";
         choice vendor {
           case case_1 {
             leaf larscom {
               description "Compatible with Larscom CSU (only non IQ E3 interfaces)";
               type empty;
             }
           }
           case case_2 {
             container digital-link {
               presence "enable digital-link";
               description "Compatible with Digital Link CSU";
               leaf subrate {
                 description "Set subrate value";
                 type enumeration {
                   enum "358Kb" {
                     description "358 Kbps";
                   }
                   enum "716Kb" {
                     description "716 Kbps";
                   }
                   enum "1.1Mb" {
                     description "1.1 Mbps";
                   }
                   enum "1.4Mb" {
                     description "1.4 Mbps";
                   }
                   enum "1.8Mb" {
                     description "1.8 Mbps";
                   }
                   enum "2.1Mb" {
                     description "2.1 Mbps";
                   }
                   enum "2.5Mb" {
                     description "2.5 Mbps";
                   }
                   enum "2.9Mb" {
                     description "2.9 Mbps";
                   }
                   enum "3.2Mb" {
                     description "3.2 Mbps";
                   }
                   enum "3.6Mb" {
                     description "3.6 Mbps";
                   }
                   enum "3.9Mb" {
                     description "3.9 Mbps";
                   }
                   enum "4.3Mb" {
                     description "4.3 Mbps";
                   }
                   enum "4.7Mb" {
                     description "4.7 Mbps";
                   }
                   enum "5.0Mb" {
                     description "5.0 Mbps";
                   }
                   enum "5.4Mb" {
                     description "5.4 Mbps";
                   }
                   enum "5.7Mb" {
                     description "5.7 Mbps";
                   }
                   enum "6.1Mb" {
                     description "6.1 Mbps";
                   }
                   enum "6.4Mb" {
                     description "6.4 Mbps";
                   }
                   enum "6.8Mb" {
                     description "6.8 Mbps";
                   }
                   enum "7.2Mb" {
                     description "7.2 Mbps";
                   }
                   enum "7.5Mb" {
                     description "7.5 Mbps";
                   }
                   enum "7.9Mb" {
                     description "7.9 Mbps";
                   }
                   enum "8.2Mb" {
                     description "8.2 Mbps";
                   }
                   enum "8.6Mb" {
                     description "8.6 Mbps";
                   }
                   enum "9.0Mb" {
                     description "9.0 Mbps";
                   }
                   enum "9.3Mb" {
                     description "9.3 Mbps";
                   }
                   enum "9.7Mb" {
                     description "9.7 Mbps";
                   }
                   enum "10.0Mb" {
                     description "10.0 Mbps";
                   }
                   enum "10.4Mb" {
                     description "10.4 Mbps";
                   }
                   enum "10.7Mb" {
                     description "10.7 Mbps";
                   }
                   enum "11.1Mb" {
                     description "11.1 Mbps";
                   }
                   enum "11.5Mb" {
                     description "11.5 Mbps";
                   }
                   enum "11.8Mb" {
                     description "11.8 Mbps";
                   }
                   enum "12.2Mb" {
                     description "12.2 Mbps";
                   }
                   enum "12.5Mb" {
                     description "12.5 Mbps";
                   }
                   enum "12.9Mb" {
                     description "12.9 Mbps";
                   }
                   enum "13.2Mb" {
                     description "13.2 Mbps";
                   }
                   enum "13.6Mb" {
                     description "13.6 Mbps";
                   }
                   enum "14.0Mb" {
                     description "14.0 Mbps";
                   }
                   enum "14.3Mb" {
                     description "14.3 Mbps";
                   }
                   enum "14.7Mb" {
                     description "14.7 Mbps";
                   }
                   enum "15.0Mb" {
                     description "15.0 Mbps";
                   }
                   enum "15.4Mb" {
                     description "15.4 Mbps";
                   }
                   enum "15.8Mb" {
                     description "15.8 Mbps";
                   }
                   enum "16.1Mb" {
                     description "16.1 Mbps";
                   }
                   enum "16.5Mb" {
                     description "16.5 Mbps";
                   }
                   enum "16.8Mb" {
                     description "16.8 Mbps";
                   }
                   enum "17.2Mb" {
                     description "17.2 Mbps";
                   }
                   enum "17.5Mb" {
                     description "17.5 Mbps";
                   }
                   enum "17.9Mb" {
                     description "17.9 Mbps";
                   }
                   enum "18.3Mb" {
                     description "18.3 Mbps";
                   }
                   enum "18.6Mb" {
                     description "18.6 Mbps";
                   }
                   enum "19.0Mb" {
                     description "19.0 Mbps";
                   }
                   enum "19.3Mb" {
                     description "19.3 Mbps";
                   }
                   enum "19.7Mb" {
                     description "19.7 Mbps";
                   }
                   enum "20.0Mb" {
                     description "20.0 Mbps";
                   }
                   enum "20.4Mb" {
                     description "20.4 Mbps";
                   }
                   enum "20.8Mb" {
                     description "20.8 Mbps";
                   }
                   enum "21.1Mb" {
                     description "21.1 Mbps";
                   }
                   enum "21.5Mb" {
                     description "21.5 Mbps";
                   }
                   enum "21.8Mb" {
                     description "21.8 Mbps";
                   }
                   enum "22.2Mb" {
                     description "22.2 Mbps";
                   }
                   enum "22.6Mb" {
                     description "22.6 Mbps";
                   }
                   enum "22.9Mb" {
                     description "22.9 Mbps";
                   }
                   enum "23.3Mb" {
                     description "23.3 Mbps";
                   }
                   enum "23.6Mb" {
                     description "23.6 Mbps";
                   }
                   enum "24.0Mb" {
                     description "24.0 Mbps";
                   }
                   enum "24.3Mb" {
                     description "24.3 Mbps";
                   }
                   enum "24.7Mb" {
                     description "24.7 Mbps";
                   }
                   enum "25.1Mb" {
                     description "25.1 Mbps";
                   }
                   enum "25.4Mb" {
                     description "25.4 Mbps";
                   }
                   enum "25.8Mb" {
                     description "25.8 Mbps";
                   }
                   enum "26.1Mb" {
                     description "26.1 Mbps";
                   }
                   enum "26.5Mb" {
                     description "26.5 Mbps";
                   }
                   enum "26.9Mb" {
                     description "26.9 Mbps";
                   }
                   enum "27.2Mb" {
                     description "27.2 Mbps";
                   }
                   enum "27.6Mb" {
                     description "27.6 Mbps";
                   }
                   enum "27.9Mb" {
                     description "27.9 Mbps";
                   }
                   enum "28.3Mb" {
                     description "28.3 Mbps";
                   }
                   enum "28.6Mb" {
                     description "28.6 Mbps";
                   }
                   enum "29.0Mb" {
                     description "29.0 Mbps";
                   }
                   enum "29.4Mb" {
                     description "29.4 Mbps";
                   }
                   enum "29.7Mb" {
                     description "29.7 Mbps";
                   }
                   enum "30.1Mb" {
                     description "30.1 Mbps";
                   }
                   enum "30.4Mb" {
                     description "30.4 Mbps";
                   }
                   enum "30.8Mb" {
                     description "30.8 Mbps";
                   }
                   enum "31.1Mb" {
                     description "31.1 Mbps";
                   }
                   enum "31.5Mb" {
                     description "31.5 Mbps";
                   }
                   enum "31.9Mb" {
                     description "31.9 Mbps";
                   }
                   enum "32.2Mb" {
                     description "32.2 Mbps";
                   }
                   enum "32.6Mb" {
                     description "32.6 Mbps";
                   }
                   enum "32.9Mb" {
                     description "32.9 Mbps";
                   }
                   enum "33.3Mb" {
                     description "33.3 Mbps";
                   }
                   enum "33.7Mb" {
                     description "33.7 Mbps";
                   }
                   enum "34.0Mb" {
                     description "34.0 Mbps";
                   }
                 }
               }
             }
           }
           case case_3 {
             container kentrox {
               presence "enable kentrox";
               description "Compatible with Kentrox CSU";
               leaf subrate {
                 description "Set subrate value (only for E3 IQ interfaces)";
                 type union {
                   type string {
                     pattern "<.*>|$.*";
                   }
                   type uint32 {
                     range "1 .. 48";
                   }
                 }
               }
             }
           }
         }
       }
       choice payload-scrambler-choice {
         leaf payload-scrambler {
           description "Enable payload scrambling";
           type empty;
         }
         leaf no-payload-scrambler {
           description "Don't enable payload scrambling";
           type empty;
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf invert-data {
         description "Invert data";
         type empty;
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
       leaf buildout {
         description "Line buildout";
         units "feet";
         type union {
           type string {
             pattern "<.*>|$.*";
           }
           type uint32 {
             range "0 .. 450";
           }
         }
       }
       leaf atm-encapsulation {
         description "E3 interface encapsulation";
         type enumeration {
           enum "plcp" {
             description "PLCP encapsulation";
           }
           enum "direct" {
             description "ATM direct mapping";
           }
         }
       }
       leaf framing {
         description "E3 line format";
         type enumeration {
           enum "g.751" {
             description "G.751 format";
           }
           enum "g.832" {
             description "G.832 format";
           }
         }
       }
     }
     container e1-options {
       description "E1 interface-specific options";
       uses apply-advanced;
       leaf timeslots {
         description "Timeslots (1..32); for example, 1-4,6,9-11,32 (no space)";
         type string;
       }
       leaf loopback {
         description "Loopback mode";
         type enumeration {
           enum "local" {
             description "Local loopback";
           }
           enum "remote" {
             description "Remote loopback";
           }
         }
       }
       leaf framing {
         description "Framing mode";
         type enumeration {
           enum "g704" {
             description "G704 mode with CRC4";
           }
           enum "unframed" {
             description "Unframed mode";
           }
           enum "g704-no-crc4" {
             description "G704 mode without CRC4";
           }
         }
       }
       leaf fcs {
         description "Frame checksum";
         type enumeration {
           enum "32" {
             description "32-bit mode";
           }
           enum "16" {
             description "16-bit mode";
           }
         }
       }
       leaf invert-data {
         description "Invert data";
         type empty;
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 86400";
           }
         }
       }
     }
     container t1-options {
       description "T1 interface-specific options";
       uses apply-advanced;
       leaf timeslots {
         description "Timeslots (1..24; for example, 1-3,4,9,22-24 (no space)";
         type string;
       }
       leaf voice-timeslots {
         description "Voice timeslots (1..24),for example, 1-3,4,9,22-24 (no space)";
         type string;
       }
       leaf disable-remote-alarm-detection {
         description "Disable detection of a remote alarm";
         type enumeration {
           enum "yellow" {
             description "Disable yellow alarm detection";
           }
         }
       }
       leaf loopback {
         description "Loopback mode";
         type enumeration {
           enum "local" {
             description "Local loopback";
           }
           enum "remote" {
             description "Remote loopback";
           }
           enum "payload" {
             description "Payload loopback";
           }
         }
       }
       leaf buildout {
         description "Line buildout";
         type enumeration {
           enum "0-132" {
             description "Line buildout is between 0-132 feet";
           }
           enum "133-265" {
             description "Line buildout is between 133-265 feet";
           }
           enum "266-398" {
             description "Line buildout is between 266-398 feet";
           }
           enum "399-531" {
             description "Line buildout is between 399-531 feet";
           }
           enum "532-655" {
             description "Line buildout is between 532-655 feet";
           }
           enum "long-0db" {
             description "Long buildout with 0 dB transmit attenuation";
           }
           enum "long-7.5db" {
             description "Long buildout with 7.5 dB transmit attenuation";
           }
           enum "long-15db" {
             description "Long buildout with 15 dB transmit attenuation";
           }
           enum "long-22.5db" {
             description "Long buildout with 22.5 dB transmit attenuation";
           }
         }
       }
       leaf byte-encoding {
         description "Byte encoding";
         type enumeration {
           enum "nx64" {
             description "8 bits per byte";
           }
           enum "nx56" {
             description "7 bits per byte";
           }
         }
       }
       leaf line-encoding {
         description "Line encoding";
         type enumeration {
           enum "ami" {
             description "Automatic mark inversion";
           }
           enum "b8zs" {
             description "8-bit zero suppression";
           }
         }
       }
       leaf invert-data {
         description "Invert data";
         type empty;
       }
       leaf framing {
         description "Framing mode";
         type enumeration {
           enum "sf" {
             description "Super frame";
           }
           enum "esf" {
             description "Extended super frame";
           }
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 86400";
           }
         }
       }
       leaf remote-loopback-respond {
         description "Respond to loop requests from remote end";
         type empty;
       }
       leaf crc-major-alarm-threshold {
         description "CRC Major alarm threshold value";
         default "5e-5";
         type enumeration {
           enum "1e-3" {
             description "1 crc error in 10^3 bits";
           }
           enum "5e-4" {
             description "5 crc errors in 10^4 bits";
           }
           enum "1e-4" {
             description "1 crc error in 10^4 bits";
           }
           enum "5e-5" {
             description "5 crc errors in 10^5 bits";
           }
           enum "1e-5" {
             description "1 crc error in 10^5 bits";
           }
         }
       }
       leaf crc-minor-alarm-threshold {
         description "CRC Minor alarm threshold value";
         default "5e-6";
         type enumeration {
           enum "1e-3" {
             description "1 crc error in 10^3 bits";
           }
           enum "5e-4" {
             description "5 crc errors in 10^4 bits";
           }
           enum "1e-4" {
             description "1 crc error in 10^4 bits";
           }
           enum "5e-5" {
             description "5 crc errors in 10^5 bits";
           }
           enum "1e-5" {
             description "1 crc error in 10^5 bits";
           }
           enum "5e-6" {
             description "5 crc errors in 10^6 bits";
           }
           enum "1e-6" {
             description "1 crc error in 10^6 bits";
           }
         }
       }
       leaf alarm-compliance {
         description "Enforce standard for alarm reporting";
         type enumeration {
           enum "accunet-t1-5-service" {
             description "T1.5 interface specification";
           }
         }
       }
     }
     container ds0-options {
       description "DS-0 interface-specific options";
       uses apply-advanced;
       leaf loopback {
         description "Loopback mode";
         type enumeration {
           enum "payload" {
             description "Payload loopback";
           }
         }
       }
       leaf byte-encoding {
         description "Byte encoding";
         type enumeration {
           enum "nx64" {
             description "8 bits per byte";
           }
           enum "nx56" {
             description "7 bits per byte";
           }
         }
       }
       leaf invert-data {
         description "Invert data";
         type empty;
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e11-o152" {
             description "Pattern is 2^11 -1 (per O.152 standard)";
           }
           enum "pseudo-2e15-o151" {
             description "Pattern is 2^15 - 1 (per O.151 standard)";
           }
           enum "pseudo-2e20-o153" {
             description "Pattern is 2^20 - 1 (per O.153 standard)";
           }
           enum "pseudo-2e20-o151" {
             description "Pattern is 2^20 - 1 (per O.151 standard)";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
           enum "repeating-1-in-16" {
             description "1 bit in 16 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
     }
     container serial-options {
       description "Serial interface-specific options";
       uses apply-advanced;
       leaf line-protocol {
         description "Line protocol to be used";
         default "eia530";
         type enumeration {
           enum "eia530" {
             description "Line protocol EIA530";
           }
           enum "v.35" {
             description "Line protocol V.35";
           }
           enum "x.21" {
             description "Line protocol X.21";
           }
         }
       }
       choice control_leads_choice {
         case case_1 {
           container dte-options {
             description "DTE options/control leads";
             uses apply-advanced;
             leaf ignore-all {
               description "Ignore all control leads";
               type empty;
             }
             container dtr {
               description "Data Transmit Ready signal handling";
               choice dtr_choices {
                 case case_1 {
                   leaf assert {
                     description "Assert DTR signal";
                     type empty;
                   }
                 }
                 case case_2 {
                   leaf de-assert {
                     description "Deassert DTR signal";
                     type empty;
                   }
                 }
                 case case_3 {
                   leaf normal {
                     description "Normal DTR signal";
                     type empty;
                   }
                 }
                 case case_4 {
                   container auto-synchronize {
                     presence "enable auto-synchronize";
                     description "Normal DTR signal, with autoresynchronization";
                     uses apply-advanced;
                     leaf duration {
                       description "Duration of autoresynchronization";
                       units "milliseconds";
                       type union {
                         type string {
                           pattern "<.*>|$.*";
                         }
                         type uint16 {
                           range "1 .. 1000";
                         }
                       }
                     }
                     leaf interval {
                       description "Interval for autoresynchronization";
                       units "seconds";
                       type union {
                         type string {
                           pattern "<.*>|$.*";
                         }
                         type uint16 {
                           range "1 .. 31";
                         }
                       }
                     }
                   }
                 }
               }
             }
             leaf control-signal {
               description "X.21 control signal handling";
               type enumeration {
                 enum "assert" {
                   description "Assert control signal";
                 }
                 enum "de-assert" {
                   description "Deassert control signal";
                 }
                 enum "normal" {
                   description "Normal control signal";
                 }
               }
             }
             leaf rts {
               description "Request To Send signal handling";
               type enumeration {
                 enum "assert" {
                   description "Assert RTS signal";
                 }
                 enum "de-assert" {
                   description "Deassert RTS signal";
                 }
                 enum "normal" {
                   description "Normal RTS signal";
                 }
               }
             }
             leaf dcd {
               description "Data Carrier Detect signal handling";
               type enumeration {
                 enum "require" {
                   description "Require DCD signal";
                 }
                 enum "ignore" {
                   description "Ignore DCD signal";
                 }
                 enum "normal" {
                   description "Normal DCD signal";
                 }
               }
             }
             leaf dsr {
               description "Data Set Ready signal handling";
               type enumeration {
                 enum "require" {
                   description "Require DSR signal";
                 }
                 enum "ignore" {
                   description "Ignore DSR signal";
                 }
                 enum "normal" {
                   description "Normal DSR signal";
                 }
               }
             }
             leaf cts {
               description "Clear To Send signal handling";
               type enumeration {
                 enum "require" {
                   description "Require CTS signal";
                 }
                 enum "ignore" {
                   description "Ignore CTS signal";
                 }
                 enum "normal" {
                   description "Normal CTS signal";
                 }
               }
             }
             leaf indication {
               description "X.21 Indication signal handling";
               type enumeration {
                 enum "require" {
                   description "Require Indication signal";
                 }
                 enum "ignore" {
                   description "Ignore Indication signal";
                 }
                 enum "normal" {
                   description "Normal Indication signal";
                 }
               }
             }
             leaf tm {
               description "Test Mode signal handling";
               type enumeration {
                 enum "require" {
                   description "Require TM signal";
                 }
                 enum "ignore" {
                   description "Ignore TM signal";
                 }
                 enum "normal" {
                   description "Normal TM signal";
                 }
               }
             }
           }
         }
         case case_2 {
           container dce-options {
             description "DCE options";
             uses apply-advanced;
             leaf ignore-all {
               description "Ignore all control leads";
               type empty;
             }
             leaf dtr {
               description "Data Transmit Ready signal handling";
               type enumeration {
                 enum "require" {
                   description "Require Data Carrier Detect (DCD) signal";
                 }
                 enum "ignore" {
                   description "Ignore Data Carrier Detect (DCD) signal";
                 }
                 enum "normal" {
                   description "Normal Data Carrier Detect (DCD) signal";
                 }
               }
             }
             leaf rts {
               description "Request To Send signal handling";
               type enumeration {
                 enum "require" {
                   description "Require Data Carrier Detect (DCD) signal";
                 }
                 enum "ignore" {
                   description "Ignore Data Carrier Detect (DCD) signal";
                 }
                 enum "normal" {
                   description "Normal Data Carrier Detect (DCD) signal";
                 }
               }
             }
             leaf dcd {
               description "Data Carrier Detect signal handling";
               type enumeration {
                 enum "assert" {
                   description "Assert Request To Send (RTS) signal";
                 }
                 enum "de-assert" {
                   description "Deassert Request To Send (RTS) signal";
                 }
                 enum "normal" {
                   description "Normal Request To Send (RTS) signal";
                 }
               }
             }
             leaf dsr {
               description "Data Set Ready signal handling";
               type enumeration {
                 enum "assert" {
                   description "Assert Request To Send (RTS) signal";
                 }
                 enum "de-assert" {
                   description "Deassert Request To Send (RTS) signal";
                 }
                 enum "normal" {
                   description "Normal Request To Send (RTS) signal";
                 }
               }
             }
             leaf cts {
               description "Clear To Send signal handling";
               type enumeration {
                 enum "assert" {
                   description "Assert Request To Send (RTS) signal";
                 }
                 enum "de-assert" {
                   description "Deassert Request To Send (RTS) signal";
                 }
                 enum "normal" {
                   description "Normal Request To Send (RTS) signal";
                 }
               }
             }
             leaf tm {
               description "Test Mode signal handling";
               type enumeration {
                 enum "require" {
                   description "Require TM signal";
                 }
                 enum "ignore" {
                   description "Ignore TM signal";
                 }
                 enum "normal" {
                   description "Normal TM signal";
                 }
               }
             }
             leaf dce-loopback-override {
               description "DCE loopback override";
               type empty;
             }
           }
         }
       }
       leaf dtr-circuit {
         description "Data Transmit Ready circuit mode";
         type enumeration {
           enum "balanced" {
             description "Balanced signal";
           }
           enum "unbalanced" {
             description "Unbalanced signal";
           }
         }
       }
       leaf dtr-polarity {
         description "Data Transmit Ready signal polarity";
         type enumeration {
           enum "positive" {
             description "Positive polarity";
           }
           enum "negative" {
             description "Negative polarity";
           }
         }
       }
       leaf rts-polarity {
         description "Request To Send signal polarity";
         type enumeration {
           enum "positive" {
             description "Positive polarity";
           }
           enum "negative" {
             description "Negative polarity";
           }
         }
       }
       leaf control-polarity {
         description "X.21 Control signal polarity";
         type enumeration {
           enum "positive" {
             description "Positive polarity";
           }
           enum "negative" {
             description "Negative polarity";
           }
         }
       }
       leaf dcd-polarity {
         description "Data Carrier Detect signal polarity";
         type enumeration {
           enum "positive" {
             description "Positive polarity";
           }
           enum "negative" {
             description "Negative polarity";
           }
         }
       }
       leaf dsr-polarity {
         description "Data Set Ready signal polarity";
         type enumeration {
           enum "positive" {
             description "Positive polarity";
           }
           enum "negative" {
             description "Negative polarity";
           }
         }
       }
       leaf cts-polarity {
         description "Clear To Send signal polarity";
         type enumeration {
           enum "positive" {
             description "Positive polarity";
           }
           enum "negative" {
             description "Negative polarity";
           }
         }
       }
       leaf indication-polarity {
         description "X.21 Indication signal polarity";
         type enumeration {
           enum "positive" {
             description "Positive polarity";
           }
           enum "negative" {
             description "Negative polarity";
           }
         }
       }
       leaf tm-polarity {
         description "Test Mode signal polarity";
         type enumeration {
           enum "positive" {
             description "Positive polarity";
           }
           enum "negative" {
             description "Negative polarity";
           }
         }
       }
       leaf clocking-mode {
         description "Clock mode";
         type enumeration {
           enum "dce" {
             description "DCE timing (DTE mode only, not valid for X.21)";
           }
           enum "internal" {
             description "Internal baud timing";
           }
           enum "loop" {
             description "Loop timing";
           }
         }
       }
       leaf transmit-clock {
         description "Transmit clock phase";
         type enumeration {
           enum "invert" {
             description "Shift clock phase 180 degrees";
           }
         }
       }
       leaf clock-rate {
         description "Interface clock rate";
         type enumeration {
           enum "2.048mhz" {
             description "2.048 MHz";
           }
           enum "2.341mhz" {
             description "2.341 MHz";
           }
           enum "2.731mhz" {
             description "2.731 MHz";
           }
           enum "3.277mhz" {
             description "3.277 MHz";
           }
           enum "4.096mhz" {
             description "4.096 MHz";
           }
           enum "5.461mhz" {
             description "5.461 MHz";
           }
           enum "8.192mhz" {
             description "8.192 MHz";
           }
           enum "16.384mhz" {
             description "16.384 MHz";
           }
           enum "1.2khz" {
             description "1.2 KHz";
           }
           enum "2.4khz" {
             description "2.4 KHz";
           }
           enum "9.6khz" {
             description "9.6 KHz";
           }
           enum "19.2khz" {
             description "19.2 KHz";
           }
           enum "38.4khz" {
             description "38.4 KHz";
           }
           enum "56.0khz" {
             description "56.0 KHz";
           }
           enum "64.0khz" {
             description "64.0 KHz";
           }
           enum "72.0khz" {
             description "72.0 KHz";
           }
           enum "125.0khz" {
             description "125.0 KHz";
           }
           enum "148.0khz" {
             description "148.0 KHz";
           }
           enum "250.0khz" {
             description "250.0 KHz";
           }
           enum "500.0khz" {
             description "500.0 KHz";
           }
           enum "800.0khz" {
             description "800.0 KHz";
           }
           enum "1.0mhz" {
             description "1.0 MHz";
           }
           enum "1.3mhz" {
             description "1.3 MHz";
           }
           enum "2.0mhz" {
             description "2.0 MHz";
           }
           enum "4.0mhz" {
             description "4.0 MHz";
           }
           enum "8.0mhz" {
             description "8.0 MHz";
           }
         }
       }
       leaf loopback {
         description "Loopback mode";
         type enumeration {
           enum "local" {
             description "Local loopback";
           }
           enum "remote" {
             description "Remote/LIU loopback";
           }
           enum "dce-local" {
             description "DCE local loopback (DTE mode only)";
           }
           enum "dce-remote" {
             description "DCE remote loopback";
           }
         }
       }
       leaf encoding {
         description "Line encoding";
         type enumeration {
           enum "nrz" {
             description "Non-Return-To-Zero";
           }
           enum "nrzi" {
             description "Non-Return-To-Zero-Invertible";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
     }
     choice gratuitous-arp-reply-choice {
       leaf gratuitous-arp-reply {
         description "Enable gratuitous ARP reply";
         type empty;
       }
       leaf no-gratuitous-arp-reply {
         description "Don't enable gratuitous ARP reply";
         type empty;
       }
     }
     choice no-gratuitous-arp-request-choice {
       leaf no-gratuitous-arp-request {
         description "Ignore gratuitous ARP request";
         type empty;
       }
       leaf no-no-gratuitous-arp-request {
         description "Don't ignore gratuitous ARP request";
         type empty;
       }
     }
     leaf arp-l2-validate {
       description "Validate ARP against L2";
       type empty;
     }
     container ether-options {
       description "Ethernet interface-specific options";
       uses apply-advanced;
       choice loopback-choice {
         leaf loopback {
           description "Enable loopback";
           type empty;
         }
         leaf no-loopback {
           description "Don't enable loopback";
           type empty;
         }
       }
       leaf loopback-remote {
         description "Enable remote loopback";
         type empty;
       }
       choice source-filtering-choice {
         leaf source-filtering {
           description "Enable source address filtering";
           type empty;
         }
         leaf no-source-filtering {
           description "Don't enable source address filtering";
           type empty;
         }
       }
       container ethernet-switch-profile {
         description "Ethernet virtual LAN/media access control-level options";
         uses apply-advanced;
         leaf-list tag-protocol-id {
           ordered-by user;
           description "IEEE 802.1q Tag Protocol Identifier values for VLAN-tagged frames";
           type string;
         }
         container ethernet-policer-profile {
           description "Ethernet level CoS-based policer configuration";
           uses apply-advanced;
           container input-priority-map {
             description "Input policer priority map";
             uses cos_policer_input_priority_map;
           }
           container output-priority-map {
             description "Output policer priority map";
             uses cos_policer_output_priority_map;
           }
           list policer {
             key name;
             ordered-by user;
             description "Policer template definition";
             uses cos_policer;
           }
         }
         container storm-control {
           description "Storm control profile name to bind";
           uses apply-advanced;
           leaf profile-name {
             description "Profile name";
             type string;
           }
         }
         container recovery-timeout {
           description "Recovery timeout for this interface";
           leaf time-in-seconds {
             units "seconds";
             type union {
               type string {
                 pattern "<.*>|$.*";
               }
               type uint32 {
                 range "10 .. 3600";
               }
             }
           }
         }
         choice mac-learn-enable-choice {
           leaf mac-learn-enable {
             description "Learn MAC addresses dynamically";
             type empty;
           }
           leaf no-mac-learn-enable {
             description "Don't learn MAC addresses dynamically";
             type empty;
           }
         }
       }
       leaf asynchronous-notification {
         description "Enable sending asynchronous notification to peer on CCC-down";
         type empty;
       }
       list source-address-filter {
         key name;
         description "Source address filters";
         leaf name {
           description "Remote MAC address";
           type jt:mac-addr;
         }
       }
       choice auto-negotiation-choice {
         leaf auto-negotiation {
           description "Enable auto-negotiation";
           type empty;
         }
         leaf no-auto-negotiation {
           description "Don't enable auto-negotiation";
           type empty;
         }
       }
       choice flow-control-choice {
         leaf flow-control {
           description "Enable flow control";
           type empty;
         }
         leaf no-flow-control {
           description "Don't enable flow control";
           type empty;
         }
       }
       container configured-flow-control {
         presence "enable configured-flow-control";
         description "Enable flow control";
         uses apply-advanced;
         leaf rx-buffers {
           description "Enable/Disable Rx buffers";
           type enumeration {
             enum "on" {
               description "Enable Rx buffers";
             }
             enum "off" {
               description "Disable Rx buffers";
             }
           }
         }
         leaf tx-buffers {
           description "Enable/Disable Tx buffers";
           type enumeration {
             enum "on" {
               description "Enable Tx buffers";
             }
             enum "off" {
               description "Disable Tx buffers";
             }
           }
         }
       }
       leaf link-mode {
         description "Link duplex";
         type enumeration {
           enum "automatic" {
             description "Automatic negotiate duplex ";
           }
           enum "half-duplex" {
             description "Half-duplex operation";
           }
           enum "full-duplex" {
             description "Full-duplex operation";
           }
         }
       }
       container mpls {
         description "MPLS options";
         uses mpls_ifd_options;
       }
       leaf ignore-l3-incompletes {
         description "Ignore L3 incomplete errors";
         type empty;
       }
       leaf no-auto-mdix {
         description "Disable auto MDI/MDIX";
         type empty;
       }
       leaf fec {
         description "Forward Error Correction mode";
         type enumeration {
           enum "none" {
             description "FEC disabled";
           }
           enum "fec91" {
             description "IEEE 802.3bj Clause 91, Reed-Solomon FEC (RS-FEC)";
           }
           enum "fec74" {
             description "FEC74 enabled";
           }
           enum "fec108" {
             description "IEEE 802.3by Clause 108, Reed-Solomon FEC (RS-FEC) on 25g links";
           }
           enum "fec161" {
             description "IEEE 802.3ck Clause 161 for 100G electrical links";
           }
         }
       }
       container speed {
         description "Specify speed";
         choice automatic {
           case case_1 {
             container auto-negotiation {
               presence "enable auto-negotiation";
               description "Enable auto-negotiation";
               leaf auto-negotiate-10-100 {
                 description "Limits the auto-negotiation to 10m/100m only";
                 type empty;
               }
             }
           }
           case case_2 {
             leaf ethernet-10m {
               description "10Mbps";
               type empty;
             }
           }
           case case_3 {
             leaf ethernet-100m {
               description "100Mbps";
               type empty;
             }
           }
           case case_4 {
             leaf ethernet-1g {
               description "1Gbps";
               type empty;
             }
           }
           case case_5 {
             leaf ethernet-10g {
               description "10Gbps";
               type empty;
             }
           }
         }
       }
       container ieee-802.3ad {
         description "IEEE 802.3ad";
         uses apply-advanced;
         container lacp {
           description "Link Aggregation Control Protocol configuration";
           uses apply-advanced;
           leaf force-up {
             description "Keep the port up in absence of received LACPDU";
             type empty;
           }
           leaf port-priority {
             description "Priority of the port (0 ... 65535)";
             type union {
               type uint16;
               type string {
                 pattern "<.*>|$.*";
               }
             }
           }
         }
         leaf bundle {
           description "Join an aggregated Ethernet interface";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
         container link-protection-sub-group {
           description "Link Protection subgroup configuration";
           uses apply-advanced;
           leaf subgroup-name {
             description "Name of the subgroup";
             type string {
               length "2 .. 64";
             }
           }
         }
         leaf port-priority {
           description "Link protection Priority of the port (0 ... 65535)";
           type union {
             type uint16;
             type string {
               pattern "<.*>|$.*";
             }
           }
         }
       }
       leaf ieee-802-3az-eee {
         description "IEEE 802.3az Energy Efficient Ethernet(EEE)";
         type empty;
       }
       leaf mdi-mode {
         description "Cable cross-over mode";
         type enumeration {
           enum "auto" {
             description "Automatic mdi/mdi-x mode";
           }
           enum "force" {
             description "Enable auto-MDIX always";
           }
           enum "mdi" {
             description "MDI(straight through) mode";
           }
           enum "mdix" {
             description "MDI Cross-over mode";
           }
         }
       }
       container redundant-parent {
         description " Parent of this interface";
         uses apply-advanced;
         leaf parent {
           description "Join a redundant ethernet interface";
           type union {
             type jt:interface-device;
             type string {
               pattern "<.*>|$.*";
             }
           }
         }
       }
       leaf autostate-exclude {
         description "Interface will not contribute to IRB state";
         type empty;
       }
     }
     container fibrechannel-options {
       description "Fibre Channel interface-specific options";
       uses apply-advanced;
       choice loopback-choice {
         leaf loopback {
           description "Enable loopback";
           type empty;
         }
         leaf no-loopback {
           description "Don't enable loopback";
           type empty;
         }
       }
       leaf bb-sc-n {
         description "B2B state change number";
         type union {
           type string {
             pattern "<.*>|$.*";
           }
           type uint16 {
             range "0 .. 15";
           }
         }
       }
       leaf speed {
         description "Specify speed";
         type enumeration {
           enum "auto-negotiation" {
             description "Enable auto-negotiation";
           }
           enum "1g" {
             description "1Gbps";
           }
           enum "2g" {
             description "2Gbps";
           }
           enum "4g" {
             description "4Gbps";
           }
           enum "8g" {
             description "8Gbps";
           }
         }
       }
     }
     container gigether-options {
       description "Gigabit Ethernet interface-specific options";
       uses apply-advanced;
       choice loopback-choice {
         leaf loopback {
           description "Enable loopback";
           type empty;
         }
         leaf no-loopback {
           description "Don't enable loopback";
           type empty;
         }
       }
       leaf loopback-remote {
         description "Enable remote loopback";
         type empty;
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       choice auto_negotiation_option {
         case case_1 {
           leaf no-auto-negotiation {
             description "Disable auto-negotiation";
             type empty;
           }
         }
         case case_2 {
           container auto-negotiation {
             presence "enable auto-negotiation";
             description "Enable auto-negotiation";
             leaf remote-fault {
               type enumeration {
                 enum "local-interface-offline" {
                   description "Disable local interface";
                 }
                 enum "local-interface-online" {
                   description "Enable local interface";
                 }
               }
             }
           }
         }
       }
       leaf mac-mode {
         description "Physical layer protocol of MAC's SERDES interface";
         type enumeration {
           enum "sgmii" {
             description "Serial Gigabit Media Independent Interface (10/100/1000 Mbps)";
           }
           enum "mac-mode-1000base-x" {
             description "1000Base-X (1000 Mbps)";
           }
         }
       }
       leaf asynchronous-notification {
         description "Enable sending asynchronous notification to peer on CCC-down";
         type empty;
       }
       list source-address-filter {
         key name;
         description "Source address filters";
         leaf name {
           description "Remote MAC address";
           type jt:mac-addr;
         }
       }
       leaf pad-to-minimum-frame-size {
         description "Pad Tx vlan tagged frame to minimum of 68 bytes";
         type empty;
       }
       container redundant-parent {
         description "Parent of this interface";
         uses apply-advanced;
         leaf parent {
           description "Join a redundant-ethernet interface";
           type union {
             type jt:interface-device;
             type string {
               pattern "<.*>|$.*";
             }
           }
         }
       }
       container ieee-802.3ad {
         description "IEEE 802.3ad";
         uses apply-advanced;
         container lacp {
           description "Link Aggregation Control Protocol configuration";
           uses apply-advanced;
           leaf port-priority {
             description "Priority of the port (0 ... 65535)";
             type union {
               type uint16;
               type string {
                 pattern "<.*>|$.*";
               }
             }
           }
         }
         leaf bundle {
           description "Join an aggregated Ethernet interface";
           type union {
             type jt:interface-device;
             type string {
               pattern "<.*>|$.*";
             }
           }
         }
         leaf link-index {
           description "Desired child link index within the Aggregated Interface";
           type union {
             type string {
               pattern "<.*>|$.*";
             }
             type uint16 {
               range "0 .. 63";
             }
           }
         }
         choice type {
           case case_1 {
             leaf primary {
               description "Primary interface for link-protection mode";
               type empty;
             }
           }
           case case_2 {
             leaf backup {
               description "Backup interface for link-protection mode";
               type empty;
             }
           }
         }
         leaf distribution-list {
           description "Distribution list to which interface belongs";
           type string {
             length "1 .. 20";
           }
         }
       }
       container ethernet-switch-profile {
         description "Ethernet virtual LAN/media access control-level options";
         uses apply-advanced;
         leaf-list tag-protocol-id {
           ordered-by user;
           description "IEEE 802.1q Tag Protocol Identifier values for VLAN-tagged frames";
           type string;
         }
         container ethernet-policer-profile {
           description "Ethernet level CoS-based policer configuration";
           uses apply-advanced;
           container ieee802.1-priority-map {
             presence "enable ieee802.1-priority-map";
             description "Premium priority values for IEEE 802.1p bits";
             status deprecated;
             uses apply-advanced;
             leaf-list premium {
               ordered-by user;
               description "Premium policer priority map";
               type union {
                 type string {
                   pattern "<.*>|$.*";
                 }
                 type uint32 {
                   range "0 .. 7";
                 }
               }
             }
           }
           container input-priority-map {
             description "Input policer priority map";
             uses cos_policer_input_priority_map;
           }
           container output-priority-map {
             description "Output policer priority map";
             uses cos_policer_output_priority_map;
           }
           list policer {
             key name;
             ordered-by user;
             description "Policer template definition";
             uses cos_policer;
           }
         }
         container accept-from {
           description "Accept traffic from or to specified remote MAC";
           status deprecated;
           uses apply-advanced;
           list mac-address {
             key name;
             description "Remote MAC";
             uses mac_list;
           }
         }
         choice reject-the-rest-choice {
           leaf reject-the-rest {
             description "Accept traffic from only the specified MAC addresses";
             status deprecated;
             type empty;
           }
           leaf no-reject-the-rest {
             description "Don't accept traffic from only the specified MAC addresses";
             status deprecated;
             type empty;
           }
         }
         leaf mac-learn-enable {
           description "Learn MAC addresses dynamically";
           type empty;
         }
       }
       container mpls {
         description "MPLS options";
         uses mpls_ifd_options;
       }
       leaf ignore-l3-incompletes {
         description "Ignore L3 incomplete errors";
         type empty;
       }
       leaf no-auto-mdix {
         description "Disable auto MDI/MDIX";
         type empty;
       }
       leaf ieee-802-3az-eee {
         description "IEEE 802.3az Energy Efficient Ethernet(EEE)";
         type empty;
       }
       leaf mru {
         description "Maximum receive packet size";
         type union {
           type string {
             pattern "<.*>|$.*";
           }
           type uint32;
         }
       }
       leaf fec {
         description "Forward Error Correction mode";
         type enumeration {
           enum "none" {
             description "FEC disabled";
           }
           enum "fec91" {
             description "IEEE 802.3bj Clause 91, Reed-Solomon FEC (RS-FEC)";
           }
           enum "fec74" {
             description "FEC74 enabled";
           }
           enum "fec108" {
             description "IEEE 802.3by Clause 108, Reed-Solomon FEC (RS-FEC) on 25g links";
           }
           enum "fec161" {
             description "IEEE 802.3ck Clause 161 for 100G electrical links";
           }
         }
       }
       leaf speed {
         description "Speed mode";
         type enumeration {
           enum "1g" {
             description "Speed 1g";
           }
           enum "10g" {
             description "Speed 10g";
           }
         }
       }
     }
     container optics-options {
       description "Optics options";
       uses apply-advanced;
       leaf wavelength {
         description "Wavelength of the optics (nanometers) for 50Ghz/100Ghz spacing";
         type enumeration {
           enum "1568.77" {
             description "1568.77 nm/191.1003 THz 50/100Ghz spacing";
           }
           enum "1568.36" {
             description "1568.36 nm/191.15000 THz 6.25/12.5/50GHz spacing";
           }
           enum "1568.31" {
             description "1568.31 nm/191.15625 THz 6.25GHz spacing";
           }
           enum "1568.26" {
             description "1568.26 nm/191.16250 THz 6.25/12.5GHz spacing";
           }
           enum "1568.21" {
             description "1568.21 nm/191.16875 THz 6.25GHz spacing";
           }
           enum "1568.16" {
             description "1568.16 nm/191.17500 THz 6.25/12.5GHz spacing";
           }
           enum "1568.11" {
             description "1568.11 nm/191.18125 THz 6.25GHz spacing";
           }
           enum "1568.05" {
             description "1568.05 nm/191.18750 THz 6.25/12.5GHz spacing";
           }
           enum "1568.00" {
             description "1568.00 nm/191.19375 THz 6.25GHz spacing";
           }
           enum "1567.95" {
             description "1567.95 nm/191.20000 THz 6.25/12.5/50/100GHz spacing";
           }
           enum "1567.90" {
             description "1567.90 nm/191.20625 THz 6.25GHz spacing";
           }
           enum "1567.85" {
             description "1567.85 nm/191.21250 THz 6.25/12.5GHz spacing";
           }
           enum "1567.80" {
             description "1567.80 nm/191.21875 THz 6.25GHz spacing";
           }
           enum "1567.75" {
             description "1567.75 nm/191.22500 THz 6.25/12.5GHz spacing";
           }
           enum "1567.70" {
             description "1567.70 nm/191.23125 THz 6.25GHz spacing";
           }
           enum "1567.64" {
             description "1567.64 nm/191.23750 THz 6.25/12.5GHz spacing";
           }
           enum "1567.59" {
             description "1567.59 nm/191.24375 THz 6.25GHz spacing";
           }
           enum "1567.54" {
             description "1567.54 nm/191.25000 THz 6.25/12.5/50GHz spacing";
           }
           enum "1567.49" {
             description "1567.49 nm/191.25625 THz 6.25GHz spacing";
           }
           enum "1567.44" {
             description "1567.44 nm/191.26250 THz 6.25/12.5GHz spacing";
           }
           enum "1567.39" {
             description "1567.39 nm/191.26875 THz 6.25GHz spacing";
           }
           enum "1567.34" {
             description "1567.34 nm/191.27500 THz 6.25/12.5GHz spacing";
           }
           enum "1567.29" {
             description "1567.29 nm/191.28125 THz 6.25GHz spacing";
           }
           enum "1567.23" {
             description "1567.23 nm/191.28750 THz 6.25/12.5GHz spacing";
           }
           enum "1567.18" {
             description "1567.18 nm/191.29375 THz 6.25GHz spacing";
           }
           enum "1567.13" {
             description "1567.13 nm/191.30000 THz 6.25/12.5/50/100GHz spacing";
           }
           enum "1567.08" {
             description "1567.08 nm/191.30625 THz 6.25GHz spacing";
           }
           enum "1567.03" {
             description "1567.03 nm/191.31250 THz 6.25/12.5GHz spacing";
           }
           enum "1566.98" {
             description "1566.98 nm/191.31875 THz 6.25GHz spacing";
           }
           enum "1566.93" {
             description "1566.93 nm/191.32500 THz 6.25/12.5GHz spacing";
           }
           enum "1566.88" {
             description "1566.88 nm/191.33125 THz 6.25GHz spacing";
           }
           enum "1566.83" {
             description "1566.83 nm/191.33750 THz 6.25/12.5GHz spacing";
           }
           enum "1566.77" {
             description "1566.77 nm/191.34375 THz 6.25GHz spacing";
           }
           enum "1566.72" {
             description "1566.72 nm/191.35000 THz 6.25/12.5/50GHz spacing";
           }
           enum "1566.67" {
             description "1566.67 nm/191.35625 THz 6.25GHz spacing";
           }
           enum "1566.62" {
             description "1566.62 nm/191.36250 THz 6.25/12.5GHz spacing";
           }
           enum "1566.57" {
             description "1566.57 nm/191.36875 THz 6.25GHz spacing";
           }
           enum "1566.52" {
             description "1566.52 nm/191.37500 THz 6.25/12.5/75GHz spacing";
           }
           enum "1566.47" {
             description "1566.47 nm/191.38125 THz 6.25GHz spacing";
           }
           enum "1566.42" {
             description "1566.42 nm/191.38750 THz 6.25/12.5GHz spacing";
           }
           enum "1566.36" {
             description "1566.36 nm/191.39375 THz 6.25GHz spacing";
           }
           enum "1566.31" {
             description "1566.31 nm/191.40000 THz 6.25/12.5/50/100GHz spacing";
           }
           enum "1566.26" {
             description "1566.26 nm/191.40625 THz 6.25GHz spacing";
           }
           enum "1566.21" {
             description "1566.21 nm/191.41250 THz 6.25/12.5GHz spacing";
           }
           enum "1566.16" {
             description "1566.16 nm/191.41875 THz 6.25GHz spacing";
           }
           enum "1566.11" {
             description "1566.11 nm/191.42500 THz 6.25/12.5GHz spacing";
           }
           enum "1566.06" {
             description "1566.06 nm/191.43125 THz 6.25GHz spacing";
           }
           enum "1566.01" {
             description "1566.01 nm/191.43750 THz 6.25/12.5GHz spacing";
           }
           enum "1565.96" {
             description "1565.96 nm/191.44375 THz 6.25GHz spacing";
           }
           enum "1565.90" {
             description "1565.90 nm/191.45000 THz 6.25/12.5/50/75GHz spacing";
           }
           enum "1565.85" {
             description "1565.85 nm/191.45625 THz 6.25GHz spacing";
           }
           enum "1565.80" {
             description "1565.80 nm/191.46250 THz 6.25/12.5GHz spacing";
           }
           enum "1565.75" {
             description "1565.75 nm/191.46875 THz 6.25GHz spacing";
           }
           enum "1565.70" {
             description "1565.70 nm/191.47500 THz 6.25/12.5GHz spacing";
           }
           enum "1565.65" {
             description "1565.65 nm/191.48125 THz 6.25GHz spacing";
           }
           enum "1565.60" {
             description "1565.60 nm/191.48750 THz 6.25/12.5GHz spacing";
           }
           enum "1565.55" {
             description "1565.55 nm/191.49375 THz 6.25GHz spacing";
           }
           enum "1565.50" {
             description "1565.50 nm/191.50000 THz 6.25/12.5/50/100GHz spacing";
           }
           enum "1565.44" {
             description "1565.44 nm/191.50625 THz 6.25GHz spacing";
           }
           enum "1565.39" {
             description "1565.39 nm/191.51250 THz 6.25/12.5GHz spacing";
           }
           enum "1565.34" {
             description "1565.34 nm/191.51875 THz 6.25GHz spacing";
           }
           enum "1565.29" {
             description "1565.29 nm/191.52500 THz 6.25/12.5/75GHz spacing";
           }
           enum "1565.24" {
             description "1565.24 nm/191.53125 THz 6.25GHz spacing";
           }
           enum "1565.19" {
             description "1565.19 nm/191.53750 THz 6.25/12.5GHz spacing";
           }
           enum "1565.14" {
             description "1565.14 nm/191.54375 THz 6.25GHz spacing";
           }
           enum "1565.09" {
             description "1565.09 nm/191.55000 THz 6.25/12.5/50GHz spacing";
           }
           enum "1565.04" {
             description "1565.04 nm/191.55625 THz 6.25GHz spacing";
           }
           enum "1564.99" {
             description "1564.99 nm/191.56250 THz 6.25/12.5GHz spacing";
           }
           enum "1564.93" {
             description "1564.93 nm/191.56875 THz 6.25GHz spacing";
           }
           enum "1564.88" {
             description "1564.88 nm/191.57500 THz 6.25/12.5GHz spacing";
           }
           enum "1564.83" {
             description "1564.83 nm/191.58125 THz 6.25GHz spacing";
           }
           enum "1564.78" {
             description "1564.78 nm/191.58750 THz 6.25/12.5GHz spacing";
           }
           enum "1564.73" {
             description "1564.73 nm/191.59375 THz 6.25GHz spacing";
           }
           enum "1564.68" {
             description "1564.68 nm/191.60000 THz 6.25/12.5/50/75/100GHz spacing";
           }
           enum "1564.63" {
             description "1564.63 nm/191.60625 THz 6.25GHz spacing";
           }
           enum "1564.58" {
             description "1564.58 nm/191.61250 THz 6.25/12.5GHz spacing";
           }
           enum "1564.53" {
             description "1564.53 nm/191.61875 THz 6.25GHz spacing";
           }
           enum "1564.47" {
             description "1564.47 nm/191.62500 THz 6.25/12.5GHz spacing";
           }
           enum "1564.42" {
             description "1564.42 nm/191.63125 THz 6.25GHz spacing";
           }
           enum "1564.37" {
             description "1564.37 nm/191.63750 THz 6.25/12.5GHz spacing";
           }
           enum "1564.32" {
             description "1564.32 nm/191.64375 THz 6.25GHz spacing";
           }
           enum "1564.27" {
             description "1564.27 nm/191.65000 THz 6.25/12.5/50GHz spacing";
           }
           enum "1564.22" {
             description "1564.22 nm/191.65625 THz 6.25GHz spacing";
           }
           enum "1564.17" {
             description "1564.17 nm/191.66250 THz 6.25/12.5GHz spacing";
           }
           enum "1564.12" {
             description "1564.12 nm/191.66875 THz 6.25GHz spacing";
           }
           enum "1564.07" {
             description "1564.07 nm/191.67500 THz 6.25/12.5/75GHz spacing";
           }
           enum "1564.02" {
             description "1564.02 nm/191.68125 THz 6.25GHz spacing";
           }
           enum "1563.96" {
             description "1563.96 nm/191.68750 THz 6.25/12.5GHz spacing";
           }
           enum "1563.91" {
             description "1563.91 nm/191.69375 THz 6.25GHz spacing";
           }
           enum "1563.86" {
             description "1563.86 nm/191.70000 THz 6.25/12.5/50/100GHz spacing";
           }
           enum "1563.81" {
             description "1563.81 nm/191.70625 THz 6.25GHz spacing";
           }
           enum "1563.76" {
             description "1563.76 nm/191.71250 THz 6.25/12.5GHz spacing";
           }
           enum "1563.71" {
             description "1563.71 nm/191.71875 THz 6.25GHz spacing";
           }
           enum "1563.66" {
             description "1563.66 nm/191.72500 THz 6.25/12.5GHz spacing";
           }
           enum "1563.61" {
             description "1563.61 nm/191.73125 THz 6.25GHz spacing";
           }
           enum "1563.56" {
             description "1563.56 nm/191.73750 THz 6.25/12.5GHz spacing";
           }
           enum "1563.51" {
             description "1563.51 nm/191.74375 THz 6.25GHz spacing";
           }
           enum "1563.45" {
             description "1563.45 nm/191.75000 THz 6.25/12.5/50/75GHz spacing";
           }
           enum "1563.40" {
             description "1563.40 nm/191.75625 THz 6.25GHz spacing";
           }
           enum "1563.35" {
             description "1563.35 nm/191.76250 THz 6.25/12.5GHz spacing";
           }
           enum "1563.30" {
             description "1563.30 nm/191.76875 THz 6.25GHz spacing";
           }
           enum "1563.25" {
             description "1563.25 nm/191.77500 THz 6.25/12.5GHz spacing";
           }
           enum "1563.20" {
             description "1563.20 nm/191.78125 THz 6.25GHz spacing";
           }
           enum "1563.15" {
             description "1563.15 nm/191.78750 THz 6.25/12.5GHz spacing";
           }
           enum "1563.10" {
             description "1563.10 nm/191.79375 THz 6.25GHz spacing";
           }
           enum "1563.05" {
             description "1563.05 nm/191.80000 THz 6.25/12.5/50/100GHz spacing";
           }
           enum "1563.00" {
             description "1563.00 nm/191.80625 THz 6.25GHz spacing";
           }
           enum "1562.95" {
             description "1562.95 nm/191.81250 THz 6.25/12.5GHz spacing";
           }
           enum "1562.89" {
             description "1562.89 nm/191.81875 THz 6.25GHz spacing";
           }
           enum "1562.84" {
             description "1562.84 nm/191.82500 THz 6.25/12.5/75GHz spacing";
           }
           enum "1562.79" {
             description "1562.79 nm/191.83125 THz 6.25GHz spacing";
           }
           enum "1562.74" {
             description "1562.74 nm/191.83750 THz 6.25/12.5GHz spacing";
           }
           enum "1562.69" {
             description "1562.69 nm/191.84375 THz 6.25GHz spacing";
           }
           enum "1562.64" {
             description "1562.64 nm/191.85000 THz 6.25/12.5/50GHz spacing";
           }
           enum "1562.59" {
             description "1562.59 nm/191.85625 THz 6.25GHz spacing";
           }
           enum "1562.54" {
             description "1562.54 nm/191.86250 THz 6.25/12.5GHz spacing";
           }
           enum "1562.49" {
             description "1562.49 nm/191.86875 THz 6.25GHz spacing";
           }
           enum "1562.44" {
             description "1562.44 nm/191.87500 THz 6.25/12.5GHz spacing";
           }
           enum "1562.39" {
             description "1562.39 nm/191.88125 THz 6.25GHz spacing";
           }
           enum "1562.33" {
             description "1562.33 nm/191.88750 THz 6.25/12.5GHz spacing";
           }
           enum "1562.28" {
             description "1562.28 nm/191.89375 THz 6.25GHz spacing";
           }
           enum "1562.23" {
             description "1562.23 nm/191.90000 THz 6.25/12.5/50/75/100GHz spacing";
           }
           enum "1562.18" {
             description "1562.18 nm/191.90625 THz 6.25GHz spacing";
           }
           enum "1562.13" {
             description "1562.13 nm/191.91250 THz 6.25/12.5GHz spacing";
           }
           enum "1562.08" {
             description "1562.08 nm/191.91875 THz 6.25GHz spacing";
           }
           enum "1562.03" {
             description "1562.03 nm/191.92500 THz 6.25/12.5GHz spacing";
           }
           enum "1561.98" {
             description "1561.98 nm/191.93125 THz 6.25GHz spacing";
           }
           enum "1561.93" {
             description "1561.93 nm/191.93750 THz 6.25/12.5GHz spacing";
           }
           enum "1561.88" {
             description "1561.88 nm/191.94375 THz 6.25GHz spacing";
           }
           enum "1561.83" {
             description "1561.83 nm/191.95000 THz 6.25/12.5/50GHz spacing";
           }
           enum "1561.77" {
             description "1561.77 nm/191.95625 THz 6.25GHz spacing";
           }
           enum "1561.72" {
             description "1561.72 nm/191.96250 THz 6.25/12.5GHz spacing";
           }
           enum "1561.67" {
             description "1561.67 nm/191.96875 THz 6.25GHz spacing";
           }
           enum "1561.62" {
             description "1561.62 nm/191.97500 THz 6.25/12.5/75GHz spacing";
           }
           enum "1561.57" {
             description "1561.57 nm/191.98125 THz 6.25GHz spacing";
           }
           enum "1561.52" {
             description "1561.52 nm/191.98750 THz 6.25/12.5GHz spacing";
           }
           enum "1561.47" {
             description "1561.47 nm/191.99375 THz 6.25GHz spacing";
           }
           enum "1561.42" {
             description "1561.42 nm/192.00000 THz 6.25/12.5/50/100GHz spacing";
           }
           enum "1561.37" {
             description "1561.37 nm/192.00625 THz 6.25GHz spacing";
           }
           enum "1561.32" {
             description "1561.32 nm/192.01250 THz 6.25/12.5GHz spacing";
           }
           enum "1561.27" {
             description "1561.27 nm/192.01875 THz 6.25GHz spacing";
           }
           enum "1561.22" {
             description "1561.22 nm/192.02500 THz 6.25/12.5GHz spacing";
           }
           enum "1561.16" {
             description "1561.16 nm/192.03125 THz 6.25GHz spacing";
           }
           enum "1561.11" {
             description "1561.11 nm/192.03750 THz 6.25/12.5GHz spacing";
           }
           enum "1561.06" {
             description "1561.06 nm/192.04375 THz 6.25GHz spacing";
           }
           enum "1561.01" {
             description "1561.01 nm/192.05000 THz 6.25/12.5/50G/75Hz spacing";
           }
           enum "1560.96" {
             description "1560.96 nm/192.05625 THz 6.25GHz spacing";
           }
           enum "1560.91" {
             description "1560.91 nm/192.06250 THz 6.25/12.5GHz spacing";
           }
           enum "1560.86" {
             description "1560.86 nm/192.06875 THz 6.25GHz spacing";
           }
           enum "1560.81" {
             description "1560.81 nm/192.07500 THz 6.25/12.5GHz spacing";
           }
           enum "1560.76" {
             description "1560.76 nm/192.08125 THz 6.25GHz spacing";
           }
           enum "1560.71" {
             description "1560.71 nm/192.08750 THz 6.25/12.5GHz spacing";
           }
           enum "1560.66" {
             description "1560.66 nm/192.09375 THz 6.25GHz spacing";
           }
           enum "1560.61" {
             description "1560.61 nm/192.10000 THz 6.25/12.5/50/100GHz spacing";
           }
           enum "1560.56" {
             description "1560.56 nm/192.10625 THz 6.25GHz spacing";
           }
           enum "1560.50" {
             description "1560.50 nm/192.11250 THz 6.25/12.5GHz spacing";
           }
           enum "1560.45" {
             description "1560.45 nm/192.11875 THz 6.25GHz spacing";
           }
           enum "1560.40" {
             description "1560.40 nm/192.12500 THz 6.25/12.5/75GHz spacing";
           }
           enum "1560.35" {
             description "1560.35 nm/192.13125 THz 6.25GHz spacing";
           }
           enum "1560.30" {
             description "1560.30 nm/192.13750 THz 6.25/12.5GHz spacing";
           }
           enum "1560.25" {
             description "1560.25 nm/192.14375 THz 6.25GHz spacing";
           }
           enum "1560.20" {
             description "1560.20 nm/192.15000 THz 6.25/12.5/50GHz spacing";
           }
           enum "1560.15" {
             description "1560.15 nm/192.15625 THz 6.25GHz spacing";
           }
           enum "1560.10" {
             description "1560.10 nm/192.16250 THz 6.25/12.5GHz spacing";
           }
           enum "1560.05" {
             description "1560.05 nm/192.16875 THz 6.25GHz spacing";
           }
           enum "1560.00" {
             description "1560.00 nm/192.17500 THz 6.25/12.5GHz spacing";
           }
           enum "1559.95" {
             description "1559.95 nm/192.18125 THz 6.25GHz spacing";
           }
           enum "1559.90" {
             description "1559.90 nm/192.18750 THz 6.25/12.5GHz spacing";
           }
           enum "1559.84" {
             description "1559.84 nm/192.19375 THz 6.25GHz spacing";
           }
           enum "1559.79" {
             description "1559.79 nm/192.20000 THz 6.25/12.5/50/75/100GHz spacing";
           }
           enum "1559.74" {
             description "1559.74 nm/192.20625 THz 6.25GHz spacing";
           }
           enum "1559.69" {
             description "1559.69 nm/192.21250 THz 6.25/12.5GHz spacing";
           }
           enum "1559.64" {
             description "1559.64 nm/192.21875 THz 6.25GHz spacing";
           }
           enum "1559.59" {
             description "1559.59 nm/192.22500 THz 6.25/12.5GHz spacing";
           }
           enum "1559.54" {
             description "1559.54 nm/192.23125 THz 6.25GHz spacing";
           }
           enum "1559.49" {
             description "1559.49 nm/192.23750 THz 6.25/12.5GHz spacing";
           }
           enum "1559.44" {
             description "1559.44 nm/192.24375 THz 6.25GHz spacing";
           }
           enum "1559.39" {
             description "1559.39 nm/192.25000 THz 6.25/12.5/50GHz spacing";
           }
           enum "1559.34" {
             description "1559.34 nm/192.25625 THz 6.25GHz spacing";
           }
           enum "1559.29" {
             description "1559.29 nm/192.26250 THz 6.25/12.5GHz spacing";
           }
           enum "1559.24" {
             description "1559.24 nm/192.26875 THz 6.25GHz spacing";
           }
           enum "1559.19" {
             description "1559.19 nm/192.27500 THz 6.25/12.5/75GHz spacing";
           }
           enum "1559.14" {
             description "1559.14 nm/192.28125 THz 6.25GHz spacing";
           }
           enum "1559.08" {
             description "1559.08 nm/192.28750 THz 6.25/12.5GHz spacing";
           }
           enum "1559.03" {
             description "1559.03 nm/192.29375 THz 6.25GHz spacing";
           }
           enum "1558.98" {
             description "1558.98 nm/192.30000 THz 6.25/12.5/50/100GHz spacing";
           }
           enum "1558.93" {
             description "1558.93 nm/192.30625 THz 6.25GHz spacing";
           }
           enum "1558.88" {
             description "1558.88 nm/192.31250 THz 6.25/12.5GHz spacing";
           }
           enum "1558.83" {
             description "1558.83 nm/192.31875 THz 6.25GHz spacing";
           }
           enum "1558.78" {
             description "1558.78 nm/192.32500 THz 6.25/12.5GHz spacing";
           }
           enum "1558.73" {
             description "1558.73 nm/192.33125 THz 6.25GHz spacing";
           }
           enum "1558.68" {
             description "1558.68 nm/192.33750 THz 6.25/12.5GHz spacing";
           }
           enum "1558.63" {
             description "1558.63 nm/192.34375 THz 6.25GHz spacing";
           }
           enum "1558.58" {
             description "1558.58 nm/192.35000 THz 6.25/12.5/50/75GHz spacing";
           }
           enum "1558.53" {
             description "1558.53 nm/192.35625 THz 6.25GHz spacing";
           }
           enum "1558.48" {
             description "1558.48 nm/192.36250 THz 6.25/12.5GHz spacing";
           }
           enum "1558.43" {
             description "1558.43 nm/192.36875 THz 6.25GHz spacing";
           }
           enum "1558.38" {
             description "1558.38 nm/192.37500 THz 6.25/12.5GHz spacing";
           }
           enum "1558.32" {
             description "1558.32 nm/192.38125 THz 6.25GHz spacing";
           }
           enum "1558.27" {
             description "1558.27 nm/192.38750 THz 6.25/12.5GHz spacing";
           }
           enum "1558.22" {
             description "1558.22 nm/192.39375 THz 6.25GHz spacing";
           }
           enum "1558.17" {
             description "1558.17 nm/192.40000 THz 6.25/12.5/50/100GHz spacing";
           }
           enum "1558.12" {
             description "1558.12 nm/192.40625 THz 6.25GHz spacing";
           }
           enum "1558.07" {
             description "1558.07 nm/192.41250 THz 6.25/12.5GHz spacing";
           }
           enum "1558.02" {
             description "1558.02 nm/192.41875 THz 6.25GHz spacing";
           }
           enum "1557.97" {
             description "1557.97 nm/192.42500 THz 6.25/12.5/75GHz spacing";
           }
           enum "1557.92" {
             description "1557.92 nm/192.43125 THz 6.25GHz spacing";
           }
           enum "1557.87" {
             description "1557.87 nm/192.43750 THz 6.25/12.5GHz spacing";
           }
           enum "1557.82" {
             description "1557.82 nm/192.44375 THz 6.25GHz spacing";
           }
           enum "1557.77" {
             description "1557.77 nm/192.45000 THz 6.25/12.5/50GHz spacing";
           }
           enum "1557.72" {
             description "1557.72 nm/192.45625 THz 6.25GHz spacing";
           }
           enum "1557.67" {
             description "1557.67 nm/192.46250 THz 6.25/12.5GHz spacing";
           }
           enum "1557.62" {
             description "1557.62 nm/192.46875 THz 6.25GHz spacing";
           }
           enum "1557.57" {
             description "1557.57 nm/192.47500 THz 6.25/12.5GHz spacing";
           }
           enum "1557.52" {
             description "1557.52 nm/192.48125 THz 6.25GHz spacing";
           }
           enum "1557.46" {
             description "1557.46 nm/192.48750 THz 6.25/12.5GHz spacing";
           }
           enum "1557.41" {
             description "1557.41 nm/192.49375 THz 6.25GHz spacing";
           }
           enum "1557.36" {
             description "1557.36 nm/192.50000 THz 6.25/12.5/50/75/100GHz spacing";
           }
           enum "1557.31" {
             description "1557.31 nm/192.50625 THz 6.25GHz spacing";
           }
           enum "1557.26" {
             description "1557.26 nm/192.51250 THz 6.25/12.5GHz spacing";
           }
           enum "1557.21" {
             description "1557.21 nm/192.51875 THz 6.25GHz spacing";
           }
           enum "1557.16" {
             description "1557.16 nm/192.52500 THz 6.25/12.5GHz spacing";
           }
           enum "1557.11" {
             description "1557.11 nm/192.53125 THz 6.25GHz spacing";
           }
           enum "1557.06" {
             description "1557.06 nm/192.53750 THz 6.25/12.5GHz spacing";
           }
           enum "1557.01" {
             description "1557.01 nm/192.54375 THz 6.25GHz spacing";
           }
           enum "1556.96" {
             description "1556.96 nm/192.55000 THz 6.25/12.5/50GHz spacing";
           }
           enum "1556.91" {
             description "1556.91 nm/192.55625 THz 6.25GHz spacing";
           }
           enum "1556.86" {
             description "1556.86 nm/192.56250 THz 6.25/12.5GHz spacing";
           }
           enum "1556.81" {
             description "1556.81 nm/192.56875 THz 6.25GHz spacing";
           }
           enum "1556.76" {
             description "1556.76 nm/192.57500 THz 6.25/12.5/75GHz spacing";
           }
           enum "1556.71" {
             description "1556.71 nm/192.58125 THz 6.25GHz spacing";
           }
           enum "1556.66" {
             description "1556.66 nm/192.58750 THz 6.25/12.5GHz spacing";
           }
           enum "1556.61" {
             description "1556.61 nm/192.59375 THz 6.25GHz spacing";
           }
           enum "1556.55" {
             description "1556.55 nm/192.60000 THz 6.25/12.5/50/100GHz spacing";
           }
           enum "1556.50" {
             description "1556.50 nm/192.60625 THz 6.25GHz spacing";
           }
           enum "1556.45" {
             description "1556.45 nm/192.61250 THz 6.25/12.5GHz spacing";
           }
           enum "1556.40" {
             description "1556.40 nm/192.61875 THz 6.25GHz spacing";
           }
           enum "1556.35" {
             description "1556.35 nm/192.62500 THz 6.25/12.5GHz spacing";
           }
           enum "1556.30" {
             description "1556.30 nm/192.63125 THz 6.25GHz spacing";
           }
           enum "1556.25" {
             description "1556.25 nm/192.63750 THz 6.25/12.5GHz spacing";
           }
           enum "1556.20" {
             description "1556.20 nm/192.64375 THz 6.25GHz spacing";
           }
           enum "1556.15" {
             description "1556.15 nm/192.65000 THz 6.25/12.5/50/75GHz spacing";
           }
           enum "1556.10" {
             description "1556.10 nm/192.65625 THz 6.25GHz spacing";
           }
           enum "1556.05" {
             description "1556.05 nm/192.66250 THz 6.25/12.5GHz spacing";
           }
           enum "1556.00" {
             description "1556.00 nm/192.66875 THz 6.25GHz spacing";
           }
           enum "1555.95" {
             description "1555.95 nm/192.67500 THz 6.25/12.5GHz spacing";
           }
           enum "1555.90" {
             description "1555.90 nm/192.68125 THz 6.25GHz spacing";
           }
           enum "1555.85" {
             description "1555.85 nm/192.68750 THz 6.25/12.5GHz spacing";
           }
           enum "1555.80" {
             description "1555.80 nm/192.69375 THz 6.25GHz spacing";
           }
           enum "1555.75" {
             description "1555.75 nm/192.70000 THz 6.25/12.5/50/100GHz spacing";
           }
           enum "1555.70" {
             description "1555.70 nm/192.70625 THz 6.25GHz spacing";
           }
           enum "1555.65" {
             description "1555.65 nm/192.71250 THz 6.25/12.5GHz spacing";
           }
           enum "1555.60" {
             description "1555.60 nm/192.71875 THz 6.25GHz spacing";
           }
           enum "1555.55" {
             description "1555.55 nm/192.72500 THz 6.25/12.5/75GHz spacing";
           }
           enum "1555.49" {
             description "1555.49 nm/192.73125 THz 6.25GHz spacing";
           }
           enum "1555.44" {
             description "1555.44 nm/192.73750 THz 6.25/12.5GHz spacing";
           }
           enum "1555.39" {
             description "1555.39 nm/192.74375 THz 6.25GHz spacing";
           }
           enum "1555.34" {
             description "1555.34 nm/192.75000 THz 6.25/12.5/50GHz spacing";
           }
           enum "1555.29" {
             description "1555.29 nm/192.75625 THz 6.25GHz spacing";
           }
           enum "1555.24" {
             description "1555.24 nm/192.76250 THz 6.25/12.5GHz spacing";
           }
           enum "1555.19" {
             description "1555.19 nm/192.76875 THz 6.25GHz spacing";
           }
           enum "1555.14" {
             description "1555.14 nm/192.77500 THz 6.25/12.5GHz spacing";
           }
           enum "1555.09" {
             description "1555.09 nm/192.78125 THz 6.25GHz spacing";
           }
           enum "1555.04" {
             description "1555.04 nm/192.78750 THz 6.25/12.5GHz spacing";
           }
           enum "1554.99" {
             description "1554.99 nm/192.79375 THz 6.25GHz spacing";
           }
           enum "1554.94" {
             description "1554.94 nm/192.80000 THz 6.25/12.5/50/75/100GHz spacing";
           }
           enum "1554.89" {
             description "1554.89 nm/192.80625 THz 6.25GHz spacing";
           }
           enum "1554.84" {
             description "1554.84 nm/192.81250 THz 6.25/12.5GHz spacing";
           }
           enum "1554.79" {
             description "1554.79 nm/192.81875 THz 6.25GHz spacing";
           }
           enum "1554.74" {
             description "1554.74 nm/192.82500 THz 6.25/12.5GHz spacing";
           }
           enum "1554.69" {
             description "1554.69 nm/192.83125 THz 6.25GHz spacing";
           }
           enum "1554.64" {
             description "1554.64 nm/192.83750 THz 6.25/12.5GHz spacing";
           }
           enum "1554.59" {
             description "1554.59 nm/192.84375 THz 6.25GHz spacing";
           }
           enum "1554.54" {
             description "1554.54 nm/192.85000 THz 6.25/12.5/50GHz spacing";
           }
           enum "1554.49" {
             description "1554.49 nm/192.85625 THz 6.25GHz spacing";
           }
           enum "1554.44" {
             description "1554.44 nm/192.86250 THz 6.25/12.5GHz spacing";
           }
           enum "1554.39" {
             description "1554.39 nm/192.86875 THz 6.25GHz spacing";
           }
           enum "1554.34" {
             description "1554.34 nm/192.87500 THz 6.25/12.5/75GHz spacing";
           }
           enum "1554.29" {
             description "1554.29 nm/192.88125 THz 6.25GHz spacing";
           }
           enum "1554.23" {
             description "1554.23 nm/192.88750 THz 6.25/12.5GHz spacing";
           }
           enum "1554.18" {
             description "1554.18 nm/192.89375 THz 6.25GHz spacing";
           }
           enum "1554.13" {
             description "1554.13 nm/192.90000 THz 6.25/12.5/50/100GHz spacing";
           }
           enum "1554.08" {
             description "1554.08 nm/192.90625 THz 6.25GHz spacing";
           }
           enum "1554.03" {
             description "1554.03 nm/192.91250 THz 6.25/12.5GHz spacing";
           }
           enum "1553.98" {
             description "1553.98 nm/192.91875 THz 6.25GHz spacing";
           }
           enum "1553.93" {
             description "1553.93 nm/192.92500 THz 6.25/12.5GHz spacing";
           }
           enum "1553.88" {
             description "1553.88 nm/192.93125 THz 6.25GHz spacing";
           }
           enum "1553.83" {
             description "1553.83 nm/192.93750 THz 6.25/12.5GHz spacing";
           }
           enum "1553.78" {
             description "1553.78 nm/192.94375 THz 6.25GHz spacing";
           }
           enum "1553.73" {
             description "1553.73 nm/192.95000 THz 6.25/12.5/50/75GHz spacing";
           }
           enum "1553.68" {
             description "1553.68 nm/192.95625 THz 6.25GHz spacing";
           }
           enum "1553.63" {
             description "1553.63 nm/192.96250 THz 6.25/12.5GHz spacing";
           }
           enum "1553.58" {
             description "1553.58 nm/192.96875 THz 6.25GHz spacing";
           }
           enum "1553.53" {
             description "1553.53 nm/192.97500 THz 6.25/12.5GHz spacing";
           }
           enum "1553.48" {
             description "1553.48 nm/192.98125 THz 6.25GHz spacing";
           }
           enum "1553.43" {
             description "1553.43 nm/192.98750 THz 6.25/12.5GHz spacing";
           }
           enum "1553.38" {
             description "1553.38 nm/192.99375 THz 6.25GHz spacing";
           }
           enum "1553.33" {
             description "1553.33 nm/193.00000 THz 6.25/12.5/50/100GHz spacing";
           }
           enum "1553.28" {
             description "1553.28 nm/193.00625 THz 6.25GHz spacing";
           }
           enum "1553.23" {
             description "1553.23 nm/193.01250 THz 6.25/12.5GHz spacing";
           }
           enum "1553.18" {
             description "1553.18 nm/193.01875 THz 6.25GHz spacing";
           }
           enum "1553.13" {
             description "1553.13 nm/193.02500 THz 6.25/12.5/75GHz spacing";
           }
           enum "1553.08" {
             description "1553.08 nm/193.03125 THz 6.25GHz spacing";
           }
           enum "1553.03" {
             description "1553.03 nm/193.03750 THz 6.25/12.5GHz spacing";
           }
           enum "1552.98" {
             description "1552.98 nm/193.04375 THz 6.25GHz spacing";
           }
           enum "1552.93" {
             description "1552.93 nm/193.05000 THz 6.25/12.5/50GHz spacing";
           }
           enum "1552.88" {
             description "1552.88 nm/193.05625 THz 6.25GHz spacing";
           }
           enum "1552.83" {
             description "1552.83 nm/193.06250 THz 6.25/12.5GHz spacing";
           }
           enum "1552.78" {
             description "1552.78 nm/193.06875 THz 6.25GHz spacing";
           }
           enum "1552.73" {
             description "1552.73 nm/193.07500 THz 6.25/12.5GHz spacing";
           }
           enum "1552.68" {
             description "1552.68 nm/193.08125 THz 6.25GHz spacing";
           }
           enum "1552.62" {
             description "1552.62 nm/193.08750 THz 6.25/12.5GHz spacing";
           }
           enum "1552.57" {
             description "1552.57 nm/193.09375 THz 6.25GHz spacing";
           }
           enum "1552.52" {
             description "1552.52 nm/193.10000 THz 6.25/12.5/50/75/100GHz spacing";
           }
           enum "1552.47" {
             description "1552.47 nm/193.10625 THz 6.25GHz spacing";
           }
           enum "1552.42" {
             description "1552.42 nm/193.11250 THz 6.25/12.5GHz spacing";
           }
           enum "1552.37" {
             description "1552.37 nm/193.11875 THz 6.25GHz spacing";
           }
           enum "1552.32" {
             description "1552.32 nm/193.12500 THz 6.25/12.5GHz spacing";
           }
           enum "1552.27" {
             description "1552.27 nm/193.13125 THz 6.25GHz spacing";
           }
           enum "1552.22" {
             description "1552.22 nm/193.13750 THz 6.25/12.5GHz spacing";
           }
           enum "1552.17" {
             description "1552.17 nm/193.14375 THz 6.25GHz spacing";
           }
           enum "1552.12" {
             description "1552.12 nm/193.15000 THz 6.25/12.5/50GHz spacing";
           }
           enum "1552.07" {
             description "1552.07 nm/193.15625 THz 6.25GHz spacing";
           }
           enum "1552.02" {
             description "1552.02 nm/193.16250 THz 6.25/12.5GHz spacing";
           }
           enum "1551.97" {
             description "1551.97 nm/193.16875 THz 6.25GHz spacing";
           }
           enum "1551.92" {
             description "1551.92 nm/193.17500 THz 6.25/12.5/75GHz spacing";
           }
           enum "1551.87" {
             description "1551.87 nm/193.18125 THz 6.25GHz spacing";
           }
           enum "1551.82" {
             description "1551.82 nm/193.18750 THz 6.25/12.5GHz spacing";
           }
           enum "1551.77" {
             description "1551.77 nm/193.19375 THz 6.25GHz spacing";
           }
           enum "1551.72" {
             description "1551.72 nm/193.20000 THz 6.25/12.5/50/100GHz spacing";
           }
           enum "1551.67" {
             description "1551.67 nm/193.20625 THz 6.25GHz spacing";
           }
           enum "1551.62" {
             description "1551.62 nm/193.21250 THz 6.25/12.5GHz spacing";
           }
           enum "1551.57" {
             description "1551.57 nm/193.21875 THz 6.25GHz spacing";
           }
           enum "1551.52" {
             description "1551.52 nm/193.22500 THz 6.25/12.5GHz spacing";
           }
           enum "1551.47" {
             description "1551.47 nm/193.23125 THz 6.25GHz spacing";
           }
           enum "1551.42" {
             description "1551.42 nm/193.23750 THz 6.25/12.5GHz spacing";
           }
           enum "1551.37" {
             description "1551.37 nm/193.24375 THz 6.25GHz spacing";
           }
           enum "1551.32" {
             description "1551.32 nm/193.25000 THz 6.25/12.5/50/75GHz spacing";
           }
           enum "1551.27" {
             description "1551.27 nm/193.25625 THz 6.25GHz spacing";
           }
           enum "1551.22" {
             description "1551.22 nm/193.26250 THz 6.25/12.5GHz spacing";
           }
           enum "1551.17" {
             description "1551.17 nm/193.26875 THz 6.25GHz spacing";
           }
           enum "1551.12" {
             description "1551.12 nm/193.27500 THz 6.25/12.5GHz spacing";
           }
           enum "1551.07" {
             description "1551.07 nm/193.28125 THz 6.25GHz spacing";
           }
           enum "1551.02" {
             description "1551.02 nm/193.28750 THz 6.25/12.5GHz spacing";
           }
           enum "1550.97" {
             description "1550.97 nm/193.29375 THz 6.25GHz spacing";
           }
           enum "1550.92" {
             description "1550.92 nm/193.30000 THz 6.25/12.5/50/100GHz spacing";
           }
           enum "1550.87" {
             description "1550.87 nm/193.30625 THz 6.25GHz spacing";
           }
           enum "1550.82" {
             description "1550.82 nm/193.31250 THz 6.25/12.5GHz spacing";
           }
           enum "1550.77" {
             description "1550.77 nm/193.31875 THz 6.25GHz spacing";
           }
           enum "1550.72" {
             description "1550.72 nm/193.32500 THz 6.25/12.5/75GHz spacing";
           }
           enum "1550.67" {
             description "1550.67 nm/193.33125 THz 6.25GHz spacing";
           }
           enum "1550.62" {
             description "1550.62 nm/193.33750 THz 6.25/12.5GHz spacing";
           }
           enum "1550.57" {
             description "1550.57 nm/193.34375 THz 6.25GHz spacing";
           }
           enum "1550.52" {
             description "1550.52 nm/193.35000 THz 6.25/12.5/50GHz spacing";
           }
           enum "1550.47" {
             description "1550.47 nm/193.35625 THz 6.25GHz spacing";
           }
           enum "1550.42" {
             description "1550.42 nm/193.36250 THz 6.25/12.5GHz spacing";
           }
           enum "1550.37" {
             description "1550.37 nm/193.36875 THz 6.25GHz spacing";
           }
           enum "1550.32" {
             description "1550.32 nm/193.37500 THz 6.25/12.5GHz spacing";
           }
           enum "1550.27" {
             description "1550.27 nm/193.38125 THz 6.25GHz spacing";
           }
           enum "1550.22" {
             description "1550.22 nm/193.38750 THz 6.25/12.5GHz spacing";
           }
           enum "1550.17" {
             description "1550.17 nm/193.39375 THz 6.25GHz spacing";
           }
           enum "1550.12" {
             description "1550.12 nm/193.40000 THz 6.25/12.5/50/75/100GHz spacing";
           }
           enum "1550.07" {
             description "1550.07 nm/193.40625 THz 6.25GHz spacing";
           }
           enum "1550.02" {
             description "1550.02 nm/193.41250 THz 6.25/12.5GHz spacing";
           }
           enum "1549.97" {
             description "1549.97 nm/193.41875 THz 6.25GHz spacing";
           }
           enum "1549.92" {
             description "1549.92 nm/193.42500 THz 6.25/12.5GHz spacing";
           }
           enum "1549.87" {
             description "1549.87 nm/193.43125 THz 6.25GHz spacing";
           }
           enum "1549.82" {
             description "1549.82 nm/193.43750 THz 6.25/12.5GHz spacing";
           }
           enum "1549.77" {
             description "1549.77 nm/193.44375 THz 6.25GHz spacing";
           }
           enum "1549.72" {
             description "1549.72 nm/193.45000 THz 6.25/12.5/50GHz spacing";
           }
           enum "1549.67" {
             description "1549.67 nm/193.45625 THz 6.25GHz spacing";
           }
           enum "1549.62" {
             description "1549.62 nm/193.46250 THz 6.25/12.5GHz spacing";
           }
           enum "1549.57" {
             description "1549.57 nm/193.46875 THz 6.25GHz spacing";
           }
           enum "1549.52" {
             description "1549.52 nm/193.47500 THz 6.25/12.5/75GHz spacing";
           }
           enum "1549.47" {
             description "1549.47 nm/193.48125 THz 6.25GHz spacing";
           }
           enum "1549.42" {
             description "1549.42 nm/193.48750 THz 6.25/12.5GHz spacing";
           }
           enum "1549.37" {
             description "1549.37 nm/193.49375 THz 6.25GHz spacing";
           }
           enum "1549.32" {
             description "1549.32 nm/193.50000 THz 6.25/12.5/50/100GHz spacing";
           }
           enum "1549.26" {
             description "1549.26 nm/193.50625 THz 6.25GHz spacing";
           }
           enum "1549.21" {
             description "1549.21 nm/193.51250 THz 6.25/12.5GHz spacing";
           }
           enum "1549.16" {
             description "1549.16 nm/193.51875 THz 6.25GHz spacing";
           }
           enum "1549.11" {
             description "1549.11 nm/193.52500 THz 6.25/12.5GHz spacing";
           }
           enum "1549.06" {
             description "1549.06 nm/193.53125 THz 6.25GHz spacing";
           }
           enum "1549.01" {
             description "1549.01 nm/193.53750 THz 6.25/12.5GHz spacing";
           }
           enum "1548.96" {
             description "1548.96 nm/193.54375 THz 6.25GHz spacing";
           }
           enum "1548.91" {
             description "1548.91 nm/193.55000 THz 6.25/12.5/50G/75Hz spacing";
           }
           enum "1548.86" {
             description "1548.86 nm/193.55625 THz 6.25GHz spacing";
           }
           enum "1548.81" {
             description "1548.81 nm/193.56250 THz 6.25/12.5GHz spacing";
           }
           enum "1548.76" {
             description "1548.76 nm/193.56875 THz 6.25GHz spacing";
           }
           enum "1548.71" {
             description "1548.71 nm/193.57500 THz 6.25/12.5GHz spacing";
           }
           enum "1548.66" {
             description "1548.66 nm/193.58125 THz 6.25GHz spacing";
           }
           enum "1548.61" {
             description "1548.61 nm/193.58750 THz 6.25/12.5GHz spacing";
           }
           enum "1548.56" {
             description "1548.56 nm/193.59375 THz 6.25GHz spacing";
           }
           enum "1548.51" {
             description "1548.51 nm/193.60000 THz 6.25/12.5/50/100GHz spacing";
           }
           enum "1548.46" {
             description "1548.46 nm/193.60625 THz 6.25GHz spacing";
           }
           enum "1548.41" {
             description "1548.41 nm/193.61250 THz 6.25/12.5GHz spacing";
           }
           enum "1548.36" {
             description "1548.36 nm/193.61875 THz 6.25GHz spacing";
           }
           enum "1548.31" {
             description "1548.31 nm/193.62500 THz 6.25/12.5/75GHz spacing";
           }
           enum "1548.26" {
             description "1548.26 nm/193.63125 THz 6.25GHz spacing";
           }
           enum "1548.21" {
             description "1548.21 nm/193.63750 THz 6.25/12.5GHz spacing";
           }
           enum "1548.16" {
             description "1548.16 nm/193.64375 THz 6.25GHz spacing";
           }
           enum "1548.11" {
             description "1548.11 nm/193.65000 THz 6.25/12.5/50GHz spacing";
           }
           enum "1548.06" {
             description "1548.06 nm/193.65625 THz 6.25GHz spacing";
           }
           enum "1548.02" {
             description "1548.02 nm/193.66250 THz 6.25/12.5GHz spacing";
           }
           enum "1547.97" {
             description "1547.97 nm/193.66875 THz 6.25GHz spacing";
           }
           enum "1547.92" {
             description "1547.92 nm/193.67500 THz 6.25/12.5GHz spacing";
           }
           enum "1547.87" {
             description "1547.87 nm/193.68125 THz 6.25GHz spacing";
           }
           enum "1547.82" {
             description "1547.82 nm/193.68750 THz 6.25/12.5GHz spacing";
           }
           enum "1547.77" {
             description "1547.77 nm/193.69375 THz 6.25GHz spacing";
           }
           enum "1547.72" {
             description "1547.72 nm/193.70000 THz 6.25/12.5/50/75/100GHz spacing";
           }
           enum "1547.67" {
             description "1547.67 nm/193.70625 THz 6.25GHz spacing";
           }
           enum "1547.62" {
             description "1547.62 nm/193.71250 THz 6.25/12.5GHz spacing";
           }
           enum "1547.57" {
             description "1547.57 nm/193.71875 THz 6.25GHz spacing";
           }
           enum "1547.52" {
             description "1547.52 nm/193.72500 THz 6.25/12.5GHz spacing";
           }
           enum "1547.47" {
             description "1547.47 nm/193.73125 THz 6.25GHz spacing";
           }
           enum "1547.42" {
             description "1547.42 nm/193.73750 THz 6.25/12.5GHz spacing";
           }
           enum "1547.37" {
             description "1547.37 nm/193.74375 THz 6.25GHz spacing";
           }
           enum "1547.32" {
             description "1547.32 nm/193.75000 THz 6.25/12.5/50GHz spacing";
           }
           enum "1547.27" {
             description "1547.27 nm/193.75625 THz 6.25GHz spacing";
           }
           enum "1547.22" {
             description "1547.22 nm/193.76250 THz 6.25/12.5GHz spacing";
           }
           enum "1547.17" {
             description "1547.17 nm/193.76875 THz 6.25GHz spacing";
           }
           enum "1547.12" {
             description "1547.12 nm/193.77500 THz 6.25/12.5/75GHz spacing";
           }
           enum "1547.07" {
             description "1547.07 nm/193.78125 THz 6.25GHz spacing";
           }
           enum "1547.02" {
             description "1547.02 nm/193.78750 THz 6.25/12.5GHz spacing";
           }
           enum "1546.97" {
             description "1546.97 nm/193.79375 THz 6.25GHz spacing";
           }
           enum "1546.92" {
             description "1546.92 nm/193.80000 THz 6.25/12.5/50/100GHz spacing";
           }
           enum "1546.87" {
             description "1546.87 nm/193.80625 THz 6.25GHz spacing";
           }
           enum "1546.82" {
             description "1546.82 nm/193.81250 THz 6.25/12.5GHz spacing";
           }
           enum "1546.77" {
             description "1546.77 nm/193.81875 THz 6.25GHz spacing";
           }
           enum "1546.72" {
             description "1546.72 nm/193.82500 THz 6.25/12.5GHz spacing";
           }
           enum "1546.67" {
             description "1546.67 nm/193.83125 THz 6.25GHz spacing";
           }
           enum "1546.62" {
             description "1546.62 nm/193.83750 THz 6.25/12.5GHz spacing";
           }
           enum "1546.57" {
             description "1546.57 nm/193.84375 THz 6.25GHz spacing";
           }
           enum "1546.52" {
             description "1546.52 nm/193.85000 THz 6.25/12.5/50/75GHz spacing";
           }
           enum "1546.47" {
             description "1546.47 nm/193.85625 THz 6.25GHz spacing";
           }
           enum "1546.42" {
             description "1546.42 nm/193.86250 THz 6.25/12.5GHz spacing";
           }
           enum "1546.37" {
             description "1546.37 nm/193.86875 THz 6.25GHz spacing";
           }
           enum "1546.32" {
             description "1546.32 nm/193.87500 THz 6.25/12.5GHz spacing";
           }
           enum "1546.27" {
             description "1546.27 nm/193.88125 THz 6.25GHz spacing";
           }
           enum "1546.22" {
             description "1546.22 nm/193.88750 THz 6.25/12.5GHz spacing";
           }
           enum "1546.17" {
             description "1546.17 nm/193.89375 THz 6.25GHz spacing";
           }
           enum "1546.12" {
             description "1546.12 nm/193.90000 THz 6.25/12.5/50/100GHz spacing";
           }
           enum "1546.07" {
             description "1546.07 nm/193.90625 THz 6.25GHz spacing";
           }
           enum "1546.02" {
             description "1546.02 nm/193.91250 THz 6.25/12.5GHz spacing";
           }
           enum "1545.97" {
             description "1545.97 nm/193.91875 THz 6.25GHz spacing";
           }
           enum "1545.92" {
             description "1545.92 nm/193.92500 THz 6.25/12.5/75GHz spacing";
           }
           enum "1545.87" {
             description "1545.87 nm/193.93125 THz 6.25GHz spacing";
           }
           enum "1545.82" {
             description "1545.82 nm/193.93750 THz 6.25/12.5GHz spacing";
           }
           enum "1545.77" {
             description "1545.77 nm/193.94375 THz 6.25GHz spacing";
           }
           enum "1545.72" {
             description "1545.72 nm/193.95000 THz 6.25/12.5/50GHz spacing";
           }
           enum "1545.67" {
             description "1545.67 nm/193.95625 THz 6.25GHz spacing";
           }
           enum "1545.62" {
             description "1545.62 nm/193.96250 THz 6.25/12.5GHz spacing";
           }
           enum "1545.57" {
             description "1545.57 nm/193.96875 THz 6.25GHz spacing";
           }
           enum "1545.52" {
             description "1545.52 nm/193.97500 THz 6.25/12.5GHz spacing";
           }
           enum "1545.47" {
             description "1545.47 nm/193.98125 THz 6.25GHz spacing";
           }
           enum "1545.42" {
             description "1545.42 nm/193.98750 THz 6.25/12.5GHz spacing";
           }
           enum "1545.37" {
             description "1545.37 nm/193.99375 THz 6.25GHz spacing";
           }
           enum "1545.32" {
             description "1545.32 nm/194.00000 THz 6.25/12.5/50/75/100GHz spacing";
           }
           enum "1545.27" {
             description "1545.27 nm/194.00625 THz 6.25GHz spacing";
           }
           enum "1545.22" {
             description "1545.22 nm/194.01250 THz 6.25/12.5GHz spacing";
           }
           enum "1545.17" {
             description "1545.17 nm/194.01875 THz 6.25GHz spacing";
           }
           enum "1545.12" {
             description "1545.12 nm/194.02500 THz 6.25/12.5GHz spacing";
           }
           enum "1545.07" {
             description "1545.07 nm/194.03125 THz 6.25GHz spacing";
           }
           enum "1545.02" {
             description "1545.02 nm/194.03750 THz 6.25/12.5GHz spacing";
           }
           enum "1544.97" {
             description "1544.97 nm/194.04375 THz 6.25GHz spacing";
           }
           enum "1544.92" {
             description "1544.92 nm/194.05000 THz 6.25/12.5/50GHz spacing";
           }
           enum "1544.87" {
             description "1544.87 nm/194.05625 THz 6.25GHz spacing";
           }
           enum "1544.82" {
             description "1544.82 nm/194.06250 THz 6.25/12.5GHz spacing";
           }
           enum "1544.77" {
             description "1544.77 nm/194.06875 THz 6.25GHz spacing";
           }
           enum "1544.72" {
             description "1544.72 nm/194.07500 THz 6.25/12.5/75GHz spacing";
           }
           enum "1544.68" {
             description "1544.68 nm/194.08125 THz 6.25GHz spacing";
           }
           enum "1544.63" {
             description "1544.63 nm/194.08750 THz 6.25/12.5GHz spacing";
           }
           enum "1544.58" {
             description "1544.58 nm/194.09375 THz 6.25GHz spacing";
           }
           enum "1544.53" {
             description "1544.53 nm/194.10000 THz 6.25/12.5/50/100GHz spacing";
           }
           enum "1544.48" {
             description "1544.48 nm/194.10625 THz 6.25GHz spacing";
           }
           enum "1544.43" {
             description "1544.43 nm/194.11250 THz 6.25/12.5GHz spacing";
           }
           enum "1544.38" {
             description "1544.38 nm/194.11875 THz 6.25GHz spacing";
           }
           enum "1544.33" {
             description "1544.33 nm/194.12500 THz 6.25/12.5GHz spacing";
           }
           enum "1544.28" {
             description "1544.28 nm/194.13125 THz 6.25GHz spacing";
           }
           enum "1544.23" {
             description "1544.23 nm/194.13750 THz 6.25/12.5GHz spacing";
           }
           enum "1544.18" {
             description "1544.18 nm/194.14375 THz 6.25GHz spacing";
           }
           enum "1544.13" {
             description "1544.13 nm/194.15000 THz 6.25/12.5/50/75GHz spacing";
           }
           enum "1544.08" {
             description "1544.08 nm/194.15625 THz 6.25GHz spacing";
           }
           enum "1544.03" {
             description "1544.03 nm/194.16250 THz 6.25/12.5GHz spacing";
           }
           enum "1543.98" {
             description "1543.98 nm/194.16875 THz 6.25GHz spacing";
           }
           enum "1543.93" {
             description "1543.93 nm/194.17500 THz 6.25/12.5GHz spacing";
           }
           enum "1543.88" {
             description "1543.88 nm/194.18125 THz 6.25GHz spacing";
           }
           enum "1543.83" {
             description "1543.83 nm/194.18750 THz 6.25/12.5GHz spacing";
           }
           enum "1543.78" {
             description "1543.78 nm/194.19375 THz 6.25GHz spacing";
           }
           enum "1543.73" {
             description "1543.73 nm/194.20000 THz 6.25/12.5/50/100GHz spacing";
           }
           enum "1543.68" {
             description "1543.68 nm/194.20625 THz 6.25GHz spacing";
           }
           enum "1543.63" {
             description "1543.63 nm/194.21250 THz 6.25/12.5GHz spacing";
           }
           enum "1543.58" {
             description "1543.58 nm/194.21875 THz 6.25GHz spacing";
           }
           enum "1543.53" {
             description "1543.53 nm/194.22500 THz 6.25/12.5/75GHz spacing";
           }
           enum "1543.48" {
             description "1543.48 nm/194.23125 THz 6.25GHz spacing";
           }
           enum "1543.43" {
             description "1543.43 nm/194.23750 THz 6.25/12.5GHz spacing";
           }
           enum "1543.38" {
             description "1543.38 nm/194.24375 THz 6.25GHz spacing";
           }
           enum "1543.33" {
             description "1543.33 nm/194.25000 THz 6.25/12.5/50GHz spacing";
           }
           enum "1543.28" {
             description "1543.28 nm/194.25625 THz 6.25GHz spacing";
           }
           enum "1543.23" {
             description "1543.23 nm/194.26250 THz 6.25/12.5GHz spacing";
           }
           enum "1543.18" {
             description "1543.18 nm/194.26875 THz 6.25GHz spacing";
           }
           enum "1543.13" {
             description "1543.13 nm/194.27500 THz 6.25/12.5GHz spacing";
           }
           enum "1543.08" {
             description "1543.08 nm/194.28125 THz 6.25GHz spacing";
           }
           enum "1543.04" {
             description "1543.04 nm/194.28750 THz 6.25/12.5GHz spacing";
           }
           enum "1542.99" {
             description "1542.99 nm/194.29375 THz 6.25GHz spacing";
           }
           enum "1542.94" {
             description "1542.94 nm/194.30000 THz 6.25/12.5/50/75/100GHz spacing";
           }
           enum "1542.89" {
             description "1542.89 nm/194.30625 THz 6.25GHz spacing";
           }
           enum "1542.84" {
             description "1542.84 nm/194.31250 THz 6.25/12.5GHz spacing";
           }
           enum "1542.79" {
             description "1542.79 nm/194.31875 THz 6.25GHz spacing";
           }
           enum "1542.74" {
             description "1542.74 nm/194.32500 THz 6.25/12.5GHz spacing";
           }
           enum "1542.69" {
             description "1542.69 nm/194.33125 THz 6.25GHz spacing";
           }
           enum "1542.64" {
             description "1542.64 nm/194.33750 THz 6.25/12.5GHz spacing";
           }
           enum "1542.59" {
             description "1542.59 nm/194.34375 THz 6.25GHz spacing";
           }
           enum "1542.54" {
             description "1542.54 nm/194.35000 THz 6.25/12.5/50GHz spacing";
           }
           enum "1542.49" {
             description "1542.49 nm/194.35625 THz 6.25GHz spacing";
           }
           enum "1542.44" {
             description "1542.44 nm/194.36250 THz 6.25/12.5GHz spacing";
           }
           enum "1542.39" {
             description "1542.39 nm/194.36875 THz 6.25GHz spacing";
           }
           enum "1542.34" {
             description "1542.34 nm/194.37500 THz 6.25/12.5/75GHz spacing";
           }
           enum "1542.29" {
             description "1542.29 nm/194.38125 THz 6.25GHz spacing";
           }
           enum "1542.24" {
             description "1542.24 nm/194.38750 THz 6.25/12.5GHz spacing";
           }
           enum "1542.19" {
             description "1542.19 nm/194.39375 THz 6.25GHz spacing";
           }
           enum "1542.14" {
             description "1542.14 nm/194.40000 THz 6.25/12.5/50/100GHz spacing";
           }
           enum "1542.09" {
             description "1542.09 nm/194.40625 THz 6.25GHz spacing";
           }
           enum "1542.04" {
             description "1542.04 nm/194.41250 THz 6.25/12.5GHz spacing";
           }
           enum "1541.99" {
             description "1541.99 nm/194.41875 THz 6.25GHz spacing";
           }
           enum "1541.94" {
             description "1541.94 nm/194.42500 THz 6.25/12.5GHz spacing";
           }
           enum "1541.89" {
             description "1541.89 nm/194.43125 THz 6.25GHz spacing";
           }
           enum "1541.84" {
             description "1541.84 nm/194.43750 THz 6.25/12.5GHz spacing";
           }
           enum "1541.80" {
             description "1541.80 nm/194.44375 THz 6.25GHz spacing";
           }
           enum "1541.75" {
             description "1541.75 nm/194.45000 THz 6.25/12.5/50/75GHz spacing";
           }
           enum "1541.70" {
             description "1541.70 nm/194.45625 THz 6.25GHz spacing";
           }
           enum "1541.65" {
             description "1541.65 nm/194.46250 THz 6.25/12.5GHz spacing";
           }
           enum "1541.60" {
             description "1541.60 nm/194.46875 THz 6.25GHz spacing";
           }
           enum "1541.55" {
             description "1541.55 nm/194.47500 THz 6.25/12.5GHz spacing";
           }
           enum "1541.50" {
             description "1541.50 nm/194.48125 THz 6.25GHz spacing";
           }
           enum "1541.45" {
             description "1541.45 nm/194.48750 THz 6.25/12.5GHz spacing";
           }
           enum "1541.40" {
             description "1541.40 nm/194.49375 THz 6.25GHz spacing";
           }
           enum "1541.35" {
             description "1541.35 nm/194.50000 THz 6.25/12.5/50/100GHz spacing";
           }
           enum "1541.30" {
             description "1541.30 nm/194.50625 THz 6.25GHz spacing";
           }
           enum "1541.25" {
             description "1541.25 nm/194.51250 THz 6.25/12.5GHz spacing";
           }
           enum "1541.20" {
             description "1541.20 nm/194.51875 THz 6.25GHz spacing";
           }
           enum "1541.15" {
             description "1541.15 nm/194.52500 THz 6.25/12.5/75GHz spacing";
           }
           enum "1541.10" {
             description "1541.10 nm/194.53125 THz 6.25GHz spacing";
           }
           enum "1541.05" {
             description "1541.05 nm/194.53750 THz 6.25/12.5GHz spacing";
           }
           enum "1541.00" {
             description "1541.00 nm/194.54375 THz 6.25GHz spacing";
           }
           enum "1540.95" {
             description "1540.95 nm/194.55000 THz 6.25/12.5/50GHz spacing";
           }
           enum "1540.90" {
             description "1540.90 nm/194.55625 THz 6.25GHz spacing";
           }
           enum "1540.85" {
             description "1540.85 nm/194.56250 THz 6.25/12.5GHz spacing";
           }
           enum "1540.80" {
             description "1540.80 nm/194.56875 THz 6.25GHz spacing";
           }
           enum "1540.76" {
             description "1540.76 nm/194.57500 THz 6.25/12.5GHz spacing";
           }
           enum "1540.71" {
             description "1540.71 nm/194.58125 THz 6.25GHz spacing";
           }
           enum "1540.66" {
             description "1540.66 nm/194.58750 THz 6.25/12.5GHz spacing";
           }
           enum "1540.61" {
             description "1540.61 nm/194.59375 THz 6.25GHz spacing";
           }
           enum "1540.56" {
             description "1540.56 nm/194.60000 THz 6.25/12.5/50/75/100GHz spacing";
           }
           enum "1540.51" {
             description "1540.51 nm/194.60625 THz 6.25GHz spacing";
           }
           enum "1540.46" {
             description "1540.46 nm/194.61250 THz 6.25/12.5GHz spacing";
           }
           enum "1540.41" {
             description "1540.41 nm/194.61875 THz 6.25GHz spacing";
           }
           enum "1540.36" {
             description "1540.36 nm/194.62500 THz 6.25/12.5GHz spacing";
           }
           enum "1540.31" {
             description "1540.31 nm/194.63125 THz 6.25GHz spacing";
           }
           enum "1540.26" {
             description "1540.26 nm/194.63750 THz 6.25/12.5GHz spacing";
           }
           enum "1540.21" {
             description "1540.21 nm/194.64375 THz 6.25GHz spacing";
           }
           enum "1540.16" {
             description "1540.16 nm/194.65000 THz 6.25/12.5/50GHz spacing";
           }
           enum "1540.11" {
             description "1540.11 nm/194.65625 THz 6.25GHz spacing";
           }
           enum "1540.06" {
             description "1540.06 nm/194.66250 THz 6.25/12.5GHz spacing";
           }
           enum "1540.01" {
             description "1540.01 nm/194.66875 THz 6.25GHz spacing";
           }
           enum "1539.96" {
             description "1539.96 nm/194.67500 THz 6.25/12.5/50/75GHz spacing";
           }
           enum "1539.91" {
             description "1539.91 nm/194.68125 THz 6.25GHz spacing";
           }
           enum "1539.86" {
             description "1539.86 nm/194.68750 THz 6.25/12.5GHz spacing";
           }
           enum "1539.82" {
             description "1539.82 nm/194.69375 THz 6.25GHz spacing";
           }
           enum "1539.77" {
             description "1539.77 nm/194.70000 THz 6.25/12.5/50/100GHz spacing";
           }
           enum "1539.72" {
             description "1539.72 nm/194.70625 THz 6.25GHz spacing";
           }
           enum "1539.67" {
             description "1539.67 nm/194.71250 THz 6.25/12.5GHz spacing";
           }
           enum "1539.62" {
             description "1539.62 nm/194.71875 THz 6.25GHz spacing";
           }
           enum "1539.57" {
             description "1539.57 nm/194.72500 THz 6.25/12.5GHz spacing";
           }
           enum "1539.52" {
             description "1539.52 nm/194.73125 THz 6.25GHz spacing";
           }
           enum "1539.47" {
             description "1539.47 nm/194.73750 THz 6.25/12.5GHz spacing";
           }
           enum "1539.42" {
             description "1539.42 nm/194.74375 THz 6.25GHz spacing";
           }
           enum "1539.37" {
             description "1539.37 nm/194.75000 THz 6.25/12.5/50/75GHz spacing";
           }
           enum "1539.32" {
             description "1539.32 nm/194.75625 THz 6.25GHz spacing";
           }
           enum "1539.27" {
             description "1539.27 nm/194.76250 THz 6.25/12.5GHz spacing";
           }
           enum "1539.22" {
             description "1539.22 nm/194.76875 THz 6.25GHz spacing";
           }
           enum "1539.17" {
             description "1539.17 nm/194.77500 THz 6.25/12.5GHz spacing";
           }
           enum "1539.12" {
             description "1539.12 nm/194.78125 THz 6.25GHz spacing";
           }
           enum "1539.07" {
             description "1539.07 nm/194.78750 THz 6.25/12.5GHz spacing";
           }
           enum "1539.03" {
             description "1539.03 nm/194.79375 THz 6.25GHz spacing";
           }
           enum "1538.98" {
             description "1538.98 nm/194.80000 THz 6.25/12.5/50/100GHz spacing";
           }
           enum "1538.93" {
             description "1538.93 nm/194.80625 THz 6.25GHz spacing";
           }
           enum "1538.88" {
             description "1538.88 nm/194.81250 THz 6.25/12.5GHz spacing";
           }
           enum "1538.83" {
             description "1538.83 nm/194.81875 THz 6.25GHz spacing";
           }
           enum "1538.78" {
             description "1538.78 nm/194.82500 THz 6.25/12.5/75GHz spacing";
           }
           enum "1538.73" {
             description "1538.73 nm/194.83125 THz 6.25GHz spacing";
           }
           enum "1538.68" {
             description "1538.68 nm/194.83750 THz 6.25/12.5GHz spacing";
           }
           enum "1538.63" {
             description "1538.63 nm/194.84375 THz 6.25GHz spacing";
           }
           enum "1538.58" {
             description "1538.58 nm/194.85000 THz 6.25/12.5/50GHz spacing";
           }
           enum "1538.53" {
             description "1538.53 nm/194.85625 THz 6.25GHz spacing";
           }
           enum "1538.48" {
             description "1538.48 nm/194.86250 THz 6.25/12.5GHz spacing";
           }
           enum "1538.43" {
             description "1538.43 nm/194.86875 THz 6.25GHz spacing";
           }
           enum "1538.38" {
             description "1538.38 nm/194.87500 THz 6.25/12.5/75GHz spacing";
           }
           enum "1538.33" {
             description "1538.33 nm/194.88125 THz 6.25GHz spacing";
           }
           enum "1538.28" {
             description "1538.28 nm/194.88750 THz 6.25/12.5GHz spacing";
           }
           enum "1538.24" {
             description "1538.24 nm/194.89375 THz 6.25GHz spacing";
           }
           enum "1538.19" {
             description "1538.19 nm/194.90000 THz 6.25/12.5/50/75/100GHz spacing";
           }
           enum "1538.14" {
             description "1538.14 nm/194.90625 THz 6.25GHz spacing";
           }
           enum "1538.09" {
             description "1538.09 nm/194.91250 THz 6.25/12.5GHz spacing";
           }
           enum "1538.04" {
             description "1538.04 nm/194.91875 THz 6.25GHz spacing";
           }
           enum "1537.99" {
             description "1537.99 nm/194.92500 THz 6.25/12.5GHz spacing";
           }
           enum "1537.94" {
             description "1537.94 nm/194.93125 THz 6.25GHz spacing";
           }
           enum "1537.89" {
             description "1537.89 nm/194.93750 THz 6.25/12.5GHz spacing";
           }
           enum "1537.84" {
             description "1537.84 nm/194.94375 THz 6.25GHz spacing";
           }
           enum "1537.79" {
             description "1537.79 nm/194.95000 THz 6.25/12.5/50GHz spacing";
           }
           enum "1537.74" {
             description "1537.74 nm/194.95625 THz 6.25GHz spacing";
           }
           enum "1537.69" {
             description "1537.69 nm/194.96250 THz 6.25/12.5GHz spacing";
           }
           enum "1537.64" {
             description "1537.64 nm/194.96875 THz 6.25GHz spacing";
           }
           enum "1537.59" {
             description "1537.59 nm/194.97500 THz 6.25/12.5/75GHz spacing";
           }
           enum "1537.55" {
             description "1537.55 nm/194.98125 THz 6.25GHz spacing";
           }
           enum "1537.50" {
             description "1537.50 nm/194.98750 THz 6.25/12.5GHz spacing";
           }
           enum "1537.45" {
             description "1537.45 nm/194.99375 THz 6.25GHz spacing";
           }
           enum "1537.40" {
             description "1537.40 nm/195.00000 THz 6.25/12.5/50/100GHz spacing";
           }
           enum "1537.35" {
             description "1537.35 nm/195.00625 THz 6.25GHz spacing";
           }
           enum "1537.30" {
             description "1537.30 nm/195.01250 THz 6.25/12.5GHz spacing";
           }
           enum "1537.25" {
             description "1537.25 nm/195.01875 THz 6.25GHz spacing";
           }
           enum "1537.20" {
             description "1537.20 nm/195.02500 THz 6.25/12.5GHz spacing";
           }
           enum "1537.15" {
             description "1537.15 nm/195.03125 THz 6.25GHz spacing";
           }
           enum "1537.10" {
             description "1537.10 nm/195.03750 THz 6.25/12.5GHz spacing";
           }
           enum "1537.05" {
             description "1537.05 nm/195.04375 THz 6.25GHz spacing";
           }
           enum "1537.00" {
             description "1537.00 nm/195.05000 THz 6.25/12.5/50/75GHz spacing";
           }
           enum "1536.95" {
             description "1536.95 nm/195.05625 THz 6.25GHz spacing";
           }
           enum "1536.90" {
             description "1536.90 nm/195.06250 THz 6.25/12.5GHz spacing";
           }
           enum "1536.86" {
             description "1536.86 nm/195.06875 THz 6.25GHz spacing";
           }
           enum "1536.81" {
             description "1536.81 nm/195.07500 THz 6.25/12.5GHz spacing";
           }
           enum "1536.76" {
             description "1536.76 nm/195.08125 THz 6.25GHz spacing";
           }
           enum "1536.71" {
             description "1536.71 nm/195.08750 THz 6.25/12.5GHz spacing";
           }
           enum "1536.66" {
             description "1536.66 nm/195.09375 THz 6.25GHz spacing";
           }
           enum "1536.61" {
             description "1536.61 nm/195.10000 THz 6.25/12.5/50/100GHz spacing";
           }
           enum "1536.56" {
             description "1536.56 nm/195.10625 THz 6.25GHz spacing";
           }
           enum "1536.51" {
             description "1536.51 nm/195.11250 THz 6.25/12.5GHz spacing";
           }
           enum "1536.46" {
             description "1536.46 nm/195.11875 THz 6.25GHz spacing";
           }
           enum "1536.41" {
             description "1536.41 nm/195.12500 THz 6.25/12.5/75GHz spacing";
           }
           enum "1536.36" {
             description "1536.36 nm/195.13125 THz 6.25GHz spacing";
           }
           enum "1536.31" {
             description "1536.31 nm/195.13750 THz 6.25/12.5GHz spacing";
           }
           enum "1536.26" {
             description "1536.26 nm/195.14375 THz 6.25GHz spacing";
           }
           enum "1536.22" {
             description "1536.22 nm/195.15000 THz 6.25/12.5/50GHz spacing";
           }
           enum "1536.17" {
             description "1536.17 nm/195.15625 THz 6.25GHz spacing";
           }
           enum "1536.12" {
             description "1536.12 nm/195.16250 THz 6.25/12.5GHz spacing";
           }
           enum "1536.07" {
             description "1536.07 nm/195.16875 THz 6.25GHz spacing";
           }
           enum "1536.02" {
             description "1536.02 nm/195.17500 THz 6.25/12.5GHz spacing";
           }
           enum "1535.97" {
             description "1535.97 nm/195.18125 THz 6.25GHz spacing";
           }
           enum "1535.92" {
             description "1535.92 nm/195.18750 THz 6.25/12.5GHz spacing";
           }
           enum "1535.87" {
             description "1535.87 nm/195.19375 THz 6.25GHz spacing";
           }
           enum "1535.82" {
             description "1535.82 nm/195.20000 THz 6.25/12.5/50/75/100GHz spacing";
           }
           enum "1535.77" {
             description "1535.77 nm/195.20625 THz 6.25GHz spacing";
           }
           enum "1535.72" {
             description "1535.72 nm/195.21250 THz 6.25/12.5GHz spacing";
           }
           enum "1535.67" {
             description "1535.67 nm/195.21875 THz 6.25GHz spacing";
           }
           enum "1535.63" {
             description "1535.63 nm/195.22500 THz 6.25/12.5GHz spacing";
           }
           enum "1535.58" {
             description "1535.58 nm/195.23125 THz 6.25GHz spacing";
           }
           enum "1535.53" {
             description "1535.53 nm/195.23750 THz 6.25/12.5GHz spacing";
           }
           enum "1535.48" {
             description "1535.48 nm/195.24375 THz 6.25GHz spacing";
           }
           enum "1535.43" {
             description "1535.43 nm/195.25000 THz 6.25/12.5/50GHz spacing";
           }
           enum "1535.38" {
             description "1535.38 nm/195.25625 THz 6.25GHz spacing";
           }
           enum "1535.33" {
             description "1535.33 nm/195.26250 THz 6.25/12.5GHz spacing";
           }
           enum "1535.28" {
             description "1535.28 nm/195.26875 THz 6.25GHz spacing";
           }
           enum "1535.23" {
             description "1535.23 nm/195.27500 THz 6.25/12.5/75GHz spacing";
           }
           enum "1535.18" {
             description "1535.18 nm/195.28125 THz 6.25GHz spacing";
           }
           enum "1535.13" {
             description "1535.13 nm/195.28750 THz 6.25/12.5GHz spacing";
           }
           enum "1535.08" {
             description "1535.08 nm/195.29375 THz 6.25GHz spacing";
           }
           enum "1535.04" {
             description "1535.04 nm/195.30000 THz 6.25/12.5/50/100GHz spacing";
           }
           enum "1534.99" {
             description "1534.99 nm/195.30625 THz 6.25GHz spacing";
           }
           enum "1534.94" {
             description "1534.94 nm/195.31250 THz 6.25/12.5GHz spacing";
           }
           enum "1534.89" {
             description "1534.89 nm/195.31875 THz 6.25GHz spacing";
           }
           enum "1534.84" {
             description "1534.84 nm/195.32500 THz 6.25/12.5GHz spacing";
           }
           enum "1534.79" {
             description "1534.79 nm/195.33125 THz 6.25GHz spacing";
           }
           enum "1534.74" {
             description "1534.74 nm/195.33750 THz 6.25/12.5GHz spacing";
           }
           enum "1534.69" {
             description "1534.69 nm/195.34375 THz 6.25GHz spacing";
           }
           enum "1534.64" {
             description "1534.64 nm/195.35000 THz 6.25/12.5/50/75GHz spacing";
           }
           enum "1534.59" {
             description "1534.59 nm/195.35625 THz 6.25GHz spacing";
           }
           enum "1534.54" {
             description "1534.54 nm/195.36250 THz 6.25/12.5GHz spacing";
           }
           enum "1534.50" {
             description "1534.50 nm/195.36875 THz 6.25GHz spacing";
           }
           enum "1534.45" {
             description "1534.45 nm/195.37500 THz 6.25/12.5GHz spacing";
           }
           enum "1534.40" {
             description "1534.40 nm/195.38125 THz 6.25GHz spacing";
           }
           enum "1534.35" {
             description "1534.35 nm/195.38750 THz 6.25/12.5GHz spacing";
           }
           enum "1534.30" {
             description "1534.30 nm/195.39375 THz 6.25GHz spacing";
           }
           enum "1534.25" {
             description "1534.25 nm/195.40000 THz 6.25/12.5/50/100GHz spacing";
           }
           enum "1534.20" {
             description "1534.20 nm/195.40625 THz 6.25GHz spacing";
           }
           enum "1534.15" {
             description "1534.15 nm/195.41250 THz 6.25/12.5GHz spacing";
           }
           enum "1534.10" {
             description "1534.10 nm/195.41875 THz 6.25GHz spacing";
           }
           enum "1534.05" {
             description "1534.05 nm/195.42500 THz 6.25/12.5/75GHz spacing";
           }
           enum "1534.00" {
             description "1534.00 nm/195.43125 THz 6.25GHz spacing";
           }
           enum "1533.96" {
             description "1533.96 nm/195.43750 THz 6.25/12.5GHz spacing";
           }
           enum "1533.91" {
             description "1533.91 nm/195.44375 THz 6.25GHz spacing";
           }
           enum "1533.86" {
             description "1533.86 nm/195.45000 THz 6.25/12.5/50GHz spacing";
           }
           enum "1533.81" {
             description "1533.81 nm/195.45625 THz 6.25GHz spacing";
           }
           enum "1533.76" {
             description "1533.76 nm/195.46250 THz 6.25/12.5GHz spacing";
           }
           enum "1533.71" {
             description "1533.71 nm/195.46875 THz 6.25GHz spacing";
           }
           enum "1533.66" {
             description "1533.66 nm/195.47500 THz 6.25/12.5GHz spacing";
           }
           enum "1533.61" {
             description "1533.61 nm/195.48125 THz 6.25GHz spacing";
           }
           enum "1533.56" {
             description "1533.56 nm/195.48750 THz 6.25/12.5GHz spacing";
           }
           enum "1533.51" {
             description "1533.51 nm/195.49375 THz 6.25GHz spacing";
           }
           enum "1533.47" {
             description "1533.47 nm/195.50000 THz 6.25/12.5/50/75/100GHz spacing";
           }
           enum "1533.42" {
             description "1533.42 nm/195.50625 THz 6.25GHz spacing";
           }
           enum "1533.37" {
             description "1533.37 nm/195.51250 THz 6.25/12.5GHz spacing";
           }
           enum "1533.32" {
             description "1533.32 nm/195.51875 THz 6.25GHz spacing";
           }
           enum "1533.27" {
             description "1533.27 nm/195.52500 THz 6.25/12.5GHz spacing";
           }
           enum "1533.22" {
             description "1533.22 nm/195.53125 THz 6.25GHz spacing";
           }
           enum "1533.17" {
             description "1533.17 nm/195.53750 THz 6.25/12.5GHz spacing";
           }
           enum "1533.12" {
             description "1533.12 nm/195.54375 THz 6.25GHz spacing";
           }
           enum "1533.07" {
             description "1533.07 nm/195.55000 THz 6.25/12.5/50GHz spacing";
           }
           enum "1533.02" {
             description "1533.02 nm/195.55625 THz 6.25GHz spacing";
           }
           enum "1532.98" {
             description "1532.98 nm/195.56250 THz 6.25/12.5GHz spacing";
           }
           enum "1532.93" {
             description "1532.93 nm/195.56875 THz 6.25GHz spacing";
           }
           enum "1532.88" {
             description "1532.88 nm/195.57500 THz 6.25/12.5/75GHz spacing";
           }
           enum "1532.83" {
             description "1532.83 nm/195.58125 THz 6.25GHz spacing";
           }
           enum "1532.78" {
             description "1532.78 nm/195.58750 THz 6.25/12.5GHz spacing";
           }
           enum "1532.73" {
             description "1532.73 nm/195.59375 THz 6.25GHz spacing";
           }
           enum "1532.68" {
             description "1532.68 nm/195.60000 THz 6.25/12.5/50/100GHz spacing";
           }
           enum "1532.63" {
             description "1532.63 nm/195.60625 THz 6.25GHz spacing";
           }
           enum "1532.58" {
             description "1532.58 nm/195.61250 THz 6.25/12.5GHz spacing";
           }
           enum "1532.53" {
             description "1532.53 nm/195.61875 THz 6.25GHz spacing";
           }
           enum "1532.49" {
             description "1532.49 nm/195.62500 THz 6.25/12.5GHz spacing";
           }
           enum "1532.44" {
             description "1532.44 nm/195.63125 THz 6.25GHz spacing";
           }
           enum "1532.39" {
             description "1532.39 nm/195.63750 THz 6.25/12.5GHz spacing";
           }
           enum "1532.34" {
             description "1532.34 nm/195.64375 THz 6.25GHz spacing";
           }
           enum "1532.29" {
             description "1532.29 nm/195.65000 THz 6.25/12.5/50/75GHz spacing";
           }
           enum "1532.24" {
             description "1532.24 nm/195.65625 THz 6.25GHz spacing";
           }
           enum "1532.19" {
             description "1532.19 nm/195.66250 THz 6.25/12.5GHz spacing";
           }
           enum "1532.14" {
             description "1532.14 nm/195.66875 THz 6.25GHz spacing";
           }
           enum "1532.09" {
             description "1532.09 nm/195.67500 THz 6.25/12.5GHz spacing";
           }
           enum "1532.04" {
             description "1532.04 nm/195.68125 THz 6.25GHz spacing";
           }
           enum "1532.00" {
             description "1532.00 nm/195.68750 THz 6.25/12.5GHz spacing";
           }
           enum "1531.95" {
             description "1531.95 nm/195.69375 THz 6.25GHz spacing";
           }
           enum "1531.90" {
             description "1531.90 nm/195.70000 THz 6.25/12.5/50/100GHz spacing";
           }
           enum "1531.85" {
             description "1531.85 nm/195.70625 THz 6.25GHz spacing";
           }
           enum "1531.80" {
             description "1531.80 nm/195.71250 THz 6.25/12.5GHz spacing";
           }
           enum "1531.75" {
             description "1531.75 nm/195.71875 THz 6.25GHz spacing";
           }
           enum "1531.70" {
             description "1531.70 nm/195.72500 THz 6.25/12.5/75GHz spacing";
           }
           enum "1531.65" {
             description "1531.65 nm/195.73125 THz 6.25GHz spacing";
           }
           enum "1531.60" {
             description "1531.60 nm/195.73750 THz 6.25/12.5GHz spacing";
           }
           enum "1531.56" {
             description "1531.56 nm/195.74375 THz 6.25GHz spacing";
           }
           enum "1531.51" {
             description "1531.51 nm/195.75000 THz 6.25/12.5/50GHz spacing";
           }
           enum "1531.46" {
             description "1531.46 nm/195.75625 THz 6.25GHz spacing";
           }
           enum "1531.41" {
             description "1531.41 nm/195.76250 THz 6.25/12.5GHz spacing";
           }
           enum "1531.36" {
             description "1531.36 nm/195.76875 THz 6.25GHz spacing";
           }
           enum "1531.31" {
             description "1531.31 nm/195.77500 THz 6.25/12.5GHz spacing";
           }
           enum "1531.26" {
             description "1531.26 nm/195.78125 THz 6.25GHz spacing";
           }
           enum "1531.21" {
             description "1531.21 nm/195.78750 THz 6.25/12.5GHz spacing";
           }
           enum "1531.16" {
             description "1531.16 nm/195.79375 THz 6.25GHz spacing";
           }
           enum "1531.12" {
             description "1531.12 nm/195.80000 THz 6.25/12.5/50/75/100GHz spacing";
           }
           enum "1531.07" {
             description "1531.07 nm/195.80625 THz 6.25GHz spacing";
           }
           enum "1531.02" {
             description "1531.02 nm/195.81250 THz 6.25/12.5GHz spacing";
           }
           enum "1530.97" {
             description "1530.97 nm/195.81875 THz 6.25GHz spacing";
           }
           enum "1530.92" {
             description "1530.92 nm/195.82500 THz 6.25/12.5GHz spacing";
           }
           enum "1530.87" {
             description "1530.87 nm/195.83125 THz 6.25GHz spacing";
           }
           enum "1530.82" {
             description "1530.82 nm/195.83750 THz 6.25/12.5GHz spacing";
           }
           enum "1530.77" {
             description "1530.77 nm/195.84375 THz 6.25GHz spacing";
           }
           enum "1530.72" {
             description "1530.72 nm/195.85000 THz 6.25/12.5/50GHz spacing";
           }
           enum "1530.68" {
             description "1530.68 nm/195.85625 THz 6.25GHz spacing";
           }
           enum "1530.63" {
             description "1530.63 nm/195.86250 THz 6.25/12.5GHz spacing";
           }
           enum "1530.58" {
             description "1530.58 nm/195.86875 THz 6.25GHz spacing";
           }
           enum "1530.53" {
             description "1530.53 nm/195.87500 THz 6.25/12.5/75GHz spacing";
           }
           enum "1530.48" {
             description "1530.48 nm/195.88125 THz 6.25GHz spacing";
           }
           enum "1530.43" {
             description "1530.43 nm/195.88750 THz 6.25/12.5GHz spacing";
           }
           enum "1530.38" {
             description "1530.38 nm/195.89375 THz 6.25GHz spacing";
           }
           enum "1530.33" {
             description "1530.33 nm/195.90000 THz 6.25/12.5/50/100GHz spacing";
           }
           enum "1530.29" {
             description "1530.29 nm/195.90625 THz 6.25GHz spacing";
           }
           enum "1530.24" {
             description "1530.24 nm/195.91250 THz 6.25/12.5GHz spacing";
           }
           enum "1530.19" {
             description "1530.19 nm/195.91875 THz 6.25GHz spacing";
           }
           enum "1530.14" {
             description "1530.14 nm/195.92500 THz 6.25/12.5GHz spacing";
           }
           enum "1530.09" {
             description "1530.09 nm/195.93125 THz 6.25GHz spacing";
           }
           enum "1530.04" {
             description "1530.04 nm/195.93750 THz 6.25/12.5GHz spacing";
           }
           enum "1529.99" {
             description "1529.99 nm/195.94375 THz 6.25GHz spacing";
           }
           enum "1529.94" {
             description "1529.94 nm/195.95000 THz 6.25/12.5/50/75GHz spacing";
           }
           enum "1529.89" {
             description "1529.89 nm/195.95625 THz 6.25GHz spacing";
           }
           enum "1529.85" {
             description "1529.85 nm/195.96250 THz 6.25/12.5GHz spacing";
           }
           enum "1529.80" {
             description "1529.80 nm/195.96875 THz 6.25GHz spacing";
           }
           enum "1529.75" {
             description "1529.75 nm/195.97500 THz 6.25/12.5GHz spacing";
           }
           enum "1529.70" {
             description "1529.70 nm/195.98125 THz 6.25GHz spacing";
           }
           enum "1529.65" {
             description "1529.65 nm/195.98750 THz 6.25/12.5GHz spacing";
           }
           enum "1529.60" {
             description "1529.60 nm/195.99375 THz 6.25GHz spacing";
           }
           enum "1529.55" {
             description "1529.55 nm/196.00000 THz 6.25/12.5/50/100GHz spacing";
           }
           enum "1529.50" {
             description "1529.50 nm/196.00625 THz 6.25GHz spacing";
           }
           enum "1529.46" {
             description "1529.46 nm/196.01250 THz 6.25/12.5GHz spacing";
           }
           enum "1529.41" {
             description "1529.41 nm/196.01875 THz 6.25GHz spacing";
           }
           enum "1529.36" {
             description "1529.36 nm/196.02500 THz 6.25/12.5/75GHz spacing";
           }
           enum "1529.31" {
             description "1529.31 nm/196.03125 THz 6.25GHz spacing";
           }
           enum "1529.26" {
             description "1529.26 nm/196.03750 THz 6.25/12.5GHz spacing";
           }
           enum "1529.21" {
             description "1529.21 nm/196.04375 THz 6.25GHz spacing";
           }
           enum "1529.16" {
             description "1529.16 nm/196.05000 THz 6.25/12.5/50GHz spacing";
           }
           enum "1529.11" {
             description "1529.11 nm/196.05625 THz 6.25GHz spacing";
           }
           enum "1529.07" {
             description "1529.07 nm/196.06250 THz 6.25/12.5GHz spacing";
           }
           enum "1529.02" {
             description "1529.02 nm/196.06875 THz 6.25GHz spacing";
           }
           enum "1528.97" {
             description "1528.97 nm/196.07500 THz 6.25/12.5GHz spacing";
           }
           enum "1528.92" {
             description "1528.92 nm/196.08125 THz 6.25GHz spacing";
           }
           enum "1528.87" {
             description "1528.87 nm/196.08750 THz 6.25/12.5GHz spacing";
           }
           enum "1528.82" {
             description "1528.82 nm/196.09375 THz 6.25GHz spacing";
           }
           enum "1528.77" {
             description "1528.77 nm/196.10000 THz 6.25/12.5/50/75/100GHz spacing";
           }
           enum "1528.38" {
             description "1528.38 nm/196.15040 THz 50Ghz spacing";
           }
         }
       }
       leaf tx-power {
         description "Transmit laser output power";
         units "dBm";
         type string {
         }
       }
       container loopback {
         presence "enable loopback";
         description "Put the optics in loopback mode";
         uses apply-advanced;
         leaf loopbacktype {
           description "Set loopback type";
           type enumeration {
             enum "media-side-out" {
               description "Loop media side output back to input";
             }
             enum "media-side-in" {
               description "Loop media side input back to output";
             }
             enum "host-side-out" {
               description "Loop host side output back to input";
             }
             enum "host-side-in" {
               description "Loop host side input back to output";
             }
           }
         }
       }
       leaf los-warning-threshold {
         description "LOS warning threshold";
         units "dBm";
         type string;
       }
       leaf los-alarm-threshold {
         description "LOS alarm threshold";
         units "dBm";
         type string;
       }
       leaf modulation-format {
         description "Type of Modulation Format";
         type enumeration {
           enum "16qam" {
             description "16-QAM Modulation Format";
           }
           enum "8qam" {
             description "8-QAM MOdulation Format";
           }
           enum "qpsk" {
             description "QPSK Modulation Format";
           }
         }
       }
       choice laser-enable-choice {
         leaf laser-enable {
           description "Enable Laser";
           type empty;
         }
         leaf no-laser-enable {
           description "Don't enable Laser";
           type empty;
         }
       }
       choice is-ma-choice {
         leaf is-ma {
           description "Link is enabled with alarms masked";
           type empty;
         }
         leaf no-is-ma {
           description "Don't link is enabled with alarms masked";
           type empty;
         }
       }
       leaf encoding {
         description "Line encoding";
         type enumeration {
           enum "differential" {
             description "Differential phase line encoding";
           }
           enum "non-differential" {
             description "Non-differential phase line encoding";
           }
         }
       }
       leaf fec {
         description "Forward Error Correction mode";
         type enumeration {
           enum "sdfec" {
             description "Sky-Compatible Soft Decision Forward Error Correction";
           }
           enum "sdfec25" {
             description "Denali-Compatible Soft Decision Forward Error Correction with 25 percent overhead";
           }
           enum "hgfec" {
             description "High Gain Forward Error Correction";
           }
           enum "sdfec15" {
             description "Soft Decision Forward Error Correction with 15 percent overhead";
           }
         }
       }
       leaf high-polarization {
         description "High polarization tracking mode";
         type empty;
       }
       container application {
         description "Config Host and Media Code";
         uses apply-advanced;
         leaf hostid {
           description "Enter Host Code";
           type union {
             type string {
               pattern "<.*>|$.*";
             }
             type uint32 {
               range "1 .. 300";
             }
           }
         }
         leaf mediaid {
           description "Enter Media Code";
           type union {
             type string {
               pattern "<.*>|$.*";
             }
             type uint32 {
               range "1 .. 300";
             }
           }
         }
         leaf domainid {
           description "Enter Domain ID";
           type union {
             type string {
               pattern "<.*>|$.*";
             }
             type uint32 {
               range "0 .. 300";
             }
           }
         }
       }
       container signal-degrade {
         description "Signal degrade thresholds";
         uses apply-advanced;
         leaf interval {
           description "Time interval";
           default "10";
           units "milliseconds";
           type union {
             type string {
               pattern "<.*>|$.*";
             }
             type uint32 {
               range "1 .. 1000";
             }
           }
         }
         leaf ber-threshold-clear {
           description "Ber threshold for signal degrade clear (format: xe-n, example: 4.5e-3)";
           type string {
           }
         }
         leaf ber-threshold-signal-degrade {
           description "Ber threshold for signal-degrade (format: xe-n, example: 4.5e-3)";
           type string {
           }
         }
         leaf q-threshold-signal-degrade-clear {
           description "Q threshold for signal-degrade clear (e.g. 14.26)";
           units "dB";
           type string;
         }
         leaf q-threshold-signal-degrade {
           description "Q threshold for signal-degrade (e.g. 9.26)";
           units "dB";
           type string;
         }
       }
       list alarm {
         key name;
         ordered-by user;
         description "Set optic alarms";
         leaf name {
           type enumeration {
             enum "low-light-alarm" {
               description "Enable low light alarm";
             }
           }
         }
         uses apply-advanced;
         choice actiontype {
           case case_1 {
             leaf syslog {
               type empty;
             }
           }
           case case_2 {
             leaf link-down {
               type empty;
             }
           }
         }
       }
       container tca {
         description "Set tca for optic alarms";
         uses apply-advanced;
         container tx-power-high-tca {
           description "Tx power high TCA";
           uses apply-advanced;
           choice enable-tca-choice {
             leaf enable-tca {
               description "Enable tca";
               type empty;
             }
             leaf no-enable-tca {
               description "Don't enable tca";
               type empty;
             }
           }
           leaf threshold {
             description "Threshold for 15 minute tx power high TCA in dBm";
             type string {
             }
           }
           leaf threshold-24hrs {
             description "Threshold for 24 hour tx power high TCA in dBm";
             type string {
             }
           }
         }
         container tx-power-low-tca {
           description "Tx power low TCA";
           uses apply-advanced;
           choice enable-tca-choice {
             leaf enable-tca {
               description "Enable tca";
               type empty;
             }
             leaf no-enable-tca {
               description "Don't enable tca";
               type empty;
             }
           }
           leaf threshold {
             description "Threshold for 15 minute tx power low TCA in dBm";
             type string {
             }
           }
           leaf threshold-24hrs {
             description "Threshold for 24 hour tx power low TCA in dBm";
             type string {
             }
           }
         }
         container rx-power-high-tca {
           description "Rx power high TCA";
           uses apply-advanced;
           choice enable-tca-choice {
             leaf enable-tca {
               description "Enable tca";
               type empty;
             }
             leaf no-enable-tca {
               description "Don't enable tca";
               type empty;
             }
           }
           leaf threshold {
             description "Threshold for 15 minute rx power high TCA in dBm";
             type string {
             }
           }
           leaf threshold-24hrs {
             description "Threshold for 24 hour rx power high TCA in dBm";
             type string {
             }
           }
         }
         container rx-power-low-tca {
           description "Rx power low TCA";
           uses apply-advanced;
           choice enable-tca-choice {
             leaf enable-tca {
               description "Enable tca";
               type empty;
             }
             leaf no-enable-tca {
               description "Don't enable tca";
               type empty;
             }
           }
           leaf threshold {
             description "Threshold for 15 minute rx power low TCA in dBm";
             type string {
             }
           }
           leaf threshold-24hrs {
             description "Threshold for 24 hour rx power low TCA in dBm";
             type string {
             }
           }
         }
         container rx-signal-power-high-tca {
           description "Rx signal power high TCA";
           uses apply-advanced;
           choice enable-tca-choice {
             leaf enable-tca {
               description "Enable tca";
               type empty;
             }
             leaf no-enable-tca {
               description "Don't enable tca";
               type empty;
             }
           }
           leaf threshold {
             description "Threshold for 15 minute rx signal power high TCA in dBm";
             type string {
             }
           }
           leaf threshold-24hrs {
             description "Threshold for 24 hour rx signal power high TCA in dBm";
             type string {
             }
           }
         }
         container rx-signal-power-low-tca {
           description "Rx signal power low TCA";
           uses apply-advanced;
           choice enable-tca-choice {
             leaf enable-tca {
               description "Enable tca";
               type empty;
             }
             leaf no-enable-tca {
               description "Don't enable tca";
               type empty;
             }
           }
           leaf threshold {
             description "Threshold for 15 minute rx signal power low TCA in dBm";
             type string {
             }
           }
           leaf threshold-24hrs {
             description "Threshold for 24 hour rx signal power low TCA in dBm";
             type string {
             }
           }
         }
         container temperature-high-tca {
           description "Temperature high TCA";
           uses apply-advanced;
           choice enable-tca-choice {
             leaf enable-tca {
               description "Enable tca";
               type empty;
             }
             leaf no-enable-tca {
               description "Don't enable tca";
               type empty;
             }
           }
           leaf threshold {
             description "Threshold for 15 minute high temperature TCA in celsius";
             type string {
             }
           }
           leaf threshold-24hrs {
             description "Threshold for 24 hour high temperature TCA in celsius";
             type string {
             }
           }
         }
         container temperature-low-tca {
           description "Temperature low TCA";
           uses apply-advanced;
           choice enable-tca-choice {
             leaf enable-tca {
               description "Enable tca";
               type empty;
             }
             leaf no-enable-tca {
               description "Don't enable tca";
               type empty;
             }
           }
           leaf threshold {
             description "Threshold for 15 minute low temperature TCA in celsius";
             type string {
             }
           }
           leaf threshold-24hrs {
             description "Threshold for 24 hour low temperature TCA in celsius";
             type string {
             }
           }
         }
         container carrier-frequency-offset-high-tca {
           description "Carrier frequency offset high TCA";
           uses apply-advanced;
           choice enable-tca-choice {
             leaf enable-tca {
               description "Enable tca";
               type empty;
             }
             leaf no-enable-tca {
               description "Don't enable tca";
               type empty;
             }
           }
           leaf threshold {
             description "Threshold for 15 minute frequency offset high TCA in MHz";
             type string {
             }
           }
           leaf threshold-24hrs {
             description "Threshold for 24 hour frequency offset high TCA in MHz";
             type string {
             }
           }
         }
         container carrier-frequency-offset-low-tca {
           description "Carrier frequency offset low TCA";
           uses apply-advanced;
           choice enable-tca-choice {
             leaf enable-tca {
               description "Enable tca";
               type empty;
             }
             leaf no-enable-tca {
               description "Don't enable tca";
               type empty;
             }
           }
           leaf threshold {
             description "Threshold for 15 minute frequency offset low TCA in MHz";
             type string {
             }
           }
           leaf threshold-24hrs {
             description "Threshold for 24 hour frequency offset low TCA in MHz";
             type string {
             }
           }
         }
         container fec-ber {
           description "Optics Errored Seconds Threshold crossing defect trigger";
           choice enable-tca-choice {
             leaf enable-tca {
               description "Enable the Optics errored seconds threshold crossing alert";
               type empty;
             }
             leaf no-enable-tca {
               description "Don't enable the Optics errored seconds threshold crossing alert";
               type empty;
             }
           }
           leaf threshold {
             description "TCA threshold for BER value in format: xe-n, x is an integer or decimal number, n = 0..9";
             default "10e-3";
             type string {
             }
           }
           leaf threshold-24hrs {
             description "TCA threshold for BER value in format: xe-n, x is an integer or decimal number, n = 0..9";
             default "10e-3";
             type string {
             }
           }
         }
         container tec-current-high-tca {
           description "TEC Current high TCA";
           uses apply-advanced;
           choice enable-tca-choice {
             leaf enable-tca {
               description "Enable tca";
               type empty;
             }
             leaf no-enable-tca {
               description "Don't enable tca";
               type empty;
             }
           }
           leaf threshold {
             description "Threshold for 15 minute TEC Current high TCA in mA";
             type string {
             }
           }
           leaf threshold-24hrs {
             description "Threshold for 24 hour TEC Current high TCA in mA";
             type string {
             }
           }
         }
         container tec-current-low-tca {
           description "TEC Current low TCA";
           uses apply-advanced;
           choice enable-tca-choice {
             leaf enable-tca {
               description "Enable tca";
               type empty;
             }
             leaf no-enable-tca {
               description "Don't enable tca";
               type empty;
             }
           }
           leaf threshold {
             description "Threshold for 15 minute TEC Current low TCA in mA";
             type string {
             }
           }
           leaf threshold-24hrs {
             description "Threshold for 24 hour TEC Current low TCA in mA";
             type string {
             }
           }
         }
         container residual-isi-high-tca {
           description "Residual ISI high TCA";
           uses apply-advanced;
           choice enable-tca-choice {
             leaf enable-tca {
               description "Enable tca";
               type empty;
             }
             leaf no-enable-tca {
               description "Don't enable tca";
               type empty;
             }
           }
           leaf threshold {
             description "Threshold for 15 minute Residual ISI high TCA in ps/nm";
             type string {
             }
           }
           leaf threshold-24hrs {
             description "Threshold for 24 hour Residual ISI high TCA in ps/nm";
             type string {
             }
           }
         }
         container residual-isi-low-tca {
           description "Residual ISI low TCA";
           uses apply-advanced;
           choice enable-tca-choice {
             leaf enable-tca {
               description "Enable tca";
               type empty;
             }
             leaf no-enable-tca {
               description "Don't enable tca";
               type empty;
             }
           }
           leaf threshold {
             description "Threshold for 15 minute Residual ISI low TCA in ps/nm";
             type string {
             }
           }
           leaf threshold-24hrs {
             description "Threshold for 24 hour Residual ISI low TCA in ps/nm";
             type string {
             }
           }
         }
         container pam-histogram-high-tca {
           description "PAM Histogram high TCA";
           uses apply-advanced;
           choice enable-tca-choice {
             leaf enable-tca {
               description "Enable tca";
               type empty;
             }
             leaf no-enable-tca {
               description "Don't enable tca";
               type empty;
             }
           }
           leaf threshold {
             description "Threshold for 15 minute PAM Histogram high TCA";
             type string {
             }
           }
           leaf threshold-24hrs {
             description "Threshold for 24 hour PAM Histogram high TCA";
             type string {
             }
           }
         }
         container snr-low-tca {
           description "SNR low TCA";
           uses apply-advanced;
           choice enable-tca-choice {
             leaf enable-tca {
               description "Enable tca";
               type empty;
             }
             leaf no-enable-tca {
               description "Don't enable tca";
               type empty;
             }
           }
           leaf threshold {
             description "Threshold for 15 minute SNR low TCA in dBm ";
             type string {
             }
           }
           leaf threshold-24hrs {
             description "Threshold for 24 hour SNR low TCA in dBm";
             type string {
             }
           }
         }
         container fec-corrected-errors-high-tca {
           description "FEC Corrected Error High Threshold crossing defect trigger";
           uses apply-advanced;
           choice enable-tca-choice {
             leaf enable-tca {
               description "Enable the FEC Corrected Errors threshold crossing alert";
               type empty;
             }
             leaf no-enable-tca {
               description "Don't enable the FEC Corrected Errors threshold crossing alert";
               type empty;
             }
           }
           leaf threshold {
             description "FEC Corrected-Errs value in format: xe-n, x is an integer or decimal number, n = 0..9";
             default "10e-3";
             type string {
             }
           }
           leaf threshold-24hrs {
             description "FEC Corrected-Errs value in format: xe-n, x is an integer or decimal number, n = 0..9";
             default "10e-3";
             type string {
             }
           }
         }
         container fec-ucorrected-words-high-tca {
           description "FEC UCorrected Words High Threshold crossing defect trigger";
           uses apply-advanced;
           choice enable-tca-choice {
             leaf enable-tca {
               description "Enable the FEC UCorrected Words threshold crossing alert";
               type empty;
             }
             leaf no-enable-tca {
               description "Don't enable the FEC UCorrected Words threshold crossing alert";
               type empty;
             }
           }
           leaf threshold {
             description "FEC UCorrected-Words value in format: xe-n, x is an integer or decimal number, n = 0..9";
             default "10e-3";
             type string {
             }
           }
           leaf threshold-24hrs {
             description "FEC UCorrected-Words value in format: xe-n, x is an integer or decimal number, n = 0..9";
             default "10e-3";
             type string {
             }
           }
         }
         container laser-frequency-error-high-tca {
           description "Laser frequency error high TCA";
           uses apply-advanced;
           choice enable-tca-choice {
             leaf enable-tca {
               description "Enable tca";
               type empty;
             }
             leaf no-enable-tca {
               description "Don't enable tca";
               type empty;
             }
           }
           leaf threshold {
             description "Threshold for 15 minute frequency error high TCA in MHz";
             type string {
             }
           }
           leaf threshold-24hrs {
             description "Threshold for 24 hour frequency error high TCA in MHz";
             type string {
             }
           }
         }
         container laser-frequency-error-low-tca {
           description "Laser frequency error low TCA";
           uses apply-advanced;
           choice enable-tca-choice {
             leaf enable-tca {
               description "Enable tca";
               type empty;
             }
             leaf no-enable-tca {
               description "Don't enable tca";
               type empty;
             }
           }
           leaf threshold {
             description "Threshold for 15 minute frequency error low TCA in MHz";
             type string {
             }
           }
           leaf threshold-24hrs {
             description "Threshold for 24 hour frequency error low TCA in MHz";
             type string {
             }
           }
         }
       }
       list warning {
         key name;
         ordered-by user;
         description "Set optic warnings";
         leaf name {
           type enumeration {
             enum "low-light-warning" {
               description "Enable low light warning";
             }
           }
         }
         uses apply-advanced;
         choice actiontype {
           case case_1 {
             leaf syslog {
               description "Set action as syslog";
               type empty;
             }
           }
           case case_2 {
             leaf link-down {
               description "Set action as link-down";
               type empty;
             }
           }
         }
       }
       leaf low-power-mode {
         description "Force optics to low power mode";
         type empty;
       }
       leaf high-power-mode {
         description "High power optic mode";
         type empty;
       }
       leaf host-side-fec {
         description "Host side optics FEC ON/OFF";
         type enumeration {
           enum "off" {
             description "Host side FEC OFF for optics";
           }
           enum "on" {
             description "Host side FEC ON for optics";
           }
         }
       }
       leaf media-side-fec {
         description "Media side FEC ON/OFF";
         type enumeration {
           enum "off" {
             description "Media side FEC OFF for optics";
           }
           enum "on" {
             description "Media side FEC ON for optics";
           }
         }
       }
       choice lane-info {
         case case_1 {
           list lane {
             key name;
             description "Media lane number";
             leaf name {
               description "Lane number";
               type union {
                 type string {
                   pattern "<.*>|$.*";
                 }
                 type uint32 {
                   range "0 .. 7";
                 }
               }
             }
             uses apply-advanced;
             leaf tx-laser {
               description "Transmit Laser ON/OFF";
               type enumeration {
                 enum "off" {
                   description "Transmit laser OFF for optics";
                 }
                 enum "on" {
                   description "Transmit laser ON for optics";
                 }
               }
             }
             leaf rx-output {
               description "Receive output ON/OFF";
               type enumeration {
                 enum "off" {
                   description "Receive output OFF for optics";
                 }
                 enum "on" {
                   description "Receive output ON for optics";
                 }
               }
             }
             leaf tx-cdr {
               description "Transmit Clock and Data Recovery ON/OFF";
               type enumeration {
                 enum "off" {
                   description "Transmit Clock and Data Recovery OFF for optics";
                 }
                 enum "on" {
                   description "Transmit Clock and Data Recovery ON for optics";
                 }
               }
             }
             leaf rx-cdr {
               description "Receive Clock and Data Recovery ON/OFF";
               type enumeration {
                 enum "off" {
                   description "Receive Clock and Data Recovery OFF for optics";
                 }
                 enum "on" {
                   description "Receive Clock and Data Recovery ON for optics";
                 }
               }
             }
             leaf tx-input-equalization-adaptive {
               description "Transmit adaptive equalization ON/OFF";
               type enumeration {
                 enum "off" {
                   description "Transmit adaptive equalization OFF for optics";
                 }
                 enum "on" {
                   description "Transmit adaptive equalization ON for optics";
                 }
               }
             }
             leaf tx-input-equalization-manual {
               description "Transmit manual equalization for optics";
               units "dB";
               type union {
                 type string {
                   pattern "<.*>|$.*";
                 }
                 type int32 {
                   range "0 .. 15";
                 }
               }
             }
             leaf rx-output-emphasis {
               description "Receive output emphasis for optics";
               units "dB";
               type union {
                 type string {
                   pattern "<.*>|$.*";
                 }
                 type int32 {
                   range "0 .. 15";
                 }
               }
             }
             leaf rx-output-amplitude {
               description "Receive output amplitude setting";
               type enumeration {
                 enum "400mV" {
                   description "No equalization for 100mV - 400mV amplitude";
                 }
                 enum "600mV" {
                   description "No equalization for 300mV - 600mV amplitude";
                 }
                 enum "800mV" {
                   description "No equalization for 400mV - 800mV amplitude";
                 }
                 enum "1200mV" {
                   description "No equalization for 600mV - 1200mV amplitude";
                 }
               }
             }
             leaf tx-squelch {
               description "Transmit squelch ON/OFF";
               type enumeration {
                 enum "off" {
                   description "Transmit squelch OFF for optics";
                 }
                 enum "on" {
                   description "Transmit squelch ON for optics";
                 }
               }
             }
             leaf rx-squelch {
               description "Receive squelch ON/OFF";
               type enumeration {
                 enum "off" {
                   description "Receive squelch OFF for optics";
                 }
                 enum "on" {
                   description "Receive squelch ON for optics";
                 }
               }
             }
             leaf tx-rate-select {
               description "Transmit rate select for optics";
               type union {
                 type string {
                   pattern "<.*>|$.*";
                 }
                 type int32 {
                   range "0 .. 3";
                 }
               }
             }
             leaf rx-rate-select {
               description "Receive rate select for optics";
               type union {
                 type string {
                   pattern "<.*>|$.*";
                 }
                 type int32 {
                   range "0 .. 3";
                 }
               }
             }
           }
         }
         case case_2 {
           container lane-all {
             presence "enable lane-all";
             description "Apply settings to all lane";
             uses apply-advanced;
             leaf tx-laser {
               description "Transmit Laser ON/OFF";
               type enumeration {
                 enum "off" {
                   description "Transmit laser OFF for optics";
                 }
                 enum "on" {
                   description "Transmit laser ON for optics";
                 }
               }
             }
             leaf rx-output {
               description "Receive output ON/OFF";
               type enumeration {
                 enum "off" {
                   description "Receive output OFF for optics";
                 }
                 enum "on" {
                   description "Receive output ON for optics";
                 }
               }
             }
             leaf tx-cdr {
               description "Transmit Clock and Data Recovery ON/OFF";
               type enumeration {
                 enum "off" {
                   description "Transmit Clock and Data Recovery OFF for optics";
                 }
                 enum "on" {
                   description "Transmit Clock and Data Recovery ON for optics";
                 }
               }
             }
             leaf rx-cdr {
               description "Receive Clock and Data Recovery ON/OFF";
               type enumeration {
                 enum "off" {
                   description "Receive Clock and Data Recovery OFF for optics";
                 }
                 enum "on" {
                   description "Receive Clock and Data Recovery ON for optics";
                 }
               }
             }
             leaf tx-input-equalization-adaptive {
               description "Transmit adaptive equalization ON/OFF";
               type enumeration {
                 enum "off" {
                   description "Transmit adaptive equalization OFF for optics";
                 }
                 enum "on" {
                   description "Transmit adaptive equalization ON for optics";
                 }
               }
             }
             leaf tx-input-equalization-manual {
               description "Transmit manual equalization for optics";
               units "dB";
               type union {
                 type string {
                   pattern "<.*>|$.*";
                 }
                 type int32 {
                   range "0 .. 15";
                 }
               }
             }
             leaf rx-output-emphasis {
               description "Receive output emphasis for optics";
               units "dB";
               type union {
                 type string {
                   pattern "<.*>|$.*";
                 }
                 type int32 {
                   range "0 .. 15";
                 }
               }
             }
             leaf rx-output-amplitude {
               description "Receive output amplitude setting";
               type enumeration {
                 enum "400mV" {
                   description "No equalization for 100mV - 400mV amplitude";
                 }
                 enum "600mV" {
                   description "No equalization for 300mV - 600mV amplitude";
                 }
                 enum "800mV" {
                   description "No equalization for 400mV - 800mV amplitude";
                 }
                 enum "1200mV" {
                   description "No equalization for 600mV - 1200mV amplitude";
                 }
               }
             }
             leaf tx-squelch {
               description "Transmit squelch ON/OFF";
               type enumeration {
                 enum "off" {
                   description "Transmit squelch OFF for optics";
                 }
                 enum "on" {
                   description "Transmit squelch ON for optics";
                 }
               }
             }
             leaf rx-squelch {
               description "Receive squelch ON/OFF";
               type enumeration {
                 enum "off" {
                   description "Receive squelch OFF for optics";
                 }
                 enum "on" {
                   description "Receive squelch ON for optics";
                 }
               }
             }
             leaf tx-rate-select {
               description "Transmit rate select for optics";
               type union {
                 type string {
                   pattern "<.*>|$.*";
                 }
                 type int32 {
                   range "0 .. 3";
                 }
               }
             }
             leaf rx-rate-select {
               description "Receive rate select for optics";
               type union {
                 type string {
                   pattern "<.*>|$.*";
                 }
                 type int32 {
                   range "0 .. 3";
                 }
               }
             }
           }
         }
       }
     }
     container otn-options {
       description "Optical Transmission Network interface-specific options";
       uses otn_options_type;
     }
     container tdm-options {
       description "Time division multiplexing (TDM) interface-specific options";
       uses tdm_options_type;
     }
     container och-options {
       description "Optical channel configuration options";
       uses och-attributes;
     }
     container otu-options {
       description "Optical transmission unit configuration options";
       uses otu-attributes;
     }
     container odu-options {
       description "Optical data unit configuration options";
       uses odu-attributes;
     }
     container ett-options {
       description "Transport ethernet client configuration options";
       uses ett-attributes;
     }
     container fastether-options {
       description "Fast Ethernet interface-specific options";
       uses apply-advanced;
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       choice auto-negotiation-choice {
         leaf auto-negotiation {
           description "Enable auto-negotiation";
           type empty;
         }
         leaf no-auto-negotiation {
           description "Don't enable auto-negotiation";
           type empty;
         }
       }
       leaf ingress-rate-limit {
         description "Ingress rate at port";
         units "megabits per second";
         type union {
           type string {
             pattern "<.*>|$.*";
           }
           type uint32 {
             range "1 .. 100";
           }
         }
       }
       list source-address-filter {
         key name;
         ordered-by user;
         description "Source address filters";
         leaf name {
           description "Remote MAC address";
           type jt:mac-addr;
         }
       }
       container redundant-parent {
         description " Parent of this interface";
         uses apply-advanced;
         leaf parent {
           description "Join a redundant ethernet interface";
           type union {
             type jt:interface-device;
             type string {
               pattern "<.*>|$.*";
             }
           }
         }
       }
       container ieee-802.3ad {
         description "IEEE 802.3ad";
         uses apply-advanced;
         container lacp {
           description "Link Aggregation Control Protocol configuration";
           uses apply-advanced;
           leaf port-priority {
             description "Priority of the port (0 ... 65535)";
             type union {
               type uint16;
               type string {
                 pattern "<.*>|$.*";
               }
             }
           }
         }
         leaf bundle {
           description "Join an aggregated Ethernet interface";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
       }
       container mpls {
         description "MPLS options";
         uses mpls_ifd_options;
       }
       leaf ignore-l3-incompletes {
         description "Ignore L3 incomplete errors";
         type empty;
       }
     }
     container redundant-ether-options {
       description "Ethernet redundancy options";
       uses apply-advanced;
       leaf redundancy-group {
         description "Redundancy group of this interface";
         type union {
           type string {
             pattern "<.*>|$.*";
           }
           type uint16 {
             range "1 .. 128";
           }
         }
       }
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       list source-address-filter {
         key name;
         ordered-by user;
         description "Source address filters";
         leaf name {
           description "Remote MAC address";
           type jt:mac-addr;
         }
       }
       leaf mru {
         description "Maximum receive packet size";
         type union {
           type string {
             pattern "<.*>|$.*";
           }
           type uint32;
         }
       }
       leaf link-speed {
         description "Link speed of individual interface that joins the RETH";
         type enumeration {
           enum "10m" {
             description "Links are 10M";
           }
           enum "100m" {
             description "Links are 100M";
           }
           enum "1g" {
             description "Links are 1G";
           }
           enum "10g" {
             description "Links are 10G";
           }
           enum "25g" {
             description "Links are 25G";
           }
         }
       }
       leaf minimum-links {
         description "Minimum number of active links";
         default "1";
         type union {
           type string {
             pattern "<.*>|$.*";
           }
           type uint16 {
             range "1 .. 8";
           }
         }
       }
       container lacp {
         description "Link Aggregation Control Protocol configuration";
         uses apply-advanced;
         choice mode {
           case case_1 {
             leaf active {
               description "Initiate transmission of LACP packets";
               type empty;
             }
           }
           case case_2 {
             leaf passive {
               description "Respond to LACP packets";
               type empty;
             }
           }
         }
         leaf periodic {
           description "Timer interval for periodic transmission of LACP packets";
           type enumeration {
             enum "fast" {
               description "Receive packets every second";
             }
             enum "slow" {
               description "Receive packets every 30 seconds";
             }
           }
         }
       }
     }
     container aggregated-ether-options {
       description "Aggregated Ethernet interface-specific options";
       uses apply-advanced;
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       leaf autostate-exclude {
         description "Interface will not contribute to IRB state";
         type empty;
       }
       container link-protection {
         presence "enable link-protection";
         description "Enable link protection mode";
         uses apply-advanced;
         leaf revertive {
           description "Revert back from active backup link to primary, if primary is UP";
           type empty;
         }
         leaf non-revertive {
           description "Do not revert back (default mode) from active backup link to primary, if primary is UP";
           type empty;
         }
         leaf backup-state {
           description "Link protection backup link state";
           default "accept-data";
           type enumeration {
             enum "accept-data" {
               description "Accept data on receive channel of backup link";
             }
             enum "discard-data" {
               description "Discard data on receive channel of backup link";
             }
             enum "down" {
               description "Backup link is marked down";
             }
           }
         }
         container rtg-config {
           presence "enable rtg-config";
           description "RTG enable on AE";
           uses apply-advanced;
           leaf preempt-cutover-timer {
             description "RTG preempt-cutover-timer in seconds";
             default "1";
             type union {
               type string {
                 pattern "<.*>|$.*";
               }
               type uint32 {
                 range "0 .. 255";
               }
             }
           }
         }
       }
       choice fcoe-lag-choice {
         leaf fcoe-lag {
           description "Enable FIP/FCoE LAG";
           type empty;
         }
         leaf no-fcoe-lag {
           description "Don't enable FIP/FCoE LAG";
           type empty;
         }
       }
       list source-address-filter {
         key name;
         ordered-by user;
         description "Source address filters";
         leaf name {
           description "Remote MAC address";
           type jt:mac-addr;
         }
       }
       container configured-flow-control {
         presence "enable configured-flow-control";
         description "Enable flow control";
         uses apply-advanced;
         leaf rx-buffers {
           description "Enable/Disable Rx buffers";
           type enumeration {
             enum "on" {
               description "Enable Rx buffers";
             }
             enum "off" {
               description "Disable Rx buffers";
             }
           }
         }
         leaf tx-buffers {
           description "Enable/Disable Tx buffers";
           type enumeration {
             enum "on" {
               description "Enable Tx buffers";
             }
             enum "off" {
               description "Disable Tx buffers";
             }
           }
         }
       }
       container load-balance {
         uses aggregate-load-balance;
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 9000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         container damping {
           description "BFD flap damping parameters";
           uses apply-advanced;
           leaf suppress {
             description "Suppress threshold for figure-of-merit value";
             default "5000";
             type union {
               type string {
                 pattern "<.*>|$.*";
               }
               type uint32 {
                 range "1000 .. 200000";
               }
             }
           }
           leaf reuse {
             description "Reuse threshold for figure-of-merit value";
             default "1000";
             type union {
               type string {
                 pattern "<.*>|$.*";
               }
               type uint32 {
                 range "1000 .. 200000";
               }
             }
           }
           leaf max-suppress-time {
             description "Maximum hold-down time";
             default "600";
             units "seconds";
             type union {
               type string {
                 pattern "<.*>|$.*";
               }
               type uint32 {
                 range "1 .. 20000";
               }
             }
           }
           leaf half-life-interval {
             description "Decay half life interval";
             default "30";
             units "seconds";
             type union {
               type string {
                 pattern "<.*>|$.*";
               }
               type uint32 {
                 range "1 .. 600";
               }
             }
           }
           leaf increment {
             description "Increments applied to figure-of-merit value for every flap";
             default "1000";
             type union {
               type string {
                 pattern "<.*>|$.*";
               }
               type uint32 {
                 range "1000 .. 20000";
               }
             }
           }
         }
         leaf neighbor {
           description "BFD neighbor address";
           type jt:ipaddr;
         }
         leaf local-address {
           description "BFD local address";
           type jt:ipaddr;
         }
         leaf holddown-interval {
           description "Time to hold the session-UP notification to the client";
           units "milliseconds";
           type union {
             type string {
               pattern "<.*>|$.*";
             }
             type uint32 {
               range "0 .. 255000";
             }
           }
         }
       }
       leaf minimum-links {
         description "Minimum number of aggregated links";
         type union {
           type string {
             pattern "<.*>|$.*";
           }
           type uint16;
         }
       }
       container minimum-bandwidth {
         presence "enable minimum-bandwidth";
         description "Minimum bandwidth configured for aggregated bundle";
         uses apply-advanced;
         leaf bw-value {
           description "Bandwidth value";
           default "1";
           type union {
             type uint64;
             type string {
               pattern "<.*>|$.*";
             }
           }
         }
         leaf bw-unit {
           description "Bandwidth unit";
           type enumeration {
             enum "bps" {
               description "Links are in bits per sec";
             }
             enum "kbps" {
               description "Links are in kilo bits per sec";
             }
             enum "mbps" {
               description "Links are in mega bits per sec";
             }
             enum "gbps" {
               description "Links are in giga bits per sec ";
             }
           }
         }
       }
       container targeted-options {
         presence "enable targeted-options";
         description "Targeting specific options";
         uses apply-advanced;
         leaf type {
           description "Targeting type of AE bundle";
           type enumeration {
             enum "auto" {
               description "Targeting type is Auto";
             }
             enum "manual" {
               description "Targeting type is Manual";
             }
           }
         }
         choice redundancy_choice {
           case case_1 {
             leaf logical-interface-fpc-redundancy {
               description "Enable FPC redundancy for logical interfaces";
               type empty;
             }
           }
           case case_2 {
             leaf logical-interface-chassis-redundancy {
               description "Enable CHASSIS redundancy for logical interfaces";
               type empty;
             }
           }
         }
         container rebalance-periodic {
           presence "enable rebalance-periodic";
           uses apply-advanced;
           leaf start-time {
             description "Start time of the rebalance operation ( Wall clock time )";
             type jt:time-of-day;
           }
           leaf interval {
             description "Interval of the rebalance operation in hrs";
             type union {
               type string {
                 pattern "<.*>|$.*";
               }
               type uint32 {
                 range "1 .. 24";
               }
             }
           }
         }
         leaf rebalance-subscriber-granularity {
           description "Max subscriber aggregate weight";
           type union {
             type string {
               pattern "<.*>|$.*";
             }
             type uint32 {
               range "1 .. 65535";
             }
           }
         }
       }
       choice redundancy_choice {
         case case_1 {
           leaf logical-interface-fpc-redundancy {
             description "Enable FPC redundancy for logical interfaces";
             type empty;
           }
         }
         case case_2 {
           leaf logical-interface-chassis-redundancy {
             description "Enable CHASSIS redundancy for logical interfaces";
             type empty;
           }
         }
       }
       container rebalance-periodic {
         uses apply-advanced;
         leaf start-time {
           description "Start time of the rebalance operation ( Wall clock time )";
           type jt:time-of-day;
         }
         leaf interval {
           description "Interval of the rebalance operation in hrs";
           type union {
             type string {
               pattern "<.*>|$.*";
             }
             type uint32 {
               range "1 .. 24";
             }
           }
         }
       }
       leaf pad-to-minimum-frame-size {
         description "Pad Tx vlan tagged frame to minimum of 68 bytes";
         type empty;
       }
       leaf link-speed {
         description "Link speed of individual interface that joins the AE";
         type enumeration {
           enum "10m" {
             description "Links are 10M";
           }
           enum "100m" {
             description "Links are 100M";
           }
           enum "1g" {
             description "Links are 1G";
           }
           enum "2.5g" {
             description "Links are 2.5G";
           }
           enum "5g" {
             description "Links are 5G";
           }
           enum "8g" {
             description "Links are 8G";
           }
           enum "10g" {
             description "Links are 10G";
           }
           enum "25g" {
             description "Links are 25G";
           }
           enum "40g" {
             description "Links are 40G";
           }
           enum "50g" {
             description "Links are 50G";
           }
           enum "80g" {
             description "Links are 80G";
           }
           enum "100g" {
             description "Links are 100G";
           }
           enum "200g" {
             description "Links are 200G";
           }
           enum "400g" {
             description "Links are 400G";
           }
           enum "800g" {
             description "Links are 800G";
           }
           enum "oc192" {
             description "Links are OC-192";
           }
           enum "mixed" {
             description "Links are various speeds";
           }
         }
       }
       container local-bias {
         presence "enable local-bias";
         description "Turn on local bias functionality";
         uses apply-advanced;
         leaf disable {
           description "Disable local-bias";
           type empty;
         }
       }
       leaf local-minimum-links-threshold {
         description "Specify threshold for minimum links per VC/VCF member";
         type union {
           type string {
             pattern "<.*>|$.*";
           }
           type uint16 {
             range "1 .. 100";
           }
         }
       }
       leaf resilient-hash {
         description "Turn on resilient-hash";
         type empty;
       }
       container dlb {
         description "Enable DLB on LAG";
         uses apply-advanced;
         choice mode {
           case case_1 {
             leaf per-packet {
               description "Per-packet link assignment";
               type empty;
             }
           }
           case case_2 {
             leaf assigned-flow {
               description "Fixed link assignment";
               type empty;
             }
           }
           case case_3 {
             container flowlet {
               presence "enable flowlet";
               description "Inactivity-based link assignment";
               uses apply-advanced;
               leaf inactivity-interval {
                 description " Minimum inactivity interval in micro-seconds for link re-assignment";
                 default "256";
                 type union {
                   type string {
                     pattern "<.*>|$.*";
                   }
                   type uint32;
                 }
               }
             }
           }
         }
       }
       container lacp {
         description "Link Aggregation Control Protocol configuration";
         uses apply-advanced;
         choice mode {
           case case_1 {
             leaf active {
               description "Initiate transmission of LACP packets";
               type empty;
             }
           }
           case case_2 {
             leaf passive {
               description "Respond to LACP packets";
               type empty;
             }
           }
         }
         leaf periodic {
           description "Timer interval for periodic transmission of LACP packets";
           type enumeration {
             enum "fast" {
               description "Receive packets every second";
             }
             enum "slow" {
               description "Receive packets every 30 seconds";
             }
           }
         }
         leaf multiplier {
           description "LACP timeout detection multiplier";
           type union {
             type string {
               pattern "<.*>|$.*";
             }
             type uint32 {
               range "3 .. 30";
             }
           }
         }
         leaf fast-failover {
           description "To turn on LACP fast-failover";
           type empty;
         }
         container link-protection {
           presence "enable link-protection";
           uses apply-advanced;
           leaf disable {
             description "To turn off LACP link-protection";
             type empty;
           }
           choice mode {
             case case_1 {
               leaf revertive {
                 description "Switch links when better priority link comes up";
                 type empty;
               }
             }
             case case_2 {
               leaf non-revertive {
                 description "Do not switch links when better priority link comes up";
                 type empty;
               }
             }
           }
           container rtg-config {
             presence "enable rtg-config";
             description "RTG Feature enable on AE";
             uses apply-advanced;
             leaf preempt-cutover-timer {
               description "RTG preempt-cutover-timer in seconds";
               default "1";
               type union {
                 type string {
                   pattern "<.*>|$.*";
                 }
                 type uint32 {
                   range "0 .. 255";
                 }
               }
             }
           }
         }
         leaf accept-data {
           description "Keep receiving traffic even when LACP goes down";
           type empty;
         }
         leaf sync-reset {
           description "On minimum-link failure notify out of sync to peer";
           type enumeration {
             enum "disable" {
               description "To disable minimum-link failure handling at LACP level";
             }
             enum "enable" {
               description "To enable minimum-link failure handling at LACP level";
             }
           }
         }
         leaf system-priority {
           description "Priority of the system (0 ... 65535)";
           type string;
         }
         leaf system-id {
           description "Node's System ID, encoded as a MAC address";
           type jt:mac-addr;
         }
         leaf admin-key {
           description "Node's administrative key";
           type union {
             type uint16;
             type string {
               pattern "<.*>|$.*";
             }
           }
         }
         container hold-time {
           description "Hold time for link up and link down for AE link members";
           leaf up {
             description "Link up hold time for the AE link members";
             units "seconds";
             type union {
               type string {
                 pattern "<.*>|$.*";
               }
               type uint16 {
                 range "1 .. 6000";
               }
             }
           }
         }
         leaf aggregate-wait-time {
           description "Aggregate wait time for the AE";
           units "seconds";
           type union {
             type string {
               pattern "<.*>|$.*";
             }
             type uint16 {
               range "0 .. 1800";
             }
           }
         }
         leaf force-up {
           description "Forceup AE interface with LACP";
           type empty;
         }
         leaf no-peer-loopback-validation {
           description "Skip MCLAG peer loop back validation for LACP PDUs on Forceup AE interface";
           type empty;
         }
       }
       list link-protection-sub-group {
         key name;
         ordered-by user;
         description "Link Protection subgroup configuration";
         leaf name {
           description "Name of the subgroup";
           type string {
             length "2 .. 64";
           }
         }
         uses apply-advanced;
         choice type {
           case case_1 {
             leaf primary {
               description "Primary subgroup for N:N link-protection mode";
               type empty;
             }
           }
           case case_2 {
             leaf backup {
               description "Backup subgroup for N:N link-protection mode";
               type empty;
             }
           }
         }
       }
       container ethernet-switch-profile {
         description "Ethernet virtual LAN/media access control-level options";
         uses apply-advanced;
         leaf-list tag-protocol-id {
           ordered-by user;
           description "IEEE 802.1q Tag Protocol Identifier values for VLAN-tagged frames";
           type string;
         }
         container storm-control {
           description "Storm control profile name to bind";
           uses apply-advanced;
           leaf profile-name {
             description "Profile name";
             type string;
           }
         }
         container recovery-timeout {
           description "Recovery timeout for this interface";
           leaf time-in-seconds {
             units "seconds";
             type union {
               type string {
                 pattern "<.*>|$.*";
               }
               type uint32 {
                 range "10 .. 3600";
               }
             }
           }
         }
         leaf mac-learn-enable {
           description "Learn MAC addresses dynamically";
           type empty;
         }
       }
       container mc-ae {
         description "Multi-chassis aggregation (MC-AE) network device configuration";
         uses apply-advanced;
         leaf mc-ae-id {
           description "MC-AE group id";
           type union {
             type string {
               pattern "<.*>|$.*";
             }
             type uint16 {
               range "1 .. 65535";
             }
           }
         }
         leaf redundancy-group {
           description "Redundancy group id";
           default "1";
           type union {
             type string {
               pattern "<.*>|$.*";
             }
             type uint32 {
               range "1 .. 4294967294";
             }
           }
         }
         leaf chassis-id {
           description "Chassis id of MC-AE network device";
           type union {
             type string {
               pattern "<.*>|$.*";
             }
             type uint16 {
               range "0 .. 1";
             }
           }
         }
         leaf mode {
           description "Mode of the MC-AE";
           type enumeration {
             enum "active-active" {
               description "MC-AE in active-active mode";
             }
           }
         }
         leaf status-control {
           description "Status of the MC-AE chassis";
           type enumeration {
             enum "active" {
               description "Chassis is Active";
             }
             enum "standby" {
               description "Chassis is Standby";
             }
           }
         }
         leaf switchover-mode {
           description "Switchover mode";
           type enumeration {
             enum "revertive" {
               description "Switch mcae node when preferred link comes up";
             }
             enum "non-revertive" {
               description "Do not switch mcae node when preferred link comes up";
             }
           }
         }
         leaf revert-time {
           description "Wait interval before performing switchover";
           default "3";
           units "minute";
           type union {
             type string {
               pattern "<.*>|$.*";
             }
             type uint32 {
               range "1 .. 10";
             }
           }
         }
         leaf init-delay-time {
           description "Init delay timer for mcae sm for min traffic loss";
           units "seconds";
           type union {
             type string {
               pattern "<.*>|$.*";
             }
             type uint16 {
               range "1 .. 6000";
             }
           }
         }
         leaf recovery-delay-time {
           description "Delay timer for bringing up ICL, ICCP";
           units "seconds";
           type union {
             type string {
               pattern "<.*>|$.*";
             }
             type uint16 {
               range "1 .. 6000";
             }
           }
         }
         leaf enhanced-convergence {
           description "Optimized convergence time for mcae";
           type empty;
         }
         container events {
           presence "enable events";
           description "MCAE related events";
           uses apply-advanced;
           container iccp-peer-down {
             presence "enable iccp-peer-down";
             description "Define behavior in the event of ICCP peer down";
             uses apply-advanced;
             leaf force-icl-down {
               description "Bring down ICL logical interface";
               type empty;
             }
             leaf prefer-status-control-active {
               description "Keep this node up (recommended only on status-control active)";
               type empty;
             }
           }
         }
       }
       leaf share-standby {
         description "Share the resources with standby ports, needs FPC reboot to take effect";
         type empty;
       }
     }
     container es-options {
       description "ES PIC interface-specific options";
       uses apply-advanced;
       leaf backup-interface {
         description "Name of backup interface";
         type union {
           type jt:interface-device;
           type string {
             pattern "<.*>|$.*";
           }
         }
       }
     }
     container dsl-options {
       description "DSL interface-specific options";
       uses apply-advanced;
       leaf operating-mode {
         description "DSL operating mode";
         type enumeration {
           enum "auto" {
             description "Autonegotiate mode";
           }
           enum "ansi-dmt" {
             description "ANSI T1.413 Issue II mode";
           }
           enum "itu-dmt" {
             description "ITU G.992.1 mode";
           }
           enum "etsi" {
             description "ETSI TS 101 388 V1.3.1 mode";
           }
           enum "itu-annexb-ur2" {
             description "ITU G.992.1 UR-2 mode";
           }
           enum "itu-annexb-non-ur2" {
             description "ITU G.992.1 Non UR-2 mode";
           }
           enum "itu-dmt-bis" {
             description "ITU G.992.3 mode";
           }
           enum "adsl2plus" {
             description "ITU G.992.5 mode";
           }
           enum "annexm-itu-dmt-bis" {
             description "AnnexM ITU G.992.3 mode";
           }
           enum "annexm-adsl2plus" {
             description "AnnexM ITU G.992.5 mode";
           }
         }
       }
     }
     container vdsl-options {
       description "VDSL interface-specific options";
       uses apply-advanced;
       leaf vdsl-profile {
         description "VDSL profile";
         type enumeration {
           enum "auto" {
             description "Auto";
           }
           enum "8a" {
             description "Profile 8a";
           }
           enum "8b" {
             description "Profile 8b";
           }
           enum "8c" {
             description "Profile 8c";
           }
           enum "8d" {
             description "Profile 8d";
           }
           enum "12a" {
             description "Profile 12a";
           }
           enum "12b" {
             description "Profile 12b";
           }
           enum "17a" {
             description "Profile 17a";
           }
         }
       }
       leaf sra {
         description "DSL SRA";
         default "disable";
         type enumeration {
           enum "enable" {
             description "Enable SRA";
           }
           enum "disable" {
             description "Disable SRA";
           }
         }
       }
       leaf v43 {
         description "DSL V43 tones";
         default "enable";
         type enumeration {
           enum "enable" {
             description "Enable V43";
           }
           enum "disable" {
             description "Disable V43";
           }
         }
       }
       leaf sos {
         description "Enable SOS";
         type empty;
       }
     }
     container dsl-sfp-options {
       description "DSL SFP options";
       uses apply-advanced;
       container adsl-options {
         description "ADSL options";
         uses apply-advanced;
         leaf vpi {
           description "Virtual path identifier";
           type union {
             type string {
               pattern "<.*>|$.*";
             }
             type uint32 {
               range "0 .. 255";
             }
           }
         }
         leaf vci {
           description "Virtual circuit identifier";
           type union {
             type string {
               pattern "<.*>|$.*";
             }
             type uint32 {
               range "32 .. 65535";
             }
           }
         }
         leaf encap {
           description "Encapsulation";
           type enumeration {
             enum "bypass" {
               description "Bypass";
             }
             enum "llcsnap-bridged-802dot1q" {
               description "LLCSNAP bridged 802.1q";
             }
             enum "llcsnap-routed-ip" {
               description "LLCSNAP routed ip";
             }
             enum "vc-mux-bridged" {
               description "VC MUX bridged";
             }
             enum "vc-mux-routed-ip" {
               description "VC MUX routed ip";
             }
             enum "generic" {
               description "Generic";
             }
           }
         }
         leaf annex {
           description "Annex type";
           type enumeration {
             enum "auto" {
               description "Annex type auto";
             }
             enum "annexj-off" {
               description "Annex type annexj turn off";
             }
           }
         }
       }
       container vdsl-options {
         description "VDSL options";
         uses apply-advanced;
         leaf profile {
           description "VDSL profile";
           type enumeration {
             enum "auto" {
               description "Automatic";
             }
             enum "8a" {
               description "Profile 8a";
             }
             enum "8b" {
               description "Profile 8b";
             }
             enum "8c" {
               description "Profile 8c";
             }
             enum "8d" {
               description "Profile 8d";
             }
             enum "12a" {
               description "Profile 12a";
             }
             enum "12b" {
               description "Profile 12b";
             }
             enum "17a" {
               description "Profile 17a";
             }
             enum "30a" {
               description "Profile 30a";
             }
           }
         }
         leaf carrier {
           description "Carrier setting";
           type enumeration {
             enum "auto" {
               description "Automatic";
             }
             enum "a43" {
               description "Carrier A43";
             }
             enum "b43" {
               description "Carrier B43";
             }
           }
         }
       }
       container gfast-options {
         description "G.fast options";
         uses apply-advanced;
         leaf carrier {
           description "Carrier setting";
           type enumeration {
             enum "a43" {
               description "Carrier A43";
             }
             enum "a43c" {
               description "Carrier A43C";
             }
             enum "b43" {
               description "Carrier B43";
             }
             enum "b43c" {
               description "Carrier B43C";
             }
           }
         }
       }
     }
     container shdsl-options {
       description "SHDSL interface-specific options";
       uses apply-advanced;
       leaf annex {
         description "Type of SHDSL annex";
         default "annex-b";
         type enumeration {
           enum "annex-a" {
             description "Annex-a PIC";
           }
           enum "annex-b" {
             description "Annex-b PIC";
           }
           enum "annex-f" {
             description "Annex-f PIC";
           }
           enum "annex-g" {
             description "Annex-g PIC";
           }
           enum "annex-auto" {
             description "Annex-auto PIC";
           }
         }
       }
       leaf line-rate {
         description "SHDSL line rate";
         type string;
       }
       leaf loopback {
         description "Loopback mode";
         type enumeration {
           enum "local" {
             description "Local loopback";
           }
           enum "remote" {
             description "Remote loopback";
           }
         }
       }
       container snr-margin {
         presence "enable snr-margin";
         description "Signal to noise ratio margin";
         uses apply-advanced;
         leaf current {
           description "Current signal to noise ratio margin";
           units "dB";
           type string;
         }
         leaf snext {
           description "SNEXT signal to noise ratio margin";
           units "dB";
           type string;
         }
       }
     }
     container data-input {
       description "Configuration for drop-insert data input";
       uses apply-advanced;
       choice input-choice {
         case case_1 {
           leaf system {
             description "Data sourced from system";
             type empty;
           }
         }
         case case_2 {
           leaf interface {
             description "Interface that acts as data source";
             type union {
               type jt:interface-device;
               type string {
                 pattern "<.*>|$.*";
               }
             }
           }
         }
       }
     }
     container switch-options {
       description "Front end ports configuration";
       uses apply-advanced;
       list switch-port {
         key name;
         leaf name {
           description "Front end port number";
           type union {
             type string {
               pattern "<.*>|$.*";
             }
             type uint32 {
               range "0 .. 15";
             }
           }
         }
         uses apply-advanced;
         choice auto-negotiation-choice {
           leaf auto-negotiation {
             description "Enable auto-negotiation";
             type empty;
           }
           leaf no-auto-negotiation {
             description "Don't enable auto-negotiation";
             type empty;
           }
         }
         leaf link-mode {
           description "Link operational mode";
           type enumeration {
             enum "half-duplex" {
               description "Half-duplex operation";
             }
             enum "full-duplex" {
               description "Full-duplex operation";
             }
           }
         }
         leaf speed {
           description "Link speed";
           type enumeration {
             enum "10m" {
             }
             enum "100m" {
             }
             enum "1g" {
             }
           }
         }
         leaf vlan-id {
           description "VLAN ID for this port";
           type union {
             type string {
               pattern "<.*>|$.*";
             }
             type uint32 {
               range "0 .. 4094";
             }
           }
         }
         leaf cascade-port {
           description "Port externally connected to another cascade port";
           type empty;
         }
       }
     }
     container container-options {
       description "Container interface specific options";
       uses apply-advanced;
       container container-type {
         presence "enable container-type";
         description "Protocol type of the container interface";
         uses apply-advanced;
         choice container-type-choice {
           case case_1 {
             container aps {
               description "APS options on the container";
               presence "enable aps";
               uses aps_type;
             }
           }
         }
       }
       container member-interface-type {
         description "Link type of members of container";
         uses apply-advanced;
         choice member_interface_type_choice {
           case case_1 {
             container sonet {
               uses apply-advanced;
               leaf member-interface-speed {
                 description "Link speed of members of container";
                 type enumeration {
                   enum "oc3" {
                     description "Links are OC-3";
                   }
                   enum "oc12" {
                     description "Links are OC-12";
                   }
                   enum "oc48" {
                     description "Links are OC-48";
                   }
                   enum "oc192" {
                     description "Links are OC-192";
                   }
                   enum "oc768" {
                     description "Links are OC-768";
                   }
                   enum "mixed" {
                     description "Links are of different speeds";
                   }
                 }
               }
             }
           }
           case case_2 {
             container atm {
               uses apply-advanced;
               leaf member-interface-speed {
                 description "Link speed of members of container";
                 type enumeration {
                   enum "oc3" {
                     description "Links are OC-3";
                   }
                   enum "oc12" {
                     description "Links are OC-12";
                   }
                   enum "oc48" {
                     description "Links are OC-48";
                   }
                 }
               }
             }
           }
           case case_3 {
             container channelized-sonet {
               uses apply-advanced;
               leaf member-interface-speed {
                 description "Link speed of members of container";
                 type enumeration {
                   enum "coc3" {
                     description "Links are COC-3";
                   }
                   enum "coc12" {
                     description "Links are COC-12";
                   }
                   enum "coc48" {
                     description "Links are COC-48";
                   }
                   enum "coc192" {
                     description "Links are COC-192";
                   }
                   enum "coc768" {
                     description "Links are COC-768";
                   }
                 }
               }
             }
           }
           case case_4 {
             container channelized-sdh {
               uses apply-advanced;
               leaf member-interface-speed {
                 description "Link speed of members of container";
                 type enumeration {
                   enum "cstm1" {
                     description "Links are cstm-1";
                   }
                   enum "cstm4" {
                     description "Links are cstm-4";
                   }
                   enum "cstm16" {
                     description "Links are cstm-16";
                   }
                   enum "coc64" {
                     description "Links are cstm-64";
                   }
                   enum "cstm256" {
                     description "Links are cstm256";
                   }
                 }
               }
             }
           }
         }
       }
       container redundancy {
         description "Container interface redundancy options";
         uses apply-advanced;
         container hold-time {
           description "Hold time for link up and link down";
           leaf up {
             description "Link up hold time";
             units "milliseconds";
             type union {
               type string {
                 pattern "<.*>|$.*";
               }
               type uint32 {
                 range "0 .. 65534";
               }
             }
           }
           leaf down {
             description "Link down hold time";
             units "milliseconds";
             type union {
               type string {
                 pattern "<.*>|$.*";
               }
               type uint32 {
                 range "0 .. 65534";
               }
             }
           }
         }
       }
       leaf-list container-list {
         ordered-by user;
         description "List of container interfaces this member link is associated to";
         type union {
           type jt:interface-device;
           type string {
             pattern "<.*>|$.*";
           }
         }
       }
       choice redundancy-type {
         case case_1 {
           choice aps-redundancy {
             case case_1 {
               leaf primary {
                 description "This member link is primary interface of the container";
                 type empty;
               }
             }
             case case_2 {
               leaf standby {
                 description "This member link is standby interface of the container";
                 type empty;
               }
             }
           }
         }
       }
       leaf fast-aps {
         description "Fast APS switch";
         type empty;
       }
       leaf allow-configuration-override {
         description "Allow physical configuration of member link to override container configuration";
         type empty;
       }
     }
     container layer2-policer {
       description "Layer2 policing for interface";
       uses apply-advanced;
       choice layer2-input-policer-choice {
         case case_1 {
           leaf input-policer {
             description "Two-color policer for received packets";
             type string;
           }
         }
         case case_2 {
           leaf input-hierarchical-policer {
             description "Hierarchical policer for received packets";
             type string;
           }
         }
       }
     }
     list unit {
       key name;
       description "Logical interface";
       leaf name {
         type string;
       }
       uses apply-advanced;
       leaf interface-tag {
         description "Interface tag name";
         type string {
           length "1 .. 64";
         }
       }
       container policer-overhead {
         description "Policer overhead adjustment for this unit";
         uses apply-advanced;
         leaf policer-overhead-value {
           description "Policer overhead bytes to be accounted in ingress and egress";
           units "bytes";
           type union {
             type string {
               pattern "<.*>|$.*";
             }
             type int32;
           }
         }
         leaf ingress {
           description "Ingress value in bytes";
           units "bytes";
           type union {
             type string {
               pattern "<.*>|$.*";
             }
             type int32 {
               range "-64 .. 64";
             }
           }
         }
         leaf egress {
           description "Egress value in bytes";
           units "bytes";
           type union {
             type string {
               pattern "<.*>|$.*";
             }
             type int32 {
               range "-64 .. 64";
             }
           }
         }
       }
       leaf alias {
         description "Interface alias";
         type string;
       }
       leaf enhanced-convergence {
         description "Optimize convergence time for L3";
         type empty;
       }
       leaf proxy-macip-advertisement {
         description "Proxy advertisement of type 2 MAC+IP route for EVPN";
         type empty;
       }
       leaf virtual-gateway-accept-data {
         description "Accept packets destined for virtual gateway address";
         type empty;
       }
       container peer-psd {
         presence "enable peer-psd";
         description "Peer psd";
         leaf psd-name {
           description "Peer psd name";
           type string;
         }
       }
       container peer-interface {
         presence "enable peer-interface";
         description "Peer interface";
         uses apply-advanced;
         leaf interface-name {
           description "Peer interface name";
           type union {
             type jt:interface-unit;
             type string {
               pattern "<.*>|$.*";
             }
           }
         }
       }
       container interface-shared-with {
         presence "enable interface-shared-with";
         description "Specify which PSD owns this logical interface";
         uses apply-advanced;
         leaf psd-name {
           description "Name of protected system domain (psd[1-31], ex. psd2)";
           type string {
           }
         }
       }
       choice enable-disable {
         case case_1 {
           leaf disable {
             description "Disable this logical interface";
             type empty;
           }
         }
       }
       leaf passive-monitor-mode {
         description "Use interface to tap packets from another router";
         type empty;
       }
       leaf per-session-scheduler {
         description "Enable per-session queuing on an IQ2 interface";
         type empty;
       }
       container account-layer2-overhead {
         presence "enable account-layer2-overhead";
         description "Account layer2 overhead in IFL byte statistics";
         uses apply-advanced;
         leaf overhead-value {
           description "Layer2 overhead bytes to be accounted in ingress and egress";
           units "bytes";
           type union {
             type string {
               pattern "<.*>|$.*";
             }
             type int8 {
               range "-128 .. 127";
             }
           }
         }
         leaf ingress {
           description "Layer2 overhead bytes to be accounted in ingress";
           units "bytes";
           type union {
             type string {
               pattern "<.*>|$.*";
             }
             type int8 {
               range "-128 .. 127";
             }
           }
         }
         leaf egress {
           description "Layer2 overhead bytes to be accounted in egress";
           units "bytes";
           type union {
             type string {
               pattern "<.*>|$.*";
             }
             type int8 {
               range "-128 .. 127";
             }
           }
         }
       }
       container forwarding-class-accounting {
         presence "enable forwarding-class-accounting";
         description "Configure Forwarding-class-accounting parameters for IFL ";
         uses apply-advanced;
         leaf direction {
           description "Direction of the traffic to be accounted for IFL";
           type enumeration {
             enum "ingress" {
               description "Enable forwarding-class-accounting for ingress traffic";
             }
             enum "egress" {
               description "Enable forwarding-class-accounting for egress traffic";
             }
             enum "both" {
               description "Enable forwarding-class-accounting for both directions";
             }
           }
         }
         container enhanced {
           presence "enable enhanced";
           uses apply-advanced;
           leaf traffic-type {
             description "Traffic-type to be accounted for forwarding-class-accounting for IFL";
             type enumeration {
               enum "unicast-statistics" {
                 description "Count only unicast traffic for forwarding-class-accounting for IFL ";
               }
               enum "multicast-statistics" {
                 description "Count only multicast traffic for forwarding-class-accounting for IFL";
               }
             }
           }
           leaf family {
             description "Protocol traffic to be accounted for forwarding-class-accounting for IFL";
             type enumeration {
               enum "inet" {
                 description "Enable forwarding-class-accounting for IPv4 family only for IFL";
               }
               enum "inet6" {
                 description "Enable forwarding-class-accounting for IPv6 family only for IFL";
               }
               enum "both" {
                 description "Enable forwarding-class-accounting for both IPv4 and IPv6 family for IFL";
               }
             }
           }
           leaf direction {
             description "Direction of the traffic to be accounted for forwarding-class-accounting for IFL";
             type enumeration {
               enum "ingress" {
                 description "Enable forwarding-class-accounting for ingress traffic for IFL";
               }
               enum "egress" {
                 description "Enable forwarding-class-accounting for egress traffic for IFL";
               }
               enum "both" {
                 description "Enable forwarding-class-accounting for both ingress and egress traffic for IFL";
               }
             }
           }
           leaf overhead-bytes {
             description "Per octet overhead bytes to be accounted for forwarding-class-accounting for IFL ";
             default "0";
             type union {
               type string {
                 pattern "<.*>|$.*";
               }
               type uint32 {
                 range "0 .. 255";
               }
             }
           }
         }
       }
       leaf clear-dont-fragment-bit {
         description "Clear DF bit in packet (AS PIC and J-series only as well as MIF)";
         type empty;
       }
       leaf packet-inject-enable {
         description "Enable packet inject functionality on this IFL";
         type empty;
       }
       leaf reassemble-packets {
         description "Do reassembly of fragmented tunnel packets";
         type empty;
       }
       container ip-address-owner {
         description "Define the owner for IP addresses hosted on this interface";
         choice ip-address-owner-options {
           case case_1 {
             leaf service-plane {
               description "IP address defined on this interface is hosted by service plane";
               type empty;
             }
           }
           case case_2 {
             leaf routing-engine {
               description "IP address defined on this interface is hosted by routing engine";
               type empty;
             }
           }
         }
       }
       container services-options {
         description "Services interface-specific options";
         uses apply-advanced;
       }
       container rpm {
         description "Enable RPM service on this interface";
         uses apply-advanced;
         choice rpm_or_twamp {
           case case_1 {
             choice rpm-type {
               case case_1 {
                 leaf client {
                   description "Client mode";
                   type empty;
                 }
               }
               case case_2 {
                 leaf server {
                   description "Server mode";
                   type empty;
                 }
               }
               case case_3 {
                 leaf client-delegate-probes {
                   description "Client delegate probe mode";
                   type empty;
                 }
               }
             }
           }
           case case_2 {
             leaf twamp-server {
               description "Set TWAMP server mode on this interface";
               type empty;
             }
           }
           case case_3 {
             leaf twamp-client {
               description "Set TWAMP client mode on this interface";
               type empty;
             }
           }
         }
       }
       leaf description {
         description "Text description of interface";
         type string;
       }
       leaf metadata {
         description "Text metadata attached to interface";
         type string;
       }
       container dial-options {
         description "Dial options";
         uses apply-advanced;
         choice interface_id_choice {
           case case_1 {
             leaf l2tp-interface-id {
               description "Identifier for group of PPP sessions";
               type string {
                 length "1 .. 63";
               }
             }
           }
           case case_2 {
             leaf ipsec-interface-id {
               description "Identifier for group of dynamic peers";
               type string {
                 length "1 .. 63";
               }
             }
           }
         }
         choice ifl_type {
           case case_1 {
             leaf dedicated {
               description "Use this unit for only one PPP/IPSec session";
               type empty;
             }
           }
           case case_2 {
             leaf shared {
               description "Share this unit for multiple PPP/IPSec sessions";
               type empty;
             }
           }
         }
       }
       container actual-transit-statistics {
         presence "enable actual-transit-statistics";
         description "Actual transit statistics";
       }
       list demux-source {
         key name;
         ordered-by user;
         description "Demux based on source address";
         uses demux_options_table;
       }
       list demux-destination {
         key name;
         ordered-by user;
         description "Demux based on destination address";
         uses demux_options_table;
       }
       container demux {
         description "Demux based on source or destination address";
         uses apply-advanced;
         container inet {
           presence "enable inet";
           description "Family inet";
           uses apply-advanced;
           leaf address {
             description "Address type";
             type enumeration {
               enum "source" {
                 description "Demux based on source address";
               }
               enum "destination" {
                 description "Demux based on destination address";
               }
             }
           }
           container auto-configure {
             description "Auto configuration";
             uses dynamic_ipv4_type;
           }
         }
         container inet6 {
           presence "enable inet6";
           description "Family inet6";
           uses apply-advanced;
           leaf address {
             description "Address type";
             type enumeration {
               enum "source" {
                 description "Demux based on source address";
               }
               enum "destination" {
                 description "Demux based on destination address";
               }
             }
           }
           container auto-configure {
             description "Auto configuration";
             uses dynamic_ipv6_type;
           }
         }
       }
       leaf encapsulation {
         description "Logical link-layer encapsulation";
         type enumeration {
           enum "atm-nlpid" {
             description "ATM NLPID encapsulation";
           }
           enum "atm-cisco-nlpid" {
             description "Cisco-compatible ATM NLPID encapsulation";
           }
           enum "atm-snap" {
             description "ATM LLC/SNAP encapsulation";
           }
           enum "atm-vc-mux" {
             description "ATM VC multiplexing";
           }
           enum "atm-ccc-vc-mux" {
             description "ATM VC for CCC";
           }
           enum "atm-tcc-vc-mux" {
             description "ATM VC for translational cross-connect";
           }
           enum "atm-tcc-snap" {
             description "ATM LLC/SNAP for translational cross-connect";
           }
           enum "atm-ccc-cell-relay" {
             description "ATM cell relay for CCC";
           }
           enum "vlan-vci-ccc" {
             description "CCC for VLAN Q-in-Q and ATM VPI/VCI interworking";
           }
           enum "ether-over-atm-llc" {
             description "Ethernet over ATM (LLC/SNAP) encapsulation";
           }
           enum "ether-vpls-over-atm-llc" {
             description "Ethernet VPLS over ATM (bridging) encapsulation";
           }
           enum "ppp-over-ether-over-atm-llc" {
             description "PPPoE over ATM (LLC/SNAP) encapsulation";
           }
           enum "ppp-over-ether" {
             description "PPPoE encapsulation";
           }
           enum "atm-ppp-vc-mux" {
             description "ATM PPP over raw AAL5";
           }
           enum "atm-ppp-llc" {
             description "ATM PPP over AAL5/LLC";
           }
           enum "atm-mlppp-llc" {
             description "ATM MLPPP over AAL5/LLC";
           }
           enum "frame-relay-ppp" {
             description "PPP over Frame Relay";
           }
           enum "frame-relay-ccc" {
             description "Frame Relay DLCI for CCC";
           }
           enum "frame-relay" {
             description "Frame Relay DLCI";
           }
           enum "frame-relay-tcc" {
             description "Frame Relay DLCI for translational cross-connect";
           }
           enum "frame-relay-ether-type" {
             description "Cisco-compatible Frame Relay Encapsulation DLCI";
           }
           enum "frame-relay-ether-type-tcc" {
             description "Cisco-compatible Frame Relay Encapsulation DLCI for TCC";
           }
           enum "ether-vpls-fr" {
             description "Ethernet VPLS over Frame Relay (bridging) encapsulation";
           }
           enum "vlan-ccc" {
             description "802.1q tagging for a cross-connect";
           }
           enum "ethernet-ccc" {
             description "Ethernet for a cross-connect";
           }
           enum "vlan-vpls" {
             description "VLAN virtual private LAN service";
           }
           enum "vlan-bridge" {
             description "VLAN layer-2 bridging";
           }
           enum "ethernet-tcc" {
             description "Ethernet translational cross-connect";
           }
           enum "dix" {
             description "Ethernet DIXv2 (RFC 894)";
           }
           enum "ethernet" {
             description "Ethernet II (RFC 894)";
           }
           enum "ethernet-vpls" {
             description "Ethernet II virtual private LAN service";
           }
           enum "ethernet-bridge" {
             description "Ethernet II bridging";
           }
           enum "vlan" {
             description "802.1q-tagged Ethernet";
           }
           enum "vlan-tcc" {
             description "802.1q tagging for a translational cross-connect";
           }
           enum "multilink-ppp" {
             description "Multilink PPP";
           }
           enum "multilink-frame-relay-end-to-end" {
             description "Multilink Frame Relay end-to-end (FRF.15)";
           }
           enum "ppp-ccc" {
             description "Serial PPP device for a cross-connect";
           }
         }
       }
       leaf gre {
         description "Allow GRE packets";
         type empty;
       }
       leaf mtu {
         description "Maximum transmission unit packet size";
         type union {
           type string {
             pattern "<.*>|$.*";
           }
           type uint32;
         }
       }
       choice pointedness {
         case case_1 {
           leaf point-to-point {
             description "Point-to-point connection";
             type empty;
           }
         }
         case case_2 {
           leaf multipoint {
             description "Multipoint connection";
             type empty;
           }
         }
       }
       leaf bandwidth {
         description "Logical unit bandwidth (informational only)";
         type string;
       }
       leaf global-layer2-domainid {
         description "Global Layer-2 Identifier for this interface";
         type union {
           type string {
             pattern "<.*>|$.*";
           }
           type uint32 {
             range "5 .. 4094";
           }
         }
       }
       container radio-router {
         description "Parameters for dynamic link cost management";
         presence "enable radio-router";
         uses dynamic_ifbw_parms_type;
       }
       choice traps-choice {
         leaf traps {
           description "Enable SNMP notifications on state changes";
           type empty;
         }
         leaf no-traps {
           description "Don't enable SNMP notifications on state changes";
           type empty;
         }
       }
       choice routing-services-choice {
         leaf routing-services {
           description "Enable routing services";
           status deprecated;
           type empty;
         }
         leaf no-routing-services {
           description "Don't enable routing services";
           status deprecated;
           type empty;
         }
       }
       container routing-service {
         description "Routing Services on this interface";
         uses apply-advanced;
         choice enable-disable {
           case case_1 {
             leaf enable {
               description "Enable Routing Service";
               type empty;
             }
           }
           case case_2 {
             leaf disable {
               description "Disable Routing Service";
               type empty;
             }
           }
         }
       }
       container arp-resp {
         presence "enable arp-resp";
         description "Knob to control ARP response on the interface, default is restricted";
         choice arp-response-options {
           case case_1 {
             leaf unrestricted {
               description "Enable unrestricted ARP respone on the interface";
               type empty;
             }
           }
           case case_2 {
             leaf restricted {
               description "Enable restricted proxy ARP response on the interface";
               type empty;
             }
           }
         }
       }
       container proxy-arp {
         presence "enable proxy-arp";
         description "Enable proxy ARP on the interface, default is unrestricted";
         choice proxyarp-options {
           case case_1 {
             leaf unrestricted {
               description "Enable unrestricted proxy ARP on the interface";
               type empty;
             }
           }
           case case_2 {
             leaf restricted {
               description "Enable restricted proxy ARP on the interface";
               type empty;
             }
           }
         }
       }
       choice vlan_choice {
         case case_1 {
           leaf vlan-id {
             description "Virtual LAN identifier value for 802.1q VLAN tags";
             type string;
           }
         }
         case case_2 {
           leaf vlan-id-range {
             description "Virtual LAN identifier range of form vid1-vid2";
             type jt:vlan-range;
           }
         }
         case case_3 {
           leaf-list inner-vlan-id-swap-ranges {
             description "Inner vlan-id swap range(s) of form vid1-vid2 for dynamic L2 VLANs";
             type jt:vlan-range;
           }
         }
         case case_4 {
           leaf-list vlan-id-list {
             description "List of VLAN identifiers";
             type jt:vlan-range;
           }
         }
         case case_5 {
           leaf-list vlan-tag {
             ordered-by user;
             description "IEEE 802.1q tag list for VLAN tagged frames";
             status deprecated;
             type string;
           }
         }
         case case_6 {
           container vlan-tags {
             presence "enable vlan-tags";
             description "IEEE 802.1q tags";
             leaf outer {
               description "[tpid.]vlan-id, tpid format is 0xNNNN and is optional";
               type string;
             }
             choice inner_choice {
               case case_1 {
                 leaf inner {
                   description "[tpid.]vlan-id, tpid format is 0xNNNN and is optional";
                   type string;
                 }
               }
               case case_2 {
                 leaf inner-range {
                   description "[tpid.]vid1-vid2, tpid format is 0xNNNN and is optional";
                   type string {
                   }
                 }
               }
               case case_3 {
                 leaf-list inner-list {
                   description "List of VLAN identifiers";
                   type jt:vlan-range;
                 }
               }
             }
           }
         }
       }
       leaf deep-vlan-qualified-learning {
         description "Enable qualified MAC-address learning on the specified vlan tag";
         type union {
           type string {
             pattern "<.*>|$.*";
           }
           type uint32 {
             range 3;
           }
         }
       }
       leaf native-inner-vlan-id {
         description "Native virtual LAN identifier for singly tagged frames";
         type union {
           type string {
             pattern "<.*>|$.*";
           }
           type uint32 {
             range "0 .. 4094";
           }
         }
       }
       container inner-vlan-id-range {
         description "Inner vlan-id range start <start-vlan-id> end <end-vlan-id>";
         leaf start {
           description "Inner vlan-id range's start value";
           type union {
             type string {
               pattern "<.*>|$.*";
             }
             type uint32 {
               range "32 .. 4094";
             }
           }
         }
         leaf end {
           description "Inner vlan-id range's end value";
           type union {
             type string {
               pattern "<.*>|$.*";
             }
             type uint32 {
               range "32 .. 4094";
             }
           }
         }
       }
       container accept-source-mac {
         description "Remote media access control address to/from which to accept traffic";
         uses apply-advanced;
         list mac-address {
           key name;
           description "Remote MAC address";
           uses mac_list;
         }
       }
       container input-vlan-map {
         description "VLAN map operation on input";
         uses vlan_map;
       }
       container output-vlan-map {
         description "VLAN map operation on output";
         uses vlan_map;
       }
       leaf swap-by-poppush {
         description "Pop original vlan tag and then push a new vlan tag";
         type empty;
       }
       leaf receive-lsp {
         description "Name of incoming label-switched path";
         type string;
       }
       leaf transmit-lsp {
         description "Name of outgoing label-switched path";
         type string;
       }
       leaf dlci {
         description "Frame Relay data-link control identifier";
         type union {
           type string {
             pattern "<.*>|$.*";
           }
           type uint32 {
             range "1 .. 1022";
           }
         }
       }
       leaf multicast-dlci {
         description "Frame Relay data-link control identifier for multicast packets";
         type union {
           type string {
             pattern "<.*>|$.*";
           }
           type uint32 {
             range "1 .. 1022";
           }
         }
       }
       choice vci_type {
         case case_1 {
           leaf vci {
             description "ATM point-to-point virtual circuit identifier ([vpi.]vci)";
             type jt:atm-vci;
           }
         }
         case case_2 {
           leaf allow-any-vci {
             description "Allow all VCIs to open in atm-ccc-cell-relay mode";
             type empty;
           }
         }
         case case_3 {
           leaf vpi {
             description "ATM point-to-point virtual path identifier (vpi)";
             type union {
               type string {
                 pattern "<.*>|$.*";
               }
               type uint32 {
                 range "0 .. 255";
               }
             }
           }
         }
         case case_4 {
           leaf trunk-id {
             description "ATM trunk identifier";
             type union {
               type string {
                 pattern "<.*>|$.*";
               }
               type uint32 {
                 range "0 .. 31";
               }
             }
           }
         }
       }
       leaf no-vpivci-swapping {
         description "Do not swap VPI/VCI for Cell Relay";
         type empty;
       }
       choice psn_vci_type {
         case case_1 {
           leaf psn-vci {
             description "PSN VCI";
             type jt:atm-vci;
           }
         }
         case case_2 {
           leaf psn-vpi {
             description "PSN VPI";
             type union {
               type string {
                 pattern "<.*>|$.*";
               }
               type uint32 {
                 range "0 .. 255";
               }
             }
           }
         }
       }
       container atm-l2circuit-mode {
         description "Select ATM Layer 2 circuit transport mode";
         choice mode_choice {
           case case_1 {
             leaf cell {
               description "ATM Layer 2 circuit cell mode";
               type empty;
             }
           }
           case case_2 {
             leaf aal5 {
               description "ATM Layer 2 circuit AAL5 mode";
               type empty;
             }
           }
         }
       }
       container vci-range {
         description "ATM VCI range start <start-vci> end <end-vci>";
         leaf start {
           description "ATM VCI range's start value";
           type union {
             type string {
               pattern "<.*>|$.*";
             }
             type uint16 {
               range "32 .. 4094";
             }
           }
         }
         leaf end {
           description "ATM VCI range's end value";
           type union {
             type string {
               pattern "<.*>|$.*";
             }
             type uint16 {
               range "32 .. 4094";
             }
           }
         }
       }
       leaf trunk-bandwidth {
         description "ATM trunk bandwidth";
         units "bits per second";
         type string;
       }
       leaf multicast-vci {
         description "ATM virtual circuit identifier for multicast packets";
         type jt:atm-vci;
       }
       container shaping {
         description "Virtual circuit traffic-shaping options";
         uses dcd_shaping_config;
       }
       container oam-period {
         description "OAM cell period";
         choice oam_period_choices {
           case case_1 {
             leaf oam-period {
               description "OAM cell period";
               units "seconds";
               type union {
                 type string {
                   pattern "<.*>|$.*";
                 }
                 type uint32 {
                   range "1 .. 900";
                 }
               }
             }
           }
           case case_2 {
             container disable {
               presence "enable disable";
               description "Disable F5 OAM loopback";
             }
           }
         }
       }
       container oam-liveness {
         description "OAM virtual circuit liveness parameters";
         uses apply-advanced;
         leaf up-count {
           description "Number of OAM cells to consider VC up";
           type union {
             type string {
               pattern "<.*>|$.*";
             }
             type uint32 {
               range "1 .. 255";
             }
           }
         }
         leaf down-count {
           description "Number of OAM cells to consider VC down";
           type union {
             type string {
               pattern "<.*>|$.*";
             }
             type uint32 {
               range "1 .. 255";
             }
           }
         }
       }
       container ppp-options {
         description "Point-to-Point Protocol interface-specific options";
         uses ppp_options_type;
       }
       container pppoe-options {
         description "PPP over Ethernet interface-specific options";
         uses pppoe_options_type;
       }
       container pppoe-underlying-options {
         description "PPP over Ethernet underlying interface-specific options";
         uses pppoe_underlying_options_type;
       }
       container advisory-options {
         description "Interface-specific recommendations";
         uses advisory_options_type;
       }
       container auto-configure {
         description "Auto configuration";
         uses auto_configure_vlan_type;
       }
       container demux-options {
         description "IP demux interface-specific options";
         uses demux_options_type;
       }
       container targeted-distribution {
         presence "enable targeted-distribution";
         description "Interface participates in targeted-distribution";
         uses apply-advanced;
         leaf primary-list {
           description "Primary targeted distribution list";
           type string {
             length "1 .. 20";
           }
         }
         leaf backup-list {
           description "Backup targeted distribution list";
           type string {
             length "1 .. 20";
           }
         }
         leaf standby-list {
           description "Standby targeted distribution list";
           type string {
             length "1 .. 20";
           }
         }
       }
       container targeted-options {
         presence "enable targeted-options";
         description "Targeting specific options";
         uses apply-advanced;
         leaf weight {
           description "Targeting weight for subscriber";
           type string;
         }
         leaf primary {
           description "Primary link for the subscriber";
           type union {
             type jt:interface-device;
             type string {
               pattern "<.*>|$.*";
             }
           }
         }
         leaf backup {
           description "Backup link for the subscriber";
           type union {
             type jt:interface-device;
             type string {
               pattern "<.*>|$.*";
             }
           }
         }
         leaf group {
           description "Group name to which the subscriber is associated";
           type string {
           }
         }
       }
       choice keepalive_choices {
         case case_1 {
           container keepalives {
             description "Send or demand keepalive messages";
             presence "enable keepalives";
             uses keepalives_type;
           }
         }
         case case_2 {
           leaf no-keepalives {
             description "Do not send or demand keepalive messages";
             type empty;
           }
         }
       }
       leaf inverse-arp {
         description "Enable inverse ARP";
         type empty;
       }
       leaf transmit-weight {
         description "ATM2 transmit weight for VC under VP tunnel";
         type union {
           type string {
             pattern "<.*>|$.*";
           }
           type uint16 {
             range "1 .. 32767";
           }
         }
       }
       container epd-threshold {
         description "Early packet discard threshold for ATM2";
         uses epd_threshold_config;
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf atm-scheduler-map {
         description "Assign ATM2 CoS scheduling map";
         type union {
           type string {
             pattern "default";
           }
           type string;
         }
       }
       leaf mrru {
         description "Maximum received reconstructed unit";
         units "bytes";
         type union {
           type string {
             pattern "<.*>|$.*";
           }
           type uint16 {
             range "1500 .. 4500";
           }
         }
       }
       leaf short-sequence {
         description "Short sequence number header format (MLPPP only)";
         type empty;
       }
       leaf fragment-threshold {
         description "Fragmentation threshold";
         units "bytes";
         type union {
           type string {
             pattern "<.*>|$.*";
           }
           type uint32 {
             range "64 .. 4500";
           }
         }
       }
       leaf drop-timeout {
         description "Drop timeout";
         units "milliseconds";
         type union {
           type string {
             pattern "<.*>|$.*";
           }
           type uint16 {
             range "0 .. 2000";
           }
         }
       }
       leaf disable-mlppp-inner-ppp-pfc {
         description "Disable compression for inner PPP header in MLPPP payload";
         type empty;
       }
       leaf minimum-links {
         description "Minimum number of links to sustain the bundle";
         type union {
           type string {
             pattern "<.*>|$.*";
           }
           type uint16;
         }
       }
       leaf multilink-max-classes {
         description "Number of multilink classes";
         type union {
           type string {
             pattern "<.*>|$.*";
           }
           type uint16;
         }
       }
       container compression {
         presence "enable compression";
         description "Various packet header compressions";
         uses apply-advanced;
         container rtp {
           presence "enable rtp";
           description "Compress and decompress RTP";
           uses apply-advanced;
           leaf f-max-period {
             description "Maximum number of compressed packets between transmission of full headers";
             type union {
               type string {
                 pattern "<.*>|$.*";
               }
               type uint32 {
                 range "1 .. 65535";
               }
             }
           }
           leaf-list queues {
             ordered-by user;
             description "Queue holding RTP packets. Default is queue 1";
             type enumeration {
               enum "q0" {
                 description "RTP packets assigned to queue 0";
               }
               enum "q1" {
                 description "RTP packets assigned to queue 1";
               }
               enum "q2" {
                 description "RTP packets assigned to queue 2";
               }
               enum "q3" {
                 description "RTP packets assigned to queue 3";
               }
             }
           }
           container port {
             presence "enable port";
             description "UDP destination ports reserved for RTP packets";
             leaf minimum {
               type union {
                 type string {
                   pattern "<.*>|$.*";
                 }
                 type uint32 {
                   range "0 .. 65535";
                 }
               }
             }
             leaf maximum {
               type union {
                 type string {
                   pattern "<.*>|$.*";
                 }
                 type uint32 {
                   range "0 .. 65535";
                 }
               }
             }
           }
           container maximum-contexts {
             description "Maximum number of simultaneous RTP contexts";
             leaf number {
               description "Maximum number of simultaneous RTP contexts";
               type union {
                 type string {
                   pattern "<.*>|$.*";
                 }
                 type uint32 {
                   range "16 .. 2048";
                 }
               }
             }
           }
         }
       }
       leaf interleave-fragments {
         description "Interleave long packets with high priority ones";
         type empty;
       }
       leaf link-layer-overhead {
         description "Link layer bit stuffing overhead (0.0 .. 50.0 percent)";
         type jt:unsigned-float;
       }
       leaf accounting-profile {
         description "Accounting profile name";
         type string;
       }
       leaf peer-unit {
         description "Peer unit number";
         type union {
           type string {
             pattern "<.*>|$.*";
           }
           type uint32 {
             range "0 .. 16385";
           }
         }
       }
       container tunnel {
         description "Tunnel parameters";
         uses apply-advanced;
         container encapsulation {
           presence "enable encapsulation";
           description "Encapsulation over tunnel";
           container vxlan-gpe {
             presence "enable vxlan-gpe";
             uses apply-advanced;
             container source {
               uses apply-advanced;
               leaf address {
                 description "Interface address prefix";
                 type jt:ipv4addr;
               }
               leaf mac-address {
                 description "Interface source mac address";
                 type jt:mac-addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
               leaf mac-address {
                 description "Interface destination mac address";
                 type jt:mac-addr;
               }
             }
             leaf tunnel-endpoint {
               description "Tunnel end point type";
               type enumeration {
                 enum "vxlan" {
                   description "To configure vxlan tunnel-end-point";
                 }
               }
             }
             container source-udp-port-range {
               description "Value range for source-udp-port";
               leaf min {
                 description "Minimum range value";
                 type union {
                   type string {
                     pattern "<.*>|$.*";
                   }
                   type uint32 {
                     range "1 .. 65535";
                   }
                 }
               }
               leaf max {
                 description "Maximum range value";
                 type union {
                   type string {
                     pattern "<.*>|$.*";
                   }
                   type uint32 {
                     range "1 .. 65535";
                   }
                 }
               }
             }
             leaf destination-udp-port {
               description "Value to write to the destination-udp-port field";
               type union {
                 type string {
                   pattern "<.*>|$.*";
                 }
                 type uint32 {
                   range "1 .. 65535";
                 }
               }
             }
             leaf vni {
               description "Value to write to the vni field";
               type union {
                 type string {
                   pattern "<.*>|$.*";
                 }
                 type uint32 {
                   range "0 .. 16777214";
                 }
               }
             }
           }
           container udp {
             presence "enable udp";
             description "Family for tunnel encapsulation udp";
             uses apply-advanced;
             container source {
               uses apply-advanced;
               leaf address {
                 description "Interface address prefix";
                 type jt:ipv4addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
             }
           }
           container ipip {
             presence "enable ipip";
             description "Family for tunnel encapsulation ipip";
             uses apply-advanced;
             container source {
               uses apply-advanced;
               leaf address {
                 description "Interface address prefix";
                 type jt:ipv4addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
             }
           }
         }
         leaf encap-type {
           description "Tunnel encapsulation type";
           type enumeration {
             enum "ipv4" {
               description "Tunnel IPv4 encapsulation";
             }
             enum "ipv6" {
               description "Tunnel IPv6 encapsulation";
             }
           }
         }
         choice source_type {
           case case_1 {
             leaf source {
               description "Tunnel source address";
               type jt:ipaddr;
             }
           }
           case case_2 {
             leaf source-hostname {
               description "Tunnel source hostname";
               type string;
             }
           }
           case case_3 {
             leaf source-interface {
               description "Tunnel source interface";
               type union {
                 type jt:interface-name;
                 type string {
                   pattern "<.*>|$.*";
                 }
               }
             }
           }
         }
         choice destination_type {
           case case_1 {
             leaf destination {
               description "Tunnel destination address";
               type jt:ipaddr;
             }
           }
           case case_2 {
             leaf destination-hostname {
               description "Tunnel destination hostname";
               type string;
             }
           }
         }
         leaf key {
           description "Tunnel key";
           type union {
             type string {
               pattern "<.*>|$.*";
             }
             type uint32 {
               range "0 .. 4294967295";
             }
           }
         }
         leaf backup-destination {
           description "Backup tunnel destination";
           type jt:ipaddr;
         }
         choice fragmentation {
           case case_1 {
             leaf allow-fragmentation {
               description "Do not set DF bit on packets";
               type empty;
             }
           }
           case case_2 {
             leaf do-not-fragment {
               description "Set DF bit on packets";
               type empty;
             }
           }
         }
         leaf ttl {
           description "Time to live";
           type union {
             type string {
               pattern "<.*>|$.*";
             }
             type uint32 {
               range "1 .. 255";
             }
           }
         }
         leaf traffic-class {
           description "TOS/Traffic class field of IP-header";
           type union {
             type string {
               pattern "<.*>|$.*";
             }
             type uint32 {
               range "0 .. 255";
             }
           }
         }
         leaf flow-label {
           description "Flow label field of IP6-header";
           type union {
             type string {
               pattern "<.*>|$.*";
             }
             type uint32 {
               range "0 .. 1048575";
             }
           }
         }
         choice path-mtu-discovery-choice {
           leaf path-mtu-discovery {
             description "Enable path MTU discovery for tunnels";
             type empty;
           }
           leaf no-path-mtu-discovery {
             description "Don't enable path MTU discovery for tunnels";
             type empty;
           }
         }
         container routing-instance {
           description "Routing instance to which tunnel ends belong";
           uses apply-advanced;
           leaf destination {
             description "Routing instance of tunnel destination";
             type string {
             }
           }
         }
       }
       leaf compression-device {
         description "Logical interface used for compression";
         type union {
           type jt:interface-unit;
           type string {
             pattern "<.*>|$.*";
           }
         }
       }
       container atm-policer {
         description "ATM policing for logical interface";
         uses apply-advanced;
         leaf input-atm-policer {
           description "Input atm policer";
           type string;
         }
       }
       container layer2-policer {
         description "Layer2 policing for logical interface";
         uses apply-advanced;
         choice layer2-input-policer-choice {
           case case_1 {
             leaf input-policer {
               description "Two-color policer for received packets";
               type string;
             }
           }
           case case_2 {
             leaf input-hierarchical-policer {
               description "Hierarchical policer for received packets";
               type string;
             }
           }
           case case_3 {
             leaf input-three-color {
               description "Color-blind three-color policer for received packets";
               type string;
             }
           }
         }
         choice layer2-output-policer-choice {
           case case_1 {
             leaf output-policer {
               description "Two-color policer for transmitted packets";
               type string;
             }
           }
           case case_2 {
             leaf output-three-color {
               description "Three-color policer for transmitted packets";
               type string;
             }
           }
         }
       }
       container filter {
         description "Filters to apply to all families configured under this logical interface";
         uses apply-advanced;
         choice chain_choice {
           case case_1 {
             leaf-list chain {
               ordered-by user;
               description "List of filter modules applied to TAG packets ";
               type string;
               max-elements 6;
             }
           }
         }
         choice input_choice {
           case case_1 {
             container input {
               description "Name of filter to be applied to received packets";
               leaf filter-name {
                 description "Name of the filter";
                 type string;
               }
               leaf shared-name {
                 description "Filter shared-name of instances of interface-shared filter";
                 type string;
               }
               leaf precedence {
                 description "Precedence of the filter";
                 type union {
                   type string {
                     pattern "<.*>|$.*";
                   }
                   type uint32 {
                     range "0 .. 255";
                   }
                 }
               }
             }
           }
         }
         choice output_choice {
           case case_1 {
             container output {
               description "Name of filter to be applied to transmitted packets";
               leaf filter-name {
                 description "Name of the filter";
                 type string;
               }
               leaf shared-name {
                 description "Filter shared-name of instances of interface-shared filter";
                 type string;
               }
               leaf precedence {
                 description "Precedence of the filter";
                 type union {
                   type string {
                     pattern "<.*>|$.*";
                   }
                   type uint32 {
                     range "0 .. 255";
                   }
                 }
               }
             }
           }
         }
       }
       list multi-chassis-protection {
         key name;
         description "Inter-Chassis protection configuration";
         uses multi-chassis-protection-group-ifl;
       }
       leaf statistics {
         description "Enable statistics collection in PFE";
         type empty;
       }
       container esi {
         presence "enable esi";
         description "ESI configuration of logical interface";
         uses apply-advanced;
         container auto-derive {
           description "Auto-derive ESI value for the interface";
           uses apply-advanced;
           choice esitype {
             case case_1 {
               leaf lacp-pe-system-id-and-admin-key {
                 description "Auto-derive ESI from lacp";
                 type empty;
               }
             }
           }
         }
         leaf identifier {
           description "ESI value for the interface";
           type jt:esi;
         }
         choice mode {
           case case_1 {
             leaf single-active {
               description "Single-active mode";
               type empty;
             }
           }
           case case_2 {
             leaf all-active {
               description "All-active mode";
               type empty;
             }
           }
         }
         container df-election-granularity {
           presence "enable df-election-granularity";
           description "DF Election Granularity Selection ";
           uses apply-advanced;
           choice mode {
             case case_1 {
               container per-esi {
                 presence "enable per-esi";
                 description "DF Election Granularity Per Esi";
                 uses apply-advanced;
                 leaf lacp-oos-on-ndf {
                   description "Lacp Oos";
                   type empty;
                 }
               }
             }
             case case_2 {
               leaf per-esi-vlan {
                 description "Per Esi Vlan";
                 type empty;
               }
             }
           }
         }
         container df-election-type {
           presence "enable df-election-type";
           description "DF Election Type";
           uses apply-advanced;
           choice pref_choice {
             case case_1 {
               container preference {
                 presence "enable preference";
                 description "Preference based DF election";
                 uses apply-advanced;
                 leaf value {
                   description "Preference value for EVPN Multihoming DF election";
                   default "32767";
                   type union {
                     type string {
                       pattern "<.*>|$.*";
                     }
                     type uint32 {
                       range "0 .. 65535";
                     }
                   }
                 }
               }
             }
           }
           choice mod_choice {
             case case_1 {
               container mod {
                 presence "enable mod";
                 description "MOD based DF election";
               }
             }
           }
         }
         leaf source-bmac {
           description "Unicast Source B-MAC address per ESI for PBB-EVPN";
           type jt:mac-unicast;
         }
       }
       choice virtual-gateway {
         case case_1 {
           leaf no-auto-virtual-gateway-esi {
             description "Disable auto ESI generation for virtual gateway address";
             type empty;
           }
         }
         case case_2 {
           container virtual-gateway-esi {
             description "ESI configuration of virtual gateway";
             uses apply-advanced;
             leaf identifier {
               description "ESI value for the interface";
               type jt:esi;
             }
             choice mode {
               case case_1 {
                 leaf single-active {
                   description "Single-active mode";
                   type empty;
                 }
               }
               case case_2 {
                 leaf all-active {
                   description "All-active mode";
                   type empty;
                 }
               }
             }
           }
         }
       }
       container service {
         description "Service operations";
         uses apply-advanced;
         list pcef {
           key name;
           ordered-by user;
           description "PCEF configuration";
           leaf name {
             description "PCEF Profile name";
             type string;
           }
           uses apply-advanced;
           leaf activate-all {
             description "Activate all rules and rulebases in the pcef profile";
             type empty;
           }
           list activate {
             key name;
             ordered-by user;
             description "Name of pcef profile rule or rulebase to activate";
             leaf name {
               description "Name of pcef profile rule or rulebase to activate";
               type string;
             }
             uses apply-advanced;
           }
         }
       }
       choice generate-eui64-choice {
         leaf generate-eui64 {
           description "To generate Link Local EUI-64 addresses";
           type empty;
         }
         leaf no-generate-eui64 {
           description "Don't to generate Link Local EUI-64 addresses";
           type empty;
         }
       }
       container family {
         description "Protocol family";
         container inet {
           presence "enable inet";
           description "IPv4 parameters";
           uses apply-advanced;
           container dhcp {
             description "Dynamic Host Configuration Protocol client configuration";
             presence "enable dhcp";
             uses dhcp-client-type;
           }
           container targeted-broadcast {
             presence "enable targeted-broadcast";
             description "Directed broadcast";
             uses apply-advanced;
             choice targeted-bcast-choice {
               case case_1 {
                 leaf forward-and-send-to-re {
                   description "Allow packets to be forwarded and sent to re";
                   type empty;
                 }
               }
               case case_2 {
                 leaf forward-only {
                   description "Allow packets only to be forwarded";
                   type empty;
                 }
               }
             }
           }
           leaf destination-class-usage {
             description "Enable destination class usage on this interface";
             status deprecated;
             type empty;
           }
           leaf transit-options-packets {
             description "Transit IP options packets (don't send to Routing Engine)";
             status deprecated;
             type empty;
           }
           leaf transit-ttl-exceeded {
             description "Transit IP TTL-exceeded packets (don't send to Routing Engine)";
             status deprecated;
             type empty;
           }
           leaf receive-options-packets {
             description "Receive IP options packets (don't send to Routing Engine)";
             type empty;
           }
           leaf receive-ttl-exceeded {
             description "Receive IP TTL-exceeded packets (don't send to Routing Engine)";
             type empty;
           }
           container accounting {
             description "Configure interface-based accounting options";
             uses apply-advanced;
             container source-class-usage {
               description "Enable source class usage on this interface";
               uses apply-advanced;
               leaf input {
                 description "Specify this interface for source-class-usage input";
                 type empty;
               }
               leaf output {
                 description "Specify this interface for source-class-usage output";
                 type empty;
               }
             }
             leaf destination-class-usage {
               description "Enable destination class usage on this interface";
               type empty;
             }
           }
           leaf mac-validate {
             description "Validate source MAC address";
             type enumeration {
               enum "strict" {
                 description "Strict mac-validation";
               }
               enum "loose" {
                 description "Loose mac-validation";
               }
             }
           }
           container rpf-check {
             presence "enable rpf-check";
             description "Enable reverse-path-forwarding checks on this interface";
             uses apply-advanced;
             leaf fail-filter {
               description "Name of filter applied to packets failing RPF check";
               type string;
             }
             container mode {
               description "Mode for reverse path forwarding";
               leaf loose {
                 description "Reverse-path-forwarding loose mode";
                 type empty;
               }
             }
           }
           leaf mtu {
             description "Protocol family maximum transmission unit";
             type union {
               type uint32;
               type string {
                 pattern "<.*>|$.*";
               }
             }
           }
           leaf arp-max-cache {
             description "Max interface ARP nexthop cache size";
             type union {
               type string {
                 pattern "<.*>|$.*";
               }
               type uint32 {
                 range "1 .. 2000000";
               }
             }
           }
           leaf arp-new-hold-limit {
             description "Max no. of new unresolved nexthops";
             type union {
               type string {
                 pattern "<.*>|$.*";
               }
               type uint32 {
                 range "1 .. 2000000";
               }
             }
           }
           leaf tcp-mss {
             description "Protocol family tcp maximum segment size";
             type union {
               type string {
                 pattern "<.*>|$.*";
               }
               type uint32 {
                 range "1 .. 65535";
               }
             }
           }
           leaf no-redirects {
             description "Do not redirect traffic";
             type empty;
           }
           leaf no-neighbor-learn {
             description "Disable neighbor address learning on interface";
             type empty;
           }
           leaf unconditional-src-learn {
             description "Glean from arp packets even when source cannot be validated";
             type empty;
           }
           leaf multicast-only {
             description "Allow only multicast traffic (tunnels only)";
             type empty;
           }
           leaf primary {
             description "Candidate for primary interface in system";
             type empty;
           }
           leaf ipsec-sa {
             description "Name of security association";
             type string {
               length "1 .. 32";
             }
           }
           leaf allow-filter-on-re {
             description "Enable kernel filter on network ports";
             type empty;
           }
           list demux-source {
             key name;
             ordered-by user;
             description "Demux based on source prefix";
             leaf name {
               type string;
             }
             uses apply-advanced;
           }
           list demux-destination {
             key name;
             ordered-by user;
             description "Demux based on destination prefix";
             leaf name {
               type string;
             }
             uses apply-advanced;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             leaf-list input-chain {
               ordered-by user;
               description "List of filter modules applied to received packets ";
               type string;
             }
             leaf-list output-chain {
               ordered-by user;
               description "List of filter modules applied to transmitted packets ";
               type string;
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32;
               }
             }
             leaf dialer {
               description "Name of filter applied on dialer";
               type string;
             }
           }
           container ingress-queuing-filter {
             description "Protocol family ingress-queuing-filter";
             leaf filter-name {
               description "Name of the ingress-queuing-filter";
               type string;
             }
           }
           container iq-policing-filter {
             description "Protocol family ingress-queuing-policing-filter";
             leaf filter-name {
               description "Name of the ingress-queuing-policing-filter";
               type string;
             }
           }
           container simple-filter {
             description "Filter for doing multifield classification";
             uses apply-advanced;
             leaf input {
               description "Name of simple filter applied to received packets";
               type string;
             }
           }
           leaf input-hierarchical-policer {
             description "Hierarchical policer for received packets";
             type string;
           }
           container policer {
             description "Interface policing";
             uses apply-advanced;
             leaf disable-arp-policer {
               description "Disable the arp policer for the interface";
               type empty;
             }
             leaf arp {
               description "Name of policer applied to received ARP packets";
               type string;
             }
             leaf input {
               description "Name of policer applied to received packets";
               type string;
             }
             leaf output {
               description "Name of policer applied to transmitted packets";
               type string;
             }
           }
           container sampling {
             description "Interface sampling";
             uses apply-advanced;
             leaf input {
               description "Sample all packets input on this interface";
               type empty;
             }
             leaf output {
               description "Sample all packets output on this interface";
               type empty;
             }
           }
           container service {
             description "Service operations";
             uses apply-advanced;
             container input {
               description "Service sets to consider for received packets";
               uses apply-advanced;
               list service-set {
                 key name;
                 ordered-by user;
                 description "Service set to consider for received packets";
                 leaf name {
                   description "Name of service set";
                   type string {
                   }
                 }
                 uses apply-advanced;
                 leaf service-filter {
                   description "Name of service filter";
                   type string;
                 }
               }
               leaf post-service-filter {
                 description "Post-service filter to apply to received packets";
                 type string;
               }
             }
             container output {
               description "Service sets to consider for transmitted packets";
               uses apply-advanced;
               list service-set {
                 key name;
                 ordered-by user;
                 description "Service set to consider for transmitted packets";
                 leaf name {
                   description "Name of service set";
                   type string {
                   }
                 }
                 uses apply-advanced;
                 leaf service-filter {
                   description "Name of service filter";
                   type string;
                 }
               }
             }
           }
           list next-hop-tunnel {
             key name;
             ordered-by user;
             description "One or more next-hop tunnel tables";
             leaf name {
               description "Next-hop tunnel gateway address";
               type string;
             }
             uses apply-advanced;
             leaf ipsec-vpn {
               description "Name of IPSec VPN";
               type string;
             }
           }
           choice tunnel-termination-status {
             case case_1 {
               leaf tunnel-termination {
                 description "Tunnel termination";
                 type empty;
               }
             }
             case case_2 {
               leaf no-tunnel-termination {
                 description "No Tunnel termination";
                 type empty;
               }
             }
           }
           leaf tunnel-loopback {
             description "Allows tunnel packet processing on IRB underlay using the loopback path";
             type empty;
           }
           list address {
             key name;
             ordered-by user;
             description "Interface address/destination prefix";
             leaf name {
               description "Interface address/destination prefix";
               type jt:ipv4prefix;
             }
             uses apply-advanced;
             leaf destination {
               description "Destination address";
               type jt:ipv4addr;
             }
             leaf destination-profile {
               description "Profile to use for destination address";
               type string;
             }
             leaf broadcast {
               description "Broadcast address";
               type jt:ipv4addr;
             }
             leaf primary {
               description "Candidate for primary address in system";
               type empty;
             }
             leaf preferred {
               description "Preferred address on interface";
               type empty;
             }
             leaf master-only {
               description "Master management IP address for router";
               type empty;
             }
             list multipoint-destination {
               key name;
               ordered-by user;
               description "Multipoint NBMA destination";
               leaf name {
                 description "Destination address";
                 type jt:ipv4addr;
               }
               uses apply-advanced;
               choice link-address {
                 case case_1 {
                   leaf dlci {
                     description "Frame Relay data-link control identifier";
                     type union {
                       type string {
                         pattern "<.*>|$.*";
                       }
                       type uint32 {
                         range "1 .. 1022";
                       }
                     }
                   }
                 }
                 case case_2 {
                   leaf vci {
                     description "ATM virtual circuit identifier ([vpi.]vci)";
                     type jt:atm-vci;
                   }
                 }
               }
               container shaping {
                 description "Virtual circuit traffic-shaping options";
                 uses dcd_shaping_config;
               }
               container oam-period {
                 description "OAM cell period";
                 choice oam_period_choices {
                   case case_1 {
                     leaf oam_period {
                       description "OAM cell period";
                       units "seconds";
                       type union {
                         type string {
                           pattern "<.*>|$.*";
                         }
                         type uint32 {
                           range "1 .. 900";
                         }
                       }
                     }
                   }
                   case case_2 {
                     container disable {
                       presence "enable disable";
                       description "Disable OAM loopback";
                     }
                   }
                 }
               }
               container oam-liveness {
                 description "OAM virtual circuit liveness parameters";
                 uses apply-advanced;
                 leaf up-count {
                   description "Number of OAM cells to consider VC up";
                   type union {
                     type string {
                       pattern "<.*>|$.*";
                     }
                     type uint32 {
                       range "1 .. 255";
                     }
                   }
                 }
                 leaf down-count {
                   description "Number of OAM cells to consider VC down";
                   type union {
                     type string {
                       pattern "<.*>|$.*";
                     }
                     type uint32 {
                       range "1 .. 255";
                     }
                   }
                 }
               }
               leaf inverse-arp {
                 description "Enable inverse ARP reply messages";
                 type empty;
               }
               leaf transmit-weight {
                 description "ATM2 transmit weight for VC under VP tunnel";
                 type union {
                   type string {
                     pattern "<.*>|$.*";
                   }
                   type uint16 {
                     range "1 .. 32767";
                   }
                 }
               }
               container epd-threshold {
                 description "Early packet discard threshold for ATM2";
                 uses epd_threshold_config;
               }
             }
             list arp {
               key name;
               ordered-by user;
               description "Static Address Resolution Protocol entries";
               leaf name {
                 description "Destination IP address";
                 type jt:ipv4addr;
               }
               leaf l2-interface {
                 description "Layer 2 interface name for ARP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to ARP requests for this entry";
                 type empty;
               }
               leaf flood-as-unknown-unicast {
                 description "Broadcast the packet with unicast MAC";
                 type empty;
               }
             }
             list host-discovery {
               key name;
               ordered-by user;
               description "Discover servers IP based on subnet range";
               max-elements 8;
               leaf name {
                 description "IP address subnet range";
                 type jt:ipv4prefix;
               }
               leaf aging-timer {
                 description "ARP aging timer";
                 type union {
                   type string {
                     pattern "<.*>|$.*";
                   }
                   type uint32 {
                     range "10 .. 1200";
                   }
                 }
               }
               leaf discovery-interval {
                 description "ARP proactive discovery time";
                 type union {
                   type string {
                     pattern "<.*>|$.*";
                   }
                   type uint32 {
                     range "3 .. 300";
                   }
                 }
               }
             }
             container web-authentication {
               description "Parameters for web-based firewall-user authentication";
               uses apply-advanced;
               leaf http {
                 description "Enable authentication via HTTP";
                 type empty;
               }
               leaf https {
                 description "Enable authentication via HTTPS";
                 type empty;
               }
               leaf redirect-to-https {
                 description "Web authentication redirect to HTTPS";
                 type empty;
               }
             }
             list vrrp-group {
               key name;
               ordered-by user;
               description "VRRP group";
               uses vrrp-group;
             }
             leaf virtual-gateway-address {
               description "Virtual Gateway IP address";
               type jt:ipv4addr;
             }
           }
           container unnumbered-address {
             description "Unnumbered interface address/destination prefix";
             leaf source {
               description "Interface from which to take local address";
               type union {
                 type jt:interface-unit;
                 type string {
                   pattern "<.*>|$.*";
                 }
               }
             }
             leaf preferred-source-address {
               description "Preferred address on the donor interface";
               type string;
             }
             leaf destination {
               description "Destination address";
               type jt:ipv4addr;
             }
             leaf destination-profile {
               description "Profile to use for destination address";
               type string;
             }
           }
           container location-pool-address {
             presence "enable location-pool-address";
             description "Location-based IP address pool";
             uses apply-advanced;
             leaf pool-name {
               description "Pool name";
               type string {
                 length "1 .. 64";
               }
             }
           }
           leaf negotiate-address {
             description "Negotiate address with remote";
             type empty;
           }
           leaf destination-udp-port {
             description "Choose destination UDP port number";
             type union {
               type string {
                 pattern "<.*>|$.*";
               }
               type uint32 {
                 range "10000 .. 10009";
               }
             }
           }
           container auto-configure {
             description "Auto configuration";
             uses dynamic_ipv4_type;
           }
           leaf clear-dont-fragment-bit {
             description "Clear DF bit in packet (AS PIC and J-series only as well as MIF)";
             type empty;
           }
         }
         container iso {
           presence "enable iso";
           description "OSI ISO protocol parameters";
           uses apply-advanced;
           list address {
             key name;
             ordered-by user;
             description "Interface address";
             leaf name {
               description "Interface address";
               type jt:isoaddr;
             }
             uses apply-advanced;
           }
           leaf mtu {
             description "Protocol family maximum transmission unit";
             type union {
               type uint32;
               type string {
                 pattern "<.*>|$.*";
               }
             }
           }
           leaf destination-udp-port {
             description "Choose destination UDP port number";
             type union {
               type string {
                 pattern "<.*>|$.*";
               }
               type uint32 {
                 range "10030 .. 10039";
               }
             }
           }
         }
         container inet6 {
           presence "enable inet6";
           description "IPv6 protocol parameters";
           uses apply-advanced;
           container dhcpv6-client {
             description "Dynamic Host Configuration Protocol DHCPv6 client configuration";
             uses apply-advanced;
             leaf client-type {
               description "DHCPv6 client type";
               type enumeration {
                 enum "stateful" {
                   description "Stateful client type for address assignment.";
                 }
                 enum "autoconfig" {
                   description "Autoconfig  client type for router-advertisement";
                 }
               }
             }
             list client-ia-type {
               key name;
               ordered-by user;
               description "DHCPv6 client identity association type";
               leaf name {
                 type enumeration {
                   enum "ia-na" {
                     description "Identity Association-Non-temporary Address";
                   }
                   enum "ia-pd" {
                     description "Identity Association-Prefix Address";
                   }
                 }
               }
               uses apply-advanced;
             }
             container rapid-commit {
               presence "enable rapid-commit";
               description "Option is used to signal the use of the two message exchange for address assignment";
             }
             leaf interface-identifier {
               description "Identifier for this interface";
               type jt:ipv6addr;
             }
             leaf use-ra-prefix {
               description "Assign interface IP from RA prefix when ia-na address not received";
               type empty;
             }
             container prefix-delegating {
               description "Prefix delegating parameters";
               uses apply-advanced;
               leaf preferred-prefix-length {
                 description "Client preferred prefix length";
                 type union {
                   type string {
                     pattern "<.*>|$.*";
                   }
                   type uint32 {
                     range "0 .. 64";
                   }
                 }
               }
               leaf sub-prefix-length {
                 description "The sub prefix length for LAN interfaces";
                 type union {
                   type string {
                     pattern "<.*>|$.*";
                   }
                   type uint32 {
                     range "1 .. 127";
                   }
                 }
               }
             }
             container client-identifier {
               description "DHCP Server identifies a client by client-identifier value ";
               leaf duid-type {
                 description "DUID identifying a client";
                 type enumeration {
                   enum "duid-llt" {
                     description "Link-layer address plus time";
                   }
                   enum "vendor" {
                     description "Vendor-assigned unique ID based on Enterprise Number";
                   }
                   enum "duid-ll" {
                     description "Link-layer address";
                   }
                 }
               }
             }
             leaf vendor-id {
               description "Vendor class id for the dhcpv6 client";
               type string {
                 length "1 .. 60";
               }
             }
             list req-option {
               key name;
               ordered-by user;
               description "DHCPV6 client requested option configuration";
               leaf name {
                 type enumeration {
                   enum "dns-server" {
                     description "Dns-server option";
                   }
                   enum "domain" {
                     description "Dns-server option";
                   }
                   enum "ntp-server" {
                     description "Ntp-server option";
                   }
                   enum "time-zone" {
                     description "Time-zone option";
                   }
                   enum "sip-server" {
                     description "Sip-server option";
                   }
                   enum "sip-domain" {
                     description "Sip-domain option";
                   }
                   enum "nis-server" {
                     description "Nis-server option";
                   }
                   enum "nis-domain" {
                     description "Nis-domain option";
                   }
                   enum "fqdn" {
                     description "Fully-qualified-domain option";
                   }
                   enum "vendor-spec" {
                     description "Vendor-spec option";
                   }
                   enum "zero-touch-redirect" {
                     description "Zero-touch-redirect";
                   }
                   enum "bootfile-url" {
                     description "Bootfile url";
                   }
                   enum "bootfile-param" {
                     description "Bootfile param";
                   }
                 }
               }
               uses apply-advanced;
             }
             container options {
               description "DHCP options";
               uses apply-advanced;
               list number {
                 key name;
                 description "DHCP option code";
                 leaf name {
                   description "DHCP option identifier code";
                   type union {
                     type string {
                       pattern "<.*>|$.*";
                     }
                     type uint32 {
                       range "1 .. 254";
                     }
                   }
                 }
                 choice option-type-choice {
                   case case_1 {
                     leaf hex-string {
                       description "Hexadecimal string";
                       type string {
                         length "1 .. 510";
                       }
                     }
                   }
                 }
               }
             }
             leaf retransmission-attempt {
               description "Number of attempts to retransmit the DHCPV6 client protocol packet";
               default "9";
               type union {
                 type string {
                   pattern "<.*>|$.*";
                 }
                 type uint32 {
                   range "0 .. 50000";
                 }
               }
             }
             container no-dns-install {
               presence "enable no-dns-install";
               description "Not propagate DNS to kernel";
             }
             container update-router-advertisement {
               description "Dhcpv6 client update rpd for prefix delegation";
               uses apply-advanced;
               list interface {
                 key name;
                 ordered-by user;
                 description "Interfaces on which to delegate prefix";
                 max-elements 3;
                 leaf name {
                   description "Interfaces-name on which to delegate prefix";
                   type union {
                     type jt:interface-name;
                     type string {
                       pattern "<.*>|$.*";
                     }
                   }
                 }
                 uses apply-advanced;
                 leaf interface-identifier {
                   description "Identifier for this interface";
                   type jt:ipv6addr;
                 }
                 leaf prefix-identifier {
                   description "Prefix identifier for prefix used in this interface";
                   type jt:ipv6addr;
                 }
                 choice managed-configuration-choice {
                   leaf managed-configuration {
                     description "Set managed address configuration";
                     type empty;
                   }
                   leaf no-managed-configuration {
                     description "Don't set managed address configuration";
                     type empty;
                   }
                 }
                 choice other-stateful-configuration-choice {
                   leaf other-stateful-configuration {
                     description "Set other stateful configuration";
                     type empty;
                   }
                   leaf no-other-stateful-configuration {
                     description "Don't set other stateful configuration";
                     type empty;
                   }
                 }
                 leaf max-advertisement-interval {
                   description "Maximum advertisement interval";
                   units "seconds";
                   type union {
                     type string {
                       pattern "<.*>|$.*";
                     }
                     type uint32 {
                       range "4 .. 1800";
                     }
                   }
                 }
                 leaf min-advertisement-interval {
                   description "Minimum advertisement interval";
                   units "seconds";
                   type union {
                     type string {
                       pattern "<.*>|$.*";
                     }
                     type uint32 {
                       range "3 .. 1350";
                     }
                   }
                 }
                 choice enable-recursive-dns-server-option-choice {
                   leaf enable-recursive-dns-server-option {
                     description "Enables the recursive DNS server option";
                     type empty;
                   }
                   leaf no-enable-recursive-dns-server-option {
                     description "Don't enables the recursive DNS server option";
                     type empty;
                   }
                 }
               }
             }
             leaf update-server {
               description "Propagate TCP/IP settings to DHCP server";
               type empty;
             }
           }
           container rpf-check {
             presence "enable rpf-check";
             description "Enable reverse-path-forwarding checks on this interface";
             uses apply-advanced;
             leaf fail-filter {
               description "Name of filter applied to packets failing RPF check";
               type string;
             }
             container mode {
               description "Mode for reverse path forwarding";
               leaf loose {
                 description "Reverse-path-forwarding loose mode";
                 type empty;
               }
             }
           }
           container accounting {
             description "Interface-based accounting options";
             uses apply-advanced;
             container source-class-usage {
               uses apply-advanced;
               leaf input {
                 description "Interface for source-class-usage input";
                 type empty;
               }
               leaf output {
                 description "Interface for source-class-usage output";
                 type empty;
               }
             }
             leaf destination-class-usage {
               description "Enable destination class usage on this interface";
               type empty;
             }
           }
           leaf mtu {
             description "Protocol family maximum transmission unit";
             type union {
               type uint32;
               type string {
                 pattern "<.*>|$.*";
               }
             }
           }
           leaf tcp-mss {
             description "Protocol family tcp maximum segment size";
             type union {
               type string {
                 pattern "<.*>|$.*";
               }
               type uint32 {
                 range "1 .. 65535";
               }
             }
           }
           leaf nd6-stale-time {
             description "Stale time to reconfirm reachability with inet6 neighbour";
             units "seconds";
             type union {
               type string {
                 pattern "<.*>|$.*";
               }
               type uint32 {
                 range "1 .. 18000";
               }
             }
           }
           leaf no-neighbor-learn {
             description "Disable neighbor address learning on interface";
             type empty;
           }
           leaf slaac-enable {
             description "Enable slaac on management interface";
             type empty;
           }
           container ndp-proxy {
             description "Enable ndp proxy on interface";
             uses apply-advanced;
             leaf interface-restricted {
               description "Enable ndp interface proxy restricted to interface";
               type empty;
             }
             leaf interface-unrestricted {
               description "Enable ndp interface proxy unrestricted to interface";
               type empty;
             }
           }
           container dad-proxy {
             description "DAD proxy on interface";
             uses apply-advanced;
             leaf interface-restricted {
               description "Enable DAD interface proxy restricted to interface";
               type empty;
             }
             leaf interface-unrestricted {
               description "Enable DAD interface proxy unrestricted to interface";
               type empty;
             }
           }
           leaf nd6-max-cache {
             description "Max interface ND nexthop cache size";
             type union {
               type string {
                 pattern "<.*>|$.*";
               }
               type uint32 {
                 range "1 .. 2000000";
               }
             }
           }
           leaf nd6-new-hold-limit {
             description "Max no. of new unresolved nexthops";
             type union {
               type string {
                 pattern "<.*>|$.*";
               }
               type uint32 {
                 range "1 .. 2000000";
               }
             }
           }
           leaf no-redirects {
             description "Do not redirect traffic";
             type empty;
           }
           leaf allow-filter-on-re {
             description "Enable kernel filter on network ports";
             type empty;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             leaf-list input-chain {
               ordered-by user;
               description "List of filter modules applied to received packets ";
               type string;
             }
             leaf-list output-chain {
               ordered-by user;
               description "List of filter modules applied to transmitted packets ";
               type string;
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32;
               }
             }
             leaf dialer {
               description "Name of filter applied on dialer";
               type string;
             }
           }
           container ingress-queuing-filter {
             description "Protocol family ingress-queuing-filter";
             leaf filter-name {
               description "Name of the ingress-queuing-filter";
               type string;
             }
           }
           leaf input-hierarchical-policer {
             description "Hierarchical policer for received packets";
             type string;
           }
           container policer {
             description "Interface policing";
             uses apply-advanced;
             leaf input {
               description "Name of policer applied to received packets";
               type string;
             }
             leaf output {
               description "Name of policer applied to transmitted packets";
               type string;
             }
           }
           container sampling {
             description "Interface sampling";
             uses apply-advanced;
             leaf input {
               description "Sample all packets input on this interface";
               type empty;
             }
             leaf output {
               description "Sample all packets output on this interface";
               type empty;
             }
           }
           container service {
             description "Service operations";
             uses apply-advanced;
             container input {
               description "Service sets to consider for received packets";
               uses apply-advanced;
               list service-set {
                 key name;
                 ordered-by user;
                 description "Service set to consider for received packets";
                 leaf name {
                   description "Name of service set";
                   type string {
                   }
                 }
                 uses apply-advanced;
                 leaf service-filter {
                   description "Name of service filter";
                   type string;
                 }
               }
               leaf post-service-filter {
                 description "Post-service filter to apply to received packets";
                 type string;
               }
             }
             container output {
               description "Service sets to consider for transmitted packets";
               uses apply-advanced;
               list service-set {
                 key name;
                 ordered-by user;
                 description "Service set to consider for transmitted packets";
                 leaf name {
                   description "Name of service set";
                   type string {
                   }
                 }
                 uses apply-advanced;
                 leaf service-filter {
                   description "Name of service filter";
                   type string;
                 }
               }
             }
           }
           choice tunnel-termination-status {
             case case_1 {
               leaf tunnel-termination {
                 description "Tunnel termination";
                 type empty;
               }
             }
             case case_2 {
               leaf no-tunnel-termination {
                 description "No Tunnel termination";
                 type empty;
               }
             }
           }
           list address {
             key name;
             ordered-by user;
             description "Interface address or destination prefix";
             leaf name {
               description "Interface address or destination prefix";
               type jt:ipv6prefix;
             }
             uses apply-advanced;
             leaf destination {
               description "Destination address";
               type jt:ipv6addr;
             }
             leaf eui-64 {
               description "Generate EUI-64 interface ID";
               type empty;
             }
             leaf primary {
               description "Candidate for primary address in system";
               type empty;
             }
             leaf preferred {
               description "Preferred address on interface";
               type empty;
             }
             leaf master-only {
               description "Master management IP address for router";
               type empty;
             }
             list ndp {
               key name;
               ordered-by user;
               description "Static Neighbor Discovery Protocol  entries";
               leaf name {
                 description "Destination IP address";
                 type jt:ipv6addr;
               }
               leaf l2-interface {
                 description "Layer 2 interface name for NDP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to NDP requests for this entry";
                 type empty;
               }
             }
             list vrrp-inet6-group {
               key name;
               ordered-by user;
               description "VRRP group";
               uses vrrp-group;
             }
             container web-authentication {
               description "Parameters for web-based firewall-user authentication";
               uses apply-advanced;
               leaf http {
                 description "Enable authentication via HTTP";
                 type empty;
               }
               leaf https {
                 description "Enable authentication via HTTPS";
                 type empty;
               }
               leaf redirect-to-https {
                 description "Web authentication redirect to HTTPS";
                 type empty;
               }
             }
             leaf virtual-gateway-address {
               description "Virtual Gateway IP address";
               type jt:ipv6addr;
             }
             leaf subnet-router-anycast {
               description "Create a subnet roter anycast address for this address.";
               type empty;
             }
           }
           list demux-source {
             key name;
             ordered-by user;
             description "Demux based on source prefix";
             leaf name {
               type string;
             }
             uses apply-advanced;
           }
           list demux-destination {
             key name;
             ordered-by user;
             description "Demux based on destination prefix";
             leaf name {
               type string;
             }
             uses apply-advanced;
           }
           container unnumbered-address {
             description "Unnumbered interface address/destination prefix";
             leaf source {
               description "Interface from which to take local address";
               type union {
                 type jt:interface-unit;
                 type string {
                   pattern "<.*>|$.*";
                 }
               }
             }
             leaf preferred-source-address {
               description "Preferred address on the donor interface";
               type string;
             }
           }
           choice dad-disable-choice {
             leaf dad-disable {
               description "Disable duplicate-address-detection";
               type empty;
             }
             leaf no-dad-disable {
               description "Don't disable duplicate-address-detection";
               type empty;
             }
           }
           leaf destination-udp-port {
             description "Choose destination UDP port number";
             type union {
               type string {
                 pattern "<.*>|$.*";
               }
               type uint32 {
                 range "10010 .. 10019";
               }
             }
           }
           container auto-configure {
             description "Auto configuration";
             uses dynamic_ipv6_type;
           }
           leaf negotiate-address {
             description "Negotiate address with remote";
             type empty;
           }
         }
         container mpls {
           presence "enable mpls";
           description "MPLS protocol parameters";
           uses apply-advanced;
           leaf mtu {
             description "Protocol family maximum transmission unit";
             type union {
               type uint32;
               type string {
                 pattern "<.*>|$.*";
               }
             }
           }
           leaf maximum-labels {
             description "Protocol family maximum number of labels";
             type union {
               type string {
                 pattern "<.*>|$.*";
               }
               type uint32;
             }
           }
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
             leaf dialer {
               description "Name of filter applied on dialer";
               type string;
             }
           }
           container ingress-queuing-filter {
             description "Protocol family ingress-queuing-filter";
             leaf filter-name {
               description "Name of the ingress-queuing-filter";
               type string;
             }
           }
           leaf input-hierarchical-policer {
             description "Hierarchical policer for received packets";
             type string;
           }
           container policer {
             description "Interface policing";
             uses apply-advanced;
             leaf input {
               description "Name of policer applied to received packets";
               type string;
             }
             leaf output {
               description "Name of policer applied to transmitted packets";
               type string;
             }
           }
           leaf destination-udp-port {
             description "Choose destination UDP port number";
             type union {
               type string {
                 pattern "<.*>|$.*";
               }
               type uint32 {
                 range "10020 .. 10029";
               }
             }
           }
         }
         container mlppp {
           description "Multilink PPP protocol parameters";
           uses apply-advanced;
           leaf bundle {
             description "Logical interface name this link will join";
             type string;
           }
           choice anchor-points {
             case case_1 {
               leaf service-interface {
                 description "Services interface to use";
                 type union {
                   type jt:interface-device;
                   type string {
                     pattern "<.*>|$.*";
                   }
                 }
               }
             }
             case case_2 {
               leaf service-device-pool {
                 description "Service interface pool name to use";
                 type string {
                   length "1 .. 63";
                 }
               }
             }
           }
           leaf dynamic-profile {
             description " dynamic profile for interface to use";
             type string {
               length "1 .. 80";
             }
           }
         }
         container mlfr-end-to-end {
           presence "enable mlfr-end-to-end";
           description "Multilink Frame Relay end-to-end protocol parameters";
           uses apply-advanced;
           leaf bundle {
             description "Logical interface name this link will join";
             type union {
               type jt:interface-unit;
               type string {
                 pattern "<.*>|$.*";
               }
             }
           }
         }
         container mlfr-uni-nni {
           presence "enable mlfr-uni-nni";
           description "Multilink Frame Relay UNI NNI protocol parameters";
           uses apply-advanced;
           leaf bundle {
             description "Logical interface name this link will join";
             type union {
               type jt:interface-unit;
               type string {
                 pattern "<.*>|$.*";
               }
             }
           }
         }
         container ccc {
           presence "enable ccc";
           description "Circuit cross-connect parameters";
           uses apply-advanced;
           leaf mtu {
             description "Protocol family maximum transmission unit";
             type union {
               type uint32;
               type string {
                 pattern "<.*>|$.*";
               }
             }
           }
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
           }
           container ingress-queuing-filter {
             description "Protocol family ingress-queuing-filter";
             leaf filter-name {
               description "Name of the ingress-queuing-filter";
               type string;
             }
           }
           container policer {
             description "Interface policing";
             uses apply-advanced;
             leaf input {
               description "Name of policer applied to received packets";
               type string;
             }
             leaf output {
               description "Name of policer applied to transmitted packets";
               type string;
             }
           }
           leaf translate-fecn-and-becn {
             description "Translate FECN and BECN bits";
             type empty;
           }
           choice de-or-plp {
             case case_1 {
               leaf translate-discard-eligible {
                 description "Translate DE bit";
                 type empty;
               }
             }
             case case_2 {
               leaf translate-plp-control-word-de {
                 description "Translate PLP to/from Martini Control DE bit";
                 type empty;
               }
             }
           }
           leaf keep-address-and-control {
             description "Don't strip PPP address and control bytes";
             type empty;
           }
         }
         container tcc {
           presence "enable tcc";
           description "Translational cross-connect parameters";
           uses apply-advanced;
           container policer {
             description "Interface policing";
             uses apply-advanced;
             leaf input {
               description "Name of policer applied to received packets";
               type string;
             }
             leaf output {
               description "Name of policer applied to transmitted packets";
               type string;
             }
           }
           container proxy {
             presence "enable proxy";
             uses apply-advanced;
             leaf inet-address {
               description "Remote host address on non-Ethernet side of Ethernet TCC";
               type jt:ipv4addr;
             }
           }
           container remote {
             presence "enable remote";
             uses apply-advanced;
             leaf inet-address {
               description "Remote host address on Ethernet side of Ethernet TCC";
               type jt:ipv4addr;
             }
             leaf mac-address {
               description "Remote host MAC address on Ethernet side of Ethernet TCC";
               type jt:mac-addr;
             }
           }
           leaf-list protocols {
             ordered-by user;
             description "Protocols supported on TCC interface";
             type enumeration {
               enum "mpls" {
                 description "Multiprotocol Label Switching";
               }
               enum "inet" {
                 description "IP version 4";
               }
               enum "iso" {
                 description "International Organization for Standardization";
               }
               enum "inet6" {
                 description "IP version 6";
               }
             }
           }
         }
         container vpls {
           presence "enable vpls";
           description "Virtual private LAN service parameters";
           uses apply-advanced;
           leaf core-facing {
             description "Interface is core facing";
             type empty;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             leaf-list input-chain {
               ordered-by user;
               description "List of filter modules applied to received packets ";
               type string;
             }
             leaf-list output-chain {
               ordered-by user;
               description "List of filter modules applied to transmitted packets ";
               type string;
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container ingress-queuing-filter {
             description "Protocol family ingress-queuing-filter";
             leaf filter-name {
               description "Name of the ingress-queuing-filter";
               type string;
             }
           }
           container iq-policing-filter {
             description "Protocol family ingress-queuing-policing-filter";
             leaf filter-name {
               description "Name of the ingress-queuing-policing-filter";
               type string;
             }
           }
           container policer {
             description "Interface policing";
             uses apply-advanced;
             leaf input {
               description "Name of policer applied to received packets";
               type string;
             }
             leaf output {
               description "Name of policer applied to transmitted packets";
               type string;
             }
           }
           container sampling {
             description "Interface sampling";
             uses apply-advanced;
             leaf input {
               description "Sample all packets input on this interface";
               type empty;
             }
             leaf output {
               description "Sample all packets output on this interface";
               type empty;
             }
           }
         }
         container bridge {
           presence "enable bridge";
           description "Layer-2 bridging parameters";
           uses apply-advanced;
           leaf core-facing {
             description "Interface is core facing";
             type empty;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             leaf-list input-chain {
               ordered-by user;
               description "List of filter modules applied to received packets ";
               type string;
             }
             leaf-list output-chain {
               ordered-by user;
               description "List of filter modules applied to transmitted packets ";
               type string;
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container ingress-queuing-filter {
             description "Protocol family ingress-queuing-filter";
             leaf filter-name {
               description "Name of the ingress-queuing-filter";
               type string;
             }
           }
           container iq-policing-filter {
             description "Protocol family ingress-queuing-policing-filter";
             leaf filter-name {
               description "Name of the ingress-queuing-policing-filter";
               type string;
             }
           }
           container policer {
             description "Interface policing";
             uses apply-advanced;
             leaf input {
               description "Name of policer applied to received packets";
               type string;
             }
             leaf output {
               description "Name of policer applied to transmitted packets";
               type string;
             }
           }
           leaf interface-mode {
             description "Interface mode (access or trunk)";
             type enumeration {
               enum "access" {
                 description "Interface mode is access";
               }
               enum "trunk" {
                 description "Interface mode is trunk";
               }
             }
           }
           leaf vlan-auto-sense {
             description "Enable VLAN auto sense on this interface";
             type empty;
           }
           leaf bridge-domain-type {
             description "Bridge domain type (svlan or bvlan)";
             type enumeration {
               enum "svlan" {
                 description "Bridge domain type svlan";
               }
               enum "bvlan" {
                 description "Bridge domain type bvlan";
               }
             }
           }
           leaf inter-switch-link {
             description "PVLAN inter switch link";
             type empty;
           }
           choice vlan_list {
             case case_1 {
               leaf vlan-id {
                 description "Access mode and trunk mode VLAN membership";
                 type union {
                   type string {
                     pattern "<.*>|$.*";
                   }
                   type uint32 {
                     range "1 .. 4094";
                   }
                 }
               }
             }
             case case_2 {
               leaf-list vlan-id-list {
                 description "Trunk mode VLAN membership for this interface";
                 type jt:vlan-range;
               }
             }
             case case_3 {
               leaf-list inner-vlan-id-list {
                 description "Trunk mode VLAN membership for this interface based on inner VLAN tag";
                 type jt:vlan-range;
               }
             }
           }
           container vlan-rewrite {
             description "Specify vlan translation";
             uses apply-advanced;
             list translate {
               key name;
               ordered-by user;
               description "Translate incoming VLAN tag";
               leaf name {
                 description "Specify the incoming VLAN tag";
                 type union {
                   type string {
                     pattern "<.*>|$.*";
                   }
                   type uint32 {
                     range "1 .. 4094";
                   }
                 }
               }
               leaf to-vlan-id {
                 description "Specify the bridge-domain VLAN-ID";
                 type union {
                   type string {
                     pattern "<.*>|$.*";
                   }
                   type uint32 {
                     range "1 .. 4094";
                   }
                 }
               }
             }
           }
           choice isid_list {
             case case_1 {
               leaf isid-list {
                 description "Specify the ISID list";
                 type enumeration {
                   enum "all-service-groups" {
                     description "Map all ISIDs specified under the service-groups";
                   }
                   enum "all" {
                     description "Map all ISIDs";
                   }
                 }
               }
             }
           }
           container storm-control {
             description "Storm control profile name to bind";
             uses apply-advanced;
             leaf profile-name {
               description "Profile name";
               type string;
             }
           }
           container recovery-timeout {
             description "Recovery timeout for this interface";
             leaf time-in-seconds {
               units "seconds";
               type union {
                 type string {
                   pattern "<.*>|$.*";
                 }
                 type uint32 {
                   range "10 .. 3600";
                 }
               }
             }
           }
           container sampling {
             description "Interface sampling";
             uses apply-advanced;
             leaf input {
               description "Sample all packets input on this interface";
               type empty;
             }
             leaf output {
               description "Sample all packets output on this interface";
               type empty;
             }
           }
         }
         container ethernet-switching {
           description "Ethernet switching parameters";
           presence "enable ethernet-switching";
           uses ethernet-switching-type;
         }
         container fibre-channel {
           description "Fibre channel switching parameters";
           presence "enable fibre-channel";
           uses fibre-channel-type;
         }
         container pppoe {
           description "PPP over Ethernet underlying interface-specific options";
           presence "enable pppoe";
           uses pppoe_underlying_options_type;
         }
         container any {
           presence "enable any";
           description "Parameters for 'any' family";
           uses apply-advanced;
           container filter {
             description "Layer 2 packet filtering";
             uses apply-advanced;
             leaf input {
               description "Name of filter applied to received packets";
               type string {
               }
             }
             leaf group {
               description "Group to which interface belongs";
               type union {
                 type string {
                   pattern "<.*>|$.*";
                 }
                 type uint32 {
                   range "1 .. 255";
                 }
               }
             }
           }
         }
         uses apply-advanced;
       }
       leaf service-domain {
         description "Service domain to which interface belongs";
         type enumeration {
           enum "inside" {
             description "Inside network";
           }
           enum "outside" {
             description "Outside network";
           }
         }
       }
       leaf copy-tos-to-outer-ip-header {
         description "Copy IP payload header's ToS field to GRE delivery header";
         type empty;
       }
       leaf copy-tos-to-outer-ip-header-transit {
         description "Copy IP ToS field to GRE header for transit packets";
         type empty;
       }
       leaf force-control-packets-on-transit-path {
         description "Force control packets to follow transit path";
         type empty;
       }
       container load-balancing-options {
         description "AMS subunit load balancing options";
         uses apply-advanced;
         leaf preferred-active {
           description "Preferred active Interface name";
           type union {
             type jt:interface-device;
             type string {
               pattern "<.*>|$.*";
             }
           }
         }
         leaf disable-hash {
           description "Hash based distribution is not needed for this subunit";
           type empty;
         }
         leaf modulo-key {
           description "Modulo based distribution";
           type enumeration {
             enum "source-ip" {
               description "Source Ip Address";
             }
             enum "destination-ip" {
               description "Destination Ip Address";
             }
           }
         }
         container hash-keys {
           uses apply-advanced;
           leaf-list ingress-key {
             ordered-by user;
             description "Hash Key for the ingress direction";
             type enumeration {
               enum "source-ip" {
                 description "Source Ip Address";
               }
               enum "destination-ip" {
                 description "Destination Ip Address";
               }
               enum "protocol" {
                 description "Protocol";
               }
               enum "iif" {
                 description "Incoming Interface";
               }
             }
           }
           leaf-list egress-key {
             ordered-by user;
             description "Hash Key for the egress direction";
             status deprecated;
             type enumeration {
               enum "source-ip" {
                 description "Source Ip Address";
                 status deprecated;
               }
               enum "destination-ip" {
                 description "Destination Ip Address";
                 status deprecated;
               }
               enum "protocol" {
                 description "Protocol";
                 status deprecated;
               }
               enum "oif" {
                 description "Outgoing Interface";
                 status deprecated;
               }
             }
           }
           leaf ipv6-source-prefix-length {
             description "IPv6 source prefix length for hash computation";
             type enumeration {
               enum "56" {
                 description "56 bit IPv6 address prefix";
               }
               enum "64" {
                 description "64 bit IPv6 address prefix";
               }
               enum "96" {
                 description "96 bit IPv6 address prefix";
               }
               enum "128" {
                 description "Complete 128 bit IPv6 address";
               }
             }
           }
         }
       }
       container interface-state {
         description "IRB interface state computation";
         uses apply-advanced;
         choice state {
           case case_1 {
             leaf local {
               description "IRB State computation based on local interface state";
               type empty;
             }
           }
           case case_2 {
             leaf remote {
               description "IRB State computation based on remote reachability";
               type empty;
             }
           }
           case case_3 {
             leaf local-remote {
               description "IRB State computation based on local or remote reachability";
               type empty;
             }
           }
           case case_4 {
             leaf local-interface {
               description "IRB State computation based on loopback AE port state";
               type union {
                 type jt:interface-name;
                 type string {
                   pattern "<.*>|$.*";
                 }
               }
             }
           }
         }
         leaf local-count {
           description "Minimum number of local layer2 link in up state to consider IRB up";
           type union {
             type uint16;
             type string {
               pattern "<.*>|$.*";
             }
           }
         }
         leaf vtep-count {
           description "Minimum number of VTEP link in up state to consider IRB up";
           type union {
             type uint16;
             type string {
               pattern "<.*>|$.*";
             }
           }
         }
         container hold-time {
           description "Delay before marking interface up or down for defect";
           uses apply-advanced;
           leaf up {
             description "Delay in seconds before marking IRB interface up";
             units "seconds";
             type union {
               type uint32;
               type string {
                 pattern "<.*>|$.*";
               }
             }
           }
           leaf down {
             description "Delay in seconds before marking IRB interface down";
             units "seconds";
             type union {
               type uint32;
               type string {
                 pattern "<.*>|$.*";
               }
             }
           }
         }
       }
       leaf mac {
         description "Configure logical interface MAC address";
         type jt:mac-unicast;
       }
       leaf virtual-gateway-v4-mac {
         description "Configure virtual gateway IPV4 virtual MAC address";
         type jt:mac-unicast;
       }
       leaf virtual-gateway-v6-mac {
         description "Configure virtual gateway IPV6 virtual MAC address";
         type jt:mac-unicast;
       }
       leaf no-dhcp-flood {
         description "Disable dhcp flooding";
         type empty;
       }
       container forwarding-options {
         description "Aggregated Ethernet interface forwarding-options";
         uses apply-advanced;
         container load-balance-stateful {
           description "Stateful load balancing";
           uses apply-advanced;
           leaf per-flow {
             description "Enable feature";
             type empty;
           }
           leaf rebalance {
             description "Rebalancing interval";
             units "per minute";
             type union {
               type string {
                 pattern "<.*>|$.*";
               }
               type uint32 {
                 range "1 .. 1000";
               }
             }
           }
           leaf load-type {
             description "Load - defines the flows";
             type enumeration {
               enum "high" {
                 description "If the no of flows on this aggregate is large(1000-10000 flows) ";
               }
               enum "medium" {
                 description "If the no of flows on this aggregate is moderate(100-1000 flows)";
               }
               enum "low" {
                 description "If the no of flows on this aggregate is less(1-100)";
               }
             }
           }
         }
       }
       leaf etree-ac-role {
         description "ETREE attachment circuit role";
         type enumeration {
           enum "root" {
             description "ETREE root interface";
           }
           enum "leaf" {
             description "ETREE leaf interface";
           }
         }
       }
       container load-balance {
         description "Load-balance weight per subscriber interface";
         uses apply-advanced;
         leaf weight {
           description "Load-balance weight";
           type union {
             type string {
               pattern "<.*>|$.*";
             }
             type uint32 {
               range "1 .. 1000";
             }
           }
         }
       }
       container explicit-proxy {
         presence "enable explicit-proxy";
         description "Attach explicit proxy profiles";
         uses apply-advanced;
         leaf-list profile {
           description "Explicit proxy profile name";
           type string {
             length "1 .. 63";
           }
         }
       }
       container dialer-options {
         presence "enable dialer-options";
         description "Dialer options";
         uses apply-advanced;
         leaf pool {
           description "Dialer pool";
           type string {
             length "1 .. 64";
           }
         }
         leaf-list route {
           ordered-by user;
           description "Route on dialer";
           type jt:ipprefix;
         }
         leaf always-on {
           description "Always keep on-line";
           type empty;
         }
         leaf-list dial-string {
           ordered-by user;
           description "String to dial out";
           type string {
             length "1 .. 63";
           }
           max-elements 15;
         }
         container incoming-map {
           description "Map incoming call to dialer";
           uses apply-advanced;
           choice caller-type {
             case case_1 {
               list caller {
                 key name;
                 ordered-by user;
                 description "Caller Id to be screened";
                 max-elements 300;
                 leaf name {
                   description "Caller ID (upto 15 digits)";
                   type string {
                   }
                 }
               }
             }
             case case_2 {
               leaf accept-all {
                 description "Accept all incoming calls";
                 type empty;
               }
             }
           }
         }
         leaf callback {
           description "Call back on any incoming call to the dialer";
           type empty;
         }
         leaf callback-wait-period {
           description "Time to wait before calling back";
           units "seconds";
           type union {
             type string {
               pattern "<.*>|$.*";
             }
             type uint32 {
               range "2 .. 255";
             }
           }
         }
         leaf redial-delay {
           description "Time to wait before redialing";
           units "seconds";
           type union {
             type string {
               pattern "<.*>|$.*";
             }
             type uint32 {
               range "2 .. 255";
             }
           }
         }
         leaf self-recover-time {
           description "Sub-interface self-recover time";
           units "seconds";
           type union {
             type string {
               pattern "<.*>|$.*";
             }
             type uint32 {
               range "2 .. 120";
             }
           }
         }
         leaf idle-timeout {
           description "Delay before taking down the interface";
           default "120";
           units "seconds";
           type union {
             type string {
               pattern "<.*>|$.*";
             }
             type uint32 {
               range "0 .. 4294967295";
             }
           }
         }
         list watch-list {
           key name;
           description "Dialer watch list";
           leaf name {
             description "Address prefix";
             type jt:ipprefix-only;
           }
           uses apply-advanced;
         }
         leaf load-threshold {
           description "Load threshold for adding interfaces";
           type union {
             type string {
               pattern "<.*>|$.*";
             }
             type uint32 {
               range "0 .. 100";
             }
           }
         }
         leaf load-interval {
           description "Interval used to calculate average load";
           units "seconds";
           type union {
             type string {
               pattern "<.*>|$.*";
             }
             type uint32 {
               range "20 .. 180";
             }
           }
         }
         leaf activation-delay {
           description "Activation delay";
           units "seconds";
           type union {
             type string {
               pattern "<.*>|$.*";
             }
             type uint32 {
               range "1 .. 4294967295";
             }
           }
         }
         leaf deactivation-delay {
           description "Deactivation delay";
           units "seconds";
           type union {
             type string {
               pattern "<.*>|$.*";
             }
             type uint32 {
               range "1 .. 4294967295";
             }
           }
         }
         leaf initial-route-check {
           description "Delay to check primary after the router is up";
           default "120";
           units "seconds";
           type union {
             type string {
               pattern "<.*>|$.*";
             }
             type uint16 {
               range "1 .. 300";
             }
           }
         }
       }
       container backup-options {
         description "Backup interface configuration options";
         uses apply-advanced;
         leaf interface {
           description "Backup interface";
           type union {
             type jt:interface-name;
             type string {
               pattern "<.*>|$.*";
             }
           }
         }
       }
     }
     container no-partition {
       description "Use channelizable interface as clear channel";
       leaf interface-type {
         description "Interface type";
         type enumeration {
           enum "e1" {
             description "E1 interface";
           }
           enum "t1" {
             description "T1 interface";
           }
           enum "at" {
             description "ATM interface";
           }
           enum "t3" {
             description "T3 interface";
           }
           enum "e3" {
             description "E3 interface";
           }
           enum "ct3" {
             description "Channelized T3 interface";
           }
           enum "so" {
             description "SONET interface";
           }
           enum "cau4" {
             description "CAU4 interface";
           }
         }
       }
     }
     list partition {
       key name;
       ordered-by user;
       description "Channelized interface partition";
       leaf name {
         description "Sublevel interface partition index (for example, 1, 3-4)";
         type string;
       }
       leaf oc-slice {
         description "Range of SONET/SDH slices (for example, 1, 7-9)";
         type string;
       }
       leaf timeslots {
         description "Timeslots [(1..24) for T1, (1..31) for E1]; for example, 1-3,4,9,22-24 (no spaces)";
         type string;
       }
       leaf interface-type {
         description "Sublevel interface type";
         type enumeration {
           enum "ds" {
             description "DS0 interface";
           }
           enum "e1" {
             description "E1 interface";
           }
           enum "t1" {
             description "T1 interface";
           }
           enum "at" {
             description "ATM interface";
           }
           enum "ct1" {
             description "Channelized T1 interface";
           }
           enum "ce1" {
             description "Channelized E1 interface";
           }
           enum "t3" {
             description "T3 interface";
           }
           enum "ct3" {
             description "Channelized T3 interface";
           }
           enum "e3" {
             description "E3 interface";
           }
           enum "so" {
             description "SONET interface";
           }
           enum "coc1" {
             description "Channelized OC1 interface";
           }
           enum "cau4" {
             description "Channelized AU4 interface";
           }
           enum "dc" {
             description "D channel interface";
           }
           enum "bc" {
             description "B channel interface";
           }
         }
       }
     }
     container radius-options {
       description "Interface RADIUS Options";
       uses radius_options_vlan_type;
     }
     leaf rpf-stats {
       description "Enable Reverse path forwarding stats for this interface";
       type empty;
     }
     container redundant-pseudo-interface-options {
       description "Pseudo interface redundancy options";
       uses apply-advanced;
       leaf redundancy-group {
         description "Redundancy group of this interface";
         type union {
           type string {
             pattern "<.*>|$.*";
           }
           type uint16 {
             range "0 .. 255";
           }
         }
       }
     }
     container modem-options {
       description "MODEM interface-specific options";
       uses apply-advanced;
       leaf init-command-string {
         description "AT command string to initialize modem";
         type string {
           length "1 .. 127";
         }
       }
       leaf dialin {
         default "console";
         type enumeration {
           enum "console" {
             description "Management console access";
           }
           enum "routable" {
             description "Routable access";
           }
         }
       }
     }
     leaf act-sim {
       description "Default SIM slot to connect LTE network";
       type union {
         type string {
           pattern "<.*>|$.*";
         }
         type uint32;
       }
     }
     container cellular-options {
       presence "enable cellular-options";
       description "Cellular interface specific options";
       uses apply-advanced;
       list sim {
         key name;
         description "SIM slot to connect LTE network";
         leaf name {
           description "SIM slot number";
           type union {
             type string {
               pattern "<.*>|$.*";
             }
             type uint32;
           }
         }
         uses apply-advanced;
         container select-profile {
           description "Profile to be applied";
           leaf profile-id {
             description "Profile to be used for data calls";
             type union {
               type string {
                 pattern "<.*>|$.*";
               }
               type uint32 {
                 range "1 .. 16";
               }
             }
           }
         }
         container radio-access {
           description "Select radio access technology";
           choice rat-value {
             case case_1 {
               leaf automatic {
                 description "Automatically selects radio access type";
                 type empty;
               }
             }
             case case_2 {
               leaf umts-3g-only {
                 description "3G only";
                 type empty;
               }
             }
             case case_3 {
               leaf umts-3g-preferred {
                 description "UMTS 3G Preferred";
                 type empty;
               }
             }
             case case_4 {
               leaf lte-only {
                 description "Only LTE";
                 type empty;
               }
             }
             case case_5 {
               leaf lte-preferred {
                 description "LTE Preferred";
                 type empty;
               }
             }
           }
         }
         leaf encrypted-sim-unlock-code {
           description "Encrypted PIN";
           type jt:unreadable;
         }
         leaf gateway {
           description "Set customer gateway for LTE network";
           type jt:ipprefix;
         }
       }
     }
     container isdn-options {
       description "ISDN interface-specific options";
       uses apply-advanced;
       leaf switch-type {
         description "ISDN switch type";
         type enumeration {
           enum "ni1" {
             description "NI1 BRI variant";
           }
           enum "etsi" {
             description "ETSI variant";
           }
           enum "att5e" {
             description "ATT5E variant";
           }
           enum "ntdms100" {
             description "NTDMS100 variant";
           }
           enum "ntt" {
             description "INS NET (NTT) PRI/BRI variant";
           }
           enum "ni2" {
             description "NI2 PRI variant";
           }
         }
       }
       leaf media-type {
         description "IDSN media type - voice, data or both";
         default "data";
         type enumeration {
           enum "data" {
             description "Data";
           }
           enum "voice" {
             description "Voice";
           }
           enum "combined" {
             description "Combined";
           }
         }
       }
       leaf spid1 {
         description "Service profile identifier";
         type string {
           length "1 .. 20";
         }
       }
       leaf spid2 {
         description "Additional service profile identifier";
         type string {
           length "1 .. 20";
         }
       }
       leaf calling-number {
         description "Calling number included in outgoing calls";
         type string {
         }
       }
       list incoming-called-number {
         key name;
         ordered-by user;
         description "Incoming called number to be screened";
         max-elements 30;
         leaf name {
           description "Number called (upto 15 digits)";
           type string {
           }
         }
         leaf reject {
           description "Reject the called number";
           type empty;
         }
       }
       leaf tei-option {
         description "ISDN terminal endpoint identifier negotiation options";
         type enumeration {
           enum "first-call" {
             description "Terminal endpoint identifier negotiation during first call";
           }
           enum "power-up" {
             description "Terminal endpoint identifier negotiation during power-up";
           }
         }
       }
       leaf static-tei-val {
         description "Static TEI value";
         type union {
           type string {
             pattern "<.*>|$.*";
           }
           type uint32 {
             range "0 .. 63";
           }
         }
       }
       leaf t310 {
         description "Timer T310 value";
         units "seconds";
         type union {
           type string {
             pattern "<.*>|$.*";
           }
           type uint32 {
             range "1 .. 65536";
           }
         }
       }
       leaf bchannel-allocation {
         description "Allocate PRI dialout b-channel in ascending/descending order";
         default "descending";
         type enumeration {
           enum "ascending" {
             description "Allocate b-channel in ascending order";
           }
           enum "descending" {
             description "Allocate b-channel in descending order";
           }
         }
       }
     }
     container dialer-options {
       presence "enable dialer-options";
       description "Dialer options";
       uses apply-advanced;
       list pool {
         key name;
         description "Dialer pool";
         max-elements 30;
         leaf name {
           description "Dialer pool identifier";
           type string {
             length "1 .. 64";
           }
         }
         leaf priority {
           description "Dialer pool priority";
           type union {
             type string {
               pattern "<.*>|$.*";
             }
             type uint32 {
               range "1 .. 255";
             }
           }
         }
       }
     }
   }
   grouping juniper-class-of-service-options {
     uses apply-advanced;
     container classifiers {
       description "Classify incoming packets based on code point value";
       uses apply-advanced;
       list dscp {
         key name;
         ordered-by user;
         description "Differentiated Services code point classifier";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list dscp-ipv6 {
         key name;
         ordered-by user;
         description "Differentiated Services code point classifier IPv6";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list exp {
         key name;
         ordered-by user;
         description "MPLS EXP classifier";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list ieee-802.1 {
         key name;
         ordered-by user;
         description "IEEE-802.1 classifier";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list inet-precedence {
         key name;
         ordered-by user;
         description "IPv4 precedence classifier";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list ieee-802.1ad {
         key name;
         ordered-by user;
         description "IEEE-802.1ad (DEI) classifier";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
     }
     container traffic-class-map {
       description "Packet input priority map based on incoming packets code point";
       uses apply-advanced;
       list inet-precedence {
         key name;
         description "IPv4 precedence traffic-class-map";
         leaf name {
           description "Traffic-class-map name";
           type string {
             length "1 .. 64";
           }
         }
         uses apply-advanced;
         list traffic-class {
           key name;
           description "Map code points to a input packet priority";
           leaf name {
             type enumeration {
               enum "real-time" {
                 description "Code points map to traffic-class real-time";
               }
               enum "network-control" {
                 description "Code points map to traffic-class network-control";
               }
               enum "best-effort" {
                 description "Code points map to traffic-class best-effort";
               }
             }
           }
           leaf-list code-points {
             ordered-by user;
             description "List of code point aliases and/or bit strings";
             type string;
           }
         }
       }
       list dscp {
         key name;
         description "Differentiated Services code point traffic-class-map";
         leaf name {
           description "Traffic-class-map name";
           type string {
             length "1 .. 64";
           }
         }
         uses apply-advanced;
         list traffic-class {
           key name;
           description "Map code points to a input packet priority";
           leaf name {
             type enumeration {
               enum "real-time" {
                 description "Code points map to traffic-class real-time";
               }
               enum "network-control" {
                 description "Code points map to traffic-class network-control";
               }
               enum "best-effort" {
                 description "Code points map to traffic-class best-effort";
               }
             }
           }
           leaf-list code-points {
             ordered-by user;
             description "List of code point aliases and/or bit strings";
             type string;
           }
         }
       }
       list exp {
         key name;
         description "MPLS EXP traffic-class-map";
         leaf name {
           description "Traffic-class-map name";
           type string {
             length "1 .. 64";
           }
         }
         uses apply-advanced;
         list traffic-class {
           key name;
           description "Map code points to a input packet priority";
           leaf name {
             type enumeration {
               enum "real-time" {
                 description "Code points map to traffic-class real-time";
               }
               enum "network-control" {
                 description "Code points map to traffic-class network-control";
               }
               enum "best-effort" {
                 description "Code points map to traffic-class best-effort";
               }
             }
           }
           leaf-list code-points {
             ordered-by user;
             description "List of code point aliases and/or bit strings";
             type string;
           }
         }
       }
       list ieee-802.1 {
         key name;
         description "IEEE-802.1 traffic-class-map";
         leaf name {
           description "Traffic-class-map name";
           type string {
             length "1 .. 64";
           }
         }
         uses apply-advanced;
         list traffic-class {
           key name;
           description "Map code points to a input packet priority";
           leaf name {
             type enumeration {
               enum "real-time" {
                 description "Code points map to traffic-class real-time";
               }
               enum "network-control" {
                 description "Code points map to traffic-class network-control";
               }
               enum "best-effort" {
                 description "Code points map to traffic-class best-effort";
               }
             }
           }
           leaf-list code-points {
             ordered-by user;
             description "List of code point aliases and/or bit strings";
             type string;
           }
         }
       }
       list ieee-802.1ad {
         key name;
         description "IEEE-802.1ad (DEI) traffic-class-map";
         leaf name {
           description "Traffic-class-map name";
           type string {
             length "1 .. 64";
           }
         }
         uses apply-advanced;
         list traffic-class {
           key name;
           description "Map code points to a input packet priority";
           leaf name {
             type enumeration {
               enum "real-time" {
                 description "Code points map to traffic-class real-time";
               }
               enum "network-control" {
                 description "Code points map to traffic-class network-control";
               }
               enum "best-effort" {
                 description "Code points map to traffic-class best-effort";
               }
             }
           }
           leaf-list code-points {
             ordered-by user;
             description "List of code point aliases and/or bit strings";
             type string;
           }
         }
       }
     }
     list policy-map {
       key name;
       description "Policy-map describing the packet marking rule";
       max-elements 65535;
       leaf name {
         description "Policy-map name";
         type string {
           length "1 .. 64";
         }
       }
       uses apply-advanced;
       list inet-precedence {
         key name;
         description "IPv4 INET-Precedence Policy-map code point";
         leaf name {
           description "Optional flag to specify marking behavior";
           type enumeration {
             enum "proto-ip" {
               description "Default marking behavior";
             }
             enum "proto-mpls" {
               description "Enable IP header marking for IP->MPLS packet";
             }
             enum "proto-all" {
               description "Enable IP header marking";
             }
           }
         }
         leaf code-point {
           description "List of code point aliases and/or bit strings";
           type string {
           }
         }
       }
       list dscp {
         key name;
         description "IPv4 Differentiated Services Policy-map code point";
         leaf name {
           description "Optional flag to specify marking behavior";
           type enumeration {
             enum "proto-ip" {
               description "Default marking behavior";
             }
             enum "proto-mpls" {
               description "Enable IP header marking for IPV6->MPLS packet";
             }
             enum "proto-all" {
               description "Enable IP header marking";
             }
           }
         }
         leaf code-point {
           description "List of code point aliases and/or bit strings";
           type string {
           }
         }
       }
       list dscp-ipv6 {
         key name;
         description "IPv6 Differentiated Services Policy-map code point";
         leaf name {
           description "Optional flag to specify marking behavior";
           type enumeration {
             enum "proto-ip" {
               description "Default marking behavior";
             }
             enum "proto-mpls" {
               description "Enable IP header marking for IP->MPLS packet";
             }
           }
         }
         leaf code-point {
           description "List of code point aliases and/or bit strings";
           type string {
           }
         }
       }
       list exp {
         key name;
         description "MPLS EXP Policy-map code point";
         leaf name {
           description "Optional flag to specify marking behavior";
           type enumeration {
             enum "all-label" {
               description "Default marking behavior";
             }
             enum "outer-label" {
               description "Marking on only outer MPLS label";
             }
           }
         }
         leaf code-point {
           description "List of code point aliases and/or bit strings";
           type string {
           }
         }
       }
       list ieee-802.1 {
         key name;
         description "IEEE-802.1 Policy-map code point";
         leaf name {
           description "Optional flag to specify marking behavior";
           type enumeration {
             enum "outer" {
               description "Marking on outer VLAN tag";
             }
             enum "outer-and-inner" {
               description "Marking on both outer and inner VLAN tag";
             }
           }
         }
         leaf code-point {
           description "List of code point aliases and/or bit strings";
           type string {
           }
         }
       }
       list ieee-802.1ad {
         key name;
         description "IEEE-802.1ad Policy-map code point";
         leaf name {
           description "Optional flag to specify marking behavior";
           type enumeration {
             enum "outer" {
               description "Marking on outer VLAN tag";
             }
             enum "outer-and-inner" {
               description "Marking on both outer and inner VLAN tag";
             }
           }
         }
         leaf code-point {
           description "IEEE-802.1ad (DEI) Policy-map code point";
           type string {
           }
         }
       }
     }
     list forwarding-class-map {
       key name;
       description "Map forwarding class to queue number for interfaces";
       leaf name {
         description "Interface specific forwarding class name";
         type string {
           length "1 .. 64";
         }
       }
       uses apply-advanced;
       list class {
         key name;
         description "Forwarding class";
         leaf name {
           description "Name of forwarding class";
           type string {
             length "1 .. 64";
           }
         }
         leaf queue-num {
           description "Queue number";
           type union {
             type string {
               pattern "<.*>|$.*";
             }
             type uint32;
           }
         }
         leaf restricted-queue {
           description "Restricted queue number";
           type union {
             type string {
               pattern "<.*>|$.*";
             }
             type uint32 {
               range "0 .. 3";
             }
           }
         }
       }
     }
     container loss-priority-maps {
       description "Map loss priority of incoming packets based on code point value";
       uses apply-advanced;
       list frame-relay-de {
         key name;
         description "Frame relay discard eligible bit loss priority map";
         leaf name {
           description "Loss priority map name";
           type string {
             length "1 .. 64";
           }
         }
         uses apply-advanced;
         list loss-priority {
           key name;
           description "Map code points to a loss priority";
           leaf name {
             type enumeration {
               enum "low" {
                 description "Code points to classify to low loss priority";
               }
               enum "high" {
                 description "Code points to classify to high loss priority";
               }
               enum "medium-low" {
                 description "Code points to classify to medium-low loss priority";
               }
               enum "medium-high" {
                 description "Code points to classify to medium-high loss priority";
               }
             }
           }
           leaf-list code-points {
             ordered-by user;
             description "List of bit strings";
             type string;
           }
         }
       }
     }
     container loss-priority-rewrites {
       description "Rewrite code point of outgoing packet based on loss priority";
       uses apply-advanced;
       list frame-relay-de {
         key name;
         description "Frame relay discard eligible bit loss priority rewrite";
         leaf name {
           description "Loss priority rewrite name";
           type string {
             length "1 .. 64";
           }
         }
         uses apply-advanced;
         list loss-priority {
           key name;
           description "Code point marking based on loss priority";
           leaf name {
             type enumeration {
               enum "low" {
                 description "Marking when loss priority is low";
               }
               enum "high" {
                 description "Marking when loss priority is high";
               }
               enum "medium-low" {
                 description "Marking when loss priority is medium-low";
               }
               enum "medium-high" {
                 description "Marking when loss priority is medium-high";
               }
             }
           }
           leaf code-point {
             description "Code point aliases or bit string";
             type string {
             }
           }
         }
       }
     }
     container code-point-aliases {
       description "Mapping of code point aliases to bit strings";
       uses apply-advanced;
       list dscp {
         key name;
         description "Differentiated Services code point aliases";
         leaf name {
           description "DSCP alias name";
           type string {
           }
         }
         leaf bits {
           description "DSCP 6-bit pattern";
           type string {
           }
         }
       }
       list dscp-ipv6 {
         key name;
         description "Differentiated Services code point aliases IPv6";
         leaf name {
           description "DSCP IPv6 alias name";
           type string {
           }
         }
         leaf bits {
           description "DSCP 6-bit pattern";
           type string {
           }
         }
       }
       list exp {
         key name;
         description "MPLS EXP code point aliases";
         leaf name {
           description "EXP alias name";
           type string {
           }
         }
         leaf bits {
           description "EXP 3-bit pattern";
           type string {
           }
         }
       }
       list ieee-802.1 {
         key name;
         description "IEEE-802.1 code point aliases";
         leaf name {
           description "IEEE-802.1 alias name";
           type string {
           }
         }
         leaf bits {
           description "IEEE-802.1 3-bit pattern";
           type string {
           }
         }
       }
       list inet-precedence {
         key name;
         description "IPv4 precedence code point aliases";
         leaf name {
           description "IPv4 precedence alias name";
           type string {
           }
         }
         leaf bits {
           description "IPv4 precedence 3-bit pattern";
           type string {
           }
         }
       }
       list ieee-802.1ad {
         key name;
         description "IEEE-802.1ad (DEI) code point aliases";
         leaf name {
           description "IEEE-802.1ad (DEI) alias name";
           type string {
           }
         }
         leaf bits {
           description "IEEE-802.1ad (DEI) 4-bit pattern";
           type string {
           }
         }
       }
       list inet6-precedence {
         key name;
         description "IPv6 precedence code point aliases";
         leaf name {
           description "IPv6 precedence alias name";
           type string {
           }
         }
         leaf bits {
           description "IPv6 precedence 3-bit pattern";
           type string {
           }
         }
       }
     }
     container translation-table {
       description "Translation table";
       uses apply-advanced;
       list to-802.1p-from-dscp {
         key name;
         description "DSCP to 802.1 translation table";
         leaf name {
           description "Translation table name";
           type string {
             length "1 .. 64";
           }
         }
         uses apply-advanced;
         list to-code-point {
           key name;
           description "IEEE 802.1 code point";
           leaf name {
             description "IEEE 802.1 code point";
             type string {
             }
           }
           leaf-list from-code-points {
             ordered-by user;
             description "DSCP code point";
             type string;
           }
         }
       }
       list to-inet-precedence-from-inet-precedence {
         key name;
         description "INET PRECEDENCE to INET PRECEDENCE translation table";
         leaf name {
           description "Translation table name";
           type string {
             length "1 .. 64";
           }
         }
         uses apply-advanced;
         list to-code-point {
           key name;
           description "INET PRECEDENCE code point";
           leaf name {
             description "INET PRECEDENCE code point";
             type string {
             }
           }
           leaf-list from-code-points {
             ordered-by user;
             description "INET PRECEDENCE code point";
             type union {
               type string {
                 pattern "\*";
               }
               type string;
             }
           }
         }
       }
       list to-dscp-from-dscp {
         key name;
         description "DSCP to DSCP translation table";
         leaf name {
           description "Translation table name";
           type string {
             length "1 .. 64";
           }
         }
         uses apply-advanced;
         list to-code-point {
           key name;
           description "DSCP code point";
           leaf name {
             description "DSCP code point";
             type string {
             }
           }
           leaf-list from-code-points {
             ordered-by user;
             description "DSCP code point";
             type union {
               type string {
                 pattern "\*";
               }
               type string;
             }
           }
         }
       }
       list to-dscp-ipv6-from-dscp-ipv6 {
         key name;
         description "DSCP-IPV6 to DSCP-IPV6 translation table";
         leaf name {
           description "Translation table name";
           type string {
             length "1 .. 64";
           }
         }
         uses apply-advanced;
         list to-code-point {
           key name;
           description "DSCP-IPV6 code point";
           leaf name {
             description "DSCP-IPV6 code point";
             type string {
             }
           }
           leaf-list from-code-points {
             ordered-by user;
             description "DSCP-IPV6 code point";
             type union {
               type string {
                 pattern "\*";
               }
               type string;
             }
           }
         }
       }
       list to-exp-from-exp {
         key name;
         description "EXP to EXP translation table";
         leaf name {
           description "Translation table name";
           type string {
             length "1 .. 64";
           }
         }
         uses apply-advanced;
         list to-code-point {
           key name;
           description "EXP code point";
           leaf name {
             description "EXP code point";
             type string {
             }
           }
           leaf-list from-code-points {
             ordered-by user;
             description "EXP code point";
             type union {
               type string {
                 pattern "\*";
               }
               type string;
             }
           }
         }
       }
     }
     container host-outbound-traffic {
       description "Classify and mark host traffic to forwarding engine";
       uses apply-advanced;
       leaf forwarding-class {
         description "Classification of host traffic to forwarding engine";
         type string {
           length "1 .. 64";
         }
       }
       leaf dscp-code-point {
         description "Static DSCP code point of egress host traffic";
         type string {
         }
       }
       leaf override-firewall {
         description "Override firewall filter actions for RE generated traffic";
         type empty;
       }
       container translation-table {
         description "Translation table for host outbound packets";
         leaf to-802.1p-from-dscp {
           description "DSCP to 802.1 translation table";
           type string {
             length "1 .. 64";
           }
         }
       }
       container tcp {
         presence "enable tcp";
         description "Settings for host outbound TCP packets";
         uses apply-advanced;
         leaf raise-internet-control-priority {
           description "Place packets with IP Precedence set to Internet control into Q3 (network-control)";
           type empty;
         }
       }
       container ieee-802.1 {
         presence "enable ieee-802.1";
         description "Mark IEEE 802.1p for host output traffic";
         uses apply-advanced;
         leaf rewrite-rules {
           description "Mark IEEE 802.1p for host outbound traffic using rewrite-rules";
           type empty;
         }
         leaf default {
           description "Mark IEEE 802.1p for host outbound traffic default value";
           type string {
           }
         }
       }
       container protocol {
         description "Settings for specific host outbound protocol packets";
         uses apply-advanced;
         container isis-over-gre {
           description "Settings for ISIS over GRE packets";
           uses apply-advanced;
           leaf dscp-code-point {
             description "Static DSCP code point of egress host traffic";
             type string {
             }
           }
         }
       }
     }
     list drop-profiles {
       key name;
       description "Random Early Drop (RED) data point map";
       leaf name {
         description "Drop profile name";
         type string {
           length "1 .. 64";
         }
       }
       uses apply-advanced;
       list fill-level {
         key name;
         description "Fill-level value of data point";
         leaf name {
           description "Percentage the queue is full";
           type union {
             type string {
               pattern "<.*>|$.*";
             }
             type uint32 {
               range "0 .. 100";
             }
           }
         }
         leaf drop-probability {
           description "Probability packet will be dropped";
           type union {
             type string {
               pattern "<.*>|$.*";
             }
             type uint32 {
               range "0 .. 100";
             }
           }
         }
       }
       container interpolate {
         description "Data points interpolated";
         uses apply-advanced;
         leaf-list fill-level {
           ordered-by user;
           description "Data points for queue full percentage";
           type union {
             type string {
               pattern "<.*>|$.*";
             }
             type uint32 {
               range "0 .. 100";
             }
           }
         }
         leaf-list drop-probability {
           ordered-by user;
           description "Data points for packet drop probability";
           type union {
             type string {
               pattern "<.*>|$.*";
             }
             type uint32 {
               range "0 .. 100";
             }
           }
         }
       }
     }
     list adaptive-shapers {
       key name;
       description "Define the list of trigger types and associated rates";
       leaf name {
         description "Adaptive shaper name";
         type string {
           length "1 .. 64";
         }
       }
       uses apply-advanced;
       list trigger {
         key name;
         description "List of trigger types";
         leaf name {
           type enumeration {
             enum "becn" {
               description "Backward explicit congestion notification";
             }
           }
         }
         container shaping-rate {
           description "Shaping rate for the trigger";
           choice rate-choice {
             case case_1 {
               leaf absolute-rate {
                 description "Shaping rate as an absolute rate";
                 units "bits per second";
                 type string;
               }
             }
             case case_2 {
               leaf percent {
                 description "Shaping rate as a percentage";
                 type union {
                   type string {
                     pattern "<.*>|$.*";
                   }
                   type uint32 {
                     range "1 .. 100";
                   }
                 }
               }
             }
           }
         }
       }
     }
     list virtual-channels {
       key name;
       description "Define the list of virtual channels";
       leaf name {
         description "Virtual channel name";
         type string {
           length "1 .. 64";
         }
       }
       uses apply-advanced;
     }
     list virtual-channel-groups {
       key name;
       description "Define list of virtual channel groups";
       leaf name {
         description "Virtual channel group name";
         type string {
           length "1 .. 64";
         }
       }
       uses apply-advanced;
       list channel {
         key name;
         description "Configure virtual channel for this group";
         leaf name {
           description "Virtual channel group name";
           type string {
             length "1 .. 64";
           }
         }
         uses apply-advanced;
         leaf scheduler-map {
           description "Scheduler map applied to this virtual channel";
           type string {
             length "1 .. 64";
           }
         }
         container shaping-rate {
           description "Shaping rate for the trigger";
           choice rate-choice {
             case case_1 {
               leaf absolute-rate {
                 description "Adaptive shaping rate as an absolute rate";
                 units "bits per second";
                 type string;
               }
             }
             case case_2 {
               leaf percent {
                 description "Adaptive shaping rate as a percentage";
                 type union {
                   type string {
                     pattern "<.*>|$.*";
                   }
                   type uint32 {
                     range "1 .. 100";
                   }
                 }
               }
             }
           }
         }
         leaf default {
           description "Default virtual channel";
           type empty;
         }
       }
     }
     leaf copy-plp-all {
       description "Turn on loss-precedence copying including IP multicast";
       type empty;
     }
     leaf tri-color {
       description "Enable tricolor marking";
       type empty;
     }
     leaf non-strict-priority-scheduling {
       description "Enable non-strict-priority scheduling";
       type empty;
     }
     container shared-buffer {
       description "Shared buffer configuration";
       uses apply-advanced;
       leaf percent {
         description "Percentage of shared buffer to be used";
         type union {
           type string {
             pattern "<.*>|$.*";
           }
           type uint32 {
             range "5 .. 100";
           }
         }
       }
       container ingress {
         description "Shared buffer configuration at ingress";
         uses apply-advanced;
         leaf percent {
           description "Percentage of shared buffer to be used at ingress";
           type union {
             type string {
               pattern "<.*>|$.*";
             }
             type uint32 {
               range "0 .. 100";
             }
           }
         }
         list buffer-partition {
           key name;
           description "Buffer-partition";
           leaf name {
             description "Buffer-partition name";
             type string {
             }
           }
           uses apply-advanced;
           leaf percent {
             description "Percentage of ingress shared buffer to be used";
             type union {
               type string {
                 pattern "<.*>|$.*";
               }
               type uint32 {
                 range "0 .. 100";
               }
             }
           }
           leaf dynamic-threshold {
             description "Threshold for maximum buffer share for a queue at ingress buffer-partition";
             type union {
               type string {
                 pattern "<.*>|$.*";
               }
               type uint32 {
                 range "0 .. 10";
               }
             }
           }
         }
       }
       container egress {
         description "Shared buffer configuration at egress";
         uses apply-advanced;
         leaf percent {
           description "Percentage of shared buffer to be used at egress";
           type union {
             type string {
               pattern "<.*>|$.*";
             }
             type uint32 {
               range "0 .. 100";
             }
           }
         }
         list buffer-partition {
           key name;
           description "Buffer-partition";
           leaf name {
             description "Buffer-partition name";
             type string {
             }
           }
           uses apply-advanced;
           leaf percent {
             description "Percentage of egress shared buffer to be used";
             type union {
               type string {
                 pattern "<.*>|$.*";
               }
               type uint32 {
                 range "0 .. 100";
               }
             }
           }
           leaf dynamic-threshold {
             description "Threshold for maximum buffer share for a queue at egress buffer-partition";
             type union {
               type string {
                 pattern "<.*>|$.*";
               }
               type uint32 {
                 range "0 .. 10";
               }
             }
           }
         }
       }
     }
     container dedicated-buffer {
       description "Dedicated buffer configuration";
       uses apply-advanced;
       container ingress {
         description "Dedicated buffer configuration at ingress";
         uses apply-advanced;
         leaf percent {
           description "Percentage of dedicated buffer to be used at ingress";
           type union {
             type string {
               pattern "<.*>|$.*";
             }
             type uint32 {
               range "15 .. 100";
             }
           }
         }
       }
       container egress {
         description "Dedicated buffer configuration at egress";
         uses apply-advanced;
         leaf percent {
           description "Percentage of dedicated buffer to be used at egress";
           type union {
             type string {
               pattern "<.*>|$.*";
             }
             type uint32 {
               range "15 .. 100";
             }
           }
         }
       }
     }
     list dedicated-buffer-profile {
       key name;
       description "Dedicated buffer profile configuration";
       leaf name {
         description "Dedicated buffer profile name";
         type string {
           length "1 .. 64";
         }
       }
       uses apply-advanced;
       container ingress {
         presence "enable ingress";
         uses apply-advanced;
         container buffer-size {
           presence "enable buffer-size";
           description "Dedicated buffer size";
           uses apply-advanced;
           choice buffer_size_choice {
             case case_1 {
               leaf none {
                 description "No dedicated buffer";
                 type empty;
               }
             }
             case case_2 {
               leaf cells {
                 description "Dedicated buffer size in terms of cells";
                 type union {
                   type string {
                     pattern "<.*>|$.*";
                   }
                   type uint32 {
                     range "20 .. 50000";
                   }
                 }
               }
             }
           }
         }
       }
       container egress {
         presence "enable egress";
         uses apply-advanced;
         container buffer-size {
           presence "enable buffer-size";
           description "Dedicated buffer size";
           uses apply-advanced;
           choice buffer_size_choice {
             case case_1 {
               leaf none {
                 description "No dedicated buffer";
                 type empty;
               }
             }
             case case_2 {
               leaf cells {
                 description "Dedicated buffer size in terms of cells";
                 type union {
                   type string {
                     pattern "<.*>|$.*";
                   }
                   type uint32 {
                     range "20 .. 100000";
                   }
                 }
               }
             }
           }
         }
       }
     }
     container forwarding-classes {
       description "One or more mappings of forwarding class to queue number";
       uses apply-advanced;
       list class {
         key name;
         description "Forwarding class to map to queue number";
         max-elements 16;
         leaf name {
           description "Name of forwarding class";
           type string {
             length "1 .. 64";
           }
         }
         leaf queue-num {
           description "Queue number";
           type union {
             type string {
               pattern "<.*>|$.*";
             }
             type uint32;
           }
         }
         leaf priority {
           description "Fabric priority";
           type enumeration {
             enum "low" {
               description "Low fabric priority";
             }
             enum "high" {
               description "High fabric priority";
             }
           }
         }
         leaf policing-priority {
           description "Policing priority for hierarchical policers";
           type enumeration {
             enum "normal" {
               description "Normal policing priority";
             }
             enum "premium" {
               description "Premium policing priority";
             }
           }
         }
         leaf no-loss {
           description "This is no traffic loss class";
           type empty;
         }
         leaf multicast {
           description "This is a multicast traffic class";
           type empty;
         }
         leaf pfc-priority {
           description "PFC priority (FC id's)";
           type union {
             type string {
               pattern "<.*>|$.*";
             }
             type uint32 {
               range "0 .. 7";
             }
           }
         }
         leaf spu-priority {
           description "SPU priority";
           type enumeration {
             enum "low" {
               description "Low spu priority";
             }
             enum "high" {
               description "High spu priority";
             }
             enum "medium-low" {
               description "Medium-low spu priority";
             }
             enum "medium-high" {
               description "Medium-high spu priority";
             }
             enum "medium" {
               description "Medium spu priority";
             }
           }
         }
       }
       list queue {
         key name;
         description "Queue number to map to forwarding class";
         leaf name {
           description "Queue number";
           type union {
             type string {
               pattern "<.*>|$.*";
             }
             type uint32;
           }
         }
         leaf class-name {
           description "Forwarding class name";
           type string {
             length "1 .. 64";
           }
         }
         leaf priority {
           description "Fabric priority";
           type enumeration {
             enum "low" {
               description "Fabric priority low";
             }
             enum "high" {
               description "Fabric priority high";
             }
           }
         }
         leaf policing-priority {
           description "Policing priority for hierarchical policers";
           type enumeration {
             enum "normal" {
               description "Normal policing priority";
             }
             enum "premium" {
               description "Premium policing priority";
             }
           }
         }
       }
     }
     container restricted-queues {
       description "Map forwarding classes to restricted queues";
       uses apply-advanced;
       list forwarding-class {
         key name;
         description "Forwarding class to map to a restricted queue";
         leaf name {
           description "Forwarding class name";
           type string {
             length "1 .. 64";
           }
         }
         leaf rqueue-num {
           description "Restricted queue number";
           type union {
             type string {
               pattern "<.*>|$.*";
             }
             type uint32 {
               range "0 .. 3";
             }
           }
         }
       }
     }
     list traffic-control-profiles {
       key name;
       description "Traffic shaping and scheduling profiles";
       leaf name {
         description "Traffic control profile name";
         type string {
           length "1 .. 64";
         }
       }
       uses apply-advanced;
       leaf scheduler-map {
         description "Mapping of forwarding classes to packet schedulers";
         type string {
           length "1 .. 64";
         }
       }
       leaf strict-priority-scheduler {
         description "Enable strict priority scheduler.";
         type empty;
       }
       leaf atm-service {
         description "ATM service category";
         type enumeration {
           enum "cbr" {
             description "Constant bit rate";
           }
           enum "rtvbr" {
             description "Real-time variable bit rate";
           }
           enum "nrtvbr" {
             description "Non-real-time variable bit rate";
           }
         }
       }
       leaf peak-rate {
         description "ATM Peak Cell Rate (PCR)";
         units "cps";
         type string;
       }
       leaf sustained-rate {
         description "ATM Sustained Cell Rate (SCR)";
         units "cps";
         type string;
       }
       leaf max-burst-size {
         description "ATM Maximum Burst Size (MBS)";
         units "cells";
         type union {
           type string {
             pattern "<.*>|$.*";
           }
           type uint64 {
             range "1 .. 4000";
           }
         }
       }
       container shaping-rate {
         description "Shaping rate";
         choice shaping_rate_choice {
           case case_1 {
             leaf rate {
               description "Shaping rate as an absolute rate";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container overhead-accounting {
         description "Overhead accounting";
         leaf mode {
           type string {
             length "1 .. 64";
           }
         }
         leaf bytes {
           description "Byte adjust value";
           type union {
             type string {
               pattern "<.*>|$.*";
             }
             type int32;
           }
         }
         leaf frame-mode-bytes {
           description "Overhead bytes when in frame-mode";
           type union {
             type string {
               pattern "<.*>|$.*";
             }
             type int32 {
               range "-120 .. 124";
             }
           }
         }
         leaf cell-mode-bytes {
           description "Overhead bytes when in cell-mode";
           type union {
             type string {
               pattern "<.*>|$.*";
             }
             type int32 {
               range "-120 .. 124";
             }
           }
         }
       }
       container shaping-rate-priority-strict-high {
         description "Shaping rate for strict high priority traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-priority-high {
         description "Shaping rate for high priority traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-priority-medium {
         description "Shaping rate for medium priority traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-priority-medium-low {
         description "Shaping rate for medium low priority traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-priority-low {
         description "Shaping rate for low priority traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-excess-high {
         description "Shaping rate for excess high traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-excess-low {
         description "Shaping rate for excess low traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-excess-medium-high {
         description "Shaping rate for excess medium-high traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-excess-medium-low {
         description "Shaping rate for excess medium-low traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container guaranteed-rate {
         description "Guaranteed rate";
         choice guaranteed_rate_choice {
           case case_1 {
             leaf rate {
               description "Guaranteed rate as an absolute rate";
               units "bits per second";
               type string;
             }
           }
           case case_2 {
             leaf percent {
               description "Guaranteed rate as a percentage";
               type union {
                 type string {
                   pattern "<.*>|$.*";
                 }
                 type uint32 {
                   range "1 .. 100";
                 }
               }
             }
           }
         }
         leaf burst-size {
           description "Guaranteed rate burst size";
           units "bytes";
           type string;
         }
       }
       container excess-rate {
         description "Excess bandwidth sharing proportion";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-high {
         description "Excess bandwidth sharing for excess-high priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-medium-high {
         description "Excess bandwidth sharing for excess-medium-high priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-low {
         description "Excess bandwidth sharing for excess-low priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-medium-low {
         description "Excess bandwidth sharing for excess-medium-low priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       choice delay_buffer_sizing {
         case case_1 {
           container delay-buffer-rate {
             description "Delay buffer rate";
             choice delay_buffer_rate_choice {
               case case_1 {
                 leaf rate {
                   description "Delay buffer rate as an absolute rate";
                   units "bits per second";
                   type string;
                 }
               }
               case case_2 {
                 leaf percent {
                   description "Delay buffer rate as a percentage";
                   type union {
                     type string {
                       pattern "<.*>|$.*";
                     }
                     type uint32 {
                       range "1 .. 100";
                     }
                   }
                 }
               }
               case case_3 {
                 leaf cps {
                   description "Delay buffer rate as an absolute cells per second rate";
                   units "cells per second";
                   type string;
                 }
               }
             }
           }
         }
       }
       container adjust-minimum {
         description "Minimum shaping-rate when adjusted";
         leaf rate {
           description "Minimum shaping rate in bits per second";
           units "bits per second";
           type string;
         }
       }
     }
     list monitoring-profile {
       key name;
       description "Monitoring profile";
       leaf name {
         description "Monitoring profile name";
         type string {
           length "1 .. 64";
         }
       }
       uses apply-advanced;
       list export-filters {
         key name;
         description "List of export filters";
         leaf name {
           description "Export filter name";
           type string {
             length "1 .. 64";
           }
         }
         uses apply-advanced;
         container peak-queue-length {
           presence "enable peak-queue-length";
           description "Peak queue length as percentage";
           uses apply-advanced;
           leaf percent {
             default "0";
             type union {
               type string {
                 pattern "<.*>|$.*";
               }
               type uint32 {
                 range "0 .. 100";
               }
             }
           }
         }
         leaf-list queue {
           ordered-by user;
           description "Queue number to add in export filter";
           type union {
             type string {
               pattern "<.*>|$.*";
             }
             type uint32 {
               range "0 .. 7";
             }
           }
         }
       }
     }
     list forwarding-class-sets {
       key name;
       description "Forwarding class sets";
       leaf name {
         description "Forwarding class set";
         type string {
           length "1 .. 64";
         }
       }
       uses apply-advanced;
       list class {
         key name;
         description "Forwarding class";
         leaf name {
           description "Class name";
           type string {
             length "1 .. 64";
           }
         }
         uses apply-advanced;
       }
     }
     list congestion-notification-profile {
       key name;
       description "Congestion notification profile";
       leaf name {
         description "Congestion notification name";
         type string {
           length "1 .. 64";
         }
       }
       uses apply-advanced;
       container pfc-watchdog {
         presence "enable pfc-watchdog";
         description "Configure pfc-watchdog parameters";
         uses apply-advanced;
         leaf poll-interval {
           description "Pfc watchdog poll interval timings";
           units "milliseconds";
           type union {
             type string {
               pattern "<.*>|$.*";
             }
             type uint16;
           }
         }
         leaf detection {
           description "Pfc Number of poll periods";
           type union {
             type string {
               pattern "<.*>|$.*";
             }
             type uint32;
           }
         }
         leaf recovery {
           description "Pfc watchdog recovery time interval";
           units "milliseconds";
           type union {
             type string {
               pattern "<.*>|$.*";
             }
             type uint16;
           }
         }
         leaf watchdog-action {
           description "Configure pfc-wathdog action";
           type enumeration {
             enum "drop" {
               description "Pfc watchdog action drop";
             }
             enum "forward" {
               description "Pfc watchdog action forward";
             }
           }
         }
       }
       container input {
         description "Input congestion notification components";
         uses apply-advanced;
         leaf cable-length {
           description "Length of cable in metre";
           units "metre";
           type string;
         }
         list pfc-account {
           key name;
           description "PFC account configurations";
           leaf name {
             description "PFC account name";
             type string {
               length "1 .. 64";
             }
           }
           uses apply-advanced;
           leaf xon {
             description "Specifies account threshold for resume in microseconds of source port speed";
             type union {
               type string {
                 pattern "<.*>|$.*";
               }
               type uint32 {
                 range "0 .. 100000";
               }
             }
           }
           leaf xoff {
             description "Specifies account threshold for pause in microseconds of source port speed";
             type union {
               type string {
                 pattern "<.*>|$.*";
               }
               type uint32 {
                 range "0 .. 100000";
               }
             }
           }
           leaf-list pfc-priority {
             ordered-by user;
             description "PFC priorities( set of priorities)";
             type union {
               type string {
                 pattern "<.*>|$.*";
               }
               type uint32 {
                 range "0 .. 7";
               }
             }
           }
         }
         container ieee-802.1 {
           description "IEEE 802.1 code point";
           uses apply-advanced;
           list code-point {
             key name;
             description "IEEE 802.1 code point";
             max-elements 8;
             leaf name {
               description "IEEE 802.1 code point";
               type string {
               }
             }
             uses apply-advanced;
             leaf pfc {
               description "PFC";
               type empty;
             }
             leaf pfc-account-name {
               description "Attach PFC account to code point";
               type string {
                 length "1 .. 64";
               }
             }
             leaf mru {
               description "Max Receive Size of packet for this code point";
               units "bytes";
               type string;
             }
             leaf xon {
               description "Specifies XON threshold offset cells for Tx resume from dynamic shared buffer";
               type union {
                 type string {
                   pattern "<.*>|$.*";
                 }
                 type uint32 {
                   range "0 .. 100000";
                 }
               }
             }
             choice qfc-control {
               case case_1 {
                 leaf qfc {
                   description "QFC";
                   type empty;
                 }
               }
               case case_2 {
                 container qcn {
                   presence "enable qcn";
                   description "QCN";
                   uses apply-advanced;
                   container defense-mode-edge {
                     description "Choose the defense mode edge";
                     uses apply-advanced;
                     container alternate-priority {
                       description "Choose the alternate priority for defense mode edge";
                       uses apply-advanced;
                       leaf bits {
                         description "IEEE 802.1 code point";
                         type string {
                         }
                       }
                     }
                   }
                 }
               }
             }
           }
         }
         container dscp {
           description "DSCP code point";
           uses apply-advanced;
           list code-point {
             key name;
             description "DSCP code point";
             max-elements 64;
             leaf name {
               description "DSCP code point";
               type string {
               }
             }
             uses apply-advanced;
             leaf pfc {
               description "PFC";
               type empty;
             }
             leaf pfc-account-name {
               description "Attach PFC account to code point";
               type string {
                 length "1 .. 64";
               }
             }
             leaf mru {
               description "Max Receive Size of packet for this code point";
               units "bytes";
               type string;
             }
             leaf xon {
               description "Specifies XON threshold offset cells for TX resume from dynamic shared buffer";
               type union {
                 type string {
                   pattern "<.*>|$.*";
                 }
                 type uint32 {
                   range "0 .. 100000";
                 }
               }
             }
           }
         }
       }
       container output {
         description "Output congestion notification components";
         uses apply-advanced;
         list class {
           key name;
           description "Forwarding class";
           max-elements 16;
           leaf name {
             description "Class name";
             type string {
               length "1 .. 64";
             }
           }
           uses apply-advanced;
           leaf remove-cntag {
             description "Remove cntag for this forwarding class";
             type empty;
           }
           leaf qcn {
             description "Enabling Quantized Congestion Notification for this forwarding class";
             type empty;
           }
         }
         container ieee-802.1 {
           description "IEEE 802.1 code point";
           uses apply-advanced;
           list code-point {
             key name;
             description "IEEE 802.1 code point";
             max-elements 8;
             leaf name {
               description "IEEE 802.1 code point";
               type string {
               }
             }
             uses apply-advanced;
             leaf-list flow-control-queue {
               ordered-by user;
               description "Flow control queue( set of queues)";
               type union {
                 type string {
                   pattern "<.*>|$.*";
                 }
                 type uint32 {
                   range "0 .. 7";
                 }
               }
             }
           }
         }
       }
     }
     list scheduler-map-forwarding-class-sets {
       key name;
       description "Mapping of forwarding class sets to packet schedulers";
       leaf name {
         description "Scheduler map forwarding class set name";
         type string {
           length "1 .. 64";
         }
       }
       uses apply-advanced;
       list forwarding-class-set {
         key name;
         description "Forwarding class set name to map to scheduler";
         leaf name {
           description "Forwarding class set name";
           type string {
             length "1 .. 64";
           }
         }
         leaf scheduler {
           description "Scheduler name";
           type string {
             length "1 .. 64";
           }
         }
       }
     }
     container system-defaults {
       description "System defaults";
       uses apply-advanced;
       container classifiers {
         description "System wide Classifiers applied to incoming packets";
         uses apply-advanced;
         container exp {
           description "EXP classifier";
           leaf classifier-name {
             description "Name of classifier to be applied";
             type union {
               type string {
                 pattern "default";
               }
               type string {
                 length "1 .. 64";
               }
             }
           }
         }
       }
       container traffic-control-profiles {
         description "Default traffic control profiles";
         uses apply-advanced;
         container interface-set-input {
           description "Default input traffic control profile for dynamic interface-set";
           leaf profile-name {
             description "Name of traffic control profile";
             type string {
               length "1 .. 64";
             }
           }
         }
         container interface-set-output {
           description "Default output traffic control profile for dynamic interface-set";
           leaf profile-name {
             description "Name of traffic control profile";
             type string {
               length "1 .. 64";
             }
           }
         }
       }
     }
     container dynamic-class-of-service-options {
       description "Dynamic class-of-service options";
       uses apply-advanced;
       list vendor-specific-tags {
         key name;
         description "Enable vendor specific tags";
         leaf name {
           type enumeration {
             enum "actual-data-rate-downstream" {
               description "Enable shaping based on actual-data-rate-downstream";
             }
             enum "access-loop-encapsulation" {
               description "Enable overhead-accounting based on access-loop-encapsulation";
             }
             enum "apply-to-interface-set" {
               description "Apply adjusted rate to the underlying interface-set";
             }
           }
         }
         uses apply-advanced;
       }
     }
     container interfaces {
       description "Apply class-of-service options to interfaces";
       uses apply-advanced;
       list interface-set {
         key name;
         description "Interface set traffic-control-profile attachment";
         leaf name {
           description "Name of the interface set";
           type string {
             length "1 .. 64";
           }
         }
         uses apply-advanced;
         leaf internal-node {
           description "Internal node";
           type empty;
         }
         container input-excess-bandwidth-share {
           description "Input Excess bandwidth sharing policy";
           choice input_excess_bandwidth_share {
             case case_1 {
               leaf proportional {
                 description "Maximum Queue Bandwidth";
                 units "bits per second";
                 type string;
               }
             }
             case case_2 {
               leaf equal {
                 description "Equal sharing of excess bandwidth";
                 type empty;
               }
             }
           }
         }
         container excess-bandwidth-share {
           description "Output Excess bandwidth sharing policy";
           choice output_excess_bandwidth_share {
             case case_1 {
               leaf proportional {
                 description "Maximum Queue Bandwidth";
                 units "bits per second";
                 type string;
               }
             }
             case case_2 {
               leaf equal {
                 description "Equal sharing of excess bandwidth";
                 type empty;
               }
             }
           }
         }
         container input-traffic-control-profile {
           description "Input traffic control profile for the interface set";
           leaf profile-name {
             description "Name of the input traffic control profile associated with the interface set";
             type string {
               length "1 .. 64";
             }
           }
         }
         container input-traffic-control-profile-remaining {
           description "Input traffic control profile for the remaining traffic on an interface set";
           leaf profile-name {
             description "Name of the input traffic control profile associated with the remaining traffic for the interface set";
             type string {
               length "1 .. 64";
             }
           }
         }
         container output-traffic-control-profile {
           description "Output traffic control profile for the interface set";
           leaf profile-name {
             description "Name of the output traffic control profile associated with the interface set";
             type string {
               length "1 .. 64";
             }
           }
         }
         container output-traffic-control-profile-remaining {
           description "Output traffic control profile for the remaining traffic on an interface set";
           leaf profile-name {
             description "Name of the output traffic control profile associated with the remaining traffic for the interface set";
             type string {
               length "1 .. 64";
             }
           }
         }
         container monitoring-profile {
           description "Monitoring profile";
           leaf profile-name {
             description "Name of the monitoring profile";
             type string {
               length "1 .. 64";
             }
           }
         }
       }
       list interface {
         key name;
         uses cos_interfaces_type;
       }
     }
     list routing-instances {
       key name;
       description "Apply CoS options to routing instances with VRF table label";
       leaf name {
         description "Routing instance name (or wildcard)";
         type string {
         }
       }
       uses apply-advanced;
       container classifiers {
         description "Classifiers applied to incoming packets";
         uses apply-advanced;
         leaf no-default {
           description "Do not apply default classifiers to this interface";
           type empty;
         }
         container exp {
           description "EXP classifier";
           leaf classifier-name {
             description "Name of classifier to be applied";
             type union {
               type string {
                 pattern "default";
               }
               type string {
                 length "1 .. 64";
               }
             }
           }
         }
         container ieee-802.1 {
           description "IEEE-802.1 classifier";
           leaf classifier-name {
             description "Name of classifier to be applied";
             type union {
               type string {
                 pattern "default";
               }
               type string {
                 length "1 .. 64";
               }
             }
           }
           leaf encapsulated {
             description "Inner or outer ethernet header";
             type empty;
           }
           leaf vlan-tag {
             description "VLAN tag used for classification";
             type enumeration {
               enum "outer" {
                 description "Classification based on outer VLAN tag";
               }
               enum "inner" {
                 description "Classification based on inner VLAN tag";
               }
             }
           }
         }
         container dscp {
           description "Differentiated Services code point classifier";
           leaf classifier-name {
             description "Name of classifier to be applied";
             type union {
               type string {
                 pattern "default";
               }
               type string {
                 length "1 .. 64";
               }
             }
           }
         }
         container dscp-ipv6 {
           description "Differentiated Services code point classifier IPv6";
           leaf classifier-name {
             description "Name of classifier to be applied";
             type union {
               type string {
                 pattern "default";
               }
               type string {
                 length "1 .. 64";
               }
             }
           }
         }
       }
       container rewrite-rules {
         description "Rewrite rules applied to outgoing packets";
         uses apply-advanced;
         choice _802_rewrites {
           case case_1 {
             container ieee-802.1 {
               description "IEEE-802.1 rewrite rule";
               leaf rewrite-rule-name {
                 description "Name of rewrite rule to be applied";
                 type union {
                   type string {
                     pattern "default";
                   }
                   type string {
                     length "1 .. 64";
                   }
                 }
               }
               leaf encapsulated {
                 description "Inner ethernet header";
                 type empty;
               }
               leaf vlan-tag {
                 description "One or more VLAN tags to which rewrite rule applies";
                 type enumeration {
                   enum "outer" {
                     description "Rewrite rule applies to outer VLAN tag";
                   }
                   enum "outer-and-inner" {
                     description "Rewrite rule applies to outer and inner VLAN tag";
                   }
                 }
               }
             }
           }
           case case_2 {
             container ieee-802.1ad {
               description "IEEE-802.1ad (DEI) rewrite rule";
               leaf rewrite-rule-name {
                 description "Name of rewrite rule to be applied";
                 type union {
                   type string {
                     pattern "default";
                   }
                   type string {
                     length "1 .. 64";
                   }
                 }
               }
               leaf encapsulated {
                 description "Inner ethernet header";
                 type empty;
               }
               leaf vlan-tag {
                 description "One or more VLAN tags to which rewrite rule applies";
                 type enumeration {
                   enum "outer" {
                     description "Rewrite rule applies to outer VLAN tag";
                   }
                   enum "outer-and-inner" {
                     description "Rewrite rule applies to outer and inner VLAN tag";
                   }
                 }
               }
             }
           }
         }
       }
       container policy-map {
         description "Policy-map describing the packet marking rule";
         leaf policy-map-name {
           description "Name of Policy-map to be applied";
           type string;
         }
       }
       container forwarding-class {
         description "Forwarding class set to injected packets on this instances";
         uses apply-advanced;
       }
     }
     container rewrite-rules {
       description "Write code point value of outgoing packets";
       uses apply-advanced;
       list dscp {
         key name;
         ordered-by user;
         description "Differentiated Services code point rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
             }
           }
         }
       }
       list dscp-ipv6 {
         key name;
         ordered-by user;
         description "Differentiated Services code point rewrite rule IPv6";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
             }
           }
         }
       }
       list exp {
         key name;
         ordered-by user;
         description "MPLS EXP rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
             }
           }
         }
       }
       list ieee-802.1 {
         key name;
         ordered-by user;
         description "IEEE-802.1 rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
             }
           }
         }
       }
       list inet-precedence {
         key name;
         ordered-by user;
         description "IPv4 precedence rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
             }
           }
         }
       }
       list frame-relay-de {
         key name;
         ordered-by user;
         description "Frame relay discard eligible bit rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
             }
           }
         }
       }
       list ieee-802.1ad {
         key name;
         ordered-by user;
         description "IEEE-802.1ad (DEI) rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
             }
           }
         }
       }
       list inet6-precedence {
         key name;
         ordered-by user;
         description "IPv6 precedence rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
             }
           }
         }
       }
     }
     container fabric {
       description "Define CoS parameters of switch fabric";
       uses apply-advanced;
       container scheduler-map {
         description "Mapping of fabric traffic to packet schedulers";
         uses apply-advanced;
         list priority {
           key name;
           description "Fabric traffic priority";
           leaf name {
             type enumeration {
               enum "low" {
                 description "Low priority fabric traffic";
               }
               enum "high" {
                 description "High priority fabric traffic";
               }
             }
           }
           leaf scheduler {
             description "Scheduler name";
             type string {
               length "1 .. 64";
             }
           }
         }
       }
     }
     list scheduler-maps {
       key name;
       description "Mapping of forwarding classes to packet schedulers";
       leaf name {
         description "Scheduler map name";
         type string {
           length "1 .. 64";
         }
       }
       uses apply-advanced;
       list forwarding-class {
         key name;
         description "Forwarding class name to map to scheduler";
         leaf name {
           description "Forwarding class name";
           type string {
             length "1 .. 64";
           }
         }
         leaf scheduler {
           description "Scheduler name";
           type string {
             length "1 .. 64";
           }
         }
       }
     }
     list fragmentation-maps {
       key name;
       description "Mapping of forwarding class to fragmentation options";
       leaf name {
         description "Fragmentation map name";
         type string {
           length "1 .. 64";
         }
       }
       uses apply-advanced;
       list forwarding-class {
         key name;
         description "Forwarding class name to map to fragmentation options";
         leaf name {
           description "Forwarding class name";
           type string {
             length "1 .. 64";
           }
         }
         uses apply-advanced;
         choice fragmentation-control {
           case case_1 {
             leaf fragment-threshold {
               description "Fragmentation threshold";
               units "bytes";
               type union {
                 type string {
                   pattern "<.*>|$.*";
                 }
                 type uint16 {
                   range "64 .. 9192";
                 }
               }
             }
           }
           case case_2 {
             leaf no-fragmentation {
               description "Don't allow fragmentation";
               type empty;
             }
           }
         }
         leaf multilink-class {
           description "Multilink-Class assigned to the forwarding class";
           type union {
             type string {
               pattern "<.*>|$.*";
             }
             type uint16 {
               range "0 .. 7";
             }
           }
         }
         leaf drop-timeout {
           description "Drop timeout";
           units "milliseconds";
           type union {
             type string {
               pattern "<.*>|$.*";
             }
             type uint16 {
               range "0 .. 2000";
             }
           }
         }
       }
     }
     container options {
       description "Configure class-of-service optional parameters";
       uses apply-advanced;
       leaf hierarchical-scheduler-disable {
         description "Enable or disable HQoS scheduler mode";
         type empty;
       }
     }
     list schedulers {
       key name;
       description "Packet schedulers";
       leaf name {
         description "Scheduler name";
         type string {
           length "1 .. 64";
         }
       }
       uses apply-advanced;
       container transmit-rate {
         description "Transmit rate";
         uses apply-advanced;
         choice transmit_rate_choice {
           case case_1 {
             leaf rate {
               description "Transmit rate as rate";
               units "bits per second";
               type string;
             }
           }
           case case_2 {
             leaf percent {
               description "Transmit rate as percentage";
               type union {
                 type string {
                   pattern "<.*>|$.*";
                 }
                 type uint32 {
                   range "1 .. 100";
                 }
               }
             }
           }
           case case_3 {
             container remainder {
               presence "enable remainder";
               description "Remainder available";
               uses apply-advanced;
               leaf percent {
                 default "0";
                 type union {
                   type string {
                     pattern "<.*>|$.*";
                   }
                   type uint32 {
                     range "0 .. 100";
                   }
                 }
               }
             }
           }
         }
         choice rate_limit_choice {
           case case_1 {
             leaf exact {
               description "Enforce exact transmit rate";
               type empty;
             }
           }
           case case_2 {
             leaf rate-limit {
               description "Enforce rate limit that uses policer";
               type empty;
             }
           }
         }
       }
       container excess-rate {
         description "Excess bandwidth sharing proportion";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container shaping-rate {
         description "Shaping rate";
         choice shaping_rate_choice {
           case case_1 {
             leaf rate {
               description "Shaping rate as an absolute rate";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container buffer-size {
         description "Queue transmission buffer size";
         uses apply-advanced;
         choice buffer_size_choice {
           case case_1 {
             leaf percent {
               description "Buffer size as a percentage";
               type union {
                 type string {
                   pattern "<.*>|$.*";
                 }
                 type uint32 {
                   range "0 .. 100";
                 }
               }
             }
           }
           case case_2 {
             container remainder {
               presence "enable remainder";
               description "Remainder of buffer size available";
               uses apply-advanced;
               leaf percent {
                 default "0";
                 type union {
                   type string {
                     pattern "<.*>|$.*";
                   }
                   type uint32 {
                     range "0 .. 100";
                   }
                 }
               }
             }
           }
           case case_3 {
             leaf shared {
               description "Shared buffer allocation";
               type empty;
             }
           }
           case case_4 {
             leaf temporal {
               description "Buffer size as temporal value";
               units "microseconds";
               type string;
             }
           }
         }
         choice buffer_limit {
           case case_1 {
             leaf exact {
               description "Enforce exact buffer size";
               type empty;
             }
           }
         }
         container buffer-partition {
           presence "enable buffer-partition";
           description "Partition buffer size among multicast and unicast";
           uses apply-advanced;
           container multicast {
             presence "enable multicast";
             description "Specify multicast fraction of reserved buffer";
             uses apply-advanced;
             leaf percent {
               default "50";
               type union {
                 type string {
                   pattern "<.*>|$.*";
                 }
                 type uint32 {
                   range "0 .. 100";
                 }
               }
             }
           }
         }
       }
       container shared-buffer {
         description "Queue transmission shared-buffer";
         uses apply-advanced;
         container maximum {
           presence "enable maximum";
           description "Control the amount of shared buffer a given queue can consume";
           uses apply-advanced;
           leaf percent {
             description "Maximum shared buffer size as a percentage";
             default "0";
             type union {
               type string {
                 pattern "<.*>|$.*";
               }
               type uint32 {
                 range "0 .. 100";
               }
             }
           }
           container multicast {
             presence "enable multicast";
             description "Control the amount of shared buffer mcast pkts consume";
             uses apply-advanced;
             leaf percent {
               description "Maximum shared buffer size as a percentage";
               default "0";
               type union {
                 type string {
                   pattern "<.*>|$.*";
                 }
                 type uint32 {
                   range "0 .. 100";
                 }
               }
             }
           }
         }
       }
       leaf priority {
         description "Scheduling priority";
         type string {
           length "1 .. 64";
         }
       }
       leaf excess-priority {
         description "Priority in the excess region";
         type string {
           length "1 .. 64";
         }
       }
       list drop-profile-map {
         key "loss-priority protocol";
         description "Assign drop profile to a loss priority and protocol";
         leaf loss-priority {
           description "Loss priority value";
           type enumeration {
             enum "low" {
               description "Loss priority low";
             }
             enum "high" {
               description "Loss priority high";
             }
             enum "medium-low" {
               description "Loss priority medium-low";
             }
             enum "medium-high" {
               description "Loss priority medium-high";
             }
             enum "any" {
               description "Ignore loss priority when assigning drop profile";
             }
           }
         }
         leaf protocol {
           description "Protocol type";
           type enumeration {
             enum "tcp" {
               description "TCP protocol only";
             }
             enum "non-tcp" {
               description "Non-TCP protocols only";
             }
             enum "any" {
               description "Ignore protocol type when assigning drop profile";
             }
           }
         }
         leaf drop-profile {
           description "Name of drop profile to apply";
           type string {
             length "1 .. 64";
           }
         }
       }
       leaf explicit-congestion-notification {
         description "Enable or Disable Explicit Congestion Notification";
         type empty;
       }
       leaf ecn-rtlog-rate-limit {
         description "Rate-limit for ECN security logs";
         units "logs per second";
         type union {
           type string {
             pattern "<.*>|$.*";
           }
           type uint32 {
             range "1 .. 65535";
           }
         }
       }
       container ecn-enhanced {
         description "Configure enhanced explicit congestion notification parameters";
         uses apply-advanced;
         leaf no-pfc-assist {
           description "Enable or disable PFC assist for explicit congestion notification";
           type empty;
         }
         leaf head-marking {
           description "Enable or disable Head Marking for explicit congestion notification";
           type empty;
         }
       }
       container drop-profile-map-set {
         presence "enable drop-profile-map-set";
         description "System drop profile";
         uses apply-advanced;
         leaf profile-name {
           description "Drop Profile Name";
           type string {
             length "1 .. 64";
           }
         }
         leaf profile-type {
           type enumeration {
             enum "drop" {
               description "Set drop type";
             }
             enum "mark" {
               description "Set ECN marking";
             }
           }
         }
       }
       leaf adjust-percent {
         description "Percent of a bandwidth adjustment applied to a queue";
         units "percent";
         type union {
           type string {
             pattern "<.*>|$.*";
           }
           type uint32 {
             range "0 .. 100";
           }
         }
       }
       leaf adjust-minimum {
         description "Minimum shaping-rate when adjusted";
         units "bits per second";
         type string;
       }
       leaf queue-monitoring {
         description "Enable queue depth monitoring";
         type empty;
       }
       leaf buffer-dynamic-threshold {
         description "Threshold for maximum buffer share for a queue at egress buffer-partition";
         type union {
           type string {
             pattern "<.*>|$.*";
           }
           type uint32 {
             range "0 .. 10";
           }
         }
       }
     }
     list adjustment-control-profiles {
       key name;
       description "Adjustment control profiles";
       leaf name {
         description "Adjustment control profile name";
         type string {
           length "1 .. 64";
         }
       }
       uses apply-advanced;
       list application {
         key name;
         description "Applications that can perform adjustments";
         leaf name {
           description "Applications that can perform adjustments";
           type enumeration {
             enum "ancp" {
               description "Access Node Configuration Protocol";
             }
             enum "radius-coa" {
               description "RADIUS Change of Authorization";
             }
             enum "pppoe-tags" {
               description "Point to Point Protocol over Ethernet IA Tags";
             }
             enum "dhcp-tags" {
               description "Dynamic Host Configuration Protocol Tags";
             }
           }
         }
         leaf priority {
           description "Priority for the application; 1 is the highest";
           type union {
             type string {
               pattern "<.*>|$.*";
             }
             type uint32 {
               range "1 .. 10";
             }
           }
         }
         leaf algorithm {
           description "Adjustment algorithm for the application";
           type enumeration {
             enum "adjust-less" {
               description "Adjust if less than the configured value";
             }
             enum "adjust-less-or-equal" {
               description "Adjust if <= the configured value";
             }
             enum "adjust-greater" {
               description "Adjust if greater than the configured value";
             }
             enum "adjust-greater-or-equal" {
               description "Adjust if >= the configured value";
             }
             enum "adjust-always" {
               description "Adjust unconditionally";
             }
             enum "adjust-never" {
               description "Do not perform adjustments";
             }
           }
         }
       }
     }
     container traceoptions {
       description "Trace options for class-of-service process";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         description "Tracing parameters";
         leaf name {
           type enumeration {
             enum "init" {
               description "Trace initialization events";
             }
             enum "show" {
               description "Trace show command servicing";
             }
             enum "route-socket" {
               description "Trace route-socket events";
             }
             enum "parse" {
               description "Trace parser processing";
             }
             enum "process" {
               description "Trace configuration processing";
             }
             enum "util" {
               description "Trace utilities";
             }
             enum "restart" {
               description "Trace restart processing";
             }
             enum "snmp" {
               description "Trace SNMP-related processing";
             }
             enum "hardware-database" {
               description "Trace chassis hardware database related processing";
             }
             enum "asynch" {
               description "Trace asynchronous configuration processing";
             }
             enum "dynamic" {
               description "Trace dynamic CoS functions";
             }
             enum "cos-adjustment" {
               description "Trace CoS rate adjustments";
             }
             enum "performance-monitor" {
               description "Trace performance monitor counters";
             }
             enum "chassis-scheduler" {
               description "Trace chassis stream scheduler processing";
             }
             enum "cn-util" {
               description "Trace utilities for congestion-notification";
             }
             enum "snmp-timeouts" {
               description "Trace SNMP COSD kernel timeouts";
             }
             enum "all" {
               description "Trace everything";
             }
             enum "feature-capability" {
               description "Trace feature capability";
             }
             enum "application" {
               description "Trace Junos application programming";
             }
             enum "jvision" {
               description "Cos Junos Jvision traces";
             }
           }
         }
       }
     }
     container multi-destination {
       description "Multicast class of service";
       uses apply-advanced;
       leaf scheduler-map {
         description "Scheduler map for multi destination";
         type string {
           length "1 .. 64";
         }
       }
       container family {
         description "Family Inet/Inet6/Ethernet";
         uses apply-advanced;
         container ethernet {
           description "Ethernet switching options";
           uses apply-advanced;
           leaf broadcast {
             description "Forwarding class to be applied to broadcast";
             type string {
               length "1 .. 64";
             }
           }
         }
         container inet {
           description "IP Multicast";
           uses apply-advanced;
           container classifier {
             description "Classifier applied to ip-multicast";
             uses apply-advanced;
             container dscp {
               description "Differentiated Services code point classifier";
               leaf classifier-name {
                 description "Name of classifier to be applied";
                 type string {
                   length "1 .. 64";
                 }
               }
             }
             container inet-precedence {
               description "IPv4 precedence classifier";
               leaf classifier-name {
                 description "Name of classifier to be applied";
                 type string {
                   length "1 .. 64";
                 }
               }
             }
           }
         }
         container inet6 {
           description "IPv6 Multicast";
           uses apply-advanced;
           container classifier {
             description "Classifier applied to ipv6-multicast";
             uses apply-advanced;
             container dscp-ipv6 {
               description "Differentiated Services code point classifier";
               leaf classifier-name {
                 description "Name of classifier to be applied";
                 type string {
                   length "1 .. 64";
                 }
               }
             }
           }
         }
       }
       container classifiers {
         description "Classifier applied to multicast traffic";
         uses apply-advanced;
         container ieee-802.1 {
           description "IEEE-802.1 classifier";
           leaf classifier-name {
             description "Name of classifier to be applied";
             type string {
               length "1 .. 64";
             }
           }
         }
         container dscp {
           description "Differentiated services code point classifier";
           leaf classifier-name {
             description "Name of classifier to be applied";
             type string {
               length "1 .. 64";
             }
           }
         }
         container dscp-ipv6 {
           description "Differentiated services code point classifier IPv6";
           leaf classifier-name {
             description "Name of classifier to be applied";
             type string {
               length "1 .. 64";
             }
           }
         }
         container inet-precedence {
           description "IPv4 precedence classifier";
           leaf classifier-name {
             description "Name of classifier to be applied";
             type string {
               length "1 .. 64";
             }
           }
         }
       }
       leaf forwarding-class {
         description "Forwarding class assigned to incoming Multi-destination packets";
         type string {
         }
       }
     }
     container application-traffic-control {
       presence "enable application-traffic-control";
       description "Application classifier configuration";
       uses apply-advanced;
       container traceoptions {
         description "Trace options for application classifier";
         uses appqos-traceoptions-type;
       }
       list rate-limiters {
         key name;
         ordered-by user;
         description "Configure application-traffic-control rate limiters";
         leaf name {
           description "Application classifier rate-limiter name";
           type string {
             length "1 .. 63";
           }
         }
         uses apply-advanced;
         leaf bandwidth-limit {
           description "Bandwidth limit";
           units "kbps";
           type union {
             type string {
               pattern "<.*>|$.*";
             }
             type uint32 {
               range "64 .. 10485760";
             }
           }
         }
         leaf burst-size-limit {
           description "Burst size limit (default with bandwidth-limit and no larger than 6400 * bandwidth)";
           units "bytes";
           type union {
             type string {
               pattern "<.*>|$.*";
             }
             type uint32 {
               range "1 .. 1342177280";
             }
           }
         }
       }
       list rule-sets {
         key name;
         ordered-by user;
         description "Configure application-traffic-control rule-sets";
         leaf name {
           description "Application classifier rule-set name";
           type string {
             length "1 .. 63";
           }
         }
         uses apply-advanced;
         list rule {
           key name;
           ordered-by user;
           description "Rule";
           uses appqos_rule_type;
         }
       }
     }
     container forwarding-policy {
       description "Class-of-service forwarding policy";
       uses apply-advanced;
       list next-hop-map {
         key name;
         ordered-by user;
         description "Class-of-service next-hop map";
         leaf name {
           description "Name to identify next-hop map";
           type string {
           }
         }
         uses apply-advanced;
         list forwarding-class {
           key name;
           ordered-by user;
           description "Forwarding class from which to map";
           leaf name {
             description "Forwarding class";
             type string {
             }
           }
           uses apply-advanced;
           leaf-list next-hop {
             ordered-by user;
             description "Next-hop identifier to which to map";
             type union {
               type jt:ipaddr-or-interface;
               type string {
                 pattern "<.*>|$.*";
               }
             }
           }
           leaf-list lsp-next-hop {
             ordered-by user;
             description "Regular expression for LSP next hop";
             type string;
           }
           leaf non-lsp-next-hop {
             description "Any non-RSVP LSP next hop";
             type empty;
           }
           leaf non-labelled-next-hop {
             description "Any non-labelled next hop";
             type empty;
           }
           leaf discard {
             description "Discard next hop";
             type empty;
           }
           container transport-class {
             description "Transport class to be mapped with forwarding class";
             uses apply-advanced;
             list color {
               key name;
               ordered-by user;
               description "Transport class color";
               leaf name {
                 description "Transport class color";
                 type union {
                   type uint32;
                   type string {
                     pattern "<.*>|$.*";
                   }
                 }
               }
               uses apply-advanced;
             }
           }
         }
         container forwarding-class-default {
           description "Next Hop For traffic which does not meet any FC in the next-hop-map";
           uses apply-advanced;
           leaf-list next-hop {
             ordered-by user;
             description "Next-hop identifier to which to map";
             type union {
               type jt:ipaddr-or-interface;
               type string {
                 pattern "<.*>|$.*";
               }
             }
           }
           leaf-list lsp-next-hop {
             ordered-by user;
             description "Regular expression for LSP next hop";
             type string;
           }
           leaf non-lsp-next-hop {
             description "Any non-RSVP LSP next hop";
             type empty;
           }
           leaf non-labelled-next-hop {
             description "Any non-labelled next hop";
             type empty;
           }
           leaf discard {
             description "Discard next hop";
             type empty;
           }
           container transport-class {
             description "Transport class to be mapped with forwarding class";
             uses apply-advanced;
             list name {
               key name;
               ordered-by user;
               description "Transport class name";
               leaf name {
                 description "Transport class name";
                 type string;
               }
               uses apply-advanced;
             }
             list color {
               key name;
               ordered-by user;
               description "Transport class color";
               leaf name {
                 description "Transport class color";
                 type union {
                   type uint32;
                   type string {
                     pattern "<.*>|$.*";
                   }
                 }
               }
               uses apply-advanced;
             }
           }
         }
       }
       list class {
         key name;
         ordered-by user;
         description "Class-of-service description";
         leaf name {
           description "Name to identify class of service";
           type string {
           }
         }
         uses apply-advanced;
         container classification-override {
           description "Define classification overrides";
           uses apply-advanced;
           leaf forwarding-class {
             description "Forwarding class name";
             type string {
             }
           }
         }
       }
     }
   }
   grouping appqos-traceoptions-type {
     description "Trace options for application classifier";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events and other information to include in trace output";
       leaf name {
         description "Flag name to include in trace output";
         type enumeration {
           enum "all" {
             description "All events";
           }
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
   }
   grouping appqos_rule_type {
     leaf name {
       description "Rule name";
       type string {
         length "1 .. 63";
       }
     }
     uses apply-advanced;
     container match {
       description "Specify application traffic control rule match-criteria";
       uses apply-advanced;
       leaf application-any {
         description "Any applications";
         type empty;
       }
       leaf application-unknown {
         description "Uknown applcations";
         status deprecated;
         type empty;
       }
       leaf application-known {
         description "Identifiable applications";
         type empty;
       }
       leaf-list application {
         ordered-by user;
         description "Specify application name to match";
         type string {
           length "1 .. 63";
         }
       }
       leaf-list application-group {
         ordered-by user;
         description "Specify application group name to match";
         type string {
           length "1 .. 63";
         }
       }
     }
     container then {
       description "Specify rule action to take when packet match criteria";
       uses apply-advanced;
       leaf forwarding-class {
         description "Forwarding class for outgoing packets";
         type string {
         }
       }
       leaf dscp-code-point {
         description "DSCP code point bitmap or alias";
         type string {
         }
       }
       leaf loss-priority {
         description "Packet loss priority";
         type enumeration {
           enum "low" {
             description "Low loss priority";
           }
           enum "medium-low" {
             description "Medium-low loss priority";
           }
           enum "medium-high" {
             description "Medium-high loss priority";
           }
           enum "high" {
             description "High loss priority";
           }
         }
       }
       container rate-limit {
         description "Apply rate limiters";
         uses apply-advanced;
         leaf client-to-server {
           description "Client-to-server rate limiter";
           type string;
         }
         leaf server-to-client {
           description "Server-to-client rate limiter";
           type string;
         }
         leaf loss-priority-high {
           description "Set Rate limiter's action Loss-Priority to high";
           type empty;
         }
       }
       leaf log {
         description "Log the action";
         type empty;
       }
     }
   }
   grouping cos_interfaces_type {
     description "Physical interface";
     leaf name {
       description "Interface name (or wildcard)";
       type union {
         type jt:interface-device-wildcard;
         type string {
           pattern "<.*>|$.*";
         }
       }
     }
     uses apply-advanced;
     list forwarding-class-set {
       key name;
       description "Map forwarding class sets to output traffic control profile";
       max-elements 4;
       leaf name {
         description "Forwarding class sets name";
         type string {
           length "1 .. 64";
         }
       }
       uses apply-advanced;
       container output-traffic-control-profile {
         description "Output traffic control profile for the interface";
         leaf profile-name {
           description "Name of the output traffic control profile associated with the interface";
           type string {
             length "1 .. 64";
           }
         }
       }
     }
     leaf congestion-notification-profile {
       description "Congestion notification profile for the interface";
       type string {
         length "1 .. 64";
       }
     }
     leaf dedicated-buffer-profile {
       description "Dedicated buffer profile on the ifd";
       type string {
         length "1 .. 64";
       }
     }
     container rewrite-value {
       description "FC interface rewrite value";
       uses apply-advanced;
       container input {
         description "Input direction";
         uses apply-advanced;
         container ieee-802.1 {
           description "IEEE 802.1 code point";
           uses apply-advanced;
           container code-point {
             description "IEEE 802.1 code point";
             uses apply-advanced;
             leaf bits {
               description "IEEE 802.1 code point";
               type string {
               }
             }
           }
         }
       }
     }
     leaf scheduler-map-forwarding-class-set {
       description "Output scheduler map forwarding-class-set  ";
       type string {
       }
     }
     leaf scheduler-map {
       description "Output scheduler map";
       type string {
         length "1 .. 64";
       }
     }
     leaf input-scheduler-map {
       description "Input scheduler map";
       type string {
         length "1 .. 64";
       }
     }
     leaf scheduler-map-chassis {
       description "Scheduler map applied to chassis queues (not PIC queues)";
       type union {
         type string {
           pattern "derived";
         }
         type string {
           length "1 .. 64";
         }
       }
     }
     leaf output-forwarding-class-map {
       description "Output forwarding class map name";
       type string {
         length "1 .. 64";
       }
     }
     container shaping-rate {
       description "Output shaping rate";
       leaf rate {
         description "Shaping rate as an absolute rate";
         units "bits per second";
         type string;
       }
       leaf overhead {
         description "Shaping overhead bytes to be accounted in egress";
         units "bytes";
         type union {
           type string {
             pattern "<.*>|$.*";
           }
           type int32 {
             range "-62 .. 192";
           }
         }
       }
     }
     container input-excess-bandwidth-share {
       description "Input Excess bandwidth sharing policy";
       choice input_excess_bandwidth_share {
         case case_1 {
           leaf proportional {
             description "Maximum Queue Bandwidth";
             units "bits per second";
             type string;
           }
         }
         case case_2 {
           leaf equal {
             description "Equal sharing of excess bandwidth";
             type empty;
           }
         }
       }
     }
     container excess-bandwidth-share {
       description "Output Excess bandwidth sharing policy";
       choice output_excess_bandwidth_share {
         case case_1 {
           leaf proportional {
             description "Maximum Queue Bandwidth";
             units "bits per second";
             type string;
           }
         }
         case case_2 {
           leaf equal {
             description "Equal sharing of excess bandwidth";
             type empty;
           }
         }
       }
     }
     container input-shaping-rate {
       description "Input shaping rate";
       leaf rate {
         description "Input shaping rate as an absolute rate";
         units "bits per second";
         type string;
       }
     }
     container input-traffic-control-profile {
       description "Input traffic control profile";
       leaf profile-name {
         description "Name of the traffic control profile";
         type string {
           length "1 .. 64";
         }
       }
     }
     container input-traffic-control-profile-remaining {
       description "Input traffic control profile for remaining traffic on the ifd";
       leaf profile-name {
         description "Name of the traffic control profile";
         type string {
           length "1 .. 64";
         }
       }
     }
     container output-traffic-control-profile {
       description "Output traffic control profile";
       leaf profile-name {
         description "Name of the traffic control profile";
         type string {
           length "1 .. 64";
         }
       }
     }
     container monitoring-profile {
       description "Monitoring profile";
       leaf profile-name {
         description "Name of the monitoring profile";
         type string {
           length "1 .. 64";
         }
       }
     }
     container output-traffic-control-profile-remaining {
       description "Output traffic control profile for remaining traffic on the ifd";
       leaf profile-name {
         description "Name of the traffic control profile";
         type string {
           length "1 .. 64";
         }
       }
     }
     list slice {
       key name;
       description "Slice to output-traffic-control-profile mapping";
       leaf name {
         description "Name of the network slice";
         type string {
           length "1 .. 64";
         }
       }
       uses apply-advanced;
       leaf output-traffic-control-profile {
         description "Name of the traffic control profile";
         type string {
           length "1 .. 64";
         }
       }
     }
     container member-link-scheduler {
       description "Scheduler parameter model for member link";
       choice model {
         case case_1 {
           leaf scale {
             description "Scale scheduler parameters on aggregate interface";
             type empty;
           }
         }
         case case_2 {
           leaf replicate {
             description "Copy scheduler parameters from aggregate interface";
             type empty;
           }
         }
       }
     }
     container traffic-class-map {
       description "Packet code point to input priority mapping";
       uses apply-advanced;
       container inet-precedence {
         description "IPv4 precedence code point traffic-class-map";
         uses apply-advanced;
         leaf traffic-class-map-name {
           description "Name of traffic-class-map to be applied on IFD";
           type string {
             length "1 .. 64";
           }
         }
       }
       container dscp {
         description "Differentiated services code point traffic-class-map";
         uses apply-advanced;
         leaf traffic-class-map-name {
           description "Name of traffic-class-map to be applied on IFD";
           type string {
             length "1 .. 64";
           }
         }
       }
       container exp {
         description "MPLS experimental code point traffic-class-map";
         uses apply-advanced;
         leaf traffic-class-map-name {
           description "Name of traffic-class-map to be applied on IFD";
           type string {
             length "1 .. 64";
           }
         }
       }
       container ieee-802.1 {
         description "IEEE-802.1 code point traffic-class-map";
         uses apply-advanced;
         leaf traffic-class-map-name {
           description "Name of traffic-class-map to be applied on IFD";
           type string {
             length "1 .. 64";
           }
         }
         leaf vlan-tag {
           description "VLAN tag used for traffic-class-map";
           type enumeration {
             enum "outer" {
               description "Traffic-class-map based on outer VLAN tag";
             }
             enum "inner" {
               description "Traffic-class-map based on inner VLAN tag";
             }
           }
         }
       }
       container ieee-802.1ad {
         description "IEEE-802.1ad (DEI) code point traffic-class-map";
         uses apply-advanced;
         leaf traffic-class-map-name {
           description "Name of traffic-class-map to be applied on IFD";
           type string {
             length "1 .. 64";
           }
         }
         leaf vlan-tag {
           description "VLAN tag used for traffic-class-map";
           type enumeration {
             enum "outer" {
               description "Traffic-class-map based on outer VLAN tag";
             }
             enum "inner" {
               description "Traffic-class-map based on inner VLAN tag";
             }
           }
         }
       }
     }
     container exclude-queue-overhead-bytes {
       presence "enable exclude-queue-overhead-bytes";
       description "Exclude the overhead bytes from the queue statistics";
       uses apply-advanced;
       leaf include-hierarchy {
         description "Perform overhead adjustment on IFD and all children";
         type empty;
       }
     }
     container logical-interface-aggregate-statistics {
       presence "enable logical-interface-aggregate-statistics";
       description "Logical interface aggregate queue statistics";
     }
     list unit {
       key name;
       description "Logical interface unit (or wildcard)";
       leaf name {
         description "Logical unit number";
         type union {
           type string {
             pattern "\*";
           }
           type union {
             type string {
               pattern "<.*>|$.*";
             }
             type uint32 {
               range "0 .. 1073741823";
             }
           }
         }
       }
       uses apply-advanced;
       leaf output-forwarding-class-map {
         description "Output forwarding class map name";
         type string {
           length "1 .. 64";
         }
       }
       leaf forwarding-class {
         description "Forwarding class assigned to incoming packets";
         type string {
           length "1 .. 64";
         }
       }
       leaf virtual-channel-group {
         description "Virtual channel group applied to this logical interface";
         type string {
           length "1 .. 64";
         }
       }
       leaf vc-shared-scheduler {
         description "Virtual channel group shared scheduler indicator";
         type empty;
       }
       leaf scheduler-map {
         description "Output scheduler map";
         type string {
           length "1 .. 64";
         }
       }
       leaf input-scheduler-map {
         description "Input scheduler map";
         type string {
           length "1 .. 64";
         }
       }
       leaf fragmentation-map {
         description "Fragmentation map applied to this logical interface";
         type string {
           length "1 .. 64";
         }
       }
       leaf adaptive-shaper {
         description "Adaptive shaper applied to this logical interface";
         type string {
           length "1 .. 64";
         }
       }
       container shaping-rate {
         presence "enable shaping-rate";
         description "Output shaping rate";
         choice shaping_rate_choice {
           case case_1 {
             leaf rate {
               description "Shaping rate as an absolute rate";
               units "bits per second";
               type string;
             }
           }
           case case_2 {
             leaf percent {
               description "Shaping rate as a percentage";
               type union {
                 type string {
                   pattern "<.*>|$.*";
                 }
                 type uint32 {
                   range "0 .. 100";
                 }
               }
             }
           }
         }
       }
       container input-shaping-rate {
         description "Input shaping rate";
         choice shaping_rate_choice {
           case case_1 {
             leaf rate {
               description "Shaping rate as an absolute rate";
               units "bits per second";
               type string;
             }
           }
           case case_2 {
             leaf percent {
               description "Shaping rate as a percentage";
               type union {
                 type string {
                   pattern "<.*>|$.*";
                 }
                 type uint32 {
                   range "0 .. 100";
                 }
               }
             }
           }
         }
       }
       container input-traffic-control-profile {
         description "Input traffic control profile";
         leaf profile-name {
           description "Name of traffic control profile";
           type string {
             length "1 .. 64";
           }
         }
         leaf shared-instance {
           description "Name of the shared instance";
           type string {
             length "1 .. 64";
           }
         }
       }
       container output-traffic-control-profile {
         description "Output traffic control profile";
         leaf profile-name {
           description "Name of the traffic control profile";
           type string {
             length "1 .. 64";
           }
         }
         leaf shared-instance {
           description "Name of the shared instance";
           type string {
             length "1 .. 64";
           }
         }
       }
       container output-traffic-control-profile-remaining {
         description "Output traffic control profile for remaining traffic on the ifl";
         leaf profile-name {
           description "Name of the traffic control profile";
           type string {
           }
         }
       }
       container report-ingress-shaping-rate {
         description "Report ingress shaping rate";
         choice report_ingress_shaping_rate_choice {
           case case_1 {
             leaf rate {
               description "Ingress shaping rate as an absolute value";
               units "bits per second";
               type string;
             }
           }
         }
       }
       container classifiers {
         description "Classifiers applied to incoming packets";
         uses apply-advanced;
         leaf no-default {
           description "Do not apply default classifiers to this interface";
           type empty;
         }
         list dscp {
           key name;
           description "Differentiated Services code point classifier";
           leaf name {
             description "Name of classifier to be applied";
             type union {
               type string {
                 pattern "default";
               }
               type string {
                 length "1 .. 64";
               }
             }
           }
           uses apply-advanced;
           leaf-list family {
             ordered-by user;
             description "Family for DSCP classifier";
             type string;
           }
         }
         list dscp-ipv6 {
           key name;
           description "Differentiated Services code point classifier IPv6";
           leaf name {
             description "Name of classifier to be applied";
             type union {
               type string {
                 pattern "default";
               }
               type string {
                 length "1 .. 64";
               }
             }
           }
           uses apply-advanced;
           leaf-list family {
             ordered-by user;
             description "Family for DSCP Ipv6 classifier";
             type string;
           }
         }
         container exp {
           description "EXP classifier";
           leaf classifier-name {
             description "Name of classifier to be applied";
             type union {
               type string {
                 pattern "default";
               }
               type string {
                 length "1 .. 64";
               }
             }
           }
         }
         container ieee-802.1 {
           description "IEEE-802.1 classifier";
           leaf classifier-name {
             description "Name of classifier to be applied";
             type union {
               type string {
                 pattern "default";
               }
               type string {
                 length "1 .. 64";
               }
             }
           }
           leaf vlan-tag {
             description "VLAN tag used for classification";
             type enumeration {
               enum "outer" {
                 description "Classification based on outer VLAN tag";
               }
               enum "inner" {
                 description "Classification based on inner VLAN tag";
               }
               enum "transparent" {
                 description "Classification based on hidden VLAN tag";
               }
             }
           }
         }
         container inet-precedence {
           description "IPv4 precedence classifier";
           leaf classifier-name {
             description "Name of classifier to be applied";
             type union {
               type string {
                 pattern "default";
               }
               type string {
                 length "1 .. 64";
               }
             }
           }
         }
         container ieee-802.1ad {
           description "IEEE-802.1ad (DEI) classifier";
           leaf classifier-name {
             description "Name of classifier to be applied";
             type union {
               type string {
                 pattern "default";
               }
               type string {
                 length "1 .. 64";
               }
             }
           }
           leaf vlan-tag {
             description "VLAN tag used for classification";
             type enumeration {
               enum "outer" {
                 description "Classification based on outer VLAN tag";
               }
               enum "inner" {
                 description "Classification based on inner VLAN tag";
               }
             }
           }
         }
       }
       container ingress-rewrite-rules {
         description "Rewrite rules applied to outgoing packets of the ingress interface";
         uses apply-advanced;
         list dscp {
           key name;
           description "Differentiated Services code point rewrite rule";
           leaf name {
             description "Name of rewrite rule to be applied";
             type union {
               type string {
                 pattern "default";
               }
               type string {
                 length "1 .. 64";
               }
             }
           }
         }
         container dscp-ipv6 {
           description "Differentiated Services code point rewrite rule IPv6";
           leaf rewrite-rule-name {
             description "Name of rewrite rule to be applied";
             type union {
               type string {
                 pattern "default";
               }
               type string {
                 length "1 .. 64";
               }
             }
           }
         }
         list inet-precedence {
           key name;
           description "IPv4 precedence rewrite rule";
           leaf name {
             description "Name of rewrite rule to be applied";
             type union {
               type string {
                 pattern "default";
               }
               type string {
                 length "1 .. 64";
               }
             }
           }
         }
       }
       container loss-priority-maps {
         description "Loss priority maps applied to incoming packets";
         uses apply-advanced;
         container frame-relay-de {
           description "Frame Relay discard eligible bit loss priority map";
           leaf lpmap-name {
             description "Name of loss priority map to be applied";
             type union {
               type string {
                 pattern "default";
               }
               type string {
                 length "1 .. 64";
               }
             }
           }
         }
       }
       container monitoring-profile {
         description "Monitoring profile";
         leaf profile-name {
           description "Name of the monitoring profile";
           type string {
             length "1 .. 64";
           }
         }
       }
       container rewrite-rules {
         description "Rewrite rules applied to outgoing packets";
         uses apply-advanced;
         list dscp {
           key name;
           description "Differentiated Services code point rewrite rule";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls" {
                 description "Apply to IPv4 packets entering MPLS tunnel";
               }
               enum "gtp-inet-outer" {
                 description "Apply to outer IP header";
               }
               enum "gtp-inet-both" {
                 description "Apply to both IP header";
               }
               enum "inet-outer" {
                 description "Apply to outer IP header";
               }
               enum "inet-both" {
                 description "Apply to both IP header";
               }
             }
           }
         }
         list dscp-ipv6 {
           key name;
           description "Differentiated Services code point rewrite rule IPv6";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls" {
                 description "Apply to IPv6 packets entering MPLS tunnel";
               }
               enum "gtp-inet-outer" {
                 description "Apply to outer IP header";
               }
               enum "gtp-inet-both" {
                 description "Apply to both IP header";
               }
             }
           }
         }
         list exp {
           key name;
           description "EXP rewrite rule";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls-any" {
                 description "Apply to MPLS packets, write MPLS header only";
               }
               enum "mpls-inet-both" {
                 description "Apply to IPv4 MPLS packets, write MPLS and IPv4 header";
               }
               enum "mpls-inet-both-non-vpn" {
                 description "Apply to IPv4 MPLS packets, write MPLS and IPv4 header for only non VPN traffic";
               }
             }
           }
         }
         container ieee-802.1 {
           description "IEEE-802.1 rewrite rule";
           leaf rewrite-rule-name {
             description "Name of rewrite rule to be applied";
             type union {
               type string {
                 pattern "default";
               }
               type string {
                 length "1 .. 64";
               }
             }
           }
           leaf vlan-tag {
             description "One or more VLAN tags to which rewrite rule applies";
             type enumeration {
               enum "outer" {
                 description "Rewrite rule applies to outer VLAN tag";
               }
               enum "outer-and-inner" {
                 description "Rewrite rule applies to both outer and inner VLAN tags";
               }
             }
           }
         }
         list inet-precedence {
           key name;
           description "IPv4 precedence rewrite rule";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls" {
                 description "Apply to IPv4 packets entering MPLS tunnel";
               }
               enum "gtp-inet-outer" {
                 description "Apply to outer IP header";
               }
               enum "gtp-inet-both" {
                 description "Apply to both IP header";
               }
               enum "inet-outer" {
                 description "Apply to outer IP header";
               }
               enum "inet-both" {
                 description "Apply to both IP header";
               }
             }
           }
         }
         container exp-swap-push-push {
           description "Copy incoming EXP into all swap-push-push labels";
           leaf rewrite-rule-name {
             description "Name of rewrite rule to be applied";
             type enumeration {
               enum "default" {
                 description "Apply default rewrite rule";
               }
             }
           }
         }
         container exp-push-push-push {
           description "Top-label EXP rewrite rule for push-push-push operation";
           leaf rewrite-rule-name {
             description "Name of rewrite rule to be applied";
             type enumeration {
               enum "default" {
                 description "Apply default rewrite rule";
               }
             }
           }
         }
         container frame-relay-de {
           description "Frame relay discard eligible bit rewrite rule";
           leaf rewrite-rule-name {
             description "Name of rewrite rule to be applied";
             type union {
               type string {
                 pattern "default";
               }
               type string {
                 length "1 .. 64";
               }
             }
           }
         }
         container ieee-802.1ad {
           description "IEEE-802.1ad (DEI) rewrite rule";
           uses apply-advanced;
           leaf rewrite-rule-name {
             description "Name of rewrite rule to be applied";
             type union {
               type string {
                 pattern "default";
               }
               type string {
                 length "1 .. 64";
               }
             }
           }
           leaf vlan-tag {
             description "One or more VLAN tags to which rewrite rule applies";
             type enumeration {
               enum "outer" {
                 description "Rewrite rule applies to outer VLAN tag";
               }
               enum "outer-and-inner" {
                 description "Rewrite rule applies to both outer and inner VLAN tags";
               }
             }
           }
         }
         list inet6-precedence {
           key name;
           description "IPv6 precedence rewrite rule";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls" {
                 description "Apply to IPv6 packets entering MPLS tunnel";
               }
             }
           }
         }
       }
       container loss-priority-rewrites {
         description "Loss priority rewrites applied to outgoing packets";
         uses apply-advanced;
         container frame-relay-de {
           description "Frame Relay discard eligible bit loss priority rewrite";
           leaf lprewrite-name {
             description "Name of loss priority rewrite to be applied";
             type union {
               type string {
                 pattern "default";
               }
               type string {
                 length "1 .. 64";
               }
             }
           }
         }
       }
       container translation-table {
         description "Translation tables applied to incoming packets";
         uses apply-advanced;
         container to-inet-precedence-from-inet-precedence {
           description "IPv4 precedence translation table";
           leaf translation-table-name {
             description "Name of translation table to be applied";
             type string {
               length "1 .. 64";
             }
           }
         }
         container to-dscp-from-dscp {
           description "Differentiated Services code point translation table";
           leaf translation-table-name {
             description "Name of translation table to be applied";
             type string {
               length "1 .. 64";
             }
           }
         }
         container to-dscp-ipv6-from-dscp-ipv6 {
           description "Differentiated Services code point IPV6 translation table";
           leaf translation-table-name {
             description "Name of translation table to be applied";
             type string {
               length "1 .. 64";
             }
           }
         }
         container to-exp-from-exp {
           description "EXP translation table";
           leaf translation-table-name {
             description "Name of translation table to be applied";
             type string {
               length "1 .. 64";
             }
           }
         }
       }
       container policy-map {
         description "Policy-map describing the packet marking rule";
         leaf policy-map-name {
           description "Name of Policy-map to be applied";
           type string;
         }
       }
       leaf policy-map-marking {
         description "Enable policy-map on IFL";
         type empty;
       }
     }
     container classifiers {
       description "Classifiers applied to incoming packets";
       uses apply-advanced;
       list dscp {
         key name;
         description "Differentiated Services code point classifier";
         leaf name {
           description "Name of classifier to be applied";
           type union {
             type string {
               pattern "default";
             }
             type string {
               length "1 .. 64";
             }
           }
         }
         uses apply-advanced;
       }
       list dscp-ipv6 {
         key name;
         description "Differentiated Services code point classifier IPv6";
         leaf name {
           description "Name of classifier to be applied";
           type union {
             type string {
               pattern "default";
             }
             type string {
               length "1 .. 64";
             }
           }
         }
         uses apply-advanced;
       }
       container ieee-802.1 {
         description "IEEE-802.1 classifier";
         leaf classifier-name {
           description "Name of classifier to be applied";
           type union {
             type string {
               pattern "default";
             }
             type string {
               length "1 .. 64";
             }
           }
         }
         leaf vlan-tag {
           description "VLAN tag used for classification";
           type enumeration {
             enum "outer" {
               description "Classification based on outer VLAN tag";
             }
             enum "inner" {
               description "Classification based on inner VLAN tag";
             }
           }
         }
       }
       container ieee-802.1ad {
         description "IEEE-802.1ad (DEI) classifier";
         leaf classifier-name {
           description "Name of classifier to be applied";
           type union {
             type string {
               pattern "default";
             }
             type string {
               length "1 .. 64";
             }
           }
         }
         leaf vlan-tag {
           description "VLAN tag used for classification";
           type enumeration {
             enum "outer" {
               description "Classification based on outer VLAN tag";
             }
             enum "inner" {
               description "Classification based on inner VLAN tag";
             }
           }
         }
       }
       container inet-precedence {
         description "IPv4 precedence classifier";
         leaf classifier-name {
           description "Name of classifier to be applied";
           type union {
             type string {
               pattern "default";
             }
             type string {
               length "1 .. 64";
             }
           }
         }
       }
     }
     leaf forwarding-class {
       description "Forwarding class assigned to incoming packets";
       type string {
       }
     }
     container rewrite-rules {
       description "Rewrite rules applied to outgoing packets";
       uses apply-advanced;
       list dscp {
         key name;
         description "Differentiated Services code point rewrite rule";
         leaf name {
           description "Name of rewrite rule to be applied";
           type union {
             type string {
               pattern "default";
             }
             type string {
               length "1 .. 64";
             }
           }
         }
       }
       list dscp-ipv6 {
         key name;
         description "Differentiated Services code point rewrite rule IPv6";
         leaf name {
           description "Name of rewrite rule to be applied";
           type union {
             type string {
               pattern "default";
             }
             type string {
               length "1 .. 64";
             }
           }
         }
       }
       container ieee-802.1 {
         description "IEEE-802.1 rewrite rule";
         leaf rewrite-rule-name {
           description "Name of rewrite rule to be applied";
           type union {
             type string {
               pattern "default";
             }
             type string {
               length "1 .. 64";
             }
           }
         }
       }
       container ieee-802.1ad {
         description "IEEE-802.1ad (DEI) rewrite rule";
         uses apply-advanced;
         leaf rewrite-rule-name {
           description "Name of rewrite rule to be applied";
           type union {
             type string {
               pattern "default";
             }
             type string {
               length "1 .. 64";
             }
           }
         }
         leaf vlan-tag {
           description "One or more VLAN tags to which rewrite rule applies";
           type enumeration {
             enum "outer" {
               description "Rewrite rule applies to outer VLAN tag";
             }
           }
         }
       }
       list inet-precedence {
         key name;
         description "IPv4 precedence rewrite rule";
         leaf name {
           description "Name of rewrite rule to be applied";
           type union {
             type string {
               pattern "default";
             }
             type string {
               length "1 .. 64";
             }
           }
         }
       }
     }
     container multi-destination {
       description "Multi-destination class of service";
       uses apply-advanced;
       container classifiers {
         description "Classifier applied to multi-destination traffic";
         uses apply-advanced;
         container ieee-802.1 {
           description "IEEE-802.1P classifier";
           leaf classifier-name {
             description "Name of classifier to be applied";
             type string {
               length "1 .. 64";
             }
           }
         }
         container dscp {
           description "Differentiated services code point classifier";
           leaf classifier-name {
             description "Name of classifier to be applied";
             type string {
               length "1 .. 64";
             }
           }
         }
         container dscp-ipv6 {
           description "Differentiated services code point classifier IPv6";
           leaf classifier-name {
             description "Name of classifier to be applied";
             type string {
               length "1 .. 64";
             }
           }
         }
         container inet-precedence {
           description "IPv4 precedence classifier";
           leaf classifier-name {
             description "Name of classifier to be applied";
             type string {
               length "1 .. 64";
             }
           }
         }
       }
       leaf forwarding-class {
         description "Forwarding class assigned to incoming Multi-destination packets";
         type string {
         }
       }
     }
   }
   grouping juniper-dynamic-profile-varset-object {
     leaf name {
       description "Profile varset associated with the profile";
       type string {
         length "1 .. 80";
       }
     }
     uses apply-advanced;
     leaf junos-mep-id {
       description "Dynamic variable to substitute 'mep' value in the profile";
       type union {
         type string {
           pattern "<.*>|$.*";
         }
         type uint32 {
           range "1 .. 8191";
         }
       }
     }
     leaf junos-md-level {
       description "Dynamic variable to substitute 'level' value in the profile";
       type union {
         type string {
           pattern "<.*>|$.*";
         }
         type uint32 {
           range "0 .. 7";
         }
       }
     }
     leaf junos-remote-mep-id {
       description "Dynamic variable to substitute 'remote-mep' value in the profile";
       type union {
         type string {
           pattern "<.*>|$.*";
         }
         type uint32 {
           range "1 .. 8191";
         }
       }
     }
     leaf junos-md-name {
       description "Dynamic variable to substitute 'maintenance-domain' in profile";
       type string;
     }
     leaf junos-ma-name {
       description "Dynamic variable to substitute 'maintenance-association' in profile";
       type string {
         length "1 .. 32";
       }
     }
     leaf junos-loss-threshold {
       description "Dynamic variable to substitute 'loss-threshold' in profile";
       type union {
         type string {
           pattern "<.*>|$.*";
         }
         type uint32 {
           range "3 .. 256";
         }
       }
     }
     leaf junos-md-name-format {
       description "Dynamic variable to substitute 'name-format' in profile";
       type enumeration {
         enum "none" {
           description "No format specified";
         }
         enum "dns" {
           description "Character string similar to Domain Name System name";
         }
         enum "mac+2oct" {
           description "MAC address with 2 octet integer (xx:xx:xx:xx:xx:xx.Y format)";
         }
         enum "character-string" {
           description "Character string";
         }
       }
     }
     leaf junos-ma-name-format {
       description "Dynamic variable to substitute 'short-name-format' in profile";
       type enumeration {
         enum "2octet" {
           description "An integer in the range 0..65535";
         }
         enum "rfc-2685-vpn-id" {
           description "VPN identifier that complies with RFC 2685";
         }
         enum "vlan" {
           description "Primary VLAN identifier";
         }
         enum "character-string" {
           description "Character string";
         }
         enum "icc" {
           description "ITU Carrier Code";
         }
       }
     }
     leaf junos-ccm-interval {
       description "Dynamic variable to substitute 'interval' in profile";
       type enumeration {
         enum "10ms" {
         }
         enum "100ms" {
         }
         enum "1s" {
         }
         enum "10s" {
         }
         enum "1m" {
         }
         enum "10m" {
         }
       }
     }
     leaf junos-action-profile {
       description "Dynamic variable to substitute 'action-profile' in profile";
       type string;
     }
     leaf junos-layer2-output-policer {
       description "Dynamic variable to substitute 'layer2 output-policer'";
       type string;
     }
   }
   grouping juniper-dynamic-variable-object {
     leaf name {
       description "Name of variable";
       type string {
       }
     }
     uses apply-advanced;
     leaf equals {
       description "Computable expression of dynamic profile variables";
       type string;
     }
     leaf default-value {
       description "Default value for variable";
       type string;
     }
     leaf mandatory {
       description "Variable must be supplied by external server";
       type empty;
     }
     leaf uid-reference {
       description "Variable that refers to the uid variable";
       type empty;
     }
     leaf uid {
       description "Compute unique Id value for the variable";
       type empty;
     }
   }
   grouping juniper-protocols-pim {
     uses apply-advanced;
     leaf protocol-instance-name {
       description "Name of protocol instance under routing instance";
       type string;
     }
     container family {
       description "Local address family";
       container any {
         presence "enable any";
         description "Default properties for all address families";
         uses apply-advanced;
         leaf disable {
           description "Disable all families";
           type empty;
         }
       }
       container inet {
         presence "enable inet";
         description "IPv4 specific properties";
         uses apply-advanced;
         choice enable-disable {
           case case_1 {
             leaf disable {
               description "Disable PIMv4 on all interfaces";
               type empty;
             }
           }
         }
       }
       container inet6 {
         presence "enable inet6";
         description "IPv6 specific properties";
         uses apply-advanced;
         choice enable-disable {
           case case_1 {
             leaf disable {
               description "Disable PIMv6 on all interfaces";
               type empty;
             }
           }
         }
       }
     }
     choice enable-disable {
       case case_1 {
         leaf disable {
           description "Disable PIM";
           type empty;
         }
       }
     }
     container nonstop-routing {
       description "Configure PIM nonstop-routing attributes";
       uses apply-advanced;
       choice enable-disable {
         case case_1 {
           leaf disable {
             description "Disable non-stop routing for PIM";
             type empty;
           }
         }
       }
     }
     container traceoptions {
       description "Trace options for PIM";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "packets" {
               description "Trace all PIM packets";
             }
             enum "hello" {
               description "Trace hello packets";
             }
             enum "register" {
               description "Trace register/register-stop messages";
             }
             enum "join" {
               description "Trace join/prune/graft/graft-ack messages";
             }
             enum "prune" {
               description "Trace join/prune/graft/graft-ack messages";
             }
             enum "graft" {
               description "Trace join/prune/graft/graft-ack messages";
             }
             enum "bootstrap" {
               description "Trace bootstrap/RP/auto-RP messages";
             }
             enum "rp" {
               description "Trace bootstrap/RP/auto-RP messages";
             }
             enum "autorp" {
               description "Trace bootstrap/RP/auto-RP messages";
             }
             enum "assert" {
               description "Trace assert messages";
             }
             enum "mdt" {
               description "Trace messages related to multicast data tunnels";
             }
             enum "nsr-synchronization" {
               description "Trace NSR synchronization events";
             }
             enum "bidirectional-df-election" {
               description "Trace bidirectional PIM DF election events";
             }
             enum "mofrr" {
               description "Trace Multicast only Fast Re-Route messages";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses pim_filter_obj;
         }
       }
     }
     container dense-groups {
       description "Dense mode groups for sparse-dense mode";
       uses apply-advanced;
       leaf dynamic-reject {
         description "Reject dynamic autorp negative dense-mode prefixes learnt from network";
         type empty;
       }
       list pim-dense-group-type {
         key name;
         ordered-by user;
         leaf name {
           description "Group address or range to forward in dense mode";
           type jt:ipprefix;
         }
         choice dense-group-flags {
           case case_1 {
             leaf reject {
               description "Do not include prefix as dense mode; force sparse mode";
               type empty;
             }
           }
           case case_2 {
             leaf announce {
               description "Advertise as negative prefix in auto-RP announce messages";
               type empty;
             }
           }
         }
       }
     }
     leaf vpn-tunnel-source {
       description "Source address for the provider space mGRE tunnel";
       status deprecated;
       type jt:ipv4addr;
     }
     leaf vpn-group-address {
       description "Group address for the VPN in provider space";
       status deprecated;
       type jt:ipv4addr;
     }
     leaf-list tunnel-devices {
       ordered-by user;
       description "Tunnel devices to be used for creating mt interfaces";
       type union {
         type jt:interface-device;
         type string {
           pattern "<.*>|$.*";
         }
       }
     }
     container rpf-selection {
       description "Select RPF neighbor";
       uses apply-advanced;
       list group {
         key name;
         ordered-by user;
         description "IP prefix of multicast group";
         leaf name {
           description "IP prefix of group";
           type jt:ipprefix;
         }
         uses apply-advanced;
         container wildcard-source {
           presence "enable wildcard-source";
           description "Select RPF for (*,g) and unspecified (s,g) joins";
           uses apply-advanced;
           leaf next-hop {
             description "Next-hop address";
             type jt:ipaddr;
           }
         }
         list source {
           key name;
           ordered-by user;
           description "IP prefix of one or more multicast sources";
           leaf name {
             description "IP prefix of source";
             type jt:ipprefix;
           }
           uses apply-advanced;
           leaf next-hop {
             description "Next-hop address";
             type jt:ipaddr;
           }
         }
       }
       list prefix-list {
         key name;
         ordered-by user;
         description "Multicast group prefix list";
         leaf name {
           description "Name of prefix list to match against";
           type string;
         }
         uses apply-advanced;
         container wildcard-source {
           presence "enable wildcard-source";
           description "Select RPF for (*,g) and unspecified (s,g) joins";
           uses apply-advanced;
           leaf next-hop {
             description "Next-hop address";
             type jt:ipaddr;
           }
         }
         list source {
           key name;
           ordered-by user;
           description "IP prefix of one or more multicast sources";
           leaf name {
             description "IP prefix of source";
             type jt:ipprefix;
           }
           uses apply-advanced;
           leaf next-hop {
             description "Next-hop address";
             type jt:ipaddr;
           }
         }
       }
     }
     container mvpn {
       presence "enable mvpn";
       description "PIM MVPN control-plane options";
       uses apply-advanced;
       container autodiscovery {
         description "PE router autodiscovery options for SSM MDTs";
         status deprecated;
         uses apply-advanced;
         leaf inet-mdt {
           description "MDT-SAFI PE autodiscovery for SSM MDTs";
           type empty;
         }
       }
       container family {
         description "PIM MVPN address family";
         uses apply-advanced;
         container inet {
           description "IPv4 PIM MVPN specific properties";
           uses apply-advanced;
           leaf rosen-mvpn {
             status deprecated;
             type empty;
           }
           leaf ngen-mvpn {
             status deprecated;
             type empty;
           }
           container autodiscovery {
             description "PE router autodiscovery options for SSM MDTs";
             uses apply-advanced;
             leaf inet-mdt {
               description "MDT-SAFI PE autodiscovery for SSM MDTs";
               type empty;
             }
           }
           leaf disable {
             description "Disable family IPv4";
             type empty;
           }
         }
         container inet6 {
           description "IPv6 PIM MVPN specific properties";
           uses apply-advanced;
           leaf rosen-mvpn {
             status deprecated;
             type empty;
           }
           leaf ngen-mvpn {
             status deprecated;
             type empty;
           }
           container autodiscovery {
             description "PE router autodiscovery options for SSM MDTs";
             uses apply-advanced;
             leaf inet-mdt {
               description "MDT-SAFI PE autodiscovery for SSM MDTs";
               type empty;
             }
           }
           leaf disable {
             description "Disable family IPv6";
             type empty;
           }
         }
       }
     }
     container rib-group {
       description "Routing table group";
       uses rib_group_type;
     }
     leaf-list import {
       ordered-by user;
       description "PIM sparse import join policy";
       type jt:policy-algebra;
     }
     leaf-list export {
       ordered-by user;
       description "PIM sparse export join policy";
       type jt:policy-algebra;
     }
     container mldp-inband-signalling {
       presence "enable mldp-inband-signalling";
       uses apply-advanced;
       leaf-list policy {
         ordered-by user;
         description "PIM MLDP join translation filter policy";
         type jt:policy-algebra;
       }
     }
     container rpf-vector {
       description "RPF vector TLV";
       uses apply-advanced;
       leaf-list policy {
         ordered-by user;
         description "RPF vector TLV include policy";
         type jt:policy-algebra;
       }
     }
     leaf assert-timeout {
       description "Set assert timeout";
       default "180";
       type union {
         type string {
           pattern "<.*>|$.*";
         }
         type uint32 {
           range "5 .. 210";
         }
       }
     }
     leaf assert-robust-count {
       description "Number of assert messages an assert winner sends in one cycle";
       default "2";
       type union {
         type string {
           pattern "<.*>|$.*";
         }
         type uint32 {
           range "1 .. 5";
         }
       }
     }
     leaf join-prune-timeout {
       description "Set join/prune timeout";
       default "210";
       type union {
         type string {
           pattern "<.*>|$.*";
         }
         type uint32 {
           range "210 .. 420";
         }
       }
     }
     container spt-threshold {
       description "Set shortest-path-tree threshold policy";
       uses apply-advanced;
       leaf-list infinity {
         ordered-by user;
         description "Apply policy to always remain on shared tree";
         type jt:policy-algebra;
       }
     }
     container sglimit {
       description "Set limit on number of (S,G) states ";
       uses apply-advanced;
       list family {
         key name;
         ordered-by user;
         description "Protocol family";
         leaf name {
           type enumeration {
             enum "inet" {
               description "IPv4 family";
             }
             enum "inet6" {
               description "IPv6 family";
             }
           }
         }
         uses apply-advanced;
         leaf maximum {
           description "Maximum limit above which additional entries are not accepted";
           type union {
             type string {
               pattern "<.*>|$.*";
             }
             type uint32 {
               range "1 .. 65535";
             }
           }
         }
         leaf threshold {
           description "Percentage of maximum at which to start generating warnings";
           type union {
             type string {
               pattern "<.*>|$.*";
             }
             type uint32 {
               range "1 .. 100";
             }
           }
         }
         leaf log-interval {
           description "Time between successive log messages";
           type union {
             type string {
               pattern "<.*>|$.*";
             }
             type uint32 {
               range "1 .. 65535";
             }
           }
         }
       }
       leaf maximum {
         description "Maximum limit above which additional entries are not accepted";
         type union {
           type string {
             pattern "<.*>|$.*";
           }
           type uint32 {
             range "1 .. 65535";
           }
         }
       }
       leaf threshold {
         description "Percentage of maximum at which to start generating warnings";
         type union {
           type string {
             pattern "<.*>|$.*";
           }
           type uint32 {
             range "1 .. 100";
           }
         }
       }
       leaf log-interval {
         description "Time between successive log messages";
         type union {
           type string {
             pattern "<.*>|$.*";
           }
           type uint32 {
             range "1 .. 65535";
           }
         }
       }
     }
     container rp {
       description "Router's rendezvous point properties";
       uses apply-advanced;
       leaf bootstrap-priority {
         description "Eligibility to be the bootstrap router (IPv4 only)";
         type union {
           type string {
             pattern "<.*>|$.*";
           }
           type uint32 {
             range "0 .. 255";
           }
         }
       }
       leaf-list bootstrap-import {
         ordered-by user;
         description "Bootstrap import policy (IPv4 only)";
         type jt:policy-algebra;
       }
       leaf-list bootstrap-export {
         ordered-by user;
         description "Bootstrap export policy (IPv4 only)";
         type jt:policy-algebra;
       }
       container bootstrap {
         description "Bootstrap properties";
         uses apply-advanced;
         container family {
           description "Bootstrap address family";
           container inet {
             description "IPv4 bootstrap properties";
             uses pim_bootstrap_options_type;
           }
           container inet6 {
             description "IPv6 bootstrap properties";
             uses pim_bootstrap_options_type;
           }
         }
       }
       container register-limit {
         description "Set limit on incoming registers that create (S,G) state";
         uses apply-advanced;
         list family {
           key name;
           ordered-by user;
           description "Protocol family";
           leaf name {
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             type union {
               type string {
                 pattern "<.*>|$.*";
               }
               type uint32 {
                 range "1 .. 100";
               }
             }
           }
           leaf log-interval {
             description "Time between successive log messages";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           type union {
             type string {
               pattern "<.*>|$.*";
             }
             type uint32 {
               range "1 .. 100";
             }
           }
         }
         leaf log-interval {
           description "Time between successive log messages";
           type union {
             type string {
               pattern "<.*>|$.*";
             }
             type uint32 {
               range "1 .. 65535";
             }
           }
         }
       }
       container group-rp-mapping {
         description "Group-rp-mapping";
         uses apply-advanced;
         list family {
           key name;
           ordered-by user;
           description "Protocol family";
           leaf name {
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             type union {
               type string {
                 pattern "<.*>|$.*";
               }
               type uint32 {
                 range "1 .. 100";
               }
             }
           }
           leaf log-interval {
             description "Time between successive log messages";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           type union {
             type string {
               pattern "<.*>|$.*";
             }
             type uint32 {
               range "1 .. 100";
             }
           }
         }
         leaf log-interval {
           description "Time between successive log messages";
           type union {
             type string {
               pattern "<.*>|$.*";
             }
             type uint32 {
               range "1 .. 65535";
             }
           }
         }
       }
       leaf-list rp-register-policy {
         ordered-by user;
         description "RP policy applied to incoming register messages";
         type jt:policy-algebra;
       }
       leaf-list dr-register-policy {
         ordered-by user;
         description "DR policy applied to outgoing register messages";
         type jt:policy-algebra;
       }
       container local {
         description "Router's local RP properties";
         uses apply-advanced;
         leaf address {
           description "Local RP address (IPv4 only)";
           type jt:ipv4addr;
         }
         choice enable-disable {
           case case_1 {
             leaf disable {
               description "Disable this RP (IPv4 only)";
               type empty;
             }
           }
         }
         leaf priority {
           description "Router's priority for becoming an RP (IPv4 only)";
           type union {
             type string {
               pattern "<.*>|$.*";
             }
             type uint32 {
               range "0 .. 255";
             }
           }
         }
         leaf hold-time {
           description "How long neighbor considers this router to be up, in seconds (IPv4 only)";
           type union {
             type string {
               pattern "<.*>|$.*";
             }
             type uint32 {
               range "1 .. 65535";
             }
           }
         }
         list group-ranges {
           key name;
           ordered-by user;
           description "Group address range for which this router can be an RP (IPv4 only)";
           leaf name {
             type jt:ipv4prefix;
           }
           uses apply-advanced;
         }
         leaf override {
           description "Static RP mapping will take precedence over dynamic";
           type empty;
         }
         container family {
           description "Local RP address family";
           container inet {
             description "IPv4 local RP properties";
             uses apply-advanced;
             leaf address {
               description "Local RP address";
               type jt:ipv4addr;
             }
             choice enable-disable {
               case case_1 {
                 leaf disable {
                   description "Disable this RP";
                   type empty;
                 }
               }
             }
             leaf priority {
               description "Router's priority for becoming an RP";
               type union {
                 type string {
                   pattern "<.*>|$.*";
                 }
                 type uint32 {
                   range "0 .. 255";
                 }
               }
             }
             leaf hold-time {
               description "How long neighbor considers this router to be up, in seconds";
               type union {
                 type string {
                   pattern "<.*>|$.*";
                 }
                 type uint32 {
                   range "1 .. 65535";
                 }
               }
             }
             list group-ranges {
               key name;
               ordered-by user;
               description "Group address range for which this router can be an RP";
               leaf name {
                 type jt:ipv4prefix;
               }
               uses apply-advanced;
             }
             leaf override {
               description "Static RP mapping will take precedence over dynamic";
               type empty;
             }
             container anycast-pim {
               description "Attributes for IPv4 anycast PIM";
               uses apply-advanced;
               container rp-set {
                 description "Rendezvous points belonging to anycast RP set";
                 uses apply-advanced;
                 list address {
                   key name;
                   ordered-by user;
                   description "IPv4 address of one or more remote anycast RPs";
                   leaf name {
                     description "IPv4 address of remote anycast RP";
                     type jt:ipaddr;
                   }
                   uses apply-advanced;
                   leaf forward-msdp-sa {
                     description "Forward SAs learned from MSDP to this RP";
                     type empty;
                   }
                 }
               }
               leaf local-address {
                 description "Local address for replicating register messages to other RPs";
                 type jt:ipaddr;
               }
             }
           }
           container inet6 {
             description "IPv6 local RP properties";
             uses apply-advanced;
             leaf address {
               description "Local RP address";
               type jt:ipv6addr;
             }
             choice enable-disable {
               case case_1 {
                 leaf disable {
                   description "Disable this RP";
                   type empty;
                 }
               }
             }
             leaf priority {
               description "Router's priority for becoming an RP";
               type union {
                 type string {
                   pattern "<.*>|$.*";
                 }
                 type uint32 {
                   range "0 .. 255";
                 }
               }
             }
             leaf hold-time {
               description "How long neighbor considers this router to be up, in seconds";
               type union {
                 type string {
                   pattern "<.*>|$.*";
                 }
                 type uint32 {
                   range "1 .. 65535";
                 }
               }
             }
             list group-ranges {
               key name;
               ordered-by user;
               description "Group address range for which this router can be an RP";
               leaf name {
                 type jt:ipv6prefix;
               }
               uses apply-advanced;
             }
             leaf override {
               description "Static RP mapping will take precedence over dynamic";
               type empty;
             }
             container anycast-pim {
               description "Attributes for IPv6 anycast PIM";
               uses apply-advanced;
               container rp-set {
                 description "Rendezvous points belonging to anycast RP set";
                 uses apply-advanced;
                 list address {
                   key name;
                   ordered-by user;
                   description "IPv6 address of one or more remote anycast RPs";
                   leaf name {
                     description "IPv6 address of remote anycast RP";
                     type jt:ipv6addr;
                   }
                   uses apply-advanced;
                 }
               }
               leaf local-address {
                 description "Local address for replicating register messages to other RPs";
                 type jt:ipv6addr;
               }
             }
           }
         }
       }
       container embedded-rp {
         presence "enable embedded-rp";
         description "Set embedded-RP mode (IPv6 only)";
         uses apply-advanced;
         list group-ranges {
           key name;
           ordered-by user;
           description "Group address range of RP";
           uses pim_rp_group_range_type;
         }
         leaf maximum-rps {
           description "Maximum number of embedded RPs";
           default "100";
           type union {
             type string {
               pattern "<.*>|$.*";
             }
             type uint32 {
               range "1 .. 500";
             }
           }
         }
       }
       container auto-rp {
         description "Set auto-RP mode (IPv4 only)";
         uses apply-advanced;
         choice autorp-mode {
           case case_1 {
             leaf discovery {
               description "Listen for auto-RP discovery messages";
               type empty;
             }
           }
           case case_2 {
             leaf announce {
               description "Transmit auto-RP announcement messages";
               type empty;
             }
           }
           case case_3 {
             leaf mapping {
               description "Transmit auto-RP mapping messages";
               type empty;
             }
           }
         }
         choice mapping-agent-election-choice {
           leaf mapping-agent-election {
             description "Consider higher-addressed mapping agents as authoritative";
             type empty;
           }
           leaf no-mapping-agent-election {
             description "Don't consider higher-addressed mapping agents as authoritative";
             type empty;
           }
         }
       }
       container static {
         description "Configure static PIM RPs";
         uses apply-advanced;
         list address {
           key name;
           ordered-by user;
           description "RP address";
           leaf name {
             description "IP address of RP";
             type jt:ipaddr;
           }
           uses apply-advanced;
           leaf version {
             description "PIM version of RP";
             status deprecated;
             type union {
               type string {
                 pattern "<.*>|$.*";
               }
               type uint32 {
                 range "1 .. 2";
               }
             }
           }
           list group-ranges {
             key name;
             ordered-by user;
             description "Group address range of RP";
             uses pim_rp_group_range_type;
           }
           leaf override {
             description "Static RP mapping will take precedence over dynamic";
             type empty;
           }
         }
       }
       container bidirectional {
         description "Configure PIM bidirectional-mode RPs";
         uses apply-advanced;
         list address {
           key name;
           ordered-by user;
           description "RP address";
           leaf name {
             description "IP address of RP";
             type jt:ipaddr;
           }
           uses apply-advanced;
           leaf priority {
             description "Router's priority for becoming an RP";
             type union {
               type string {
                 pattern "<.*>|$.*";
               }
               type uint32 {
                 range "0 .. 255";
               }
             }
           }
           leaf hold-time {
             description "How long neighbor considers this router to be up";
             units "seconds";
             type union {
               type string {
                 pattern "<.*>|$.*";
               }
               type uint32 {
                 range "1 .. 65535";
               }
             }
           }
           list group-ranges {
             key name;
             ordered-by user;
             description "Group address range of RP";
             uses pim_rp_group_range_type;
           }
         }
       }
       leaf register-probe-time {
         description "Register probe time";
         default "5";
         units "seconds";
         type union {
           type string {
             pattern "<.*>|$.*";
           }
           type uint32 {
             range "5 .. 60";
           }
         }
       }
     }
     leaf passive {
       description "Configure PIM protocol in passive mode";
       type empty;
     }
     list interface {
       key name;
       ordered-by user;
       description "PIM interface options";
       leaf name {
         description "Interface name";
         type string;
       }
       uses apply-advanced;
       container family {
         description "Local address family";
         container any {
           presence "enable any";
           description "Default properties for all families";
           uses apply-advanced;
           leaf disable {
             description "Disable all families";
             type empty;
           }
         }
         container inet {
           presence "enable inet";
           description "IPv4 specific properties";
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 9000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
           leaf mcae-mac-synchronize {
             description "Mclag mac synchronization";
             type empty;
           }
           choice enable-disable {
             case case_1 {
               leaf disable {
                 description "Disable PIMv4 on this interface";
                 type empty;
               }
             }
           }
         }
         container inet6 {
           presence "enable inet6";
           description "IPv6 specific properties";
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 9000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
           choice enable-disable {
             case case_1 {
               leaf disable {
                 description "Disable PIMv6 on this interface";
                 type empty;
               }
             }
           }
         }
       }
       choice enable-disable {
         case case_1 {
           leaf disable {
             description "Disable PIM on this interface";
             type empty;
           }
         }
       }
       container bidirectional {
         description "PIM bidirectional mode properties";
         uses apply-advanced;
         container df-election {
           description "Bidir designated forwarder properties";
           uses apply-advanced;
           leaf robustness-count {
             description "Election robustness count";
             type union {
               type string {
                 pattern "<.*>|$.*";
               }
               type uint32 {
                 range "1 .. 10";
               }
             }
           }
           leaf offer-period {
             description "Election offer message period";
             units "milliseconds";
             type union {
               type string {
                 pattern "<.*>|$.*";
               }
               type uint32 {
                 range "100 .. 10000";
               }
             }
           }
           leaf backoff-period {
             description "Election backoff period";
             units "milliseconds";
             type union {
               type string {
                 pattern "<.*>|$.*";
               }
               type uint32 {
                 range "100 .. 65535";
               }
             }
           }
         }
       }
       leaf mode {
         description "Mode of interface";
         type enumeration {
           enum "dense" {
             description "Dense mode";
           }
           enum "sparse" {
             description "Sparse mode";
           }
           enum "sparse-dense" {
             description "Sparse-dense mode";
           }
           enum "bidirectional-sparse" {
             description "Bidirectional-sparse mode";
           }
           enum "bidirectional-sparse-dense" {
             description "Bidirectional-sparse-dense mode";
           }
         }
       }
       leaf priority {
         description "Hello option DR priority";
         type union {
           type string {
             pattern "<.*>|$.*";
           }
           type uint32 {
             range "0 .. 4294967295";
           }
         }
       }
       container stickydr {
         presence "enable stickydr";
         description "Make DR sticky";
         uses apply-advanced;
       }
       container multiple-triggered-joins {
         presence "enable multiple-triggered-joins";
         description "Send multiple pim triggered joins in quick intervals";
         uses apply-advanced;
         leaf count {
           description "Set number of triggered joins to be sent";
           default "2";
           type union {
             type string {
               pattern "<.*>|$.*";
             }
             type uint16 {
               range "2 .. 15";
             }
           }
         }
         leaf interval {
           description "Set interval between multiple triggered joins to be sent in milliseconds";
           default "100";
           type union {
             type string {
               pattern "<.*>|$.*";
             }
             type uint16 {
               range "100 .. 1000";
             }
           }
         }
       }
       leaf version {
         description "Force PIM version";
         status deprecated;
         type union {
           type string {
             pattern "<.*>|$.*";
           }
           type uint32 {
             range "1 .. 2";
           }
         }
       }
       leaf hello-interval {
         description "Hello interval";
         units "seconds";
         type union {
           type string {
             pattern "<.*>|$.*";
           }
           type uint32 {
             range "0 .. 255";
           }
         }
       }
       leaf-list neighbor-policy {
         ordered-by user;
         description "PIM neighbor policy applied to incoming hello messages";
         type jt:policy-algebra;
       }
       leaf-list accept-join-always-from {
         ordered-by user;
         description "Accept pim join/prune messages based on the policy configured";
         type jt:policy-algebra;
       }
       leaf accept-remote-source {
         description "Accept traffic from remote source";
         type empty;
       }
       container dual-dr {
         presence "enable dual-dr";
         description "Configure PIM Dual DR";
         uses apply-advanced;
         leaf enhanced {
           description "Enable enhanced PIM Dual DR";
           type empty;
         }
       }
       leaf distributed-dr {
         description "PIM Distributed DR";
         type empty;
       }
       leaf reset-tracking-bit {
         description "Clear tracking-bit in PIM Hello LAN Prune Delay Option";
         type empty;
       }
       leaf propagation-delay {
         description "Propagation delay value";
         default "500";
         units "milliseconds";
         type union {
           type string {
             pattern "<.*>|$.*";
           }
           type uint32 {
             range "250 .. 2000";
           }
         }
       }
       leaf override-interval {
         description "Override interval value";
         default "2000";
         units "milliseconds";
         type union {
           type string {
             pattern "<.*>|$.*";
           }
           type uint32 {
             range "500 .. 6000";
           }
         }
       }
       leaf disable-packet-register {
         description "Disable PIM packet registers on first hop router";
         type empty;
       }
       container bfd-liveness-detection {
         description "Bidirectional Forwarding Detection options (ipv4 only)";
         status deprecated;
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 9000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
     }
     container mdt {
       description "Configure multicast data tunnel parameters";
       status deprecated;
       uses apply-advanced;
       container threshold {
         description "Threshold for creation of multicast tunnels";
         uses apply-advanced;
         list group {
           key name;
           ordered-by user;
           description "IP prefix of multicast group";
           leaf name {
             description "IP prefix of group";
             type jt:ipprefix;
           }
           uses apply-advanced;
           list source {
             key name;
             ordered-by user;
             description "IP prefix of one or more multicast sources ";
             leaf name {
               description "IP prefix of source";
               type jt:ipprefix;
             }
             uses apply-advanced;
             leaf rate {
               description "Data threshold to create new tunnel";
               units "kilobits";
               type union {
                 type string {
                   pattern "<.*>|$.*";
                 }
                 type uint32 {
                   range "10 .. 1000000";
                 }
               }
             }
           }
         }
       }
       leaf data-mdt-reuse {
         description "Allow multiple customer streams to be transmitted over one data tunnel ";
         type empty;
       }
       leaf tunnel-limit {
         description "Maximum multicast data tunnels";
         type union {
           type string {
             pattern "<.*>|$.*";
           }
           type uint32 {
             range "0 .. 8192";
           }
         }
       }
       leaf group-range {
         description "Group address range for multicast data tunnels";
         type jt:ipprefix;
       }
     }
     container graceful-restart {
       description "Configure graceful restart attributes";
       uses apply-advanced;
       choice enable-disable {
         case case_1 {
           leaf disable {
             description "Disable PIM graceful restart capability";
             type empty;
           }
         }
       }
       leaf restart-duration {
         description "Maximum time for graceful restart to finish (seconds)";
         units "seconds";
         type union {
           type string {
             pattern "<.*>|$.*";
           }
           type uint32 {
             range "30 .. 300";
           }
         }
       }
       leaf no-bidirectional-mode {
         description "Disable PIM graceful restart for bidirectional mode";
         type empty;
       }
       leaf restart-complete-duration {
         description "Maximum time for graceful restart to complete (seconds)";
         units "seconds";
         type union {
           type string {
             pattern "<.*>|$.*";
           }
           type uint32 {
             range "5 .. 300";
           }
         }
       }
     }
     container join-load-balance {
       presence "enable join-load-balance";
       description "Configure PIM join load balancing";
       uses apply-advanced;
       leaf automatic {
         description "Enable automatic PIM join load balancing";
         type empty;
       }
     }
     leaf standby-path-creation-delay {
       description "Amount of time to wait before creating standby path";
       units "seconds";
       type union {
         type string {
           pattern "<.*>|$.*";
         }
         type uint32 {
           range "1 .. 300";
         }
       }
     }
     leaf idle-standby-path-switchover-delay {
       description "Amount of time to wait before switching over to idle standby path";
       units "seconds";
       type union {
         type string {
           pattern "<.*>|$.*";
         }
         type uint32 {
           range "1 .. 300";
         }
       }
     }
     leaf dr-election-on-p2p {
       description "Enable DR election on Point-to-Point Interfaces";
       type empty;
     }
     leaf no-wildcard-register-stop {
       description "Disable sending of wildcard register stop message";
       type empty;
     }
     leaf nexthop-hold-time {
       description "Nexthop hold time in milliseconds";
       units "milliseconds";
       type union {
         type string {
           pattern "<.*>|$.*";
         }
         type uint32 {
           range "1 .. 1000";
         }
       }
     }
     leaf mpls-internet-multicast {
       description "Enable support for Internet Multicast over MPLS";
       type empty;
     }
     container join-make-before-break {
       description "Enable PIM Join Make-Before-Break during RPF neighbor change";
       uses apply-advanced;
       choice enable-disable {
         case case_1 {
           leaf disable {
             description "Disable Make-Before-Break for PIM RPF neighbor change";
             type empty;
           }
         }
       }
     }
     leaf reset-tracking-bit {
       description "Clear tracking-bit in PIM Hello LAN Prune Delay Option";
       type empty;
     }
     leaf propagation-delay {
       description "Propagation delay value";
       default "500";
       units "milliseconds";
       type union {
         type string {
           pattern "<.*>|$.*";
         }
         type uint32 {
           range "250 .. 2000";
         }
       }
     }
     leaf override-interval {
       description "Override interval value";
       default "2000";
       units "milliseconds";
       type union {
         type string {
           pattern "<.*>|$.*";
         }
         type uint32 {
           range "500 .. 6000";
         }
       }
     }
     leaf disable-packet-register {
       description "Disable PIM packet registers on first hop router";
       type empty;
     }
     container default-vpn-source {
       presence "enable default-vpn-source";
       description "Let all VRFs use master loopback address for mt interfaces";
       uses apply-advanced;
       leaf interface-name {
         description "Master loopback interface name";
         type union {
           type jt:interface-unit;
           type string {
             pattern "<.*>|$.*";
           }
         }
       }
     }
   }
   grouping keepalives_type {
     uses apply-advanced;
     leaf interval {
       description "Keepalive period";
       units "seconds";
       type union {
         type string {
           pattern "<.*>|$.*";
         }
         type uint16 {
           range "1 .. 32767";
         }
       }
     }
     leaf up-count {
       description "Keepalive received to bring link up";
       type union {
         type string {
           pattern "<.*>|$.*";
         }
         type uint16 {
           range "1 .. 255";
         }
       }
     }
     leaf down-count {
       description "Keepalive missed to bring link down";
       type union {
         type string {
           pattern "<.*>|$.*";
         }
         type uint16 {
           range "1 .. 255";
         }
       }
     }
   }
   grouping log-object {
     description "Configure security log";
     uses apply-advanced;
     list exclude {
       key name;
       ordered-by user;
       description "List of security log criteria to exclude from the audit log";
       status deprecated;
       leaf name {
         description "Exclude criteria name";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         description "List of security log criteria to exclude from the audit log";
         leaf name {
           description "Exclude criteria name";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         type union {
           type uint32;
           type string {
             pattern "<.*>|$.*";
           }
         }
       }
     }
     list host {
       key name;
       ordered-by user;
       max-elements 10;
       leaf name {
         description "Name of host to notify";
         type string {
         }
       }
       uses apply-advanced;
       list contents {
         key name;
         leaf name {
           description "Facility type";
           type enumeration {
             enum "services" {
               description "Adaptive Services PIC";
             }
           }
         }
         choice level {
           case case_1 {
             leaf any {
               description "All levels";
               type empty;
             }
           }
           case case_2 {
             leaf emergency {
               description "Panic conditions";
               type empty;
             }
           }
           case case_3 {
             leaf alert {
               description "Conditions that should be corrected immediately";
               type empty;
             }
           }
           case case_4 {
             leaf critical {
               description "Critical conditions";
               type empty;
             }
           }
           case case_5 {
             leaf error {
               description "Error conditions";
               type empty;
             }
           }
           case case_6 {
             leaf warning {
               description "Warning messages";
               type empty;
             }
           }
           case case_7 {
             leaf notice {
               description "Conditions that should be handled specially";
               type empty;
             }
           }
           case case_8 {
             leaf info {
               description "Informational messages";
               type empty;
             }
           }
           case case_9 {
             leaf none {
               description "No messages";
               type empty;
             }
           }
         }
       }
       leaf facility-override {
         description "Alternate facility for logging to remote host";
         type enumeration {
           enum "authorization" {
             description "Authorization system";
           }
           enum "daemon" {
             description "Various system processes";
           }
           enum "ftp" {
             description "FTP process";
           }
           enum "kernel" {
             description "Kernel";
           }
           enum "user" {
             description "User processes";
           }
           enum "local0" {
             description "Local logging option number 0";
           }
           enum "local1" {
             description "Local logging option number 1";
           }
           enum "local2" {
             description "Local logging option number 2";
           }
           enum "local3" {
             description "Local logging option number 3";
           }
           enum "local4" {
             description "Local logging option number 4";
           }
           enum "local5" {
             description "Local logging option number 5";
           }
           enum "local6" {
             description "Local logging option number 6";
           }
           enum "local7" {
             description "Local logging option number 7";
           }
         }
       }
       leaf log-prefix {
         description "Prefix for all logging to this host";
         type string {
         }
       }
       leaf port {
         description "UDP port for syslogd on the host";
         type union {
           type string {
             pattern "<.*>|$.*";
           }
           type uint16 {
             range "1 .. 65535";
           }
         }
       }
       container class {
         description "Syslog messages classes";
         uses apply-advanced;
         container session-logs {
           presence "enable session-logs";
           description "Allow syslog messages for session events";
           uses apply-advanced;
           container open {
             presence "enable open";
             description "Allow syslog messages for session open events";
           }
           container close {
             presence "enable close";
             description "Allow syslog messages for session close events";
           }
         }
         container packet-logs {
           presence "enable packet-logs";
           description "Allow syslog messages for packet related events";
         }
         container stateful-firewall-logs {
           presence "enable stateful-firewall-logs";
           description "Allow syslog messages for stateful firewall events";
         }
         container alg-logs {
           presence "enable alg-logs";
           description "Allow syslog messages for ALG events";
         }
         container nat-logs {
           presence "enable nat-logs";
           description "Allow syslog messages for NAT events";
           uses apply-advanced;
           container deterministic-nat-configuration-log {
             presence "enable deterministic-nat-configuration-log";
             description "Allow syslog messages for Determinisitic NAT config events";
           }
         }
         container ids-logs {
           presence "enable ids-logs";
           description "Allow syslog messages for IDS events";
         }
         container pcp-logs {
           presence "enable pcp-logs";
           description "PCP logs";
           container map {
             presence "enable map";
             description "Allow syslog messages for PCP";
           }
           container debug {
             presence "enable debug";
             description "Allow PCP debug syslogs";
           }
         }
         container ha-logs {
           description "Stateful high availability logs";
           uses apply-advanced;
           container open-synchronized {
             presence "enable open-synchronized";
             description "Allow syslog message for session open events";
           }
           container close-synchronized {
             presence "enable close-synchronized";
             description "Allow syslog message for session close events";
           }
         }
         container urlf-logs {
           presence "enable urlf-logs";
           description "Allow syslog messages for URLF events";
         }
       }
       leaf source-address {
         description "Use specified address as source address";
         type jt:ipv4addr;
       }
       container tcp-log {
         presence "enable tcp-log";
         description "Enable tcp log for this service-set";
         uses apply-advanced;
         leaf source-address {
           description "Source address for tcp logging";
           type jt:ipaddr;
         }
         leaf vrf-name {
           description "Routing instance name for tcp logging";
           type string;
         }
         leaf ssl-profile {
           description "SSL profile name for tcp logging";
           type string {
             length "1 .. 63";
           }
         }
       }
     }
     leaf message-rate-limit {
       description "Maximum syslog messages per second allowed from this interface. Applies per member if set at aggregate level";
       units "messages per second";
       type union {
         type string {
           pattern "<.*>|$.*";
         }
         type uint32 {
           range "0 .. 2147483647";
         }
       }
     }
     leaf disable {
       description "Disable security logging for the device";
       type empty;
     }
     leaf utc-timestamp {
       description "Use UTC time for security log timestamps";
       type empty;
     }
     leaf mode {
       description "Controls how security logs are processed and exported";
       type enumeration {
         enum "stream" {
           description "Process security logs directly in the forwarding plane";
         }
         enum "event" {
           description "Process security logs in the control plane";
         }
         enum "stream-event" {
           description "Process security logs in both forwarding plane and control plane";
         }
       }
     }
     leaf event-rate {
       description "Control plane event rate";
       units "logs per second";
       type union {
         type string {
           pattern "<.*>|$.*";
         }
         type uint32 {
           range "0 .. 1500";
         }
       }
     }
     leaf format {
       description "Set security log format for the device";
       type enumeration {
         enum "syslog" {
           description "Traditional syslog";
         }
         enum "sd-syslog" {
           description "Structured syslog";
         }
         enum "binary" {
           description "Binary log";
         }
         enum "protobuf" {
           description "Protobuf log";
         }
       }
     }
     leaf escape {
       description "Enable escape defined by RFC5424 for the sd and binary format logs";
       type empty;
     }
     container time-format {
       description "Configure year or millisecond for syslog";
       uses time-format-object;
     }
     leaf rate-cap {
       description "Data plane event rate";
       units "logs per second";
       type union {
         type string {
           pattern "<.*>|$.*";
         }
         type uint32 {
           range "0 .. 5000";
         }
       }
     }
     leaf max-database-record {
       description "Maximum records in database";
       default "0";
       type union {
         type string {
           pattern "<.*>|$.*";
         }
         type uint32;
       }
     }
     container report {
       presence "enable report";
       description "Set security log report settings";
       uses apply-advanced;
       leaf database-capacity {
         description "Total capacity of all the tables in database";
         type enumeration {
           enum "max-db-size" {
             description "Increases database size to 216M entries";
           }
         }
       }
       container logs-per-table {
         presence "enable logs-per-table";
         description "Log number per table in database";
         uses apply-advanced;
         leaf session-all {
           description "Log number of session";
           type union {
             type string {
               pattern "<.*>|$.*";
             }
             type uint32;
           }
         }
         leaf screen {
           description "Log number of screen";
           type union {
             type string {
               pattern "<.*>|$.*";
             }
             type uint32;
           }
         }
         leaf idp {
           description "Log number of idp";
           type union {
             type string {
               pattern "<.*>|$.*";
             }
             type uint32;
           }
         }
         leaf utm {
           description "Log number of utm";
           type union {
             type string {
               pattern "<.*>|$.*";
             }
             type uint32;
           }
         }
         leaf ipsec-vpn {
           description "Log number of ipsec-vpn";
           type union {
             type string {
               pattern "<.*>|$.*";
             }
             type uint32;
           }
         }
         leaf sky {
           description "Log number of sky";
           type union {
             type string {
               pattern "<.*>|$.*";
             }
             type uint32;
           }
         }
       }
       container log-share-per-table {
         presence "enable log-share-per-table";
         description "Log share(%) per table in database";
         uses apply-advanced;
         leaf session-all {
           description "Percentage share for session table (%)";
           type union {
             type string {
               pattern "<.*>|$.*";
             }
             type uint32;
           }
         }
         leaf screen {
           description "Percentage share for screen table (%)";
           type union {
             type string {
               pattern "<.*>|$.*";
             }
             type uint32;
           }
         }
         leaf idp {
           description "Percentage share for idp table (%)";
           type union {
             type string {
               pattern "<.*>|$.*";
             }
             type uint32;
           }
         }
         leaf utm {
           description "Percentage share for utm table (%)";
           type union {
             type string {
               pattern "<.*>|$.*";
             }
             type uint32;
           }
         }
         leaf ipsec-vpn {
           description "Percentage share for ipsec-vpn table (%)";
           type union {
             type string {
               pattern "<.*>|$.*";
             }
             type uint32;
           }
         }
         leaf atp {
           description "Percentage share for atp table (%)";
           type union {
             type string {
               pattern "<.*>|$.*";
             }
             type uint32;
           }
         }
         leaf dns {
           description "Percentage share for dns table (%)";
           type union {
             type string {
               pattern "<.*>|$.*";
             }
             type uint32;
           }
         }
       }
       leaf table-lifetime {
         description "Table lifetime day(s)";
         default "90";
         type union {
           type string {
             pattern "<.*>|$.*";
           }
           type uint32 {
             range "0 .. 365";
           }
         }
       }
       leaf table-mode {
         description "Report table mode";
         type enumeration {
           enum "dense" {
             description "Enable dense mode(B-Tree)";
           }
           enum "disabl-dense" {
             description "Disable dense mode(Moving to R-Tree)";
           }
         }
       }
       container database-filter {
         presence "enable database-filter";
         description "Check the logs whether should be inserted into database";
         uses apply-advanced;
         list event-category {
           key name;
           ordered-by user;
           description "Filter by event-category";
           leaf name {
             description "Name";
             type enumeration {
               enum "session" {
                 description "Session log";
               }
               enum "screen" {
                 description "Screen log";
               }
               enum "idp" {
                 description "IDP log";
               }
               enum "webfilter" {
                 description "Webfilter log";
               }
               enum "content-filter" {
                 description "Content-filter log";
               }
               enum "anti-virus" {
                 description "Antivirus log";
               }
               enum "anti-spam" {
                 description "Anti-spam log";
               }
               enum "ipsec" {
                 description "IPsec VPN log";
               }
               enum "sky" {
                 description "Sky ATP log";
               }
               enum "secintel" {
                 description "Secintel log";
               }
               enum "icap" {
                 description "ICAP log";
               }
               enum "ssl-proxy" {
                 description "SSL proxy log";
               }
               enum "dnsf" {
                 description "DNSF log";
               }
               enum "dns" {
                 description "Dns log";
               }
               enum "session-create" {
                 description "Session create log";
               }
               enum "session-close" {
                 description "Session close log";
               }
               enum "session-deny" {
                 description "Session deny log";
               }
             }
           }
           uses apply-advanced;
         }
         leaf exclude {
           description "Exclude the logs";
           type empty;
         }
       }
     }
     choice source {
       case case_1 {
         leaf source-address {
           description "Source ip address used when exporting security logs";
           type jt:ipaddr;
         }
       }
       case case_2 {
         leaf source-interface {
           description "Source interface used when exporting security logs";
           type union {
             type jt:interface-name;
             type string {
               pattern "<.*>|$.*";
             }
           }
         }
       }
     }
     container transport {
       presence "enable transport";
       description "Set security log transport settings";
       uses apply-advanced;
       leaf tcp-connections {
         description "Set tcp connection number per-stream";
         type union {
           type string {
             pattern "<.*>|$.*";
           }
           type uint32 {
             range "1 .. 5";
           }
         }
       }
       leaf protocol {
         description "Set security log transport protocol for the device";
         type enumeration {
           enum "udp" {
             description "UDP transfer for log";
           }
           enum "tcp" {
             description "TCP transfer for log";
           }
           enum "tls" {
             description "TLS transfer for log";
           }
         }
       }
       leaf tls-profile {
         description "TLS profile";
         type string;
       }
     }
     leaf facility-override {
       description "Alternate facility for logging to remote host";
       type enumeration {
         enum "authorization" {
           description "Authorization system";
         }
         enum "daemon" {
           description "Various system processes";
         }
         enum "ftp" {
           description "FTP process";
         }
         enum "kernel" {
           description "Kernel";
         }
         enum "user" {
           description "User processes";
         }
         enum "local0" {
           description "Local logging option number 0";
         }
         enum "local1" {
           description "Local logging option number 1";
         }
         enum "local2" {
           description "Local logging option number 2";
         }
         enum "local3" {
           description "Local logging option number 3";
         }
         enum "local4" {
           description "Local logging option number 4";
         }
         enum "local5" {
           description "Local logging option number 5";
         }
         enum "local6" {
           description "Local logging option number 6";
         }
         enum "local7" {
           description "Local logging option number 7";
         }
       }
     }
     leaf local-log-tag {
       description "Tag included in logs";
       type string {
       }
     }
     list local-category {
       key name;
       ordered-by user;
       description "Selects the type of events that may be logged locally";
       leaf name {
         type enumeration {
           enum "all" {
             description "All events are logged";
           }
           enum "content-security" {
             description "Content security events are logged";
           }
           enum "fw-auth" {
             description "Fw-auth events are logged";
           }
           enum "screen" {
             description "Screen events are logged";
           }
           enum "alg" {
             description "Alg events are logged";
           }
           enum "nat" {
             description "Nat events are logged";
           }
           enum "flow" {
             description "Flow events are logged";
           }
           enum "sctp" {
             description "Sctp events are logged";
           }
           enum "gtp" {
             description "Gtp events are logged";
           }
           enum "ipsec" {
             description "Ipsec events are logged";
           }
           enum "idp" {
             description "Idp events are logged";
           }
           enum "rtlog" {
             description "Rtlog events are logged";
           }
           enum "pst-ds-lite" {
             description "Pst-ds-lite events are logged";
           }
           enum "appqos" {
             description "Appqos events are logged";
           }
           enum "secintel" {
             description "Secintel events are logged";
           }
           enum "aamw" {
             description "AAMW events are logged";
           }
           enum "sfw" {
             description "Stateful Firewall events are logged";
           }
           enum "session" {
             description "Session open and close events are logged";
           }
           enum "session-open" {
             description "Session open events are logged";
           }
           enum "session-close" {
             description "Session close events are logged";
           }
           enum "urlf" {
             description "URLF events are logged";
           }
           enum "ha" {
             description "Stateful High-Availability open and close events are logged";
           }
           enum "ha-open" {
             description "Stateful High-Availability open events are logged";
           }
           enum "ha-close" {
             description "Stateful High-Availability close events are logged";
           }
           enum "pcp" {
             description "PCP logs";
           }
           enum "dnsf" {
             description "DNSF";
           }
           enum "dns" {
             description "DNS";
           }
         }
       }
       uses apply-advanced;
     }
     leaf root-streaming {
       description "Logs will be streamed from the Root LSYS";
       type empty;
     }
     list stream {
       key name;
       ordered-by user;
       description "Set security log stream settings";
       max-elements 8;
       leaf name {
         description "Name of security log stream";
         type string {
           length "1 .. 63";
         }
       }
       uses apply-advanced;
       leaf severity {
         description "Severity threshold for security logs";
         type enumeration {
           enum "emergency" {
             description "Conditions that cause security functions to stop";
           }
           enum "alert" {
             description "Conditions that require immediate attention";
           }
           enum "critical" {
             description "Critical conditions";
           }
           enum "error" {
             description "General error conditions";
           }
           enum "warning" {
             description "General warning conditions";
           }
           enum "notice" {
             description "Non-error conditions that are of interest";
           }
           enum "info" {
             description "Information about normal security operations";
           }
           enum "debug" {
             description "Information normally used in debugging";
           }
         }
       }
       leaf format {
         description "Specify the log stream format";
         type enumeration {
           enum "syslog" {
             description "Traditional syslog";
           }
           enum "sd-syslog" {
             description "Structured syslog";
           }
           enum "welf" {
             description "Web Trends Extended Log Format";
           }
           enum "binary" {
             description "Binary log";
           }
           enum "protobuf" {
             description "Protobuf log";
           }
         }
       }
       list category {
         key name;
         ordered-by user;
         description "Selects the type of events that may be logged";
         leaf name {
           type enumeration {
             enum "all" {
               description "All events are logged";
             }
             enum "content-security" {
               description "Content security events are logged";
             }
             enum "fw-auth" {
               description "Fw-auth events are logged";
             }
             enum "screen" {
               description "Screen events are logged";
             }
             enum "alg" {
               description "Alg events are logged";
             }
             enum "nat" {
               description "Nat events are logged";
             }
             enum "flow" {
               description "Flow events are logged";
             }
             enum "sctp" {
               description "Sctp events are logged";
             }
             enum "gtp" {
               description "Gtp events are logged";
             }
             enum "ipsec" {
               description "Ipsec events are logged";
             }
             enum "idp" {
               description "Idp events are logged";
             }
             enum "rtlog" {
               description "Rtlog events are logged";
             }
             enum "pst-ds-lite" {
               description "Pst-ds-lite events are logged";
             }
             enum "appqos" {
               description "Appqos events are logged";
             }
             enum "secintel" {
               description "Secintel events are logged";
             }
             enum "aamw" {
               description "AAMW events are logged";
             }
             enum "sfw" {
               description "Stateful Firewall events are logged";
             }
             enum "session" {
               description "Session open and close events are logged";
             }
             enum "session-open" {
               description "Session open events are logged";
             }
             enum "session-close" {
               description "Session close events are logged";
             }
             enum "urlf" {
               description "URLF events are logged";
             }
             enum "ha" {
               description "Stateful High-Availability open and close events are logged";
             }
             enum "ha-open" {
               description "Stateful High-Availability open events are logged";
             }
             enum "ha-close" {
               description "Stateful High-Availability close events are logged";
             }
             enum "pcp" {
               description "PCP logs";
             }
             enum "dnsf" {
               description "DNSF";
             }
             enum "dns" {
               description "DNS";
             }
           }
         }
         uses apply-advanced;
       }
       list filter {
         key name;
         ordered-by user;
         description "Selects the filter to filter the logs to be logged";
         leaf name {
           type enumeration {
             enum "threat-attack" {
               description "Threat-attack security events are logged";
             }
           }
         }
         uses apply-advanced;
       }
       container host {
         description "Destination to send security logs to";
         uses host-object;
       }
       container rate-limit {
         description "Rate-limit for security logs";
         uses apply-advanced;
         leaf rate {
           description "Log rate";
           units "logs per second";
           type union {
             type string {
               pattern "<.*>|$.*";
             }
             type uint32 {
               range "1 .. 65535";
             }
           }
         }
       }
       container file {
         description "Security log file options for logs in local file";
         uses apply-advanced;
         leaf localfilename {
           description "Name of local log file";
           type string {
             length "1 .. 256";
           }
         }
         leaf size {
           description "Maximum size of local log file in megabytes";
           type union {
             type string {
               pattern "<.*>|$.*";
             }
             type uint32;
           }
         }
         leaf rotation {
           description "Maximum number of rotate files";
           default "10";
           type union {
             type string {
               pattern "<.*>|$.*";
             }
             type uint32;
           }
         }
         leaf allow-duplicates {
           description "To disable log consolidation";
           type empty;
         }
       }
       container transport {
         presence "enable transport";
         description "Set security log transport settings";
         uses apply-advanced;
         leaf tcp-connections {
           description "Set tcp connection number per-stream";
           type union {
             type string {
               pattern "<.*>|$.*";
             }
             type uint32 {
               range "1 .. 5";
             }
           }
         }
         leaf protocol {
           description "Set security log transport protocol for the device";
           type enumeration {
             enum "udp" {
               description "UDP transfer for log";
             }
             enum "tcp" {
               description "TCP transfer for log";
             }
             enum "tls" {
               description "TLS transfer for log";
             }
           }
         }
         leaf tls-profile {
           description "TLS profile";
           type string;
         }
       }
       container time-format {
         description "Configure year or millisecond for syslog";
         uses time-format-object;
       }
       leaf source-address {
         description "Source ip address used when exporting security logs";
         type jt:ipaddr;
       }
     }
     container file {
       description "Security log file options for logs in binary/protobuf format";
       uses apply-advanced;
       leaf filename {
         description "Name of log file";
         type string {
           length "1 .. 256";
         }
       }
       leaf size {
         description "Maximum size of log file in megabytes";
         type union {
           type string {
             pattern "<.*>|$.*";
           }
           type uint32 {
             range "1 .. 10";
           }
         }
       }
       leaf path {
         description "Path to log files";
         type string {
           length "1 .. 256";
         }
       }
       leaf files {
         description "Maximum number of log files";
         type union {
           type string {
             pattern "<.*>|$.*";
           }
           type uint32 {
             range "2 .. 10";
           }
         }
       }
     }
     container apply {
       description "Apply settings from other features";
       uses apply-advanced;
       leaf dscp-code-point {
         description "Apply setting class-of-service host-outbound-traffic dscp-code-point";
         type empty;
       }
     }
     container traceoptions {
       description "Security log daemon trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "List of things to include in trace";
         leaf name {
           type enumeration {
             enum "source" {
               description "Communication with security log forwarder";
             }
             enum "configuration" {
               description "Reading of configuration";
             }
             enum "all" {
               description "Everything";
             }
             enum "report" {
               description "Trace report";
             }
             enum "hpl" {
               description "Trace HPL logging";
             }
           }
         }
       }
     }
     list profile {
       key name;
       ordered-by user;
       description "Security log profile setting";
       max-elements 10;
       leaf name {
         description "Name of security log profile";
         type string {
           length "1 .. 63";
         }
       }
       uses apply-advanced;
       list stream-name {
         key name;
         ordered-by user;
         description "Use which stream ";
         max-elements 4;
         leaf name {
           description "Name of the stream";
           type string;
         }
         uses apply-advanced;
       }
       container category {
         presence "enable category";
         description "Selects the category of events for the profile";
         uses apply-advanced;
         container session {
           presence "enable session";
           description "Select session category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container webfilter {
           presence "enable webfilter";
           description "Select webfilter category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container antivirus {
           presence "enable antivirus";
           description "Select antivirus category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container content-filter {
           presence "enable content-filter";
           description "Select content-filter category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container antispam {
           presence "enable antispam";
           description "Select antispam category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container idp {
           presence "enable idp";
           description "Select idp category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container secintel {
           presence "enable secintel";
           description "Select secintel category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container aamw {
           presence "enable aamw";
           description "Select aamw category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container ssl-proxy {
           presence "enable ssl-proxy";
           description "Select ssl-proxy category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container apptrack {
           presence "enable apptrack";
           description "Select apptrack category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container nat {
           presence "enable nat";
           description "Select nat category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container pcp {
           presence "enable pcp";
           description "Select pcp category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container sfw {
           presence "enable sfw";
           description "Select sfw category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
       }
       container default-profile {
         presence "enable default-profile";
         uses apply-advanced;
         leaf activate {
           description "Set this profile as default profile";
           type empty;
         }
       }
       container template {
         presence "enable template";
         description "Select the template for the profile";
         uses apply-advanced;
         choice template-id {
           case case_1 {
             leaf traditional-firewall {
               description "Traditional-firewall";
               type empty;
             }
           }
           case case_2 {
             leaf unified-ngfw {
               description "Unified-ngfw";
               type empty;
             }
           }
           case case_3 {
             leaf sd-wan {
               description "Sd-wan";
               type empty;
             }
           }
         }
       }
     }
   }
   grouping host-object {
     uses apply-advanced;
     leaf ipaddr {
       description "IP address/Host name";
       type string {
         length "1 .. 256";
       }
     }
     leaf port {
       description "Host port number";
       type union {
         type uint16;
         type string {
           pattern "<.*>|$.*";
         }
       }
     }
     leaf routing-instance {
       description "Routing-instance name";
       type string;
     }
     leaf log-tag {
       description "Tag included in logs to this host";
       type string {
       }
     }
   }
   grouping lsp_nh_obj {
     leaf name {
       description "LSP to use to reach destination";
       type string;
     }
     uses apply-advanced;
     leaf preference {
       description "Preference of LSP next hop";
       type union {
         type uint32;
         type string {
           pattern "<.*>|$.*";
         }
       }
     }
     leaf metric {
       description "Metric of LSP next hop";
       type union {
         type uint32;
         type string {
           pattern "<.*>|$.*";
         }
       }
     }
   }
   grouping mac_list {
     description "MAC address";
     leaf name {
       type jt:mac-addr;
     }
     uses apply-advanced;
     container policer {
       description "MAC policing";
       uses apply-advanced;
       leaf input {
         description "Name of policer applied to received packets";
         type string;
       }
       leaf output {
         description "Name of policer applied to transmitted packets";
         type string;
       }
     }
   }
   grouping macro-data-type {
     leaf name {
       description "Keyword part of the keyword-value pair";
       type string;
     }
     leaf value {
       description "Value part of the keyword-value pair";
       type string;
     }
   }
   grouping martian_type {
     description "Invalid routes";
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
       }
     }
     leaf choice-value {
       type string;
     }
     leaf allow {
       type empty;
     }
   }
   grouping match_L2_flexible_mask {
     description "Define a flexible match";
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of integer input (16 or 32 bits), Optional length of string input (1..128 bits)";
       type union {
         type uint32;
         type string {
           pattern "<.*>|$.*";
         }
       }
     }
     leaf mask-in-hex {
       description "Mask out bits in the packet data to be matched";
       type string {
       }
     }
     leaf prefix {
       description "Value data/string to be matched";
       type string {
       }
     }
     leaf flexible-mask-name {
       description "Select a flexible match from predefined template field";
       type string;
     }
   }
   grouping match_L2_flexible_range {
     description "Define a flexible match";
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits";
       type union {
         type string {
           pattern "<.*>|$.*";
         }
         type uint32 {
           range "1 .. 32";
         }
       }
     }
     choice range_choice {
       case case_1 {
         leaf range {
           description "Range of values to be matched";
           type string;
         }
       }
       case case_2 {
         leaf range-except {
           description "Range of values to be not matched";
           type string;
         }
       }
     }
     leaf flexible-range-name {
       description "Select a flexible match from predefined template field";
       type string;
     }
   }
   grouping match_L3_flexible_mask {
     description "Define a flexible match";
     uses apply-advanced;
     leaf match-start {
       description "Start point to match in packet";
       type enumeration {
         enum "layer-3" {
           description "Layer-3 match start";
         }
         enum "layer-4" {
           description "Layer-4 match start";
         }
         enum "payload" {
           description "Payload match start";
         }
       }
     }
     leaf byte-offset {
       description "Byte offset after the match start point";
       type union {
         type uint32;
         type string {
           pattern "<.*>|$.*";
         }
       }
     }
     leaf bit-offset {
       description "Bit offset after the (match-start + byte) offset";
       type union {
         type string {
           pattern "<.*>|$.*";
         }
         type uint32 {
           range "0 .. 7";
         }
       }
     }
     leaf bit-length {
       description "Length of integer input (16 or 32 bits), Optional length of string input (1..128 bits)";
       type union {
         type uint32;
         type string {
           pattern "<.*>|$.*";
         }
       }
     }
     leaf mask-in-hex {
       description "Mask out bits in the packet data to be matched";
       type string {
       }
     }
     leaf prefix {
       description "Value data/string to be matched";
       type string {
       }
     }
     leaf flexible-mask-name {
       description "Select a flexible match from predefined template field";
       type string;
     }
   }
   grouping match_L3_flexible_range {
     description "Define a flexible match";
     uses apply-advanced;
     leaf match-start {
       description "Start point to match in packet";
       type enumeration {
         enum "layer-3" {
           description "Layer-3 match start";
         }
         enum "layer-4" {
           description "Layer-4 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits";
       type union {
         type string {
           pattern "<.*>|$.*";
         }
         type uint32 {
           range "1 .. 32";
         }
       }
     }
     choice range_choice {
       case case_1 {
         leaf range {
           description "Range of values to be matched";
           type string;
         }
       }
       case case_2 {
         leaf range-except {
           description "Range of values to be not matched";
           type string;
         }
       }
     }
     leaf flexible-range-name {
       description "Select a flexible match from predefined template field";
       type string;
     }
   }
   grouping match_flags_value {
     description "Define a vxlan flag";
     uses apply-advanced;
     leaf value {
       description "Value data to be matched";
       type string {
       }
     }
     leaf mask-in-hex {
       description "Mask out bits in the packet data to be matched";
       type string {
       }
     }
   }
   grouping match_interface_object {
     leaf name {
       description "Interface to match";
       type union {
         type jt:interface-wildcard;
         type string {
           pattern "<.*>|$.*";
         }
       }
     }
   }
   grouping match_interface_object_oam {
     leaf name {
       description "Interface to match";
       type union {
         type jt:interface-wildcard;
         type string {
           pattern "<.*>|$.*";
         }
       }
     }
   }
   grouping match_interface_set_object {
     leaf name {
       description "Interface set to match";
       type string;
     }
   }
   grouping match_simple_dscp_value {
     uses apply-advanced;
     leaf value_keyword {
       type string;
     }
   }
   grouping match_simple_payload_protocol_value {
     uses apply-advanced;
     leaf value_keyword {
       type string;
     }
   }
   grouping match_simple_port_value {
     uses apply-advanced;
     leaf value_keyword {
       type string;
     }
   }
   grouping match_simple_protocol_value {
     uses apply-advanced;
     leaf value_keyword {
       type string;
     }
   }
   grouping mpls_dialer_filter {
     description "Define an MPLS DIALER filter";
     leaf name {
       description "Filter name";
       type string {
       }
     }
     uses apply-advanced;
     leaf-list accounting-profile {
       ordered-by user;
       description "Accounting profile name";
       type string;
     }
     list term {
       key name;
       ordered-by user;
       description "Define a firewall term";
       leaf name {
         description "Term name";
         type string {
         }
       }
       uses apply-advanced;
       container from {
         description "Define match criteria";
         uses apply-advanced;
         choice exp_choice {
           case case_1 {
             leaf-list exp {
               ordered-by user;
               description "Range of values";
               type string;
             }
           }
           case case_2 {
             leaf-list exp-except {
               ordered-by user;
               description "Range of values";
               type string;
             }
           }
         }
       }
       container then {
         description "Action to take if the 'from' condition is matched";
         uses apply-advanced;
         leaf log {
           description "Log the packet";
           type empty;
         }
         leaf syslog {
           description "System log (syslog) information about the packet";
           type empty;
         }
         leaf sample {
           description "Sample the packet";
           type empty;
         }
         choice designation {
           case case_1 {
             leaf note {
               description "Interested ISDN packet";
               type empty;
             }
           }
           case case_2 {
             leaf ignore {
               description "Non-interested ISDN packet";
               type empty;
             }
           }
         }
       }
     }
   }
   grouping mpls_filter {
     description "Define an MPLS firewall filter";
     leaf name {
       description "Filter name";
       type string {
       }
     }
     uses apply-advanced;
     leaf-list accounting-profile {
       ordered-by user;
       description "Accounting profile name";
       type string;
     }
     leaf fast-lookup-filter {
       description "Configure filter in the fast lookup hardware block";
       type empty;
     }
     leaf interface-specific {
       description "Defined counters are interface specific";
       type empty;
     }
     leaf scale-mode {
       description "Program the filter in scale mode(programs only one pipeline)";
       type empty;
     }
     leaf physical-interface-filter {
       description "Filter is physical interface filter";
       type empty;
     }
     leaf instance-shared {
       description "Filter is routing-instance shared";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         container ip-version {
           description "Specify inner IP version";
           uses apply-advanced;
           container ipv4 {
             presence "enable ipv4";
             description "Define L4 match items to match IPv4 packets";
             uses apply-advanced;
             list protocol {
               key name;
               ordered-by user;
               description "Specify inner IPv4 protocol";
               max-elements 1;
               leaf name {
                 description "IP protocol choices";
                 type string;
               }
               uses apply-advanced;
               choice source-port_choice {
                 case case_1 {
                   leaf-list source-port {
                     ordered-by user;
                     type string;
                   }
                 }
                 case case_2 {
                   leaf-list source-port-except {
                     ordered-by user;
                     type string;
                   }
                 }
               }
               choice destination-port_choice {
                 case case_1 {
                   leaf-list destination-port {
                     ordered-by user;
                     type string;
                   }
                 }
                 case case_2 {
                   leaf-list destination-port-except {
                     ordered-by user;
                     type string;
                   }
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             list source-address {
               key name;
               ordered-by user;
               description "Match IPv4 source address";
               uses firewall_addr_object;
             }
             list destination-address {
               key name;
               ordered-by user;
               description "Match IPv4 destination address";
               uses firewall_addr_object;
             }
             list ip-address {
               key name;
               ordered-by user;
               description "Match IPv4 source or destination addres";
               uses firewall_addr_object;
             }
             list ip-source-address {
               key name;
               ordered-by user;
               description "Match IPv4 source address";
               uses firewall_addr_object;
             }
             list ip-destination-address {
               key name;
               ordered-by user;
               description "Match IPv4 destination address";
               uses firewall_addr_object;
             }
             list source-prefix-list {
               key name;
               ordered-by user;
               description "Match IPv4 source prefixes in named list";
               uses firewall_prefix_list;
             }
             list destination-prefix-list {
               key name;
               ordered-by user;
               description "Match IPv4 destination prefixes in named list";
               uses firewall_prefix_list;
             }
             list prefix-list {
               key name;
               ordered-by user;
               description "Match source or destination prefixes in named list";
               uses firewall_prefix_list;
             }
             choice dscp_choice {
               case case_1 {
                 leaf-list dscp {
                   ordered-by user;
                   type string;
                 }
               }
               case case_2 {
                 leaf-list dscp-except {
                   ordered-by user;
                   type string;
                 }
               }
             }
             leaf first-fragment {
               description "Match if packet is the first fragment";
               type empty;
             }
             leaf fragment-flags {
               description "Match fragment flags (in symbolic or hex formats) - (Ingress only)";
               type string;
             }
             choice fragment-offset_choice {
               case case_1 {
                 leaf-list fragment-offset {
                   ordered-by user;
                   description "Range of values";
                   type string {
                   }
                 }
               }
               case case_2 {
                 leaf-list fragment-offset-except {
                   ordered-by user;
                   description "Range of values";
                   type string {
                   }
                 }
               }
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             leaf is-fragment {
               description "Match if packet is a fragment";
               type empty;
             }
             choice port_choice {
               case case_1 {
                 leaf-list port {
                   ordered-by user;
                   type string;
                 }
               }
               case case_2 {
                 leaf-list port-except {
                   ordered-by user;
                   type string;
                 }
               }
             }
             leaf tcp-initial {
               description "Match initial packet of a TCP connection";
               type empty;
             }
             leaf tcp-established {
               description "Match packet of an established TCP connection";
               type empty;
             }
             choice ip-options_choice {
               case case_1 {
                 leaf-list ip-options {
                   ordered-by user;
                   type enumeration {
                     enum "any" {
                       description "Any IP option";
                     }
                   }
                 }
               }
               case case_2 {
                 leaf-list ip-options-except {
                   ordered-by user;
                   type enumeration {
                     enum "any" {
                       description "Any IP option";
                     }
                   }
                 }
               }
             }
             choice ip-protocol_choice {
               case case_1 {
                 leaf-list ip-protocol {
                   ordered-by user;
                   type string;
                 }
               }
               case case_2 {
                 leaf-list ip-protocol-except {
                   ordered-by user;
                   type string;
                 }
               }
             }
           }
           container ipv6 {
             presence "enable ipv6";
             description "Define L3/L4 match items to match IPv6 packets";
             uses apply-advanced;
             list protocol {
               key name;
               ordered-by user;
               description "Specify inner IPv6 next-header";
               max-elements 1;
               leaf name {
                 description "IP protocol choices";
                 type string;
               }
               uses apply-advanced;
               choice source-port_choice {
                 case case_1 {
                   leaf-list source-port {
                     ordered-by user;
                     type string;
                   }
                 }
                 case case_2 {
                   leaf-list source-port-except {
                     ordered-by user;
                     type string;
                   }
                 }
               }
               choice destination-port_choice {
                 case case_1 {
                   leaf-list destination-port {
                     ordered-by user;
                     type string;
                   }
                 }
                 case case_2 {
                   leaf-list destination-port-except {
                     ordered-by user;
                     type string;
                   }
                 }
               }
             }
             choice payload-protocol_choice {
               case case_1 {
                 leaf-list payload-protocol {
                   ordered-by user;
                   type string;
                 }
               }
               case case_2 {
                 leaf-list payload-protocol-except {
                   ordered-by user;
                   type string;
                 }
               }
             }
             list ip6-source-address {
               key name;
               ordered-by user;
               description "Match IPv6 source address";
               uses firewall_addr6_object;
             }
             list ip6-destination-address {
               key name;
               ordered-by user;
               description "Match IPv6 destination address";
               uses firewall_addr6_object;
             }
             list ip6-address {
               key name;
               ordered-by user;
               description "Match IPv6 source or destination address";
               uses firewall_addr6_object;
             }
             list source-address {
               key name;
               ordered-by user;
               description "Match IPv6 source address";
               uses firewall_addr6_object;
             }
             list destination-address {
               key name;
               ordered-by user;
               description "Match IPv6 destination address";
               uses firewall_addr6_object;
             }
             list source-prefix-list {
               key name;
               ordered-by user;
               description "Match IPv4 source prefixes in named list";
               uses firewall_prefix_list;
             }
             list destination-prefix-list {
               key name;
               ordered-by user;
               description "Match IPv4 destination prefixes in named list";
               uses firewall_prefix_list;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
                 leaf-list port {
                   ordered-by user;
                   type string;
                 }
               }
               case case_2 {
                 leaf-list port-except {
                   ordered-by user;
                   type string;
                 }
               }
             }
             list prefix-list {
               key name;
               ordered-by user;
               description "Match source or destination prefixes in named list";
               uses firewall_prefix_list;
             }
             leaf tcp-initial {
               description "Match initial packet of a TCP connection";
               type empty;
             }
             leaf tcp-established {
               description "Match packet of an established TCP connection";
               type empty;
             }
             choice traffic-class_choice {
               case case_1 {
                 leaf-list traffic-class {
                   ordered-by user;
                   type string;
                 }
               }
               case case_2 {
                 leaf-list traffic-class-except {
                   ordered-by user;
                   type string;
                 }
               }
             }
           }
         }
         leaf-list label0 {
           ordered-by user;
           description "MPLS label bits at Top Of Stack";
           type string;
         }
         leaf-list label0-except {
           ordered-by user;
           description "Do not match MPLS label bits at Top Of Stack";
           type string;
         }
         leaf-list label1 {
           ordered-by user;
           description "Match MPLS label bits at Next 1 from Top Of Stack";
           type string;
         }
         leaf-list label1-except {
           ordered-by user;
           description "Do not match MPLS label bits at Next 1 from Top Of Stack";
           type string;
         }
         list label {
           key name;
           ordered-by user;
           description "MPLS label bits";
           leaf name {
             description "Range of values between 0 and 1048575 in decimal or hexadecimal";
             type string {
             }
           }
           uses apply-advanced;
           choice position {
             case case_1 {
               leaf top {
                 description "Match with reference to top-of-stack towards bottom-of-stack";
                 type empty;
               }
             }
             case case_2 {
               leaf bottom {
                 description "Match with  reference to bottom-of-stack towards top-of-stack";
                 type empty;
               }
             }
           }
           leaf offset {
             description "Target label offset from top/bottom of stack (0..15)";
             type union {
               type string {
                 pattern "<.*>|$.*";
               }
               type uint32 {
                 range "0 .. 15";
               }
             }
           }
         }
         choice exp_choice {
           case case_1 {
             leaf-list exp {
               ordered-by user;
               description "Range of values between 0 and 7 in decimal, binary or hex";
               type string;
             }
           }
           case case_2 {
             leaf-list exp-except {
               ordered-by user;
               description "Range of values between 0 and 7 in decimal, binary or hex";
               type string;
             }
           }
         }
         choice ttl_choice {
           case case_1 {
             leaf-list ttl {
               ordered-by user;
               description "Range of values";
               type string {
               }
             }
           }
           case case_2 {
             leaf-list ttl-except {
               ordered-by user;
               description "Range of values";
               type string {
               }
             }
           }
         }
         choice exp0_choice {
           case case_1 {
             leaf-list exp0 {
               ordered-by user;
               description "Range of values between 0 and 7 in decimal, binary or hex";
               type string;
             }
           }
           case case_2 {
             leaf-list exp0-except {
               ordered-by user;
               description "Range of values between 0 and 7 in decimal, binary or hex";
               type string;
             }
           }
         }
         list interface {
           key name;
           ordered-by user;
           description "Match interface name";
           uses match_interface_object;
         }
         list interface-set {
           key name;
           ordered-by user;
           description "Match interface in set";
           uses match_interface_set_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice ttl0_choice {
           case case_1 {
             leaf-list ttl0 {
               ordered-by user;
               description "Range of values";
               type string {
               }
             }
           }
           case case_2 {
             leaf-list ttl0-except {
               ordered-by user;
               description "Range of values";
               type string {
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice flex-mask_choice {
           case case_1 {
             container flexible-match-mask {
               description "Match flexible mask";
               presence "enable flexible-match-mask";
               uses match_mpls_flexible_mask;
             }
           }
         }
         choice flex-range_choice {
           case case_1 {
             container flexible-match-range {
               description "Match flexible range";
               presence "enable flexible-match-range";
               uses match_mpls_flexible_range;
             }
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice exp1_choice {
           case case_1 {
             leaf-list exp1 {
               ordered-by user;
               description "Range of values between 0 and 7 in decimal, binary or hex";
               type string;
             }
           }
           case case_2 {
             leaf-list exp1-except {
               ordered-by user;
               description "Range of values between 0 and 7 in decimal, binary or hex";
               type string;
             }
           }
         }
         choice ttl1_choice {
           case case_1 {
             leaf-list ttl1 {
               ordered-by user;
               description "Range of values";
               type string {
               }
             }
           }
           case case_2 {
             leaf-list ttl1-except {
               ordered-by user;
               description "Range of values";
               type string {
               }
             }
           }
         }
         leaf bottom-of-stack0 {
           description "Match MPLS BottomOfStack bit at Top Of Stack";
           type empty;
         }
         leaf bottom-of-stack1 {
           description "Match MPLS BottomOfStack bit at Next 1 from Top Of Stack";
           type empty;
         }
         choice slice_choice {
           case case_1 {
             leaf-list slice {
               ordered-by user;
               description "Slice name";
               type string {
                 length "1 .. 64";
               }
             }
           }
           case case_2 {
             leaf-list slice-except {
               ordered-by user;
               description "Slice name";
               type string {
                 length "1 .. 64";
               }
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
             leaf hierarchical-policer {
               description "Name of hierarchical policer to use to rate-limit traffic";
               type string {
               }
             }
           }
           case case_4 {
             container enhanced-hierarchical-policer {
               description "Police the packet using enhanced-hierarchical-policer";
               uses apply-advanced;
               leaf enhanced-hierarchical-policer-name {
                 description "Name of enhanced hierarchical policer to use to rate-limit traffic";
                 type string {
                 }
               }
               leaf traffic-priority {
                 description "Traffic priority based on hierarchy level";
                 type enumeration {
                   enum "high" {
                     description "Hierarchical policer high traffic-priority";
                   }
                   enum "medium-high" {
                     description "Hierarchical policer medium-high traffic-priority";
                   }
                   enum "medium-low" {
                     description "Hierarchical policer medium-low traffic-priority";
                   }
                   enum "low" {
                     description "Hierarchical policer low traffic-priority";
                   }
                 }
               }
             }
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         leaf slice {
           description "Set network slice action";
           type string;
         }
         container routing-instance {
           description "Packets are directed to specified routing instance";
           leaf routing-instance-name {
             description "Name of routing instance";
             type string {
             }
           }
           leaf topology {
             description "Packets are directed to specified topology";
             type string {
             }
           }
         }
         choice mplscnt {
           case case_1 {
             leaf traffic-class-count {
               description "Count the packet in the named traffic-class counter";
               type string {
               }
             }
           }
           case case_2 {
             leaf count {
               description "Count the packet in the named counter";
               type string {
               }
             }
           }
         }
         leaf sample {
           description "Sample the packet";
           type empty;
         }
         leaf loss-priority {
           description "Classify packet to loss-priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf port-mirror-instance {
           description "Port-mirror the packet to specified instance";
           type string {
           }
         }
         leaf port-mirror {
           description "Port-mirror the packet";
           type empty;
         }
         leaf inline-monitoring-instance {
           description "Inline monitoring to specified instance";
           type string {
           }
         }
         leaf packet-mode {
           description "Bypass flow mode for the packet";
           type empty;
         }
         choice designation {
           case case_1 {
             container encapsulate {
               presence "enable encapsulate";
               description "Send to a tunnel";
               leaf tunnel-end-point {
                 description "Name of the tunnel end point";
                 type string {
                 }
               }
             }
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
         }
       }
       container template {
         description "Refer a template";
         uses apply-advanced;
         leaf template-name {
           description "Template name";
           type string {
           }
         }
       }
     }
   }
   grouping match_mpls_flexible_mask {
     description "Define a flexible match";
     uses apply-advanced;
     leaf match-start {
       description "Start point to match in packet";
       type enumeration {
         enum "layer-3" {
           description "Layer-3 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of integer input (1..32 bits), Optional length of string input (1..128 bits)";
       type union {
         type uint32;
         type string {
           pattern "<.*>|$.*";
         }
       }
     }
     leaf mask-in-hex {
       description "Mask out bits in the packet data to be matched";
       type string {
       }
     }
     leaf prefix {
       description "Value data/string to be matched";
       type string {
       }
     }
     leaf flexible-mask-name {
       description "Select a flexible match from predefined template field";
       type string;
     }
   }
   grouping match_mpls_flexible_range {
     description "Define a flexible match";
     uses apply-advanced;
     leaf match-start {
       description "Start point to match in packet";
       type enumeration {
         enum "layer-3" {
           description "Layer-3 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits";
       type union {
         type string {
           pattern "<.*>|$.*";
         }
         type uint32 {
           range "1 .. 32";
         }
       }
     }
     choice range_choice {
       case case_1 {
         leaf range {
           description "Range of values to be matched";
           type string;
         }
       }
       case case_2 {
         leaf range-except {
           description "Range of values to be not matched";
           type string;
         }
       }
     }
     leaf flexible-range-name {
       description "Select a flexible match from predefined template field";
       type string;
     }
   }
   grouping mpls_ifd_options {
     uses apply-advanced;
     container pop-all-labels {
       presence "enable pop-all-labels";
       description "Pop all MPLS labels off incoming packets";
       uses apply-advanced;
       leaf-list required-depth {
         ordered-by user;
         description "Required label depth of packet to pop all labels";
         type enumeration {
           enum "all" {
             description "Takes effect only in Stoli based FPCs, in all other FPCs equivalent to '[1 2]'";
           }
           enum "1" {
             description "Required label depth of packet to pop labels";
           }
           enum "2" {
             description "Required label depth of packet to pop labels";
           }
         }
       }
     }
   }
   grouping mpls_template {
     leaf name {
       description "Template name";
       type string {
       }
     }
     uses apply-advanced;
     container attributes {
       description "Template attributes";
       uses apply-advanced;
       leaf exp {
         description "Match MPLS EXP bits";
         type empty;
       }
       leaf exp-except {
         description "Do not match MPLS EXP bits";
         type empty;
       }
       leaf flexible-match-mask {
         description "Match flexible mask";
         type empty;
       }
       leaf flexible-match-range {
         description "Match flexible range";
         type empty;
       }
       leaf forwarding-class {
         description "Match forwarding class";
         type empty;
       }
       leaf forwarding-class-except {
         description "Do not match forwarding class";
         type empty;
       }
       leaf interface {
         description "Match interface name";
         type empty;
       }
       leaf interface-group {
         description "Match interface group";
         type empty;
       }
       leaf interface-set {
         description "Match interface in set";
         type empty;
       }
       leaf loss-priority {
         description "Match Loss Priority";
         type empty;
       }
       leaf loss-priority-except {
         description "Do not match Loss Priority";
         type empty;
       }
       leaf label {
         description "MPLS label bits";
         type empty;
       }
       leaf ttl {
         description "Match MPLS ttl type";
         type empty;
       }
     }
   }
   grouping multi-chassis-protection-group {
     leaf name {
       description "IP address for this peer";
       type jt:ipv4addr;
     }
     uses apply-advanced;
     leaf interface {
       description "Inter-Chassis protection link";
       type string {
         length "1 .. 40";
       }
     }
     leaf icl-down-delay {
       description "Time in seconds between ICL down and MCAEs moving to standby";
       default "1";
       units "seconds";
       type union {
         type string {
           pattern "<.*>|$.*";
         }
         type int32 {
           range "1 .. 6000";
         }
       }
     }
   }
   grouping multi-chassis-protection-group-ifl {
     leaf name {
       description "IP address for this peer";
       type jt:ipv4addr;
     }
     uses apply-advanced;
     leaf interface {
       description "Inter-Chassis protection link";
       type string {
         length "1 .. 40";
       }
     }
     leaf icl-down-delay {
       description "Time in seconds between ICL down and MCAEs moving to standby";
       default "1";
       units "seconds";
       type union {
         type string {
           pattern "<.*>|$.*";
         }
         type int32 {
           range "1 .. 6000";
         }
       }
     }
   }
   grouping multicast_interface_options_type {
     description "Multicast interface options";
     leaf name {
       description "Interface name";
       type union {
         type jt:interface-unit;
         type string {
           pattern "<.*>|$.*";
         }
       }
     }
     uses apply-advanced;
     container maximum-bandwidth {
       presence "enable maximum-bandwidth";
       description "Maximum multicast bandwidth for the interface";
       leaf bandwidth-limit {
         description "Maximum multicast bandwidth on the interface";
         units "bps";
         type string;
       }
     }
     choice enable-disable {
       case case_1 {
         leaf enable {
           description "Enable Multicast";
           status deprecated;
           type empty;
         }
       }
       case case_2 {
         leaf disable {
           description "Disable Multicast";
           status deprecated;
           type empty;
         }
       }
     }
     container reverse-oif-mapping {
       presence "enable reverse-oif-mapping";
       description "Enable reverse OIF mapping on the multicast interface";
       uses apply-advanced;
       leaf no-qos-adjust {
         description "Disable reverse OIF mapping QoS adjustment";
         type empty;
       }
     }
     leaf subscriber-leave-timer {
       description "Timeout in seconds to credit back the bandwidth on the subscriber interface";
       units "seconds";
       type union {
         type string {
           pattern "<.*>|$.*";
         }
         type uint32 {
           range "0 .. 30";
         }
       }
     }
     leaf no-qos-adjust {
       description "Disable QoS adjustment for this interface";
       type empty;
     }
   }
   grouping och-attributes {
     description "Optical channel configuration attributes";
     uses apply-advanced;
     leaf rate {
       description "Data rate of the OCH payload";
       type enumeration {
         enum "100g" {
           description "100Gbit OCH data rate";
         }
       }
     }
     leaf modulation {
       description "Optical modulation format";
       type enumeration {
         enum "qpsk" {
           description "QPSK Modulation Format";
         }
       }
     }
     leaf encoding {
       description "Optical encoding";
       type enumeration {
         enum "differential" {
           description "Differential encoding";
         }
       }
     }
     choice channel-number {
       case case_1 {
         leaf wavelength {
           description "Optical channel wavelength in nanometers";
           type enumeration {
             enum "1568.77" {
               description "1568.77 nm/191.1003 THz 50/100Ghz spacing";
             }
             enum "1568.36" {
               description "1568.36 nm/191.15000 THz 6.25/12.5/50GHz spacing";
             }
             enum "1568.31" {
               description "1568.31 nm/191.15625 THz 6.25GHz spacing";
             }
             enum "1568.26" {
               description "1568.26 nm/191.16250 THz 6.25/12.5GHz spacing";
             }
             enum "1568.21" {
               description "1568.21 nm/191.16875 THz 6.25GHz spacing";
             }
             enum "1568.16" {
               description "1568.16 nm/191.17500 THz 6.25/12.5GHz spacing";
             }
             enum "1568.11" {
               description "1568.11 nm/191.18125 THz 6.25GHz spacing";
             }
             enum "1568.05" {
               description "1568.05 nm/191.18750 THz 6.25/12.5GHz spacing";
             }
             enum "1568.00" {
               description "1568.00 nm/191.19375 THz 6.25GHz spacing";
             }
             enum "1567.95" {
               description "1567.95 nm/191.20000 THz 6.25/12.5/50/100GHz spacing";
             }
             enum "1567.90" {
               description "1567.90 nm/191.20625 THz 6.25GHz spacing";
             }
             enum "1567.85" {
               description "1567.85 nm/191.21250 THz 6.25/12.5GHz spacing";
             }
             enum "1567.80" {
               description "1567.80 nm/191.21875 THz 6.25GHz spacing";
             }
             enum "1567.75" {
               description "1567.75 nm/191.22500 THz 6.25/12.5GHz spacing";
             }
             enum "1567.70" {
               description "1567.70 nm/191.23125 THz 6.25GHz spacing";
             }
             enum "1567.64" {
               description "1567.64 nm/191.23750 THz 6.25/12.5GHz spacing";
             }
             enum "1567.59" {
               description "1567.59 nm/191.24375 THz 6.25GHz spacing";
             }
             enum "1567.54" {
               description "1567.54 nm/191.25000 THz 6.25/12.5/50GHz spacing";
             }
             enum "1567.49" {
               description "1567.49 nm/191.25625 THz 6.25GHz spacing";
             }
             enum "1567.44" {
               description "1567.44 nm/191.26250 THz 6.25/12.5GHz spacing";
             }
             enum "1567.39" {
               description "1567.39 nm/191.26875 THz 6.25GHz spacing";
             }
             enum "1567.34" {
               description "1567.34 nm/191.27500 THz 6.25/12.5GHz spacing";
             }
             enum "1567.29" {
               description "1567.29 nm/191.28125 THz 6.25GHz spacing";
             }
             enum "1567.23" {
               description "1567.23 nm/191.28750 THz 6.25/12.5GHz spacing";
             }
             enum "1567.18" {
               description "1567.18 nm/191.29375 THz 6.25GHz spacing";
             }
             enum "1567.13" {
               description "1567.13 nm/191.30000 THz 6.25/12.5/50/100GHz spacing";
             }
             enum "1567.08" {
               description "1567.08 nm/191.30625 THz 6.25GHz spacing";
             }
             enum "1567.03" {
               description "1567.03 nm/191.31250 THz 6.25/12.5GHz spacing";
             }
             enum "1566.98" {
               description "1566.98 nm/191.31875 THz 6.25GHz spacing";
             }
             enum "1566.93" {
               description "1566.93 nm/191.32500 THz 6.25/12.5GHz spacing";
             }
             enum "1566.88" {
               description "1566.88 nm/191.33125 THz 6.25GHz spacing";
             }
             enum "1566.83" {
               description "1566.83 nm/191.33750 THz 6.25/12.5GHz spacing";
             }
             enum "1566.77" {
               description "1566.77 nm/191.34375 THz 6.25GHz spacing";
             }
             enum "1566.72" {
               description "1566.72 nm/191.35000 THz 6.25/12.5/50GHz spacing";
             }
             enum "1566.67" {
               description "1566.67 nm/191.35625 THz 6.25GHz spacing";
             }
             enum "1566.62" {
               description "1566.62 nm/191.36250 THz 6.25/12.5GHz spacing";
             }
             enum "1566.57" {
               description "1566.57 nm/191.36875 THz 6.25GHz spacing";
             }
             enum "1566.52" {
               description "1566.52 nm/191.37500 THz 6.25/12.5/75GHz spacing";
             }
             enum "1566.47" {
               description "1566.47 nm/191.38125 THz 6.25GHz spacing";
             }
             enum "1566.42" {
               description "1566.42 nm/191.38750 THz 6.25/12.5GHz spacing";
             }
             enum "1566.36" {
               description "1566.36 nm/191.39375 THz 6.25GHz spacing";
             }
             enum "1566.31" {
               description "1566.31 nm/191.40000 THz 6.25/12.5/50/100GHz spacing";
             }
             enum "1566.26" {
               description "1566.26 nm/191.40625 THz 6.25GHz spacing";
             }
             enum "1566.21" {
               description "1566.21 nm/191.41250 THz 6.25/12.5GHz spacing";
             }
             enum "1566.16" {
               description "1566.16 nm/191.41875 THz 6.25GHz spacing";
             }
             enum "1566.11" {
               description "1566.11 nm/191.42500 THz 6.25/12.5GHz spacing";
             }
             enum "1566.06" {
               description "1566.06 nm/191.43125 THz 6.25GHz spacing";
             }
             enum "1566.01" {
               description "1566.01 nm/191.43750 THz 6.25/12.5GHz spacing";
             }
             enum "1565.96" {
               description "1565.96 nm/191.44375 THz 6.25GHz spacing";
             }
             enum "1565.90" {
               description "1565.90 nm/191.45000 THz 6.25/12.5/50/75GHz spacing";
             }
             enum "1565.85" {
               description "1565.85 nm/191.45625 THz 6.25GHz spacing";
             }
             enum "1565.80" {
               description "1565.80 nm/191.46250 THz 6.25/12.5GHz spacing";
             }
             enum "1565.75" {
               description "1565.75 nm/191.46875 THz 6.25GHz spacing";
             }
             enum "1565.70" {
               description "1565.70 nm/191.47500 THz 6.25/12.5GHz spacing";
             }
             enum "1565.65" {
               description "1565.65 nm/191.48125 THz 6.25GHz spacing";
             }
             enum "1565.60" {
               description "1565.60 nm/191.48750 THz 6.25/12.5GHz spacing";
             }
             enum "1565.55" {
               description "1565.55 nm/191.49375 THz 6.25GHz spacing";
             }
             enum "1565.50" {
               description "1565.50 nm/191.50000 THz 6.25/12.5/50/100GHz spacing";
             }
             enum "1565.44" {
               description "1565.44 nm/191.50625 THz 6.25GHz spacing";
             }
             enum "1565.39" {
               description "1565.39 nm/191.51250 THz 6.25/12.5GHz spacing";
             }
             enum "1565.34" {
               description "1565.34 nm/191.51875 THz 6.25GHz spacing";
             }
             enum "1565.29" {
               description "1565.29 nm/191.52500 THz 6.25/12.5/75GHz spacing";
             }
             enum "1565.24" {
               description "1565.24 nm/191.53125 THz 6.25GHz spacing";
             }
             enum "1565.19" {
               description "1565.19 nm/191.53750 THz 6.25/12.5GHz spacing";
             }
             enum "1565.14" {
               description "1565.14 nm/191.54375 THz 6.25GHz spacing";
             }
             enum "1565.09" {
               description "1565.09 nm/191.55000 THz 6.25/12.5/50GHz spacing";
             }
             enum "1565.04" {
               description "1565.04 nm/191.55625 THz 6.25GHz spacing";
             }
             enum "1564.99" {
               description "1564.99 nm/191.56250 THz 6.25/12.5GHz spacing";
             }
             enum "1564.93" {
               description "1564.93 nm/191.56875 THz 6.25GHz spacing";
             }
             enum "1564.88" {
               description "1564.88 nm/191.57500 THz 6.25/12.5GHz spacing";
             }
             enum "1564.83" {
               description "1564.83 nm/191.58125 THz 6.25GHz spacing";
             }
             enum "1564.78" {
               description "1564.78 nm/191.58750 THz 6.25/12.5GHz spacing";
             }
             enum "1564.73" {
               description "1564.73 nm/191.59375 THz 6.25GHz spacing";
             }
             enum "1564.68" {
               description "1564.68 nm/191.60000 THz 6.25/12.5/50/75/100GHz spacing";
             }
             enum "1564.63" {
               description "1564.63 nm/191.60625 THz 6.25GHz spacing";
             }
             enum "1564.58" {
               description "1564.58 nm/191.61250 THz 6.25/12.5GHz spacing";
             }
             enum "1564.53" {
               description "1564.53 nm/191.61875 THz 6.25GHz spacing";
             }
             enum "1564.47" {
               description "1564.47 nm/191.62500 THz 6.25/12.5GHz spacing";
             }
             enum "1564.42" {
               description "1564.42 nm/191.63125 THz 6.25GHz spacing";
             }
             enum "1564.37" {
               description "1564.37 nm/191.63750 THz 6.25/12.5GHz spacing";
             }
             enum "1564.32" {
               description "1564.32 nm/191.64375 THz 6.25GHz spacing";
             }
             enum "1564.27" {
               description "1564.27 nm/191.65000 THz 6.25/12.5/50GHz spacing";
             }
             enum "1564.22" {
               description "1564.22 nm/191.65625 THz 6.25GHz spacing";
             }
             enum "1564.17" {
               description "1564.17 nm/191.66250 THz 6.25/12.5GHz spacing";
             }
             enum "1564.12" {
               description "1564.12 nm/191.66875 THz 6.25GHz spacing";
             }
             enum "1564.07" {
               description "1564.07 nm/191.67500 THz 6.25/12.5/75GHz spacing";
             }
             enum "1564.02" {
               description "1564.02 nm/191.68125 THz 6.25GHz spacing";
             }
             enum "1563.96" {
               description "1563.96 nm/191.68750 THz 6.25/12.5GHz spacing";
             }
             enum "1563.91" {
               description "1563.91 nm/191.69375 THz 6.25GHz spacing";
             }
             enum "1563.86" {
               description "1563.86 nm/191.70000 THz 6.25/12.5/50/100GHz spacing";
             }
             enum "1563.81" {
               description "1563.81 nm/191.70625 THz 6.25GHz spacing";
             }
             enum "1563.76" {
               description "1563.76 nm/191.71250 THz 6.25/12.5GHz spacing";
             }
             enum "1563.71" {
               description "1563.71 nm/191.71875 THz 6.25GHz spacing";
             }
             enum "1563.66" {
               description "1563.66 nm/191.72500 THz 6.25/12.5GHz spacing";
             }
             enum "1563.61" {
               description "1563.61 nm/191.73125 THz 6.25GHz spacing";
             }
             enum "1563.56" {
               description "1563.56 nm/191.73750 THz 6.25/12.5GHz spacing";
             }
             enum "1563.51" {
               description "1563.51 nm/191.74375 THz 6.25GHz spacing";
             }
             enum "1563.45" {
               description "1563.45 nm/191.75000 THz 6.25/12.5/50/75GHz spacing";
             }
             enum "1563.40" {
               description "1563.40 nm/191.75625 THz 6.25GHz spacing";
             }
             enum "1563.35" {
               description "1563.35 nm/191.76250 THz 6.25/12.5GHz spacing";
             }
             enum "1563.30" {
               description "1563.30 nm/191.76875 THz 6.25GHz spacing";
             }
             enum "1563.25" {
               description "1563.25 nm/191.77500 THz 6.25/12.5GHz spacing";
             }
             enum "1563.20" {
               description "1563.20 nm/191.78125 THz 6.25GHz spacing";
             }
             enum "1563.15" {
               description "1563.15 nm/191.78750 THz 6.25/12.5GHz spacing";
             }
             enum "1563.10" {
               description "1563.10 nm/191.79375 THz 6.25GHz spacing";
             }
             enum "1563.05" {
               description "1563.05 nm/191.80000 THz 6.25/12.5/50/100GHz spacing";
             }
             enum "1563.00" {
               description "1563.00 nm/191.80625 THz 6.25GHz spacing";
             }
             enum "1562.95" {
               description "1562.95 nm/191.81250 THz 6.25/12.5GHz spacing";
             }
             enum "1562.89" {
               description "1562.89 nm/191.81875 THz 6.25GHz spacing";
             }
             enum "1562.84" {
               description "1562.84 nm/191.82500 THz 6.25/12.5/75GHz spacing";
             }
             enum "1562.79" {
               description "1562.79 nm/191.83125 THz 6.25GHz spacing";
             }
             enum "1562.74" {
               description "1562.74 nm/191.83750 THz 6.25/12.5GHz spacing";
             }
             enum "1562.69" {
               description "1562.69 nm/191.84375 THz 6.25GHz spacing";
             }
             enum "1562.64" {
               description "1562.64 nm/191.85000 THz 6.25/12.5/50GHz spacing";
             }
             enum "1562.59" {
               description "1562.59 nm/191.85625 THz 6.25GHz spacing";
             }
             enum "1562.54" {
               description "1562.54 nm/191.86250 THz 6.25/12.5GHz spacing";
             }
             enum "1562.49" {
               description "1562.49 nm/191.86875 THz 6.25GHz spacing";
             }
             enum "1562.44" {
               description "1562.44 nm/191.87500 THz 6.25/12.5GHz spacing";
             }
             enum "1562.39" {
               description "1562.39 nm/191.88125 THz 6.25GHz spacing";
             }
             enum "1562.33" {
               description "1562.33 nm/191.88750 THz 6.25/12.5GHz spacing";
             }
             enum "1562.28" {
               description "1562.28 nm/191.89375 THz 6.25GHz spacing";
             }
             enum "1562.23" {
               description "1562.23 nm/191.90000 THz 6.25/12.5/50/75/100GHz spacing";
             }
             enum "1562.18" {
               description "1562.18 nm/191.90625 THz 6.25GHz spacing";
             }
             enum "1562.13" {
               description "1562.13 nm/191.91250 THz 6.25/12.5GHz spacing";
             }
             enum "1562.08" {
               description "1562.08 nm/191.91875 THz 6.25GHz spacing";
             }
             enum "1562.03" {
               description "1562.03 nm/191.92500 THz 6.25/12.5GHz spacing";
             }
             enum "1561.98" {
               description "1561.98 nm/191.93125 THz 6.25GHz spacing";
             }
             enum "1561.93" {
               description "1561.93 nm/191.93750 THz 6.25/12.5GHz spacing";
             }
             enum "1561.88" {
               description "1561.88 nm/191.94375 THz 6.25GHz spacing";
             }
             enum "1561.83" {
               description "1561.83 nm/191.95000 THz 6.25/12.5/50GHz spacing";
             }
             enum "1561.77" {
               description "1561.77 nm/191.95625 THz 6.25GHz spacing";
             }
             enum "1561.72" {
               description "1561.72 nm/191.96250 THz 6.25/12.5GHz spacing";
             }
             enum "1561.67" {
               description "1561.67 nm/191.96875 THz 6.25GHz spacing";
             }
             enum "1561.62" {
               description "1561.62 nm/191.97500 THz 6.25/12.5/75GHz spacing";
             }
             enum "1561.57" {
               description "1561.57 nm/191.98125 THz 6.25GHz spacing";
             }
             enum "1561.52" {
               description "1561.52 nm/191.98750 THz 6.25/12.5GHz spacing";
             }
             enum "1561.47" {
               description "1561.47 nm/191.99375 THz 6.25GHz spacing";
             }
             enum "1561.42" {
               description "1561.42 nm/192.00000 THz 6.25/12.5/50/100GHz spacing";
             }
             enum "1561.37" {
               description "1561.37 nm/192.00625 THz 6.25GHz spacing";
             }
             enum "1561.32" {
               description "1561.32 nm/192.01250 THz 6.25/12.5GHz spacing";
             }
             enum "1561.27" {
               description "1561.27 nm/192.01875 THz 6.25GHz spacing";
             }
             enum "1561.22" {
               description "1561.22 nm/192.02500 THz 6.25/12.5GHz spacing";
             }
             enum "1561.16" {
               description "1561.16 nm/192.03125 THz 6.25GHz spacing";
             }
             enum "1561.11" {
               description "1561.11 nm/192.03750 THz 6.25/12.5GHz spacing";
             }
             enum "1561.06" {
               description "1561.06 nm/192.04375 THz 6.25GHz spacing";
             }
             enum "1561.01" {
               description "1561.01 nm/192.05000 THz 6.25/12.5/50G/75Hz spacing";
             }
             enum "1560.96" {
               description "1560.96 nm/192.05625 THz 6.25GHz spacing";
             }
             enum "1560.91" {
               description "1560.91 nm/192.06250 THz 6.25/12.5GHz spacing";
             }
             enum "1560.86" {
               description "1560.86 nm/192.06875 THz 6.25GHz spacing";
             }
             enum "1560.81" {
               description "1560.81 nm/192.07500 THz 6.25/12.5GHz spacing";
             }
             enum "1560.76" {
               description "1560.76 nm/192.08125 THz 6.25GHz spacing";
             }
             enum "1560.71" {
               description "1560.71 nm/192.08750 THz 6.25/12.5GHz spacing";
             }
             enum "1560.66" {
               description "1560.66 nm/192.09375 THz 6.25GHz spacing";
             }
             enum "1560.61" {
               description "1560.61 nm/192.10000 THz 6.25/12.5/50/100GHz spacing";
             }
             enum "1560.56" {
               description "1560.56 nm/192.10625 THz 6.25GHz spacing";
             }
             enum "1560.50" {
               description "1560.50 nm/192.11250 THz 6.25/12.5GHz spacing";
             }
             enum "1560.45" {
               description "1560.45 nm/192.11875 THz 6.25GHz spacing";
             }
             enum "1560.40" {
               description "1560.40 nm/192.12500 THz 6.25/12.5/75GHz spacing";
             }
             enum "1560.35" {
               description "1560.35 nm/192.13125 THz 6.25GHz spacing";
             }
             enum "1560.30" {
               description "1560.30 nm/192.13750 THz 6.25/12.5GHz spacing";
             }
             enum "1560.25" {
               description "1560.25 nm/192.14375 THz 6.25GHz spacing";
             }
             enum "1560.20" {
               description "1560.20 nm/192.15000 THz 6.25/12.5/50GHz spacing";
             }
             enum "1560.15" {
               description "1560.15 nm/192.15625 THz 6.25GHz spacing";
             }
             enum "1560.10" {
               description "1560.10 nm/192.16250 THz 6.25/12.5GHz spacing";
             }
             enum "1560.05" {
               description "1560.05 nm/192.16875 THz 6.25GHz spacing";
             }
             enum "1560.00" {
               description "1560.00 nm/192.17500 THz 6.25/12.5GHz spacing";
             }
             enum "1559.95" {
               description "1559.95 nm/192.18125 THz 6.25GHz spacing";
             }
             enum "1559.90" {
               description "1559.90 nm/192.18750 THz 6.25/12.5GHz spacing";
             }
             enum "1559.84" {
               description "1559.84 nm/192.19375 THz 6.25GHz spacing";
             }
             enum "1559.79" {
               description "1559.79 nm/192.20000 THz 6.25/12.5/50/75/100GHz spacing";
             }
             enum "1559.74" {
               description "1559.74 nm/192.20625 THz 6.25GHz spacing";
             }
             enum "1559.69" {
               description "1559.69 nm/192.21250 THz 6.25/12.5GHz spacing";
             }
             enum "1559.64" {
               description "1559.64 nm/192.21875 THz 6.25GHz spacing";
             }
             enum "1559.59" {
               description "1559.59 nm/192.22500 THz 6.25/12.5GHz spacing";
             }
             enum "1559.54" {
               description "1559.54 nm/192.23125 THz 6.25GHz spacing";
             }
             enum "1559.49" {
               description "1559.49 nm/192.23750 THz 6.25/12.5GHz spacing";
             }
             enum "1559.44" {
               description "1559.44 nm/192.24375 THz 6.25GHz spacing";
             }
             enum "1559.39" {
               description "1559.39 nm/192.25000 THz 6.25/12.5/50GHz spacing";
             }
             enum "1559.34" {
               description "1559.34 nm/192.25625 THz 6.25GHz spacing";
             }
             enum "1559.29" {
               description "1559.29 nm/192.26250 THz 6.25/12.5GHz spacing";
             }
             enum "1559.24" {
               description "1559.24 nm/192.26875 THz 6.25GHz spacing";
             }
             enum "1559.19" {
               description "1559.19 nm/192.27500 THz 6.25/12.5/75GHz spacing";
             }
             enum "1559.14" {
               description "1559.14 nm/192.28125 THz 6.25GHz spacing";
             }
             enum "1559.08" {
               description "1559.08 nm/192.28750 THz 6.25/12.5GHz spacing";
             }
             enum "1559.03" {
               description "1559.03 nm/192.29375 THz 6.25GHz spacing";
             }
             enum "1558.98" {
               description "1558.98 nm/192.30000 THz 6.25/12.5/50/100GHz spacing";
             }
             enum "1558.93" {
               description "1558.93 nm/192.30625 THz 6.25GHz spacing";
             }
             enum "1558.88" {
               description "1558.88 nm/192.31250 THz 6.25/12.5GHz spacing";
             }
             enum "1558.83" {
               description "1558.83 nm/192.31875 THz 6.25GHz spacing";
             }
             enum "1558.78" {
               description "1558.78 nm/192.32500 THz 6.25/12.5GHz spacing";
             }
             enum "1558.73" {
               description "1558.73 nm/192.33125 THz 6.25GHz spacing";
             }
             enum "1558.68" {
               description "1558.68 nm/192.33750 THz 6.25/12.5GHz spacing";
             }
             enum "1558.63" {
               description "1558.63 nm/192.34375 THz 6.25GHz spacing";
             }
             enum "1558.58" {
               description "1558.58 nm/192.35000 THz 6.25/12.5/50/75GHz spacing";
             }
             enum "1558.53" {
               description "1558.53 nm/192.35625 THz 6.25GHz spacing";
             }
             enum "1558.48" {
               description "1558.48 nm/192.36250 THz 6.25/12.5GHz spacing";
             }
             enum "1558.43" {
               description "1558.43 nm/192.36875 THz 6.25GHz spacing";
             }
             enum "1558.38" {
               description "1558.38 nm/192.37500 THz 6.25/12.5GHz spacing";
             }
             enum "1558.32" {
               description "1558.32 nm/192.38125 THz 6.25GHz spacing";
             }
             enum "1558.27" {
               description "1558.27 nm/192.38750 THz 6.25/12.5GHz spacing";
             }
             enum "1558.22" {
               description "1558.22 nm/192.39375 THz 6.25GHz spacing";
             }
             enum "1558.17" {
               description "1558.17 nm/192.40000 THz 6.25/12.5/50/100GHz spacing";
             }
             enum "1558.12" {
               description "1558.12 nm/192.40625 THz 6.25GHz spacing";
             }
             enum "1558.07" {
               description "1558.07 nm/192.41250 THz 6.25/12.5GHz spacing";
             }
             enum "1558.02" {
               description "1558.02 nm/192.41875 THz 6.25GHz spacing";
             }
             enum "1557.97" {
               description "1557.97 nm/192.42500 THz 6.25/12.5/75GHz spacing";
             }
             enum "1557.92" {
               description "1557.92 nm/192.43125 THz 6.25GHz spacing";
             }
             enum "1557.87" {
               description "1557.87 nm/192.43750 THz 6.25/12.5GHz spacing";
             }
             enum "1557.82" {
               description "1557.82 nm/192.44375 THz 6.25GHz spacing";
             }
             enum "1557.77" {
               description "1557.77 nm/192.45000 THz 6.25/12.5/50GHz spacing";
             }
             enum "1557.72" {
               description "1557.72 nm/192.45625 THz 6.25GHz spacing";
             }
             enum "1557.67" {
               description "1557.67 nm/192.46250 THz 6.25/12.5GHz spacing";
             }
             enum "1557.62" {
               description "1557.62 nm/192.46875 THz 6.25GHz spacing";
             }
             enum "1557.57" {
               description "1557.57 nm/192.47500 THz 6.25/12.5GHz spacing";
             }
             enum "1557.52" {
               description "1557.52 nm/192.48125 THz 6.25GHz spacing";
             }
             enum "1557.46" {
               description "1557.46 nm/192.48750 THz 6.25/12.5GHz spacing";
             }
             enum "1557.41" {
               description "1557.41 nm/192.49375 THz 6.25GHz spacing";
             }
             enum "1557.36" {
               description "1557.36 nm/192.50000 THz 6.25/12.5/50/75/100GHz spacing";
             }
             enum "1557.31" {
               description "1557.31 nm/192.50625 THz 6.25GHz spacing";
             }
             enum "1557.26" {
               description "1557.26 nm/192.51250 THz 6.25/12.5GHz spacing";
             }
             enum "1557.21" {
               description "1557.21 nm/192.51875 THz 6.25GHz spacing";
             }
             enum "1557.16" {
               description "1557.16 nm/192.52500 THz 6.25/12.5GHz spacing";
             }
             enum "1557.11" {
               description "1557.11 nm/192.53125 THz 6.25GHz spacing";
             }
             enum "1557.06" {
               description "1557.06 nm/192.53750 THz 6.25/12.5GHz spacing";
             }
             enum "1557.01" {
               description "1557.01 nm/192.54375 THz 6.25GHz spacing";
             }
             enum "1556.96" {
               description "1556.96 nm/192.55000 THz 6.25/12.5/50GHz spacing";
             }
             enum "1556.91" {
               description "1556.91 nm/192.55625 THz 6.25GHz spacing";
             }
             enum "1556.86" {
               description "1556.86 nm/192.56250 THz 6.25/12.5GHz spacing";
             }
             enum "1556.81" {
               description "1556.81 nm/192.56875 THz 6.25GHz spacing";
             }
             enum "1556.76" {
               description "1556.76 nm/192.57500 THz 6.25/12.5/75GHz spacing";
             }
             enum "1556.71" {
               description "1556.71 nm/192.58125 THz 6.25GHz spacing";
             }
             enum "1556.66" {
               description "1556.66 nm/192.58750 THz 6.25/12.5GHz spacing";
             }
             enum "1556.61" {
               description "1556.61 nm/192.59375 THz 6.25GHz spacing";
             }
             enum "1556.55" {
               description "1556.55 nm/192.60000 THz 6.25/12.5/50/100GHz spacing";
             }
             enum "1556.50" {
               description "1556.50 nm/192.60625 THz 6.25GHz spacing";
             }
             enum "1556.45" {
               description "1556.45 nm/192.61250 THz 6.25/12.5GHz spacing";
             }
             enum "1556.40" {
               description "1556.40 nm/192.61875 THz 6.25GHz spacing";
             }
             enum "1556.35" {
               description "1556.35 nm/192.62500 THz 6.25/12.5GHz spacing";
             }
             enum "1556.30" {
               description "1556.30 nm/192.63125 THz 6.25GHz spacing";
             }
             enum "1556.25" {
               description "1556.25 nm/192.63750 THz 6.25/12.5GHz spacing";
             }
             enum "1556.20" {
               description "1556.20 nm/192.64375 THz 6.25GHz spacing";
             }
             enum "1556.15" {
               description "1556.15 nm/192.65000 THz 6.25/12.5/50/75GHz spacing";
             }
             enum "1556.10" {
               description "1556.10 nm/192.65625 THz 6.25GHz spacing";
             }
             enum "1556.05" {
               description "1556.05 nm/192.66250 THz 6.25/12.5GHz spacing";
             }
             enum "1556.00" {
               description "1556.00 nm/192.66875 THz 6.25GHz spacing";
             }
             enum "1555.95" {
               description "1555.95 nm/192.67500 THz 6.25/12.5GHz spacing";
             }
             enum "1555.90" {
               description "1555.90 nm/192.68125 THz 6.25GHz spacing";
             }
             enum "1555.85" {
               description "1555.85 nm/192.68750 THz 6.25/12.5GHz spacing";
             }
             enum "1555.80" {
               description "1555.80 nm/192.69375 THz 6.25GHz spacing";
             }
             enum "1555.75" {
               description "1555.75 nm/192.70000 THz 6.25/12.5/50/100GHz spacing";
             }
             enum "1555.70" {
               description "1555.70 nm/192.70625 THz 6.25GHz spacing";
             }
             enum "1555.65" {
               description "1555.65 nm/192.71250 THz 6.25/12.5GHz spacing";
             }
             enum "1555.60" {
               description "1555.60 nm/192.71875 THz 6.25GHz spacing";
             }
             enum "1555.55" {
               description "1555.55 nm/192.72500 THz 6.25/12.5/75GHz spacing";
             }
             enum "1555.49" {
               description "1555.49 nm/192.73125 THz 6.25GHz spacing";
             }
             enum "1555.44" {
               description "1555.44 nm/192.73750 THz 6.25/12.5GHz spacing";
             }
             enum "1555.39" {
               description "1555.39 nm/192.74375 THz 6.25GHz spacing";
             }
             enum "1555.34" {
               description "1555.34 nm/192.75000 THz 6.25/12.5/50GHz spacing";
             }
             enum "1555.29" {
               description "1555.29 nm/192.75625 THz 6.25GHz spacing";
             }
             enum "1555.24" {
               description "1555.24 nm/192.76250 THz 6.25/12.5GHz spacing";
             }
             enum "1555.19" {
               description "1555.19 nm/192.76875 THz 6.25GHz spacing";
             }
             enum "1555.14" {
               description "1555.14 nm/192.77500 THz 6.25/12.5GHz spacing";
             }
             enum "1555.09" {
               description "1555.09 nm/192.78125 THz 6.25GHz spacing";
             }
             enum "1555.04" {
               description "1555.04 nm/192.78750 THz 6.25/12.5GHz spacing";
             }
             enum "1554.99" {
               description "1554.99 nm/192.79375 THz 6.25GHz spacing";
             }
             enum "1554.94" {
               description "1554.94 nm/192.80000 THz 6.25/12.5/50/75/100GHz spacing";
             }
             enum "1554.89" {
               description "1554.89 nm/192.80625 THz 6.25GHz spacing";
             }
             enum "1554.84" {
               description "1554.84 nm/192.81250 THz 6.25/12.5GHz spacing";
             }
             enum "1554.79" {
               description "1554.79 nm/192.81875 THz 6.25GHz spacing";
             }
             enum "1554.74" {
               description "1554.74 nm/192.82500 THz 6.25/12.5GHz spacing";
             }
             enum "1554.69" {
               description "1554.69 nm/192.83125 THz 6.25GHz spacing";
             }
             enum "1554.64" {
               description "1554.64 nm/192.83750 THz 6.25/12.5GHz spacing";
             }
             enum "1554.59" {
               description "1554.59 nm/192.84375 THz 6.25GHz spacing";
             }
             enum "1554.54" {
               description "1554.54 nm/192.85000 THz 6.25/12.5/50GHz spacing";
             }
             enum "1554.49" {
               description "1554.49 nm/192.85625 THz 6.25GHz spacing";
             }
             enum "1554.44" {
               description "1554.44 nm/192.86250 THz 6.25/12.5GHz spacing";
             }
             enum "1554.39" {
               description "1554.39 nm/192.86875 THz 6.25GHz spacing";
             }
             enum "1554.34" {
               description "1554.34 nm/192.87500 THz 6.25/12.5/75GHz spacing";
             }
             enum "1554.29" {
               description "1554.29 nm/192.88125 THz 6.25GHz spacing";
             }
             enum "1554.23" {
               description "1554.23 nm/192.88750 THz 6.25/12.5GHz spacing";
             }
             enum "1554.18" {
               description "1554.18 nm/192.89375 THz 6.25GHz spacing";
             }
             enum "1554.13" {
               description "1554.13 nm/192.90000 THz 6.25/12.5/50/100GHz spacing";
             }
             enum "1554.08" {
               description "1554.08 nm/192.90625 THz 6.25GHz spacing";
             }
             enum "1554.03" {
               description "1554.03 nm/192.91250 THz 6.25/12.5GHz spacing";
             }
             enum "1553.98" {
               description "1553.98 nm/192.91875 THz 6.25GHz spacing";
             }
             enum "1553.93" {
               description "1553.93 nm/192.92500 THz 6.25/12.5GHz spacing";
             }
             enum "1553.88" {
               description "1553.88 nm/192.93125 THz 6.25GHz spacing";
             }
             enum "1553.83" {
               description "1553.83 nm/192.93750 THz 6.25/12.5GHz spacing";
             }
             enum "1553.78" {
               description "1553.78 nm/192.94375 THz 6.25GHz spacing";
             }
             enum "1553.73" {
               description "1553.73 nm/192.95000 THz 6.25/12.5/50/75GHz spacing";
             }
             enum "1553.68" {
               description "1553.68 nm/192.95625 THz 6.25GHz spacing";
             }
             enum "1553.63" {
               description "1553.63 nm/192.96250 THz 6.25/12.5GHz spacing";
             }
             enum "1553.58" {
               description "1553.58 nm/192.96875 THz 6.25GHz spacing";
             }
             enum "1553.53" {
               description "1553.53 nm/192.97500 THz 6.25/12.5GHz spacing";
             }
             enum "1553.48" {
               description "1553.48 nm/192.98125 THz 6.25GHz spacing";
             }
             enum "1553.43" {
               description "1553.43 nm/192.98750 THz 6.25/12.5GHz spacing";
             }
             enum "1553.38" {
               description "1553.38 nm/192.99375 THz 6.25GHz spacing";
             }
             enum "1553.33" {
               description "1553.33 nm/193.00000 THz 6.25/12.5/50/100GHz spacing";
             }
             enum "1553.28" {
               description "1553.28 nm/193.00625 THz 6.25GHz spacing";
             }
             enum "1553.23" {
               description "1553.23 nm/193.01250 THz 6.25/12.5GHz spacing";
             }
             enum "1553.18" {
               description "1553.18 nm/193.01875 THz 6.25GHz spacing";
             }
             enum "1553.13" {
               description "1553.13 nm/193.02500 THz 6.25/12.5/75GHz spacing";
             }
             enum "1553.08" {
               description "1553.08 nm/193.03125 THz 6.25GHz spacing";
             }
             enum "1553.03" {
               description "1553.03 nm/193.03750 THz 6.25/12.5GHz spacing";
             }
             enum "1552.98" {
               description "1552.98 nm/193.04375 THz 6.25GHz spacing";
             }
             enum "1552.93" {
               description "1552.93 nm/193.05000 THz 6.25/12.5/50GHz spacing";
             }
             enum "1552.88" {
               description "1552.88 nm/193.05625 THz 6.25GHz spacing";
             }
             enum "1552.83" {
               description "1552.83 nm/193.06250 THz 6.25/12.5GHz spacing";
             }
             enum "1552.78" {
               description "1552.78 nm/193.06875 THz 6.25GHz spacing";
             }
             enum "1552.73" {
               description "1552.73 nm/193.07500 THz 6.25/12.5GHz spacing";
             }
             enum "1552.68" {
               description "1552.68 nm/193.08125 THz 6.25GHz spacing";
             }
             enum "1552.62" {
               description "1552.62 nm/193.08750 THz 6.25/12.5GHz spacing";
             }
             enum "1552.57" {
               description "1552.57 nm/193.09375 THz 6.25GHz spacing";
             }
             enum "1552.52" {
               description "1552.52 nm/193.10000 THz 6.25/12.5/50/75/100GHz spacing";
             }
             enum "1552.47" {
               description "1552.47 nm/193.10625 THz 6.25GHz spacing";
             }
             enum "1552.42" {
               description "1552.42 nm/193.11250 THz 6.25/12.5GHz spacing";
             }
             enum "1552.37" {
               description "1552.37 nm/193.11875 THz 6.25GHz spacing";
             }
             enum "1552.32" {
               description "1552.32 nm/193.12500 THz 6.25/12.5GHz spacing";
             }
             enum "1552.27" {
               description "1552.27 nm/193.13125 THz 6.25GHz spacing";
             }
             enum "1552.22" {
               description "1552.22 nm/193.13750 THz 6.25/12.5GHz spacing";
             }
             enum "1552.17" {
               description "1552.17 nm/193.14375 THz 6.25GHz spacing";
             }
             enum "1552.12" {
               description "1552.12 nm/193.15000 THz 6.25/12.5/50GHz spacing";
             }
             enum "1552.07" {
               description "1552.07 nm/193.15625 THz 6.25GHz spacing";
             }
             enum "1552.02" {
               description "1552.02 nm/193.16250 THz 6.25/12.5GHz spacing";
             }
             enum "1551.97" {
               description "1551.97 nm/193.16875 THz 6.25GHz spacing";
             }
             enum "1551.92" {
               description "1551.92 nm/193.17500 THz 6.25/12.5/75GHz spacing";
             }
             enum "1551.87" {
               description "1551.87 nm/193.18125 THz 6.25GHz spacing";
             }
             enum "1551.82" {
               description "1551.82 nm/193.18750 THz 6.25/12.5GHz spacing";
             }
             enum "1551.77" {
               description "1551.77 nm/193.19375 THz 6.25GHz spacing";
             }
             enum "1551.72" {
               description "1551.72 nm/193.20000 THz 6.25/12.5/50/100GHz spacing";
             }
             enum "1551.67" {
               description "1551.67 nm/193.20625 THz 6.25GHz spacing";
             }
             enum "1551.62" {
               description "1551.62 nm/193.21250 THz 6.25/12.5GHz spacing";
             }
             enum "1551.57" {
               description "1551.57 nm/193.21875 THz 6.25GHz spacing";
             }
             enum "1551.52" {
               description "1551.52 nm/193.22500 THz 6.25/12.5GHz spacing";
             }
             enum "1551.47" {
               description "1551.47 nm/193.23125 THz 6.25GHz spacing";
             }
             enum "1551.42" {
               description "1551.42 nm/193.23750 THz 6.25/12.5GHz spacing";
             }
             enum "1551.37" {
               description "1551.37 nm/193.24375 THz 6.25GHz spacing";
             }
             enum "1551.32" {
               description "1551.32 nm/193.25000 THz 6.25/12.5/50/75GHz spacing";
             }
             enum "1551.27" {
               description "1551.27 nm/193.25625 THz 6.25GHz spacing";
             }
             enum "1551.22" {
               description "1551.22 nm/193.26250 THz 6.25/12.5GHz spacing";
             }
             enum "1551.17" {
               description "1551.17 nm/193.26875 THz 6.25GHz spacing";
             }
             enum "1551.12" {
               description "1551.12 nm/193.27500 THz 6.25/12.5GHz spacing";
             }
             enum "1551.07" {
               description "1551.07 nm/193.28125 THz 6.25GHz spacing";
             }
             enum "1551.02" {
               description "1551.02 nm/193.28750 THz 6.25/12.5GHz spacing";
             }
             enum "1550.97" {
               description "1550.97 nm/193.29375 THz 6.25GHz spacing";
             }
             enum "1550.92" {
               description "1550.92 nm/193.30000 THz 6.25/12.5/50/100GHz spacing";
             }
             enum "1550.87" {
               description "1550.87 nm/193.30625 THz 6.25GHz spacing";
             }
             enum "1550.82" {
               description "1550.82 nm/193.31250 THz 6.25/12.5GHz spacing";
             }
             enum "1550.77" {
               description "1550.77 nm/193.31875 THz 6.25GHz spacing";
             }
             enum "1550.72" {
               description "1550.72 nm/193.32500 THz 6.25/12.5/75GHz spacing";
             }
             enum "1550.67" {
               description "1550.67 nm/193.33125 THz 6.25GHz spacing";
             }
             enum "1550.62" {
               description "1550.62 nm/193.33750 THz 6.25/12.5GHz spacing";
             }
             enum "1550.57" {
               description "1550.57 nm/193.34375 THz 6.25GHz spacing";
             }
             enum "1550.52" {
               description "1550.52 nm/193.35000 THz 6.25/12.5/50GHz spacing";
             }
             enum "1550.47" {
               description "1550.47 nm/193.35625 THz 6.25GHz spacing";
             }
             enum "1550.42" {
               description "1550.42 nm/193.36250 THz 6.25/12.5GHz spacing";
             }
             enum "1550.37" {
               description "1550.37 nm/193.36875 THz 6.25GHz spacing";
             }
             enum "1550.32" {
               description "1550.32 nm/193.37500 THz 6.25/12.5GHz spacing";
             }
             enum "1550.27" {
               description "1550.27 nm/193.38125 THz 6.25GHz spacing";
             }
             enum "1550.22" {
               description "1550.22 nm/193.38750 THz 6.25/12.5GHz spacing";
             }
             enum "1550.17" {
               description "1550.17 nm/193.39375 THz 6.25GHz spacing";
             }
             enum "1550.12" {
               description "1550.12 nm/193.40000 THz 6.25/12.5/50/75/100GHz spacing";
             }
             enum "1550.07" {
               description "1550.07 nm/193.40625 THz 6.25GHz spacing";
             }
             enum "1550.02" {
               description "1550.02 nm/193.41250 THz 6.25/12.5GHz spacing";
             }
             enum "1549.97" {
               description "1549.97 nm/193.41875 THz 6.25GHz spacing";
             }
             enum "1549.92" {
               description "1549.92 nm/193.42500 THz 6.25/12.5GHz spacing";
             }
             enum "1549.87" {
               description "1549.87 nm/193.43125 THz 6.25GHz spacing";
             }
             enum "1549.82" {
               description "1549.82 nm/193.43750 THz 6.25/12.5GHz spacing";
             }
             enum "1549.77" {
               description "1549.77 nm/193.44375 THz 6.25GHz spacing";
             }
             enum "1549.72" {
               description "1549.72 nm/193.45000 THz 6.25/12.5/50GHz spacing";
             }
             enum "1549.67" {
               description "1549.67 nm/193.45625 THz 6.25GHz spacing";
             }
             enum "1549.62" {
               description "1549.62 nm/193.46250 THz 6.25/12.5GHz spacing";
             }
             enum "1549.57" {
               description "1549.57 nm/193.46875 THz 6.25GHz spacing";
             }
             enum "1549.52" {
               description "1549.52 nm/193.47500 THz 6.25/12.5/75GHz spacing";
             }
             enum "1549.47" {
               description "1549.47 nm/193.48125 THz 6.25GHz spacing";
             }
             enum "1549.42" {
               description "1549.42 nm/193.48750 THz 6.25/12.5GHz spacing";
             }
             enum "1549.37" {
               description "1549.37 nm/193.49375 THz 6.25GHz spacing";
             }
             enum "1549.32" {
               description "1549.32 nm/193.50000 THz 6.25/12.5/50/100GHz spacing";
             }
             enum "1549.26" {
               description "1549.26 nm/193.50625 THz 6.25GHz spacing";
             }
             enum "1549.21" {
               description "1549.21 nm/193.51250 THz 6.25/12.5GHz spacing";
             }
             enum "1549.16" {
               description "1549.16 nm/193.51875 THz 6.25GHz spacing";
             }
             enum "1549.11" {
               description "1549.11 nm/193.52500 THz 6.25/12.5GHz spacing";
             }
             enum "1549.06" {
               description "1549.06 nm/193.53125 THz 6.25GHz spacing";
             }
             enum "1549.01" {
               description "1549.01 nm/193.53750 THz 6.25/12.5GHz spacing";
             }
             enum "1548.96" {
               description "1548.96 nm/193.54375 THz 6.25GHz spacing";
             }
             enum "1548.91" {
               description "1548.91 nm/193.55000 THz 6.25/12.5/50G/75Hz spacing";
             }
             enum "1548.86" {
               description "1548.86 nm/193.55625 THz 6.25GHz spacing";
             }
             enum "1548.81" {
               description "1548.81 nm/193.56250 THz 6.25/12.5GHz spacing";
             }
             enum "1548.76" {
               description "1548.76 nm/193.56875 THz 6.25GHz spacing";
             }
             enum "1548.71" {
               description "1548.71 nm/193.57500 THz 6.25/12.5GHz spacing";
             }
             enum "1548.66" {
               description "1548.66 nm/193.58125 THz 6.25GHz spacing";
             }
             enum "1548.61" {
               description "1548.61 nm/193.58750 THz 6.25/12.5GHz spacing";
             }
             enum "1548.56" {
               description "1548.56 nm/193.59375 THz 6.25GHz spacing";
             }
             enum "1548.51" {
               description "1548.51 nm/193.60000 THz 6.25/12.5/50/100GHz spacing";
             }
             enum "1548.46" {
               description "1548.46 nm/193.60625 THz 6.25GHz spacing";
             }
             enum "1548.41" {
               description "1548.41 nm/193.61250 THz 6.25/12.5GHz spacing";
             }
             enum "1548.36" {
               description "1548.36 nm/193.61875 THz 6.25GHz spacing";
             }
             enum "1548.31" {
               description "1548.31 nm/193.62500 THz 6.25/12.5/75GHz spacing";
             }
             enum "1548.26" {
               description "1548.26 nm/193.63125 THz 6.25GHz spacing";
             }
             enum "1548.21" {
               description "1548.21 nm/193.63750 THz 6.25/12.5GHz spacing";
             }
             enum "1548.16" {
               description "1548.16 nm/193.64375 THz 6.25GHz spacing";
             }
             enum "1548.11" {
               description "1548.11 nm/193.65000 THz 6.25/12.5/50GHz spacing";
             }
             enum "1548.06" {
               description "1548.06 nm/193.65625 THz 6.25GHz spacing";
             }
             enum "1548.02" {
               description "1548.02 nm/193.66250 THz 6.25/12.5GHz spacing";
             }
             enum "1547.97" {
               description "1547.97 nm/193.66875 THz 6.25GHz spacing";
             }
             enum "1547.92" {
               description "1547.92 nm/193.67500 THz 6.25/12.5GHz spacing";
             }
             enum "1547.87" {
               description "1547.87 nm/193.68125 THz 6.25GHz spacing";
             }
             enum "1547.82" {
               description "1547.82 nm/193.68750 THz 6.25/12.5GHz spacing";
             }
             enum "1547.77" {
               description "1547.77 nm/193.69375 THz 6.25GHz spacing";
             }
             enum "1547.72" {
               description "1547.72 nm/193.70000 THz 6.25/12.5/50/75/100GHz spacing";
             }
             enum "1547.67" {
               description "1547.67 nm/193.70625 THz 6.25GHz spacing";
             }
             enum "1547.62" {
               description "1547.62 nm/193.71250 THz 6.25/12.5GHz spacing";
             }
             enum "1547.57" {
               description "1547.57 nm/193.71875 THz 6.25GHz spacing";
             }
             enum "1547.52" {
               description "1547.52 nm/193.72500 THz 6.25/12.5GHz spacing";
             }
             enum "1547.47" {
               description "1547.47 nm/193.73125 THz 6.25GHz spacing";
             }
             enum "1547.42" {
               description "1547.42 nm/193.73750 THz 6.25/12.5GHz spacing";
             }
             enum "1547.37" {
               description "1547.37 nm/193.74375 THz 6.25GHz spacing";
             }
             enum "1547.32" {
               description "1547.32 nm/193.75000 THz 6.25/12.5/50GHz spacing";
             }
             enum "1547.27" {
               description "1547.27 nm/193.75625 THz 6.25GHz spacing";
             }
             enum "1547.22" {
               description "1547.22 nm/193.76250 THz 6.25/12.5GHz spacing";
             }
             enum "1547.17" {
               description "1547.17 nm/193.76875 THz 6.25GHz spacing";
             }
             enum "1547.12" {
               description "1547.12 nm/193.77500 THz 6.25/12.5/75GHz spacing";
             }
             enum "1547.07" {
               description "1547.07 nm/193.78125 THz 6.25GHz spacing";
             }
             enum "1547.02" {
               description "1547.02 nm/193.78750 THz 6.25/12.5GHz spacing";
             }
             enum "1546.97" {
               description "1546.97 nm/193.79375 THz 6.25GHz spacing";
             }
             enum "1546.92" {
               description "1546.92 nm/193.80000 THz 6.25/12.5/50/100GHz spacing";
             }
             enum "1546.87" {
               description "1546.87 nm/193.80625 THz 6.25GHz spacing";
             }
             enum "1546.82" {
               description "1546.82 nm/193.81250 THz 6.25/12.5GHz spacing";
             }
             enum "1546.77" {
               description "1546.77 nm/193.81875 THz 6.25GHz spacing";
             }
             enum "1546.72" {
               description "1546.72 nm/193.82500 THz 6.25/12.5GHz spacing";
             }
             enum "1546.67" {
               description "1546.67 nm/193.83125 THz 6.25GHz spacing";
             }
             enum "1546.62" {
               description "1546.62 nm/193.83750 THz 6.25/12.5GHz spacing";
             }
             enum "1546.57" {
               description "1546.57 nm/193.84375 THz 6.25GHz spacing";
             }
             enum "1546.52" {
               description "1546.52 nm/193.85000 THz 6.25/12.5/50/75GHz spacing";
             }
             enum "1546.47" {
               description "1546.47 nm/193.85625 THz 6.25GHz spacing";
             }
             enum "1546.42" {
               description "1546.42 nm/193.86250 THz 6.25/12.5GHz spacing";
             }
             enum "1546.37" {
               description "1546.37 nm/193.86875 THz 6.25GHz spacing";
             }
             enum "1546.32" {
               description "1546.32 nm/193.87500 THz 6.25/12.5GHz spacing";
             }
             enum "1546.27" {
               description "1546.27 nm/193.88125 THz 6.25GHz spacing";
             }
             enum "1546.22" {
               description "1546.22 nm/193.88750 THz 6.25/12.5GHz spacing";
             }
             enum "1546.17" {
               description "1546.17 nm/193.89375 THz 6.25GHz spacing";
             }
             enum "1546.12" {
               description "1546.12 nm/193.90000 THz 6.25/12.5/50/100GHz spacing";
             }
             enum "1546.07" {
               description "1546.07 nm/193.90625 THz 6.25GHz spacing";
             }
             enum "1546.02" {
               description "1546.02 nm/193.91250 THz 6.25/12.5GHz spacing";
             }
             enum "1545.97" {
               description "1545.97 nm/193.91875 THz 6.25GHz spacing";
             }
             enum "1545.92" {
               description "1545.92 nm/193.92500 THz 6.25/12.5/75GHz spacing";
             }
             enum "1545.87" {
               description "1545.87 nm/193.93125 THz 6.25GHz spacing";
             }
             enum "1545.82" {
               description "1545.82 nm/193.93750 THz 6.25/12.5GHz spacing";
             }
             enum "1545.77" {
               description "1545.77 nm/193.94375 THz 6.25GHz spacing";
             }
             enum "1545.72" {
               description "1545.72 nm/193.95000 THz 6.25/12.5/50GHz spacing";
             }
             enum "1545.67" {
               description "1545.67 nm/193.95625 THz 6.25GHz spacing";
             }
             enum "1545.62" {
               description "1545.62 nm/193.96250 THz 6.25/12.5GHz spacing";
             }
             enum "1545.57" {
               description "1545.57 nm/193.96875 THz 6.25GHz spacing";
             }
             enum "1545.52" {
               description "1545.52 nm/193.97500 THz 6.25/12.5GHz spacing";
             }
             enum "1545.47" {
               description "1545.47 nm/193.98125 THz 6.25GHz spacing";
             }
             enum "1545.42" {
               description "1545.42 nm/193.98750 THz 6.25/12.5GHz spacing";
             }
             enum "1545.37" {
               description "1545.37 nm/193.99375 THz 6.25GHz spacing";
             }
             enum "1545.32" {
               description "1545.32 nm/194.00000 THz 6.25/12.5/50/75/100GHz spacing";
             }
             enum "1545.27" {
               description "1545.27 nm/194.00625 THz 6.25GHz spacing";
             }
             enum "1545.22" {
               description "1545.22 nm/194.01250 THz 6.25/12.5GHz spacing";
             }
             enum "1545.17" {
               description "1545.17 nm/194.01875 THz 6.25GHz spacing";
             }
             enum "1545.12" {
               description "1545.12 nm/194.02500 THz 6.25/12.5GHz spacing";
             }
             enum "1545.07" {
               description "1545.07 nm/194.03125 THz 6.25GHz spacing";
             }
             enum "1545.02" {
               description "1545.02 nm/194.03750 THz 6.25/12.5GHz spacing";
             }
             enum "1544.97" {
               description "1544.97 nm/194.04375 THz 6.25GHz spacing";
             }
             enum "1544.92" {
               description "1544.92 nm/194.05000 THz 6.25/12.5/50GHz spacing";
             }
             enum "1544.87" {
               description "1544.87 nm/194.05625 THz 6.25GHz spacing";
             }
             enum "1544.82" {
               description "1544.82 nm/194.06250 THz 6.25/12.5GHz spacing";
             }
             enum "1544.77" {
               description "1544.77 nm/194.06875 THz 6.25GHz spacing";
             }
             enum "1544.72" {
               description "1544.72 nm/194.07500 THz 6.25/12.5/75GHz spacing";
             }
             enum "1544.68" {
               description "1544.68 nm/194.08125 THz 6.25GHz spacing";
             }
             enum "1544.63" {
               description "1544.63 nm/194.08750 THz 6.25/12.5GHz spacing";
             }
             enum "1544.58" {
               description "1544.58 nm/194.09375 THz 6.25GHz spacing";
             }
             enum "1544.53" {
               description "1544.53 nm/194.10000 THz 6.25/12.5/50/100GHz spacing";
             }
             enum "1544.48" {
               description "1544.48 nm/194.10625 THz 6.25GHz spacing";
             }
             enum "1544.43" {
               description "1544.43 nm/194.11250 THz 6.25/12.5GHz spacing";
             }
             enum "1544.38" {
               description "1544.38 nm/194.11875 THz 6.25GHz spacing";
             }
             enum "1544.33" {
               description "1544.33 nm/194.12500 THz 6.25/12.5GHz spacing";
             }
             enum "1544.28" {
               description "1544.28 nm/194.13125 THz 6.25GHz spacing";
             }
             enum "1544.23" {
               description "1544.23 nm/194.13750 THz 6.25/12.5GHz spacing";
             }
             enum "1544.18" {
               description "1544.18 nm/194.14375 THz 6.25GHz spacing";
             }
             enum "1544.13" {
               description "1544.13 nm/194.15000 THz 6.25/12.5/50/75GHz spacing";
             }
             enum "1544.08" {
               description "1544.08 nm/194.15625 THz 6.25GHz spacing";
             }
             enum "1544.03" {
               description "1544.03 nm/194.16250 THz 6.25/12.5GHz spacing";
             }
             enum "1543.98" {
               description "1543.98 nm/194.16875 THz 6.25GHz spacing";
             }
             enum "1543.93" {
               description "1543.93 nm/194.17500 THz 6.25/12.5GHz spacing";
             }
             enum "1543.88" {
               description "1543.88 nm/194.18125 THz 6.25GHz spacing";
             }
             enum "1543.83" {
               description "1543.83 nm/194.18750 THz 6.25/12.5GHz spacing";
             }
             enum "1543.78" {
               description "1543.78 nm/194.19375 THz 6.25GHz spacing";
             }
             enum "1543.73" {
               description "1543.73 nm/194.20000 THz 6.25/12.5/50/100GHz spacing";
             }
             enum "1543.68" {
               description "1543.68 nm/194.20625 THz 6.25GHz spacing";
             }
             enum "1543.63" {
               description "1543.63 nm/194.21250 THz 6.25/12.5GHz spacing";
             }
             enum "1543.58" {
               description "1543.58 nm/194.21875 THz 6.25GHz spacing";
             }
             enum "1543.53" {
               description "1543.53 nm/194.22500 THz 6.25/12.5/75GHz spacing";
             }
             enum "1543.48" {
               description "1543.48 nm/194.23125 THz 6.25GHz spacing";
             }
             enum "1543.43" {
               description "1543.43 nm/194.23750 THz 6.25/12.5GHz spacing";
             }
             enum "1543.38" {
               description "1543.38 nm/194.24375 THz 6.25GHz spacing";
             }
             enum "1543.33" {
               description "1543.33 nm/194.25000 THz 6.25/12.5/50GHz spacing";
             }
             enum "1543.28" {
               description "1543.28 nm/194.25625 THz 6.25GHz spacing";
             }
             enum "1543.23" {
               description "1543.23 nm/194.26250 THz 6.25/12.5GHz spacing";
             }
             enum "1543.18" {
               description "1543.18 nm/194.26875 THz 6.25GHz spacing";
             }
             enum "1543.13" {
               description "1543.13 nm/194.27500 THz 6.25/12.5GHz spacing";
             }
             enum "1543.08" {
               description "1543.08 nm/194.28125 THz 6.25GHz spacing";
             }
             enum "1543.04" {
               description "1543.04 nm/194.28750 THz 6.25/12.5GHz spacing";
             }
             enum "1542.99" {
               description "1542.99 nm/194.29375 THz 6.25GHz spacing";
             }
             enum "1542.94" {
               description "1542.94 nm/194.30000 THz 6.25/12.5/50/75/100GHz spacing";
             }
             enum "1542.89" {
               description "1542.89 nm/194.30625 THz 6.25GHz spacing";
             }
             enum "1542.84" {
               description "1542.84 nm/194.31250 THz 6.25/12.5GHz spacing";
             }
             enum "1542.79" {
               description "1542.79 nm/194.31875 THz 6.25GHz spacing";
             }
             enum "1542.74" {
               description "1542.74 nm/194.32500 THz 6.25/12.5GHz spacing";
             }
             enum "1542.69" {
               description "1542.69 nm/194.33125 THz 6.25GHz spacing";
             }
             enum "1542.64" {
               description "1542.64 nm/194.33750 THz 6.25/12.5GHz spacing";
             }
             enum "1542.59" {
               description "1542.59 nm/194.34375 THz 6.25GHz spacing";
             }
             enum "1542.54" {
               description "1542.54 nm/194.35000 THz 6.25/12.5/50GHz spacing";
             }
             enum "1542.49" {
               description "1542.49 nm/194.35625 THz 6.25GHz spacing";
             }
             enum "1542.44" {
               description "1542.44 nm/194.36250 THz 6.25/12.5GHz spacing";
             }
             enum "1542.39" {
               description "1542.39 nm/194.36875 THz 6.25GHz spacing";
             }
             enum "1542.34" {
               description "1542.34 nm/194.37500 THz 6.25/12.5/75GHz spacing";
             }
             enum "1542.29" {
               description "1542.29 nm/194.38125 THz 6.25GHz spacing";
             }
             enum "1542.24" {
               description "1542.24 nm/194.38750 THz 6.25/12.5GHz spacing";
             }
             enum "1542.19" {
               description "1542.19 nm/194.39375 THz 6.25GHz spacing";
             }
             enum "1542.14" {
               description "1542.14 nm/194.40000 THz 6.25/12.5/50/100GHz spacing";
             }
             enum "1542.09" {
               description "1542.09 nm/194.40625 THz 6.25GHz spacing";
             }
             enum "1542.04" {
               description "1542.04 nm/194.41250 THz 6.25/12.5GHz spacing";
             }
             enum "1541.99" {
               description "1541.99 nm/194.41875 THz 6.25GHz spacing";
             }
             enum "1541.94" {
               description "1541.94 nm/194.42500 THz 6.25/12.5GHz spacing";
             }
             enum "1541.89" {
               description "1541.89 nm/194.43125 THz 6.25GHz spacing";
             }
             enum "1541.84" {
               description "1541.84 nm/194.43750 THz 6.25/12.5GHz spacing";
             }
             enum "1541.80" {
               description "1541.80 nm/194.44375 THz 6.25GHz spacing";
             }
             enum "1541.75" {
               description "1541.75 nm/194.45000 THz 6.25/12.5/50/75GHz spacing";
             }
             enum "1541.70" {
               description "1541.70 nm/194.45625 THz 6.25GHz spacing";
             }
             enum "1541.65" {
               description "1541.65 nm/194.46250 THz 6.25/12.5GHz spacing";
             }
             enum "1541.60" {
               description "1541.60 nm/194.46875 THz 6.25GHz spacing";
             }
             enum "1541.55" {
               description "1541.55 nm/194.47500 THz 6.25/12.5GHz spacing";
             }
             enum "1541.50" {
               description "1541.50 nm/194.48125 THz 6.25GHz spacing";
             }
             enum "1541.45" {
               description "1541.45 nm/194.48750 THz 6.25/12.5GHz spacing";
             }
             enum "1541.40" {
               description "1541.40 nm/194.49375 THz 6.25GHz spacing";
             }
             enum "1541.35" {
               description "1541.35 nm/194.50000 THz 6.25/12.5/50/100GHz spacing";
             }
             enum "1541.30" {
               description "1541.30 nm/194.50625 THz 6.25GHz spacing";
             }
             enum "1541.25" {
               description "1541.25 nm/194.51250 THz 6.25/12.5GHz spacing";
             }
             enum "1541.20" {
               description "1541.20 nm/194.51875 THz 6.25GHz spacing";
             }
             enum "1541.15" {
               description "1541.15 nm/194.52500 THz 6.25/12.5/75GHz spacing";
             }
             enum "1541.10" {
               description "1541.10 nm/194.53125 THz 6.25GHz spacing";
             }
             enum "1541.05" {
               description "1541.05 nm/194.53750 THz 6.25/12.5GHz spacing";
             }
             enum "1541.00" {
               description "1541.00 nm/194.54375 THz 6.25GHz spacing";
             }
             enum "1540.95" {
               description "1540.95 nm/194.55000 THz 6.25/12.5/50GHz spacing";
             }
             enum "1540.90" {
               description "1540.90 nm/194.55625 THz 6.25GHz spacing";
             }
             enum "1540.85" {
               description "1540.85 nm/194.56250 THz 6.25/12.5GHz spacing";
             }
             enum "1540.80" {
               description "1540.80 nm/194.56875 THz 6.25GHz spacing";
             }
             enum "1540.76" {
               description "1540.76 nm/194.57500 THz 6.25/12.5GHz spacing";
             }
             enum "1540.71" {
               description "1540.71 nm/194.58125 THz 6.25GHz spacing";
             }
             enum "1540.66" {
               description "1540.66 nm/194.58750 THz 6.25/12.5GHz spacing";
             }
             enum "1540.61" {
               description "1540.61 nm/194.59375 THz 6.25GHz spacing";
             }
             enum "1540.56" {
               description "1540.56 nm/194.60000 THz 6.25/12.5/50/75/100GHz spacing";
             }
             enum "1540.51" {
               description "1540.51 nm/194.60625 THz 6.25GHz spacing";
             }
             enum "1540.46" {
               description "1540.46 nm/194.61250 THz 6.25/12.5GHz spacing";
             }
             enum "1540.41" {
               description "1540.41 nm/194.61875 THz 6.25GHz spacing";
             }
             enum "1540.36" {
               description "1540.36 nm/194.62500 THz 6.25/12.5GHz spacing";
             }
             enum "1540.31" {
               description "1540.31 nm/194.63125 THz 6.25GHz spacing";
             }
             enum "1540.26" {
               description "1540.26 nm/194.63750 THz 6.25/12.5GHz spacing";
             }
             enum "1540.21" {
               description "1540.21 nm/194.64375 THz 6.25GHz spacing";
             }
             enum "1540.16" {
               description "1540.16 nm/194.65000 THz 6.25/12.5/50GHz spacing";
             }
             enum "1540.11" {
               description "1540.11 nm/194.65625 THz 6.25GHz spacing";
             }
             enum "1540.06" {
               description "1540.06 nm/194.66250 THz 6.25/12.5GHz spacing";
             }
             enum "1540.01" {
               description "1540.01 nm/194.66875 THz 6.25GHz spacing";
             }
             enum "1539.96" {
               description "1539.96 nm/194.67500 THz 6.25/12.5/50/75GHz spacing";
             }
             enum "1539.91" {
               description "1539.91 nm/194.68125 THz 6.25GHz spacing";
             }
             enum "1539.86" {
               description "1539.86 nm/194.68750 THz 6.25/12.5GHz spacing";
             }
             enum "1539.82" {
               description "1539.82 nm/194.69375 THz 6.25GHz spacing";
             }
             enum "1539.77" {
               description "1539.77 nm/194.70000 THz 6.25/12.5/50/100GHz spacing";
             }
             enum "1539.72" {
               description "1539.72 nm/194.70625 THz 6.25GHz spacing";
             }
             enum "1539.67" {
               description "1539.67 nm/194.71250 THz 6.25/12.5GHz spacing";
             }
             enum "1539.62" {
               description "1539.62 nm/194.71875 THz 6.25GHz spacing";
             }
             enum "1539.57" {
               description "1539.57 nm/194.72500 THz 6.25/12.5GHz spacing";
             }
             enum "1539.52" {
               description "1539.52 nm/194.73125 THz 6.25GHz spacing";
             }
             enum "1539.47" {
               description "1539.47 nm/194.73750 THz 6.25/12.5GHz spacing";
             }
             enum "1539.42" {
               description "1539.42 nm/194.74375 THz 6.25GHz spacing";
             }
             enum "1539.37" {
               description "1539.37 nm/194.75000 THz 6.25/12.5/50/75GHz spacing";
             }
             enum "1539.32" {
               description "1539.32 nm/194.75625 THz 6.25GHz spacing";
             }
             enum "1539.27" {
               description "1539.27 nm/194.76250 THz 6.25/12.5GHz spacing";
             }
             enum "1539.22" {
               description "1539.22 nm/194.76875 THz 6.25GHz spacing";
             }
             enum "1539.17" {
               description "1539.17 nm/194.77500 THz 6.25/12.5GHz spacing";
             }
             enum "1539.12" {
               description "1539.12 nm/194.78125 THz 6.25GHz spacing";
             }
             enum "1539.07" {
               description "1539.07 nm/194.78750 THz 6.25/12.5GHz spacing";
             }
             enum "1539.03" {
               description "1539.03 nm/194.79375 THz 6.25GHz spacing";
             }
             enum "1538.98" {
               description "1538.98 nm/194.80000 THz 6.25/12.5/50/100GHz spacing";
             }
             enum "1538.93" {
               description "1538.93 nm/194.80625 THz 6.25GHz spacing";
             }
             enum "1538.88" {
               description "1538.88 nm/194.81250 THz 6.25/12.5GHz spacing";
             }
             enum "1538.83" {
               description "1538.83 nm/194.81875 THz 6.25GHz spacing";
             }
             enum "1538.78" {
               description "1538.78 nm/194.82500 THz 6.25/12.5/75GHz spacing";
             }
             enum "1538.73" {
               description "1538.73 nm/194.83125 THz 6.25GHz spacing";
             }
             enum "1538.68" {
               description "1538.68 nm/194.83750 THz 6.25/12.5GHz spacing";
             }
             enum "1538.63" {
               description "1538.63 nm/194.84375 THz 6.25GHz spacing";
             }
             enum "1538.58" {
               description "1538.58 nm/194.85000 THz 6.25/12.5/50GHz spacing";
             }
             enum "1538.53" {
               description "1538.53 nm/194.85625 THz 6.25GHz spacing";
             }
             enum "1538.48" {
               description "1538.48 nm/194.86250 THz 6.25/12.5GHz spacing";
             }
             enum "1538.43" {
               description "1538.43 nm/194.86875 THz 6.25GHz spacing";
             }
             enum "1538.38" {
               description "1538.38 nm/194.87500 THz 6.25/12.5/75GHz spacing";
             }
             enum "1538.33" {
               description "1538.33 nm/194.88125 THz 6.25GHz spacing";
             }
             enum "1538.28" {
               description "1538.28 nm/194.88750 THz 6.25/12.5GHz spacing";
             }
             enum "1538.24" {
               description "1538.24 nm/194.89375 THz 6.25GHz spacing";
             }
             enum "1538.19" {
               description "1538.19 nm/194.90000 THz 6.25/12.5/50/75/100GHz spacing";
             }
             enum "1538.14" {
               description "1538.14 nm/194.90625 THz 6.25GHz spacing";
             }
             enum "1538.09" {
               description "1538.09 nm/194.91250 THz 6.25/12.5GHz spacing";
             }
             enum "1538.04" {
               description "1538.04 nm/194.91875 THz 6.25GHz spacing";
             }
             enum "1537.99" {
               description "1537.99 nm/194.92500 THz 6.25/12.5GHz spacing";
             }
             enum "1537.94" {
               description "1537.94 nm/194.93125 THz 6.25GHz spacing";
             }
             enum "1537.89" {
               description "1537.89 nm/194.93750 THz 6.25/12.5GHz spacing";
             }
             enum "1537.84" {
               description "1537.84 nm/194.94375 THz 6.25GHz spacing";
             }
             enum "1537.79" {
               description "1537.79 nm/194.95000 THz 6.25/12.5/50GHz spacing";
             }
             enum "1537.74" {
               description "1537.74 nm/194.95625 THz 6.25GHz spacing";
             }
             enum "1537.69" {
               description "1537.69 nm/194.96250 THz 6.25/12.5GHz spacing";
             }
             enum "1537.64" {
               description "1537.64 nm/194.96875 THz 6.25GHz spacing";
             }
             enum "1537.59" {
               description "1537.59 nm/194.97500 THz 6.25/12.5/75GHz spacing";
             }
             enum "1537.55" {
               description "1537.55 nm/194.98125 THz 6.25GHz spacing";
             }
             enum "1537.50" {
               description "1537.50 nm/194.98750 THz 6.25/12.5GHz spacing";
             }
             enum "1537.45" {
               description "1537.45 nm/194.99375 THz 6.25GHz spacing";
             }
             enum "1537.40" {
               description "1537.40 nm/195.00000 THz 6.25/12.5/50/100GHz spacing";
             }
             enum "1537.35" {
               description "1537.35 nm/195.00625 THz 6.25GHz spacing";
             }
             enum "1537.30" {
               description "1537.30 nm/195.01250 THz 6.25/12.5GHz spacing";
             }
             enum "1537.25" {
               description "1537.25 nm/195.01875 THz 6.25GHz spacing";
             }
             enum "1537.20" {
               description "1537.20 nm/195.02500 THz 6.25/12.5GHz spacing";
             }
             enum "1537.15" {
               description "1537.15 nm/195.03125 THz 6.25GHz spacing";
             }
             enum "1537.10" {
               description "1537.10 nm/195.03750 THz 6.25/12.5GHz spacing";
             }
             enum "1537.05" {
               description "1537.05 nm/195.04375 THz 6.25GHz spacing";
             }
             enum "1537.00" {
               description "1537.00 nm/195.05000 THz 6.25/12.5/50/75GHz spacing";
             }
             enum "1536.95" {
               description "1536.95 nm/195.05625 THz 6.25GHz spacing";
             }
             enum "1536.90" {
               description "1536.90 nm/195.06250 THz 6.25/12.5GHz spacing";
             }
             enum "1536.86" {
               description "1536.86 nm/195.06875 THz 6.25GHz spacing";
             }
             enum "1536.81" {
               description "1536.81 nm/195.07500 THz 6.25/12.5GHz spacing";
             }
             enum "1536.76" {
               description "1536.76 nm/195.08125 THz 6.25GHz spacing";
             }
             enum "1536.71" {
               description "1536.71 nm/195.08750 THz 6.25/12.5GHz spacing";
             }
             enum "1536.66" {
               description "1536.66 nm/195.09375 THz 6.25GHz spacing";
             }
             enum "1536.61" {
               description "1536.61 nm/195.10000 THz 6.25/12.5/50/100GHz spacing";
             }
             enum "1536.56" {
               description "1536.56 nm/195.10625 THz 6.25GHz spacing";
             }
             enum "1536.51" {
               description "1536.51 nm/195.11250 THz 6.25/12.5GHz spacing";
             }
             enum "1536.46" {
               description "1536.46 nm/195.11875 THz 6.25GHz spacing";
             }
             enum "1536.41" {
               description "1536.41 nm/195.12500 THz 6.25/12.5/75GHz spacing";
             }
             enum "1536.36" {
               description "1536.36 nm/195.13125 THz 6.25GHz spacing";
             }
             enum "1536.31" {
               description "1536.31 nm/195.13750 THz 6.25/12.5GHz spacing";
             }
             enum "1536.26" {
               description "1536.26 nm/195.14375 THz 6.25GHz spacing";
             }
             enum "1536.22" {
               description "1536.22 nm/195.15000 THz 6.25/12.5/50GHz spacing";
             }
             enum "1536.17" {
               description "1536.17 nm/195.15625 THz 6.25GHz spacing";
             }
             enum "1536.12" {
               description "1536.12 nm/195.16250 THz 6.25/12.5GHz spacing";
             }
             enum "1536.07" {
               description "1536.07 nm/195.16875 THz 6.25GHz spacing";
             }
             enum "1536.02" {
               description "1536.02 nm/195.17500 THz 6.25/12.5GHz spacing";
             }
             enum "1535.97" {
               description "1535.97 nm/195.18125 THz 6.25GHz spacing";
             }
             enum "1535.92" {
               description "1535.92 nm/195.18750 THz 6.25/12.5GHz spacing";
             }
             enum "1535.87" {
               description "1535.87 nm/195.19375 THz 6.25GHz spacing";
             }
             enum "1535.82" {
               description "1535.82 nm/195.20000 THz 6.25/12.5/50/75/100GHz spacing";
             }
             enum "1535.77" {
               description "1535.77 nm/195.20625 THz 6.25GHz spacing";
             }
             enum "1535.72" {
               description "1535.72 nm/195.21250 THz 6.25/12.5GHz spacing";
             }
             enum "1535.67" {
               description "1535.67 nm/195.21875 THz 6.25GHz spacing";
             }
             enum "1535.63" {
               description "1535.63 nm/195.22500 THz 6.25/12.5GHz spacing";
             }
             enum "1535.58" {
               description "1535.58 nm/195.23125 THz 6.25GHz spacing";
             }
             enum "1535.53" {
               description "1535.53 nm/195.23750 THz 6.25/12.5GHz spacing";
             }
             enum "1535.48" {
               description "1535.48 nm/195.24375 THz 6.25GHz spacing";
             }
             enum "1535.43" {
               description "1535.43 nm/195.25000 THz 6.25/12.5/50GHz spacing";
             }
             enum "1535.38" {
               description "1535.38 nm/195.25625 THz 6.25GHz spacing";
             }
             enum "1535.33" {
               description "1535.33 nm/195.26250 THz 6.25/12.5GHz spacing";
             }
             enum "1535.28" {
               description "1535.28 nm/195.26875 THz 6.25GHz spacing";
             }
             enum "1535.23" {
               description "1535.23 nm/195.27500 THz 6.25/12.5/75GHz spacing";
             }
             enum "1535.18" {
               description "1535.18 nm/195.28125 THz 6.25GHz spacing";
             }
             enum "1535.13" {
               description "1535.13 nm/195.28750 THz 6.25/12.5GHz spacing";
             }
             enum "1535.08" {
               description "1535.08 nm/195.29375 THz 6.25GHz spacing";
             }
             enum "1535.04" {
               description "1535.04 nm/195.30000 THz 6.25/12.5/50/100GHz spacing";
             }
             enum "1534.99" {
               description "1534.99 nm/195.30625 THz 6.25GHz spacing";
             }
             enum "1534.94" {
               description "1534.94 nm/195.31250 THz 6.25/12.5GHz spacing";
             }
             enum "1534.89" {
               description "1534.89 nm/195.31875 THz 6.25GHz spacing";
             }
             enum "1534.84" {
               description "1534.84 nm/195.32500 THz 6.25/12.5GHz spacing";
             }
             enum "1534.79" {
               description "1534.79 nm/195.33125 THz 6.25GHz spacing";
             }
             enum "1534.74" {
               description "1534.74 nm/195.33750 THz 6.25/12.5GHz spacing";
             }
             enum "1534.69" {
               description "1534.69 nm/195.34375 THz 6.25GHz spacing";
             }
             enum "1534.64" {
               description "1534.64 nm/195.35000 THz 6.25/12.5/50/75GHz spacing";
             }
             enum "1534.59" {
               description "1534.59 nm/195.35625 THz 6.25GHz spacing";
             }
             enum "1534.54" {
               description "1534.54 nm/195.36250 THz 6.25/12.5GHz spacing";
             }
             enum "1534.50" {
               description "1534.50 nm/195.36875 THz 6.25GHz spacing";
             }
             enum "1534.45" {
               description "1534.45 nm/195.37500 THz 6.25/12.5GHz spacing";
             }
             enum "1534.40" {
               description "1534.40 nm/195.38125 THz 6.25GHz spacing";
             }
             enum "1534.35" {
               description "1534.35 nm/195.38750 THz 6.25/12.5GHz spacing";
             }
             enum "1534.30" {
               description "1534.30 nm/195.39375 THz 6.25GHz spacing";
             }
             enum "1534.25" {
               description "1534.25 nm/195.40000 THz 6.25/12.5/50/100GHz spacing";
             }
             enum "1534.20" {
               description "1534.20 nm/195.40625 THz 6.25GHz spacing";
             }
             enum "1534.15" {
               description "1534.15 nm/195.41250 THz 6.25/12.5GHz spacing";
             }
             enum "1534.10" {
               description "1534.10 nm/195.41875 THz 6.25GHz spacing";
             }
             enum "1534.05" {
               description "1534.05 nm/195.42500 THz 6.25/12.5/75GHz spacing";
             }
             enum "1534.00" {
               description "1534.00 nm/195.43125 THz 6.25GHz spacing";
             }
             enum "1533.96" {
               description "1533.96 nm/195.43750 THz 6.25/12.5GHz spacing";
             }
             enum "1533.91" {
               description "1533.91 nm/195.44375 THz 6.25GHz spacing";
             }
             enum "1533.86" {
               description "1533.86 nm/195.45000 THz 6.25/12.5/50GHz spacing";
             }
             enum "1533.81" {
               description "1533.81 nm/195.45625 THz 6.25GHz spacing";
             }
             enum "1533.76" {
               description "1533.76 nm/195.46250 THz 6.25/12.5GHz spacing";
             }
             enum "1533.71" {
               description "1533.71 nm/195.46875 THz 6.25GHz spacing";
             }
             enum "1533.66" {
               description "1533.66 nm/195.47500 THz 6.25/12.5GHz spacing";
             }
             enum "1533.61" {
               description "1533.61 nm/195.48125 THz 6.25GHz spacing";
             }
             enum "1533.56" {
               description "1533.56 nm/195.48750 THz 6.25/12.5GHz spacing";
             }
             enum "1533.51" {
               description "1533.51 nm/195.49375 THz 6.25GHz spacing";
             }
             enum "1533.47" {
               description "1533.47 nm/195.50000 THz 6.25/12.5/50/75/100GHz spacing";
             }
             enum "1533.42" {
               description "1533.42 nm/195.50625 THz 6.25GHz spacing";
             }
             enum "1533.37" {
               description "1533.37 nm/195.51250 THz 6.25/12.5GHz spacing";
             }
             enum "1533.32" {
               description "1533.32 nm/195.51875 THz 6.25GHz spacing";
             }
             enum "1533.27" {
               description "1533.27 nm/195.52500 THz 6.25/12.5GHz spacing";
             }
             enum "1533.22" {
               description "1533.22 nm/195.53125 THz 6.25GHz spacing";
             }
             enum "1533.17" {
               description "1533.17 nm/195.53750 THz 6.25/12.5GHz spacing";
             }
             enum "1533.12" {
               description "1533.12 nm/195.54375 THz 6.25GHz spacing";
             }
             enum "1533.07" {
               description "1533.07 nm/195.55000 THz 6.25/12.5/50GHz spacing";
             }
             enum "1533.02" {
               description "1533.02 nm/195.55625 THz 6.25GHz spacing";
             }
             enum "1532.98" {
               description "1532.98 nm/195.56250 THz 6.25/12.5GHz spacing";
             }
             enum "1532.93" {
               description "1532.93 nm/195.56875 THz 6.25GHz spacing";
             }
             enum "1532.88" {
               description "1532.88 nm/195.57500 THz 6.25/12.5/75GHz spacing";
             }
             enum "1532.83" {
               description "1532.83 nm/195.58125 THz 6.25GHz spacing";
             }
             enum "1532.78" {
               description "1532.78 nm/195.58750 THz 6.25/12.5GHz spacing";
             }
             enum "1532.73" {
               description "1532.73 nm/195.59375 THz 6.25GHz spacing";
             }
             enum "1532.68" {
               description "1532.68 nm/195.60000 THz 6.25/12.5/50/100GHz spacing";
             }
             enum "1532.63" {
               description "1532.63 nm/195.60625 THz 6.25GHz spacing";
             }
             enum "1532.58" {
               description "1532.58 nm/195.61250 THz 6.25/12.5GHz spacing";
             }
             enum "1532.53" {
               description "1532.53 nm/195.61875 THz 6.25GHz spacing";
             }
             enum "1532.49" {
               description "1532.49 nm/195.62500 THz 6.25/12.5GHz spacing";
             }
             enum "1532.44" {
               description "1532.44 nm/195.63125 THz 6.25GHz spacing";
             }
             enum "1532.39" {
               description "1532.39 nm/195.63750 THz 6.25/12.5GHz spacing";
             }
             enum "1532.34" {
               description "1532.34 nm/195.64375 THz 6.25GHz spacing";
             }
             enum "1532.29" {
               description "1532.29 nm/195.65000 THz 6.25/12.5/50/75GHz spacing";
             }
             enum "1532.24" {
               description "1532.24 nm/195.65625 THz 6.25GHz spacing";
             }
             enum "1532.19" {
               description "1532.19 nm/195.66250 THz 6.25/12.5GHz spacing";
             }
             enum "1532.14" {
               description "1532.14 nm/195.66875 THz 6.25GHz spacing";
             }
             enum "1532.09" {
               description "1532.09 nm/195.67500 THz 6.25/12.5GHz spacing";
             }
             enum "1532.04" {
               description "1532.04 nm/195.68125 THz 6.25GHz spacing";
             }
             enum "1532.00" {
               description "1532.00 nm/195.68750 THz 6.25/12.5GHz spacing";
             }
             enum "1531.95" {
               description "1531.95 nm/195.69375 THz 6.25GHz spacing";
             }
             enum "1531.90" {
               description "1531.90 nm/195.70000 THz 6.25/12.5/50/100GHz spacing";
             }
             enum "1531.85" {
               description "1531.85 nm/195.70625 THz 6.25GHz spacing";
             }
             enum "1531.80" {
               description "1531.80 nm/195.71250 THz 6.25/12.5GHz spacing";
             }
             enum "1531.75" {
               description "1531.75 nm/195.71875 THz 6.25GHz spacing";
             }
             enum "1531.70" {
               description "1531.70 nm/195.72500 THz 6.25/12.5/75GHz spacing";
             }
             enum "1531.65" {
               description "1531.65 nm/195.73125 THz 6.25GHz spacing";
             }
             enum "1531.60" {
               description "1531.60 nm/195.73750 THz 6.25/12.5GHz spacing";
             }
             enum "1531.56" {
               description "1531.56 nm/195.74375 THz 6.25GHz spacing";
             }
             enum "1531.51" {
               description "1531.51 nm/195.75000 THz 6.25/12.5/50GHz spacing";
             }
             enum "1531.46" {
               description "1531.46 nm/195.75625 THz 6.25GHz spacing";
             }
             enum "1531.41" {
               description "1531.41 nm/195.76250 THz 6.25/12.5GHz spacing";
             }
             enum "1531.36" {
               description "1531.36 nm/195.76875 THz 6.25GHz spacing";
             }
             enum "1531.31" {
               description "1531.31 nm/195.77500 THz 6.25/12.5GHz spacing";
             }
             enum "1531.26" {
               description "1531.26 nm/195.78125 THz 6.25GHz spacing";
             }
             enum "1531.21" {
               description "1531.21 nm/195.78750 THz 6.25/12.5GHz spacing";
             }
             enum "1531.16" {
               description "1531.16 nm/195.79375 THz 6.25GHz spacing";
             }
             enum "1531.12" {
               description "1531.12 nm/195.80000 THz 6.25/12.5/50/75/100GHz spacing";
             }
             enum "1531.07" {
               description "1531.07 nm/195.80625 THz 6.25GHz spacing";
             }
             enum "1531.02" {
               description "1531.02 nm/195.81250 THz 6.25/12.5GHz spacing";
             }
             enum "1530.97" {
               description "1530.97 nm/195.81875 THz 6.25GHz spacing";
             }
             enum "1530.92" {
               description "1530.92 nm/195.82500 THz 6.25/12.5GHz spacing";
             }
             enum "1530.87" {
               description "1530.87 nm/195.83125 THz 6.25GHz spacing";
             }
             enum "1530.82" {
               description "1530.82 nm/195.83750 THz 6.25/12.5GHz spacing";
             }
             enum "1530.77" {
               description "1530.77 nm/195.84375 THz 6.25GHz spacing";
             }
             enum "1530.72" {
               description "1530.72 nm/195.85000 THz 6.25/12.5/50GHz spacing";
             }
             enum "1530.68" {
               description "1530.68 nm/195.85625 THz 6.25GHz spacing";
             }
             enum "1530.63" {
               description "1530.63 nm/195.86250 THz 6.25/12.5GHz spacing";
             }
             enum "1530.58" {
               description "1530.58 nm/195.86875 THz 6.25GHz spacing";
             }
             enum "1530.53" {
               description "1530.53 nm/195.87500 THz 6.25/12.5/75GHz spacing";
             }
             enum "1530.48" {
               description "1530.48 nm/195.88125 THz 6.25GHz spacing";
             }
             enum "1530.43" {
               description "1530.43 nm/195.88750 THz 6.25/12.5GHz spacing";
             }
             enum "1530.38" {
               description "1530.38 nm/195.89375 THz 6.25GHz spacing";
             }
             enum "1530.33" {
               description "1530.33 nm/195.90000 THz 6.25/12.5/50/100GHz spacing";
             }
             enum "1530.29" {
               description "1530.29 nm/195.90625 THz 6.25GHz spacing";
             }
             enum "1530.24" {
               description "1530.24 nm/195.91250 THz 6.25/12.5GHz spacing";
             }
             enum "1530.19" {
               description "1530.19 nm/195.91875 THz 6.25GHz spacing";
             }
             enum "1530.14" {
               description "1530.14 nm/195.92500 THz 6.25/12.5GHz spacing";
             }
             enum "1530.09" {
               description "1530.09 nm/195.93125 THz 6.25GHz spacing";
             }
             enum "1530.04" {
               description "1530.04 nm/195.93750 THz 6.25/12.5GHz spacing";
             }
             enum "1529.99" {
               description "1529.99 nm/195.94375 THz 6.25GHz spacing";
             }
             enum "1529.94" {
               description "1529.94 nm/195.95000 THz 6.25/12.5/50/75GHz spacing";
             }
             enum "1529.89" {
               description "1529.89 nm/195.95625 THz 6.25GHz spacing";
             }
             enum "1529.85" {
               description "1529.85 nm/195.96250 THz 6.25/12.5GHz spacing";
             }
             enum "1529.80" {
               description "1529.80 nm/195.96875 THz 6.25GHz spacing";
             }
             enum "1529.75" {
               description "1529.75 nm/195.97500 THz 6.25/12.5GHz spacing";
             }
             enum "1529.70" {
               description "1529.70 nm/195.98125 THz 6.25GHz spacing";
             }
             enum "1529.65" {
               description "1529.65 nm/195.98750 THz 6.25/12.5GHz spacing";
             }
             enum "1529.60" {
               description "1529.60 nm/195.99375 THz 6.25GHz spacing";
             }
             enum "1529.55" {
               description "1529.55 nm/196.00000 THz 6.25/12.5/50/100GHz spacing";
             }
             enum "1529.50" {
               description "1529.50 nm/196.00625 THz 6.25GHz spacing";
             }
             enum "1529.46" {
               description "1529.46 nm/196.01250 THz 6.25/12.5GHz spacing";
             }
             enum "1529.41" {
               description "1529.41 nm/196.01875 THz 6.25GHz spacing";
             }
             enum "1529.36" {
               description "1529.36 nm/196.02500 THz 6.25/12.5/75GHz spacing";
             }
             enum "1529.31" {
               description "1529.31 nm/196.03125 THz 6.25GHz spacing";
             }
             enum "1529.26" {
               description "1529.26 nm/196.03750 THz 6.25/12.5GHz spacing";
             }
             enum "1529.21" {
               description "1529.21 nm/196.04375 THz 6.25GHz spacing";
             }
             enum "1529.16" {
               description "1529.16 nm/196.05000 THz 6.25/12.5/50GHz spacing";
             }
             enum "1529.11" {
               description "1529.11 nm/196.05625 THz 6.25GHz spacing";
             }
             enum "1529.07" {
               description "1529.07 nm/196.06250 THz 6.25/12.5GHz spacing";
             }
             enum "1529.02" {
               description "1529.02 nm/196.06875 THz 6.25GHz spacing";
             }
             enum "1528.97" {
               description "1528.97 nm/196.07500 THz 6.25/12.5GHz spacing";
             }
             enum "1528.92" {
               description "1528.92 nm/196.08125 THz 6.25GHz spacing";
             }
             enum "1528.87" {
               description "1528.87 nm/196.08750 THz 6.25/12.5GHz spacing";
             }
             enum "1528.82" {
               description "1528.82 nm/196.09375 THz 6.25GHz spacing";
             }
             enum "1528.77" {
               description "1528.77 nm/196.10000 THz 6.25/12.5/50/75/100GHz spacing";
             }
             enum "1528.38" {
               description "1528.38 nm/196.15040 THz 50Ghz spacing";
             }
           }
         }
       }
       case case_2 {
         leaf frequency {
           description "Optical channel frequency in terahertz";
           type enumeration {
             enum "191.1003" {
               description "191.1003 THz/1568.77 nm 50/100Ghz spacing";
             }
             enum "191.15000" {
               description "191.15000 THz/1568.36 nm 6.25/12.5/50GHz spacing";
             }
             enum "191.15625" {
               description "191.15625 THz/1568.31 nm 6.25GHz spacing";
             }
             enum "191.16250" {
               description "191.16250 THz/1568.26 nm 6.25/12.5GHz spacing";
             }
             enum "191.16875" {
               description "191.16875 THz/1568.21 nm 6.25GHz spacing";
             }
             enum "191.17500" {
               description "191.17500 THz/1568.16 nm 6.25/12.5GHz spacing";
             }
             enum "191.18125" {
               description "191.18125 THz/1568.11 nm 6.25GHz spacing";
             }
             enum "191.18750" {
               description "191.18750 THz/1568.05 nm 6.25/12.5GHz spacing";
             }
             enum "191.19375" {
               description "191.19375 THz/1568.00 nm 6.25GHz spacing";
             }
             enum "191.20000" {
               description "191.20000 THz/1567.95 nm 6.25/12.5/50/100GHz spacing";
             }
             enum "191.20625" {
               description "191.20625 THz/1567.90 nm 6.25GHz spacing";
             }
             enum "191.21250" {
               description "191.21250 THz/1567.85 nm 6.25/12.5GHz spacing";
             }
             enum "191.21875" {
               description "191.21875 THz/1567.80 nm 6.25GHz spacing";
             }
             enum "191.22500" {
               description "191.22500 THz/1567.75 nm 6.25/12.5GHz spacing";
             }
             enum "191.23125" {
               description "191.23125 THz/1567.70 nm 6.25GHz spacing";
             }
             enum "191.23750" {
               description "191.23750 THz/1567.64 nm 6.25/12.5GHz spacing";
             }
             enum "191.24375" {
               description "191.24375 THz/1567.59 nm 6.25GHz spacing";
             }
             enum "191.25000" {
               description "191.25000 THz/1567.54 nm 6.25/12.5/50GHz spacing";
             }
             enum "191.25625" {
               description "191.25625 THz/1567.49 nm 6.25GHz spacing";
             }
             enum "191.26250" {
               description "191.26250 THz/1567.44 nm 6.25/12.5GHz spacing";
             }
             enum "191.26875" {
               description "191.26875 THz/1567.39 nm 6.25GHz spacing";
             }
             enum "191.27500" {
               description "191.27500 THz/1567.34 nm 6.25/12.5GHz spacing";
             }
             enum "191.28125" {
               description "191.28125 THz/1567.29 nm 6.25GHz spacing";
             }
             enum "191.28750" {
               description "191.28750 THz/1567.23 nm 6.25/12.5GHz spacing";
             }
             enum "191.29375" {
               description "191.29375 THz/1567.18 nm 6.25GHz spacing";
             }
             enum "191.30000" {
               description "191.30000 THz/1567.13 nm 6.25/12.5/50/100GHz spacing";
             }
             enum "191.30625" {
               description "191.30625 THz/1567.08 nm 6.25GHz spacing";
             }
             enum "191.31250" {
               description "191.31250 THz/1567.03 nm 6.25/12.5GHz spacing";
             }
             enum "191.31875" {
               description "191.31875 THz/1566.98 nm 6.25GHz spacing";
             }
             enum "191.32500" {
               description "191.32500 THz/1566.93 nm 6.25/12.5GHz spacing";
             }
             enum "191.33125" {
               description "191.33125 THz/1566.88 nm 6.25GHz spacing";
             }
             enum "191.33750" {
               description "191.33750 THz/1566.83 nm 6.25/12.5GHz spacing";
             }
             enum "191.34375" {
               description "191.34375 THz/1566.77 nm 6.25GHz spacing";
             }
             enum "191.35000" {
               description "191.35000 THz/1566.72 nm 6.25/12.5/50GHz spacing";
             }
             enum "191.35625" {
               description "191.35625 THz/1566.67 nm 6.25GHz spacing";
             }
             enum "191.36250" {
               description "191.36250 THz/1566.62 nm 6.25/12.5GHz spacing";
             }
             enum "191.36875" {
               description "191.36875 THz/1566.57 nm 6.25GHz spacing";
             }
             enum "191.37500" {
               description "191.37500 THz/1566.52 nm 6.25/12.5/75GHz spacing";
             }
             enum "191.38125" {
               description "191.38125 THz/1566.47 nm 6.25GHz spacing";
             }
             enum "191.38750" {
               description "191.38750 THz/1566.42 nm 6.25/12.5GHz spacing";
             }
             enum "191.39375" {
               description "191.39375 THz/1566.36 nm 6.25GHz spacing";
             }
             enum "191.40000" {
               description "191.40000 THz/1566.31 nm 6.25/12.5/50/100GHz spacing";
             }
             enum "191.40625" {
               description "191.40625 THz/1566.26 nm 6.25GHz spacing";
             }
             enum "191.41250" {
               description "191.41250 THz/1566.21 nm 6.25/12.5GHz spacing";
             }
             enum "191.41875" {
               description "191.41875 THz/1566.16 nm 6.25GHz spacing";
             }
             enum "191.42500" {
               description "191.42500 THz/1566.11 nm 6.25/12.5GHz spacing";
             }
             enum "191.43125" {
               description "191.43125 THz/1566.06 nm 6.25GHz spacing";
             }
             enum "191.43750" {
               description "191.43750 THz/1566.01 nm 6.25/12.5GHz spacing";
             }
             enum "191.44375" {
               description "191.44375 THz/1565.96 nm 6.25GHz spacing";
             }
             enum "191.45000" {
               description "191.45000 THz/1565.90 nm 6.25/12.5/50/75GHz spacing";
             }
             enum "191.45625" {
               description "191.45625 THz/1565.85 nm 6.25GHz spacing";
             }
             enum "191.46250" {
               description "191.46250 THz/1565.80 nm 6.25/12.5GHz spacing";
             }
             enum "191.46875" {
               description "191.46875 THz/1565.75 nm 6.25GHz spacing";
             }
             enum "191.47500" {
               description "191.47500 THz/1565.70 nm 6.25/12.5GHz spacing";
             }
             enum "191.48125" {
               description "191.48125 THz/1565.65 nm 6.25GHz spacing";
             }
             enum "191.48750" {
               description "191.48750 THz/1565.60 nm 6.25/12.5GHz spacing";
             }
             enum "191.49375" {
               description "191.49375 THz/1565.55 nm 6.25GHz spacing";
             }
             enum "191.50000" {
               description "191.50000 THz/1565.50 nm 6.25/12.5/50/100GHz spacing";
             }
             enum "191.50625" {
               description "191.50625 THz/1565.44 nm 6.25GHz spacing";
             }
             enum "191.51250" {
               description "191.51250 THz/1565.39 nm 6.25/12.5GHz spacing";
             }
             enum "191.51875" {
               description "191.51875 THz/1565.34 nm 6.25GHz spacing";
             }
             enum "191.52500" {
               description "191.52500 THz/1565.29 nm 6.25/12.5/75GHz spacing";
             }
             enum "191.53125" {
               description "191.53125 THz/1565.24 nm 6.25GHz spacing";
             }
             enum "191.53750" {
               description "191.53750 THz/1565.19 nm 6.25/12.5GHz spacing";
             }
             enum "191.54375" {
               description "191.54375 THz/1565.14 nm 6.25GHz spacing";
             }
             enum "191.55000" {
               description "191.55000 THz/1565.09 nm 6.25/12.5/50GHz spacing";
             }
             enum "191.55625" {
               description "191.55625 THz/1565.04 nm 6.25GHz spacing";
             }
             enum "191.56250" {
               description "191.56250 THz/1564.99 nm 6.25/12.5GHz spacing";
             }
             enum "191.56875" {
               description "191.56875 THz/1564.93 nm 6.25GHz spacing";
             }
             enum "191.57500" {
               description "191.57500 THz/1564.88 nm 6.25/12.5GHz spacing";
             }
             enum "191.58125" {
               description "191.58125 THz/1564.83 nm 6.25GHz spacing";
             }
             enum "191.58750" {
               description "191.58750 THz/1564.78 nm 6.25/12.5GHz spacing";
             }
             enum "191.59375" {
               description "191.59375 THz/1564.73 nm 6.25GHz spacing";
             }
             enum "191.60000" {
               description "191.60000 THz/1564.68 nm 6.25/12.5/50/75/100GHz spacing";
             }
             enum "191.60625" {
               description "191.60625 THz/1564.63 nm 6.25GHz spacing";
             }
             enum "191.61250" {
               description "191.61250 THz/1564.58 nm 6.25/12.5GHz spacing";
             }
             enum "191.61875" {
               description "191.61875 THz/1564.53 nm 6.25GHz spacing";
             }
             enum "191.62500" {
               description "191.62500 THz/1564.47 nm 6.25/12.5GHz spacing";
             }
             enum "191.63125" {
               description "191.63125 THz/1564.42 nm 6.25GHz spacing";
             }
             enum "191.63750" {
               description "191.63750 THz/1564.37 nm 6.25/12.5GHz spacing";
             }
             enum "191.64375" {
               description "191.64375 THz/1564.32 nm 6.25GHz spacing";
             }
             enum "191.65000" {
               description "191.65000 THz/1564.27 nm 6.25/12.5/50GHz spacing";
             }
             enum "191.65625" {
               description "191.65625 THz/1564.22 nm 6.25GHz spacing";
             }
             enum "191.66250" {
               description "191.66250 THz/1564.17 nm 6.25/12.5GHz spacing";
             }
             enum "191.66875" {
               description "191.66875 THz/1564.12 nm 6.25GHz spacing";
             }
             enum "191.67500" {
               description "191.67500 THz/1564.07 nm 6.25/12.5/75GHz spacing";
             }
             enum "191.68125" {
               description "191.68125 THz/1564.02 nm 6.25GHz spacing";
             }
             enum "191.68750" {
               description "191.68750 THz/1563.96 nm 6.25/12.5GHz spacing";
             }
             enum "191.69375" {
               description "191.69375 THz/1563.91 nm 6.25GHz spacing";
             }
             enum "191.70000" {
               description "191.70000 THz/1563.86 nm 6.25/12.5/50/100GHz spacing";
             }
             enum "191.70625" {
               description "191.70625 THz/1563.81 nm 6.25GHz spacing";
             }
             enum "191.71250" {
               description "191.71250 THz/1563.76 nm 6.25/12.5GHz spacing";
             }
             enum "191.71875" {
               description "191.71875 THz/1563.71 nm 6.25GHz spacing";
             }
             enum "191.72500" {
               description "191.72500 THz/1563.66 nm 6.25/12.5GHz spacing";
             }
             enum "191.73125" {
               description "191.73125 THz/1563.61 nm 6.25GHz spacing";
             }
             enum "191.73750" {
               description "191.73750 THz/1563.56 nm 6.25/12.5GHz spacing";
             }
             enum "191.74375" {
               description "191.74375 THz/1563.51 nm 6.25GHz spacing";
             }
             enum "191.75000" {
               description "191.75000 THz/1563.45 nm 6.25/12.5/50/75GHz spacing";
             }
             enum "191.75625" {
               description "191.75625 THz/1563.40 nm 6.25GHz spacing";
             }
             enum "191.76250" {
               description "191.76250 THz/1563.35 nm 6.25/12.5GHz spacing";
             }
             enum "191.76875" {
               description "191.76875 THz/1563.30 nm 6.25GHz spacing";
             }
             enum "191.77500" {
               description "191.77500 THz/1563.25 nm 6.25/12.5GHz spacing";
             }
             enum "191.78125" {
               description "191.78125 THz/1563.20 nm 6.25GHz spacing";
             }
             enum "191.78750" {
               description "191.78750 THz/1563.15 nm 6.25/12.5GHz spacing";
             }
             enum "191.79375" {
               description "191.79375 THz/1563.10 nm 6.25GHz spacing";
             }
             enum "191.80000" {
               description "191.80000 THz/1563.05 nm 6.25/12.5/50/100GHz spacing";
             }
             enum "191.80625" {
               description "191.80625 THz/1563.00 nm 6.25GHz spacing";
             }
             enum "191.81250" {
               description "191.81250 THz/1562.95 nm 6.25/12.5GHz spacing";
             }
             enum "191.81875" {
               description "191.81875 THz/1562.89 nm 6.25GHz spacing";
             }
             enum "191.82500" {
               description "191.82500 THz/1562.84 nm 6.25/12.5/75GHz spacing";
             }
             enum "191.83125" {
               description "191.83125 THz/1562.79 nm 6.25GHz spacing";
             }
             enum "191.83750" {
               description "191.83750 THz/1562.74 nm 6.25/12.5GHz spacing";
             }
             enum "191.84375" {
               description "191.84375 THz/1562.69 nm 6.25GHz spacing";
             }
             enum "191.85000" {
               description "191.85000 THz/1562.64 nm 6.25/12.5/50GHz spacing";
             }
             enum "191.85625" {
               description "191.85625 THz/1562.59 nm 6.25GHz spacing";
             }
             enum "191.86250" {
               description "191.86250 THz/1562.54 nm 6.25/12.5GHz spacing";
             }
             enum "191.86875" {
               description "191.86875 THz/1562.49 nm 6.25GHz spacing";
             }
             enum "191.87500" {
               description "191.87500 THz/1562.44 nm 6.25/12.5GHz spacing";
             }
             enum "191.88125" {
               description "191.88125 THz/1562.39 nm 6.25GHz spacing";
             }
             enum "191.88750" {
               description "191.88750 THz/1562.33 nm 6.25/12.5GHz spacing";
             }
             enum "191.89375" {
               description "191.89375 THz/1562.28 nm 6.25GHz spacing";
             }
             enum "191.90000" {
               description "191.90000 THz/1562.23 nm 6.25/12.5/50/75/100GHz spacing";
             }
             enum "191.90625" {
               description "191.90625 THz/1562.18 nm 6.25GHz spacing";
             }
             enum "191.91250" {
               description "191.91250 THz/1562.13 nm 6.25/12.5GHz spacing";
             }
             enum "191.91875" {
               description "191.91875 THz/1562.08 nm 6.25GHz spacing";
             }
             enum "191.92500" {
               description "191.92500 THz/1562.03 nm 6.25/12.5GHz spacing";
             }
             enum "191.93125" {
               description "191.93125 THz/1561.98 nm 6.25GHz spacing";
             }
             enum "191.93750" {
               description "191.93750 THz/1561.93 nm 6.25/12.5GHz spacing";
             }
             enum "191.94375" {
               description "191.94375 THz/1561.88 nm 6.25GHz spacing";
             }
             enum "191.95000" {
               description "191.95000 THz/1561.83 nm 6.25/12.5/50GHz spacing";
             }
             enum "191.95625" {
               description "191.95625 THz/1561.77 nm 6.25GHz spacing";
             }
             enum "191.96250" {
               description "191.96250 THz/1561.72 nm 6.25/12.5GHz spacing";
             }
             enum "191.96875" {
               description "191.96875 THz/1561.67 nm 6.25GHz spacing";
             }
             enum "191.97500" {
               description "191.97500 THz/1561.62 nm 6.25/12.5/75GHz spacing";
             }
             enum "191.98125" {
               description "191.98125 THz/1561.57 nm 6.25GHz spacing";
             }
             enum "191.98750" {
               description "191.98750 THz/1561.52 nm 6.25/12.5GHz spacing";
             }
             enum "191.99375" {
               description "191.99375 THz/1561.47 nm 6.25GHz spacing";
             }
             enum "192.00000" {
               description "192.00000 THz/1561.42 nm 6.25/12.5/50/100GHz spacing";
             }
             enum "192.00625" {
               description "192.00625 THz/1561.37 nm 6.25GHz spacing";
             }
             enum "192.01250" {
               description "192.01250 THz/1561.32 nm 6.25/12.5GHz spacing";
             }
             enum "192.01875" {
               description "192.01875 THz/1561.27 nm 6.25GHz spacing";
             }
             enum "192.02500" {
               description "192.02500 THz/1561.22 nm 6.25/12.5GHz spacing";
             }
             enum "192.03125" {
               description "192.03125 THz/1561.16 nm 6.25GHz spacing";
             }
             enum "192.03750" {
               description "192.03750 THz/1561.11 nm 6.25/12.5GHz spacing";
             }
             enum "192.04375" {
               description "192.04375 THz/1561.06 nm 6.25GHz spacing";
             }
             enum "192.05000" {
               description "192.05000 THz/1561.01 nm 6.25/12.5/50/75GHz spacing";
             }
             enum "192.05625" {
               description "192.05625 THz/1560.96 nm 6.25GHz spacing";
             }
             enum "192.06250" {
               description "192.06250 THz/1560.91 nm 6.25/12.5GHz spacing";
             }
             enum "192.06875" {
               description "192.06875 THz/1560.86 nm 6.25GHz spacing";
             }
             enum "192.07500" {
               description "192.07500 THz/1560.81 nm 6.25/12.5GHz spacing";
             }
             enum "192.08125" {
               description "192.08125 THz/1560.76 nm 6.25GHz spacing";
             }
             enum "192.08750" {
               description "192.08750 THz/1560.71 nm 6.25/12.5GHz spacing";
             }
             enum "192.09375" {
               description "192.09375 THz/1560.66 nm 6.25GHz spacing";
             }
             enum "192.10000" {
               description "192.10000 THz/1560.61 nm 6.25/12.5/50/100GHz spacing";
             }
             enum "192.10625" {
               description "192.10625 THz/1560.56 nm 6.25GHz spacing";
             }
             enum "192.11250" {
               description "192.11250 THz/1560.50 nm 6.25/12.5GHz spacing";
             }
             enum "192.11875" {
               description "192.11875 THz/1560.45 nm 6.25GHz spacing";
             }
             enum "192.12500" {
               description "192.12500 THz/1560.40 nm 6.25/12.5/75GHz spacing";
             }
             enum "192.13125" {
               description "192.13125 THz/1560.35 nm 6.25GHz spacing";
             }
             enum "192.13750" {
               description "192.13750 THz/1560.30 nm 6.25/12.5GHz spacing";
             }
             enum "192.14375" {
               description "192.14375 THz/1560.25 nm 6.25GHz spacing";
             }
             enum "192.15000" {
               description "192.15000 THz/1560.20 nm 6.25/12.5/50GHz spacing";
             }
             enum "192.15625" {
               description "192.15625 THz/1560.15 nm 6.25GHz spacing";
             }
             enum "192.16250" {
               description "192.16250 THz/1560.10 nm 6.25/12.5GHz spacing";
             }
             enum "192.16875" {
               description "192.16875 THz/1560.05 nm 6.25GHz spacing";
             }
             enum "192.17500" {
               description "192.17500 THz/1560.00 nm 6.25/12.5GHz spacing";
             }
             enum "192.18125" {
               description "192.18125 THz/1559.95 nm 6.25GHz spacing";
             }
             enum "192.18750" {
               description "192.18750 THz/1559.90 nm 6.25/12.5GHz spacing";
             }
             enum "192.19375" {
               description "192.19375 THz/1559.84 nm 6.25GHz spacing";
             }
             enum "192.20000" {
               description "192.20000 THz/1559.79 nm 6.25/12.5/50/75/100GHz spacing";
             }
             enum "192.20625" {
               description "192.20625 THz/1559.74 nm 6.25GHz spacing";
             }
             enum "192.21250" {
               description "192.21250 THz/1559.69 nm 6.25/12.5GHz spacing";
             }
             enum "192.21875" {
               description "192.21875 THz/1559.64 nm 6.25GHz spacing";
             }
             enum "192.22500" {
               description "192.22500 THz/1559.59 nm 6.25/12.5GHz spacing";
             }
             enum "192.23125" {
               description "192.23125 THz/1559.54 nm 6.25GHz spacing";
             }
             enum "192.23750" {
               description "192.23750 THz/1559.49 nm 6.25/12.5GHz spacing";
             }
             enum "192.24375" {
               description "192.24375 THz/1559.44 nm 6.25GHz spacing";
             }
             enum "192.25000" {
               description "192.25000 THz/1559.39 nm 6.25/12.5/50GHz spacing";
             }
             enum "192.25625" {
               description "192.25625 THz/1559.34 nm 6.25GHz spacing";
             }
             enum "192.26250" {
               description "192.26250 THz/1559.29 nm 6.25/12.5GHz spacing";
             }
             enum "192.26875" {
               description "192.26875 THz/1559.24 nm 6.25GHz spacing";
             }
             enum "192.27500" {
               description "192.27500 THz/1559.19 nm 6.25/12.5GHz spacing";
             }
             enum "192.28125" {
               description "192.28125 THz/1559.14 nm 6.25GHz spacing";
             }
             enum "192.28750" {
               description "192.28750 THz/1559.08 nm 6.25/12.5GHz spacing";
             }
             enum "192.29375" {
               description "192.29375 THz/1559.03 nm 6.25GHz spacing";
             }
             enum "192.30000" {
               description "192.30000 THz/1558.98 nm 6.25/12.5/50/100GHz spacing";
             }
             enum "192.30625" {
               description "192.30625 THz/1558.93 nm 6.25GHz spacing";
             }
             enum "192.31250" {
               description "192.31250 THz/1558.88 nm 6.25/12.5GHz spacing";
             }
             enum "192.31875" {
               description "192.31875 THz/1558.83 nm 6.25GHz spacing";
             }
             enum "192.32500" {
               description "192.32500 THz/1558.78 nm 6.25/12.5GHz spacing";
             }
             enum "192.33125" {
               description "192.33125 THz/1558.73 nm 6.25GHz spacing";
             }
             enum "192.33750" {
               description "192.33750 THz/1558.68 nm 6.25/12.5GHz spacing";
             }
             enum "192.34375" {
               description "192.34375 THz/1558.63 nm 6.25GHz spacing";
             }
             enum "192.35000" {
               description "192.35000 THz/1558.58 nm 6.25/12.5/50/75GHz spacing";
             }
             enum "192.35625" {
               description "192.35625 THz/1558.53 nm 6.25GHz spacing";
             }
             enum "192.36250" {
               description "192.36250 THz/1558.48 nm 6.25/12.5GHz spacing";
             }
             enum "192.36875" {
               description "192.36875 THz/1558.43 nm 6.25GHz spacing";
             }
             enum "192.37500" {
               description "192.37500 THz/1558.38 nm 6.25/12.5GHz spacing";
             }
             enum "192.38125" {
               description "192.38125 THz/1558.32 nm 6.25GHz spacing";
             }
             enum "192.38750" {
               description "192.38750 THz/1558.27 nm 6.25/12.5GHz spacing";
             }
             enum "192.39375" {
               description "192.39375 THz/1558.22 nm 6.25GHz spacing";
             }
             enum "192.40000" {
               description "192.40000 THz/1558.17 nm 6.25/12.5/50/100GHz spacing";
             }
             enum "192.40625" {
               description "192.40625 THz/1558.12 nm 6.25GHz spacing";
             }
             enum "192.41250" {
               description "192.41250 THz/1558.07 nm 6.25/12.5GHz spacing";
             }
             enum "192.41875" {
               description "192.41875 THz/1558.02 nm 6.25GHz spacing";
             }
             enum "192.42500" {
               description "192.42500 THz/1557.97 nm 6.25/12.5/75GHz spacing";
             }
             enum "192.43125" {
               description "192.43125 THz/1557.92 nm 6.25GHz spacing";
             }
             enum "192.43750" {
               description "192.43750 THz/1557.87 nm 6.25/12.5GHz spacing";
             }
             enum "192.44375" {
               description "192.44375 THz/1557.82 nm 6.25GHz spacing";
             }
             enum "192.45000" {
               description "192.45000 THz/1557.77 nm 6.25/12.5/50GHz spacing";
             }
             enum "192.45625" {
               description "192.45625 THz/1557.72 nm 6.25GHz spacing";
             }
             enum "192.46250" {
               description "192.46250 THz/1557.67 nm 6.25/12.5GHz spacing";
             }
             enum "192.46875" {
               description "192.46875 THz/1557.62 nm 6.25GHz spacing";
             }
             enum "192.47500" {
               description "192.47500 THz/1557.57 nm 6.25/12.5GHz spacing";
             }
             enum "192.48125" {
               description "192.48125 THz/1557.52 nm 6.25GHz spacing";
             }
             enum "192.48750" {
               description "192.48750 THz/1557.46 nm 6.25/12.5GHz spacing";
             }
             enum "192.49375" {
               description "192.49375 THz/1557.41 nm 6.25GHz spacing";
             }
             enum "192.50000" {
               description "192.50000 THz/1557.36 nm 6.25/12.5/50/75/100GHz spacing";
             }
             enum "192.50625" {
               description "192.50625 THz/1557.31 nm 6.25GHz spacing";
             }
             enum "192.51250" {
               description "192.51250 THz/1557.26 nm 6.25/12.5GHz spacing";
             }
             enum "192.51875" {
               description "192.51875 THz/1557.21 nm 6.25GHz spacing";
             }
             enum "192.52500" {
               description "192.52500 THz/1557.16 nm 6.25/12.5GHz spacing";
             }
             enum "192.53125" {
               description "192.53125 THz/1557.11 nm 6.25GHz spacing";
             }
             enum "192.53750" {
               description "192.53750 THz/1557.06 nm 6.25/12.5GHz spacing";
             }
             enum "192.54375" {
               description "192.54375 THz/1557.01 nm 6.25GHz spacing";
             }
             enum "192.55000" {
               description "192.55000 THz/1556.96 nm 6.25/12.5/50GHz spacing";
             }
             enum "192.55625" {
               description "192.55625 THz/1556.91 nm 6.25GHz spacing";
             }
             enum "192.56250" {
               description "192.56250 THz/1556.86 nm 6.25/12.5GHz spacing";
             }
             enum "192.56875" {
               description "192.56875 THz/1556.81 nm 6.25GHz spacing";
             }
             enum "192.57500" {
               description "192.57500 THz/1556.76 nm 6.25/12.5/75GHz spacing";
             }
             enum "192.58125" {
               description "192.58125 THz/1556.71 nm 6.25GHz spacing";
             }
             enum "192.58750" {
               description "192.58750 THz/1556.66 nm 6.25/12.5GHz spacing";
             }
             enum "192.59375" {
               description "192.59375 THz/1556.61 nm 6.25GHz spacing";
             }
             enum "192.60000" {
               description "192.60000 THz/1556.55 nm 6.25/12.5/50/100GHz spacing";
             }
             enum "192.60625" {
               description "192.60625 THz/1556.50 nm 6.25GHz spacing";
             }
             enum "192.61250" {
               description "192.61250 THz/1556.45 nm 6.25/12.5GHz spacing";
             }
             enum "192.61875" {
               description "192.61875 THz/1556.40 nm 6.25GHz spacing";
             }
             enum "192.62500" {
               description "192.62500 THz/1556.35 nm 6.25/12.5GHz spacing";
             }
             enum "192.63125" {
               description "192.63125 THz/1556.30 nm 6.25GHz spacing";
             }
             enum "192.63750" {
               description "192.63750 THz/1556.25 nm 6.25/12.5GHz spacing";
             }
             enum "192.64375" {
               description "192.64375 THz/1556.20 nm 6.25GHz spacing";
             }
             enum "192.65000" {
               description "192.65000 THz/1556.15 nm 6.25/12.5/50/75GHz spacing";
             }
             enum "192.65625" {
               description "192.65625 THz/1556.10 nm 6.25GHz spacing";
             }
             enum "192.66250" {
               description "192.66250 THz/1556.05 nm 6.25/12.5GHz spacing";
             }
             enum "192.66875" {
               description "192.66875 THz/1556.00 nm 6.25GHz spacing";
             }
             enum "192.67500" {
               description "192.67500 THz/1555.95 nm 6.25/12.5GHz spacing";
             }
             enum "192.68125" {
               description "192.68125 THz/1555.90 nm 6.25GHz spacing";
             }
             enum "192.68750" {
               description "192.68750 THz/1555.85 nm 6.25/12.5GHz spacing";
             }
             enum "192.69375" {
               description "192.69375 THz/1555.80 nm 6.25GHz spacing";
             }
             enum "192.70000" {
               description "192.70000 THz/1555.75 nm 6.25/12.5/50/100GHz spacing";
             }
             enum "192.70625" {
               description "192.70625 THz/1555.70 nm 6.25GHz spacing";
             }
             enum "192.71250" {
               description "192.71250 THz/1555.65 nm 6.25/12.5GHz spacing";
             }
             enum "192.71875" {
               description "192.71875 THz/1555.60 nm 6.25GHz spacing";
             }
             enum "192.72500" {
               description "192.72500 THz/1555.55 nm 6.25/12.5/75GHz spacing";
             }
             enum "192.73125" {
               description "192.73125 THz/1555.49 nm 6.25GHz spacing";
             }
             enum "192.73750" {
               description "192.73750 THz/1555.44 nm 6.25/12.5GHz spacing";
             }
             enum "192.74375" {
               description "192.74375 THz/1555.39 nm 6.25GHz spacing";
             }
             enum "192.75000" {
               description "192.75000 THz/1555.34 nm 6.25/12.5/50GHz spacing";
             }
             enum "192.75625" {
               description "192.75625 THz/1555.29 nm 6.25GHz spacing";
             }
             enum "192.76250" {
               description "192.76250 THz/1555.24 nm 6.25/12.5GHz spacing";
             }
             enum "192.76875" {
               description "192.76875 THz/1555.19 nm 6.25GHz spacing";
             }
             enum "192.77500" {
               description "192.77500 THz/1555.14 nm 6.25/12.5GHz spacing";
             }
             enum "192.78125" {
               description "192.78125 THz/1555.09 nm 6.25GHz spacing";
             }
             enum "192.78750" {
               description "192.78750 THz/1555.04 nm 6.25/12.5GHz spacing";
             }
             enum "192.79375" {
               description "192.79375 THz/1554.99 nm 6.25GHz spacing";
             }
             enum "192.80000" {
               description "192.80000 THz/1554.94 nm 6.25/12.5/50/75/100GHz spacing";
             }
             enum "192.80625" {
               description "192.80625 THz/1554.89 nm 6.25GHz spacing";
             }
             enum "192.81250" {
               description "192.81250 THz/1554.84 nm 6.25/12.5GHz spacing";
             }
             enum "192.81875" {
               description "192.81875 THz/1554.79 nm 6.25GHz spacing";
             }
             enum "192.82500" {
               description "192.82500 THz/1554.74 nm 6.25/12.5GHz spacing";
             }
             enum "192.83125" {
               description "192.83125 THz/1554.69 nm 6.25GHz spacing";
             }
             enum "192.83750" {
               description "192.83750 THz/1554.64 nm 6.25/12.5GHz spacing";
             }
             enum "192.84375" {
               description "192.84375 THz/1554.59 nm 6.25GHz spacing";
             }
             enum "192.85000" {
               description "192.85000 THz/1554.54 nm 6.25/12.5/50GHz spacing";
             }
             enum "192.85625" {
               description "192.85625 THz/1554.49 nm 6.25GHz spacing";
             }
             enum "192.86250" {
               description "192.86250 THz/1554.44 nm 6.25/12.5GHz spacing";
             }
             enum "192.86875" {
               description "192.86875 THz/1554.39 nm 6.25GHz spacing";
             }
             enum "192.87500" {
               description "192.87500 THz/1554.34 nm 6.25/12.5/75GHz spacing";
             }
             enum "192.88125" {
               description "192.88125 THz/1554.29 nm 6.25GHz spacing";
             }
             enum "192.88750" {
               description "192.88750 THz/1554.23 nm 6.25/12.5GHz spacing";
             }
             enum "192.89375" {
               description "192.89375 THz/1554.18 nm 6.25GHz spacing";
             }
             enum "192.90000" {
               description "192.90000 THz/1554.13 nm 6.25/12.5/50/100GHz spacing";
             }
             enum "192.90625" {
               description "192.90625 THz/1554.08 nm 6.25GHz spacing";
             }
             enum "192.91250" {
               description "192.91250 THz/1554.03 nm 6.25/12.5GHz spacing";
             }
             enum "192.91875" {
               description "192.91875 THz/1553.98 nm 6.25GHz spacing";
             }
             enum "192.92500" {
               description "192.92500 THz/1553.93 nm 6.25/12.5GHz spacing";
             }
             enum "192.93125" {
               description "192.93125 THz/1553.88 nm 6.25GHz spacing";
             }
             enum "192.93750" {
               description "192.93750 THz/1553.83 nm 6.25/12.5GHz spacing";
             }
             enum "192.94375" {
               description "192.94375 THz/1553.78 nm 6.25GHz spacing";
             }
             enum "192.95000" {
               description "192.95000 THz/1553.73 nm 6.25/12.5/50/75GHz spacing";
             }
             enum "192.95625" {
               description "192.95625 THz/1553.68 nm 6.25GHz spacing";
             }
             enum "192.96250" {
               description "192.96250 THz/1553.63 nm 6.25/12.5GHz spacing";
             }
             enum "192.96875" {
               description "192.96875 THz/1553.58 nm 6.25GHz spacing";
             }
             enum "192.97500" {
               description "192.97500 THz/1553.53 nm 6.25/12.5GHz spacing";
             }
             enum "192.98125" {
               description "192.98125 THz/1553.48 nm 6.25GHz spacing";
             }
             enum "192.98750" {
               description "192.98750 THz/1553.43 nm 6.25/12.5GHz spacing";
             }
             enum "192.99375" {
               description "192.99375 THz/1553.38 nm 6.25GHz spacing";
             }
             enum "193.00000" {
               description "193.00000 THz/1553.33 nm 6.25/12.5/50/100GHz spacing";
             }
             enum "193.00625" {
               description "193.00625 THz/1553.28 nm 6.25GHz spacing";
             }
             enum "193.01250" {
               description "193.01250 THz/1553.23 nm 6.25/12.5GHz spacing";
             }
             enum "193.01875" {
               description "193.01875 THz/1553.18 nm 6.25GHz spacing";
             }
             enum "193.02500" {
               description "193.02500 THz/1553.13 nm 6.25/12.5/75GHz spacing";
             }
             enum "193.03125" {
               description "193.03125 THz/1553.08 nm 6.25GHz spacing";
             }
             enum "193.03750" {
               description "193.03750 THz/1553.03 nm 6.25/12.5GHz spacing";
             }
             enum "193.04375" {
               description "193.04375 THz/1552.98 nm 6.25GHz spacing";
             }
             enum "193.05000" {
               description "193.05000 THz/1552.93 nm 6.25/12.5/50GHz spacing";
             }
             enum "193.05625" {
               description "193.05625 THz/1552.88 nm 6.25GHz spacing";
             }
             enum "193.06250" {
               description "193.06250 THz/1552.83 nm 6.25/12.5GHz spacing";
             }
             enum "193.06875" {
               description "193.06875 THz/1552.78 nm 6.25GHz spacing";
             }
             enum "193.07500" {
               description "193.07500 THz/1552.73 nm 6.25/12.5GHz spacing";
             }
             enum "193.08125" {
               description "193.08125 THz/1552.68 nm 6.25GHz spacing";
             }
             enum "193.08750" {
               description "193.08750 THz/1552.62 nm 6.25/12.5GHz spacing";
             }
             enum "193.09375" {
               description "193.09375 THz/1552.57 nm 6.25GHz spacing";
             }
             enum "193.10000" {
               description "193.10000 THz/1552.52 nm 6.25/12.5/50/75/100GHz spacing";
             }
             enum "193.10625" {
               description "193.10625 THz/1552.47 nm 6.25GHz spacing";
             }
             enum "193.11250" {
               description "193.11250 THz/1552.42 nm 6.25/12.5GHz spacing";
             }
             enum "193.11875" {
               description "193.11875 THz/1552.37 nm 6.25GHz spacing";
             }
             enum "193.12500" {
               description "193.12500 THz/1552.32 nm 6.25/12.5GHz spacing";
             }
             enum "193.13125" {
               description "193.13125 THz/1552.27 nm 6.25GHz spacing";
             }
             enum "193.13750" {
               description "193.13750 THz/1552.22 nm 6.25/12.5GHz spacing";
             }
             enum "193.14375" {
               description "193.14375 THz/1552.17 nm 6.25GHz spacing";
             }
             enum "193.15000" {
               description "193.15000 THz/1552.12 nm 6.25/12.5/50GHz spacing";
             }
             enum "193.15625" {
               description "193.15625 THz/1552.07 nm 6.25GHz spacing";
             }
             enum "193.16250" {
               description "193.16250 THz/1552.02 nm 6.25/12.5GHz spacing";
             }
             enum "193.16875" {
               description "193.16875 THz/1551.97 nm 6.25GHz spacing";
             }
             enum "193.17500" {
               description "193.17500 THz/1551.92 nm 6.25/12.5/75GHz spacing";
             }
             enum "193.18125" {
               description "193.18125 THz/1551.87 nm 6.25GHz spacing";
             }
             enum "193.18750" {
               description "193.18750 THz/1551.82 nm 6.25/12.5GHz spacing";
             }
             enum "193.19375" {
               description "193.19375 THz/1551.77 nm 6.25GHz spacing";
             }
             enum "193.20000" {
               description "193.20000 THz/1551.72 nm 6.25/12.5/50/100GHz spacing";
             }
             enum "193.20625" {
               description "193.20625 THz/1551.67 nm 6.25GHz spacing";
             }
             enum "193.21250" {
               description "193.21250 THz/1551.62 nm 6.25/12.5GHz spacing";
             }
             enum "193.21875" {
               description "193.21875 THz/1551.57 nm 6.25GHz spacing";
             }
             enum "193.22500" {
               description "193.22500 THz/1551.52 nm 6.25/12.5GHz spacing";
             }
             enum "193.23125" {
               description "193.23125 THz/1551.47 nm 6.25GHz spacing";
             }
             enum "193.23750" {
               description "193.23750 THz/1551.42 nm 6.25/12.5GHz spacing";
             }
             enum "193.24375" {
               description "193.24375 THz/1551.37 nm 6.25GHz spacing";
             }
             enum "193.25000" {
               description "193.25000 THz/1551.32 nm 6.25/12.5/50/75GHz spacing";
             }
             enum "193.25625" {
               description "193.25625 THz/1551.27 nm 6.25GHz spacing";
             }
             enum "193.26250" {
               description "193.26250 THz/1551.22 nm 6.25/12.5GHz spacing";
             }
             enum "193.26875" {
               description "193.26875 THz/1551.17 nm 6.25GHz spacing";
             }
             enum "193.27500" {
               description "193.27500 THz/1551.12 nm 6.25/12.5GHz spacing";
             }
             enum "193.28125" {
               description "193.28125 THz/1551.07 nm 6.25GHz spacing";
             }
             enum "193.28750" {
               description "193.28750 THz/1551.02 nm 6.25/12.5GHz spacing";
             }
             enum "193.29375" {
               description "193.29375 THz/1550.97 nm 6.25GHz spacing";
             }
             enum "193.30000" {
               description "193.30000 THz/1550.92 nm 6.25/12.5/50/100GHz spacing";
             }
             enum "193.30625" {
               description "193.30625 THz/1550.87 nm 6.25GHz spacing";
             }
             enum "193.31250" {
               description "193.31250 THz/1550.82 nm 6.25/12.5GHz spacing";
             }
             enum "193.31875" {
               description "193.31875 THz/1550.77 nm 6.25GHz spacing";
             }
             enum "193.32500" {
               description "193.32500 THz/1550.72 nm 6.25/12.5/75GHz spacing";
             }
             enum "193.33125" {
               description "193.33125 THz/1550.67 nm 6.25GHz spacing";
             }
             enum "193.33750" {
               description "193.33750 THz/1550.62 nm 6.25/12.5GHz spacing";
             }
             enum "193.34375" {
               description "193.34375 THz/1550.57 nm 6.25GHz spacing";
             }
             enum "193.35000" {
               description "193.35000 THz/1550.52 nm 6.25/12.5/50GHz spacing";
             }
             enum "193.35625" {
               description "193.35625 THz/1550.47 nm 6.25GHz spacing";
             }
             enum "193.36250" {
               description "193.36250 THz/1550.42 nm 6.25/12.5GHz spacing";
             }
             enum "193.36875" {
               description "193.36875 THz/1550.37 nm 6.25GHz spacing";
             }
             enum "193.37500" {
               description "193.37500 THz/1550.32 nm 6.25/12.5GHz spacing";
             }
             enum "193.38125" {
               description "193.38125 THz/1550.27 nm 6.25GHz spacing";
             }
             enum "193.38750" {
               description "193.38750 THz/1550.22 nm 6.25/12.5GHz spacing";
             }
             enum "193.39375" {
               description "193.39375 THz/1550.17 nm 6.25GHz spacing";
             }
             enum "193.40000" {
               description "193.40000 THz/1550.12 nm 6.25/12.5/50/75/100GHz spacing";
             }
             enum "193.40625" {
               description "193.40625 THz/1550.07 nm 6.25GHz spacing";
             }
             enum "193.41250" {
               description "193.41250 THz/1550.02 nm 6.25/12.5GHz spacing";
             }
             enum "193.41875" {
               description "193.41875 THz/1549.97 nm 6.25GHz spacing";
             }
             enum "193.42500" {
               description "193.42500 THz/1549.92 nm 6.25/12.5GHz spacing";
             }
             enum "193.43125" {
               description "193.43125 THz/1549.87 nm 6.25GHz spacing";
             }
             enum "193.43750" {
               description "193.43750 THz/1549.82 nm 6.25/12.5GHz spacing";
             }
             enum "193.44375" {
               description "193.44375 THz/1549.77 nm 6.25GHz spacing";
             }
             enum "193.45000" {
               description "193.45000 THz/1549.72 nm 6.25/12.5/50GHz spacing";
             }
             enum "193.45625" {
               description "193.45625 THz/1549.67 nm 6.25GHz spacing";
             }
             enum "193.46250" {
               description "193.46250 THz/1549.62 nm 6.25/12.5GHz spacing";
             }
             enum "193.46875" {
               description "193.46875 THz/1549.57 nm 6.25GHz spacing";
             }
             enum "193.47500" {
               description "193.47500 THz/1549.52 nm 6.25/12.5/75GHz spacing";
             }
             enum "193.48125" {
               description "193.48125 THz/1549.47 nm 6.25GHz spacing";
             }
             enum "193.48750" {
               description "193.48750 THz/1549.42 nm 6.25/12.5GHz spacing";
             }
             enum "193.49375" {
               description "193.49375 THz/1549.37 nm 6.25GHz spacing";
             }
             enum "193.50000" {
               description "193.50000 THz/1549.32 nm 6.25/12.5/50/100GHz spacing";
             }
             enum "193.50625" {
               description "193.50625 THz/1549.26 nm 6.25GHz spacing";
             }
             enum "193.51250" {
               description "193.51250 THz/1549.21 nm 6.25/12.5GHz spacing";
             }
             enum "193.51875" {
               description "193.51875 THz/1549.16 nm 6.25GHz spacing";
             }
             enum "193.52500" {
               description "193.52500 THz/1549.11 nm 6.25/12.5GHz spacing";
             }
             enum "193.53125" {
               description "193.53125 THz/1549.06 nm 6.25GHz spacing";
             }
             enum "193.53750" {
               description "193.53750 THz/1549.01 nm 6.25/12.5GHz spacing";
             }
             enum "193.54375" {
               description "193.54375 THz/1548.96 nm 6.25GHz spacing";
             }
             enum "193.55000" {
               description "193.55000 THz/1548.91 nm 6.25/12.5/50/75GHz spacing";
             }
             enum "193.55625" {
               description "193.55625 THz/1548.86 nm 6.25GHz spacing";
             }
             enum "193.56250" {
               description "193.56250 THz/1548.81 nm 6.25/12.5GHz spacing";
             }
             enum "193.56875" {
               description "193.56875 THz/1548.76 nm 6.25GHz spacing";
             }
             enum "193.57500" {
               description "193.57500 THz/1548.71 nm 6.25/12.5GHz spacing";
             }
             enum "193.58125" {
               description "193.58125 THz/1548.66 nm 6.25GHz spacing";
             }
             enum "193.58750" {
               description "193.58750 THz/1548.61 nm 6.25/12.5GHz spacing";
             }
             enum "193.59375" {
               description "193.59375 THz/1548.56 nm 6.25GHz spacing";
             }
             enum "193.60000" {
               description "193.60000 THz/1548.51 nm 6.25/12.5/50/100GHz spacing";
             }
             enum "193.60625" {
               description "193.60625 THz/1548.46 nm 6.25GHz spacing";
             }
             enum "193.61250" {
               description "193.61250 THz/1548.41 nm 6.25/12.5GHz spacing";
             }
             enum "193.61875" {
               description "193.61875 THz/1548.36 nm 6.25GHz spacing";
             }
             enum "193.62500" {
               description "193.62500 THz/1548.31 nm 6.25/12.5/75GHz spacing";
             }
             enum "193.63125" {
               description "193.63125 THz/1548.26 nm 6.25GHz spacing";
             }
             enum "193.63750" {
               description "193.63750 THz/1548.21 nm 6.25/12.5GHz spacing";
             }
             enum "193.64375" {
               description "193.64375 THz/1548.16 nm 6.25GHz spacing";
             }
             enum "193.65000" {
               description "193.65000 THz/1548.11 nm 6.25/12.5/50GHz spacing";
             }
             enum "193.65625" {
               description "193.65625 THz/1548.06 nm 6.25GHz spacing";
             }
             enum "193.66250" {
               description "193.66250 THz/1548.02 nm 6.25/12.5GHz spacing";
             }
             enum "193.66875" {
               description "193.66875 THz/1547.97 nm 6.25GHz spacing";
             }
             enum "193.67500" {
               description "193.67500 THz/1547.92 nm 6.25/12.5GHz spacing";
             }
             enum "193.68125" {
               description "193.68125 THz/1547.87 nm 6.25GHz spacing";
             }
             enum "193.68750" {
               description "193.68750 THz/1547.82 nm 6.25/12.5GHz spacing";
             }
             enum "193.69375" {
               description "193.69375 THz/1547.77 nm 6.25GHz spacing";
             }
             enum "193.70000" {
               description "193.70000 THz/1547.72 nm 6.25/12.5/50/100/75GHz spacing";
             }
             enum "193.70625" {
               description "193.70625 THz/1547.67 nm 6.25GHz spacing";
             }
             enum "193.71250" {
               description "193.71250 THz/1547.62 nm 6.25/12.5GHz spacing";
             }
             enum "193.71875" {
               description "193.71875 THz/1547.57 nm 6.25GHz spacing";
             }
             enum "193.72500" {
               description "193.72500 THz/1547.52 nm 6.25/12.5GHz spacing";
             }
             enum "193.73125" {
               description "193.73125 THz/1547.47 nm 6.25GHz spacing";
             }
             enum "193.73750" {
               description "193.73750 THz/1547.42 nm 6.25/12.5GHz spacing";
             }
             enum "193.74375" {
               description "193.74375 THz/1547.37 nm 6.25GHz spacing";
             }
             enum "193.75000" {
               description "193.75000 THz/1547.32 nm 6.25/12.5/50GHz spacing";
             }
             enum "193.75625" {
               description "193.75625 THz/1547.27 nm 6.25GHz spacing";
             }
             enum "193.76250" {
               description "193.76250 THz/1547.22 nm 6.25/12.5GHz spacing";
             }
             enum "193.76875" {
               description "193.76875 THz/1547.17 nm 6.25GHz spacing";
             }
             enum "193.77500" {
               description "193.77500 THz/1547.12 nm 6.25/12.5/75GHz spacing";
             }
             enum "193.78125" {
               description "193.78125 THz/1547.07 nm 6.25GHz spacing";
             }
             enum "193.78750" {
               description "193.78750 THz/1547.02 nm 6.25/12.5GHz spacing";
             }
             enum "193.79375" {
               description "193.79375 THz/1546.97 nm 6.25GHz spacing";
             }
             enum "193.80000" {
               description "193.80000 THz/1546.92 nm 6.25/12.5/50/100GHz spacing";
             }
             enum "193.80625" {
               description "193.80625 THz/1546.87 nm 6.25GHz spacing";
             }
             enum "193.81250" {
               description "193.81250 THz/1546.82 nm 6.25/12.5GHz spacing";
             }
             enum "193.81875" {
               description "193.81875 THz/1546.77 nm 6.25GHz spacing";
             }
             enum "193.82500" {
               description "193.82500 THz/1546.72 nm 6.25/12.5GHz spacing";
             }
             enum "193.83125" {
               description "193.83125 THz/1546.67 nm 6.25GHz spacing";
             }
             enum "193.83750" {
               description "193.83750 THz/1546.62 nm 6.25/12.5GHz spacing";
             }
             enum "193.84375" {
               description "193.84375 THz/1546.57 nm 6.25GHz spacing";
             }
             enum "193.85000" {
               description "193.85000 THz/1546.52 nm 6.25/12.5/50/75GHz spacing";
             }
             enum "193.85625" {
               description "193.85625 THz/1546.47 nm 6.25GHz spacing";
             }
             enum "193.86250" {
               description "193.86250 THz/1546.42 nm 6.25/12.5GHz spacing";
             }
             enum "193.86875" {
               description "193.86875 THz/1546.37 nm 6.25GHz spacing";
             }
             enum "193.87500" {
               description "193.87500 THz/1546.32 nm 6.25/12.5GHz spacing";
             }
             enum "193.88125" {
               description "193.88125 THz/1546.27 nm 6.25GHz spacing";
             }
             enum "193.88750" {
               description "193.88750 THz/1546.22 nm 6.25/12.5GHz spacing";
             }
             enum "193.89375" {
               description "193.89375 THz/1546.17 nm 6.25GHz spacing";
             }
             enum "193.90000" {
               description "193.90000 THz/1546.12 nm 6.25/12.5/50/100GHz spacing";
             }
             enum "193.90625" {
               description "193.90625 THz/1546.07 nm 6.25GHz spacing";
             }
             enum "193.91250" {
               description "193.91250 THz/1546.02 nm 6.25/12.5GHz spacing";
             }
             enum "193.91875" {
               description "193.91875 THz/1545.97 nm 6.25GHz spacing";
             }
             enum "193.92500" {
               description "193.92500 THz/1545.92 nm 6.25/12.5/75GHz spacing";
             }
             enum "193.93125" {
               description "193.93125 THz/1545.87 nm 6.25GHz spacing";
             }
             enum "193.93750" {
               description "193.93750 THz/1545.82 nm 6.25/12.5GHz spacing";
             }
             enum "193.94375" {
               description "193.94375 THz/1545.77 nm 6.25GHz spacing";
             }
             enum "193.95000" {
               description "193.95000 THz/1545.72 nm 6.25/12.5/50GHz spacing";
             }
             enum "193.95625" {
               description "193.95625 THz/1545.67 nm 6.25GHz spacing";
             }
             enum "193.96250" {
               description "193.96250 THz/1545.62 nm 6.25/12.5GHz spacing";
             }
             enum "193.96875" {
               description "193.96875 THz/1545.57 nm 6.25GHz spacing";
             }
             enum "193.97500" {
               description "193.97500 THz/1545.52 nm 6.25/12.5GHz spacing";
             }
             enum "193.98125" {
               description "193.98125 THz/1545.47 nm 6.25GHz spacing";
             }
             enum "193.98750" {
               description "193.98750 THz/1545.42 nm 6.25/12.5GHz spacing";
             }
             enum "193.99375" {
               description "193.99375 THz/1545.37 nm 6.25GHz spacing";
             }
             enum "194.00000" {
               description "194.00000 THz/1545.32 nm 6.25/12.5/50/75/100GHz spacing";
             }
             enum "194.00625" {
               description "194.00625 THz/1545.27 nm 6.25GHz spacing";
             }
             enum "194.01250" {
               description "194.01250 THz/1545.22 nm 6.25/12.5GHz spacing";
             }
             enum "194.01875" {
               description "194.01875 THz/1545.17 nm 6.25GHz spacing";
             }
             enum "194.02500" {
               description "194.02500 THz/1545.12 nm 6.25/12.5GHz spacing";
             }
             enum "194.03125" {
               description "194.03125 THz/1545.07 nm 6.25GHz spacing";
             }
             enum "194.03750" {
               description "194.03750 THz/1545.02 nm 6.25/12.5GHz spacing";
             }
             enum "194.04375" {
               description "194.04375 THz/1544.97 nm 6.25GHz spacing";
             }
             enum "194.05000" {
               description "194.05000 THz/1544.92 nm 6.25/12.5/50GHz spacing";
             }
             enum "194.05625" {
               description "194.05625 THz/1544.87 nm 6.25GHz spacing";
             }
             enum "194.06250" {
               description "194.06250 THz/1544.82 nm 6.25/12.5GHz spacing";
             }
             enum "194.06875" {
               description "194.06875 THz/1544.77 nm 6.25GHz spacing";
             }
             enum "194.07500" {
               description "194.07500 THz/1544.72 nm 6.25/12.5/75GHz spacing";
             }
             enum "194.08125" {
               description "194.08125 THz/1544.68 nm 6.25GHz spacing";
             }
             enum "194.08750" {
               description "194.08750 THz/1544.63 nm 6.25/12.5GHz spacing";
             }
             enum "194.09375" {
               description "194.09375 THz/1544.58 nm 6.25GHz spacing";
             }
             enum "194.10000" {
               description "194.10000 THz/1544.53 nm 6.25/12.5/50/100GHz spacing";
             }
             enum "194.10625" {
               description "194.10625 THz/1544.48 nm 6.25GHz spacing";
             }
             enum "194.11250" {
               description "194.11250 THz/1544.43 nm 6.25/12.5GHz spacing";
             }
             enum "194.11875" {
               description "194.11875 THz/1544.38 nm 6.25GHz spacing";
             }
             enum "194.12500" {
               description "194.12500 THz/1544.33 nm 6.25/12.5GHz spacing";
             }
             enum "194.13125" {
               description "194.13125 THz/1544.28 nm 6.25GHz spacing";
             }
             enum "194.13750" {
               description "194.13750 THz/1544.23 nm 6.25/12.5GHz spacing";
             }
             enum "194.14375" {
               description "194.14375 THz/1544.18 nm 6.25GHz spacing";
             }
             enum "194.15000" {
               description "194.15000 THz/1544.13 nm 6.25/12.5/50/75GHz spacing";
             }
             enum "194.15625" {
               description "194.15625 THz/1544.08 nm 6.25GHz spacing";
             }
             enum "194.16250" {
               description "194.16250 THz/1544.03 nm 6.25/12.5GHz spacing";
             }
             enum "194.16875" {
               description "194.16875 THz/1543.98 nm 6.25GHz spacing";
             }
             enum "194.17500" {
               description "194.17500 THz/1543.93 nm 6.25/12.5GHz spacing";
             }
             enum "194.18125" {
               description "194.18125 THz/1543.88 nm 6.25GHz spacing";
             }
             enum "194.18750" {
               description "194.18750 THz/1543.83 nm 6.25/12.5GHz spacing";
             }
             enum "194.19375" {
               description "194.19375 THz/1543.78 nm 6.25GHz spacing";
             }
             enum "194.20000" {
               description "194.20000 THz/1543.73 nm 6.25/12.5/50/100GHz spacing";
             }
             enum "194.20625" {
               description "194.20625 THz/1543.68 nm 6.25GHz spacing";
             }
             enum "194.21250" {
               description "194.21250 THz/1543.63 nm 6.25/12.5GHz spacing";
             }
             enum "194.21875" {
               description "194.21875 THz/1543.58 nm 6.25GHz spacing";
             }
             enum "194.22500" {
               description "194.22500 THz/1543.53 nm 6.25/12.5/75GHz spacing";
             }
             enum "194.23125" {
               description "194.23125 THz/1543.48 nm 6.25GHz spacing";
             }
             enum "194.23750" {
               description "194.23750 THz/1543.43 nm 6.25/12.5GHz spacing";
             }
             enum "194.24375" {
               description "194.24375 THz/1543.38 nm 6.25GHz spacing";
             }
             enum "194.25000" {
               description "194.25000 THz/1543.33 nm 6.25/12.5/50/75GHz spacing";
             }
             enum "194.25625" {
               description "194.25625 THz/1543.28 nm 6.25GHz spacing";
             }
             enum "194.26250" {
               description "194.26250 THz/1543.23 nm 6.25/12.5GHz spacing";
             }
             enum "194.26875" {
               description "194.26875 THz/1543.18 nm 6.25GHz spacing";
             }
             enum "194.27500" {
               description "194.27500 THz/1543.13 nm 6.25/12.5GHz spacing";
             }
             enum "194.28125" {
               description "194.28125 THz/1543.08 nm 6.25GHz spacing";
             }
             enum "194.28750" {
               description "194.28750 THz/1543.04 nm 6.25/12.5GHz spacing";
             }
             enum "194.29375" {
               description "194.29375 THz/1542.99 nm 6.25GHz spacing";
             }
             enum "194.30000" {
               description "194.30000 THz/1542.94 nm 6.25/12.5/50/75/100GHz spacing";
             }
             enum "194.30625" {
               description "194.30625 THz/1542.89 nm 6.25GHz spacing";
             }
             enum "194.31250" {
               description "194.31250 THz/1542.84 nm 6.25/12.5GHz spacing";
             }
             enum "194.31875" {
               description "194.31875 THz/1542.79 nm 6.25GHz spacing";
             }
             enum "194.32500" {
               description "194.32500 THz/1542.74 nm 6.25/12.5GHz spacing";
             }
             enum "194.33125" {
               description "194.33125 THz/1542.69 nm 6.25GHz spacing";
             }
             enum "194.33750" {
               description "194.33750 THz/1542.64 nm 6.25/12.5GHz spacing";
             }
             enum "194.34375" {
               description "194.34375 THz/1542.59 nm 6.25GHz spacing";
             }
             enum "194.35000" {
               description "194.35000 THz/1542.54 nm 6.25/12.5/50GHz spacing";
             }
             enum "194.35625" {
               description "194.35625 THz/1542.49 nm 6.25GHz spacing";
             }
             enum "194.36250" {
               description "194.36250 THz/1542.44 nm 6.25/12.5GHz spacing";
             }
             enum "194.36875" {
               description "194.36875 THz/1542.39 nm 6.25GHz spacing";
             }
             enum "194.37500" {
               description "194.37500 THz/1542.34 nm 6.25/12.5/75GHz spacing";
             }
             enum "194.38125" {
               description "194.38125 THz/1542.29 nm 6.25GHz spacing";
             }
             enum "194.38750" {
               description "194.38750 THz/1542.24 nm 6.25/12.5GHz spacing";
             }
             enum "194.39375" {
               description "194.39375 THz/1542.19 nm 6.25GHz spacing";
             }
             enum "194.40000" {
               description "194.40000 THz/1542.14 nm 6.25/12.5/50/100GHz spacing";
             }
             enum "194.40625" {
               description "194.40625 THz/1542.09 nm 6.25GHz spacing";
             }
             enum "194.41250" {
               description "194.41250 THz/1542.04 nm 6.25/12.5GHz spacing";
             }
             enum "194.41875" {
               description "194.41875 THz/1541.99 nm 6.25GHz spacing";
             }
             enum "194.42500" {
               description "194.42500 THz/1541.94 nm 6.25/12.5GHz spacing";
             }
             enum "194.43125" {
               description "194.43125 THz/1541.89 nm 6.25GHz spacing";
             }
             enum "194.43750" {
               description "194.43750 THz/1541.84 nm 6.25/12.5GHz spacing";
             }
             enum "194.44375" {
               description "194.44375 THz/1541.80 nm 6.25GHz spacing";
             }
             enum "194.45000" {
               description "194.45000 THz/1541.75 nm 6.25/12.5/50/75GHz spacing";
             }
             enum "194.45625" {
               description "194.45625 THz/1541.70 nm 6.25GHz spacing";
             }
             enum "194.46250" {
               description "194.46250 THz/1541.65 nm 6.25/12.5GHz spacing";
             }
             enum "194.46875" {
               description "194.46875 THz/1541.60 nm 6.25GHz spacing";
             }
             enum "194.47500" {
               description "194.47500 THz/1541.55 nm 6.25/12.5GHz spacing";
             }
             enum "194.48125" {
               description "194.48125 THz/1541.50 nm 6.25GHz spacing";
             }
             enum "194.48750" {
               description "194.48750 THz/1541.45 nm 6.25/12.5GHz spacing";
             }
             enum "194.49375" {
               description "194.49375 THz/1541.40 nm 6.25GHz spacing";
             }
             enum "194.50000" {
               description "194.50000 THz/1541.35 nm 6.25/12.5/50/100GHz spacing";
             }
             enum "194.50625" {
               description "194.50625 THz/1541.30 nm 6.25GHz spacing";
             }
             enum "194.51250" {
               description "194.51250 THz/1541.25 nm 6.25/12.5GHz spacing";
             }
             enum "194.51875" {
               description "194.51875 THz/1541.20 nm 6.25GHz spacing";
             }
             enum "194.52500" {
               description "194.52500 THz/1541.15 nm 6.25/12.5/75GHz spacing";
             }
             enum "194.53125" {
               description "194.53125 THz/1541.10 nm 6.25GHz spacing";
             }
             enum "194.53750" {
               description "194.53750 THz/1541.05 nm 6.25/12.5GHz spacing";
             }
             enum "194.54375" {
               description "194.54375 THz/1541.00 nm 6.25GHz spacing";
             }
             enum "194.55000" {
               description "194.55000 THz/1540.95 nm 6.25/12.5/50GHz spacing";
             }
             enum "194.55625" {
               description "194.55625 THz/1540.90 nm 6.25GHz spacing";
             }
             enum "194.56250" {
               description "194.56250 THz/1540.85 nm 6.25/12.5GHz spacing";
             }
             enum "194.56875" {
               description "194.56875 THz/1540.80 nm 6.25GHz spacing";
             }
             enum "194.57500" {
               description "194.57500 THz/1540.76 nm 6.25/12.5GHz spacing";
             }
             enum "194.58125" {
               description "194.58125 THz/1540.71 nm 6.25GHz spacing";
             }
             enum "194.58750" {
               description "194.58750 THz/1540.66 nm 6.25/12.5GHz spacing";
             }
             enum "194.59375" {
               description "194.59375 THz/1540.61 nm 6.25GHz spacing";
             }
             enum "194.60000" {
               description "194.60000 THz/1540.56 nm 6.25/12.5/50/75/100GHz spacing";
             }
             enum "194.60625" {
               description "194.60625 THz/1540.51 nm 6.25GHz spacing";
             }
             enum "194.61250" {
               description "194.61250 THz/1540.46 nm 6.25/12.5GHz spacing";
             }
             enum "194.61875" {
               description "194.61875 THz/1540.41 nm 6.25GHz spacing";
             }
             enum "194.62500" {
               description "194.62500 THz/1540.36 nm 6.25/12.5GHz spacing";
             }
             enum "194.63125" {
               description "194.63125 THz/1540.31 nm 6.25GHz spacing";
             }
             enum "194.63750" {
               description "194.63750 THz/1540.26 nm 6.25/12.5GHz spacing";
             }
             enum "194.64375" {
               description "194.64375 THz/1540.21 nm 6.25GHz spacing";
             }
             enum "194.65000" {
               description "194.65000 THz/1540.16 nm 6.25/12.5/50GHz spacing";
             }
             enum "194.65625" {
               description "194.65625 THz/1540.11 nm 6.25GHz spacing";
             }
             enum "194.66250" {
               description "194.66250 THz/1540.06 nm 6.25/12.5GHz spacing";
             }
             enum "194.66875" {
               description "194.66875 THz/1540.01 nm 6.25GHz spacing";
             }
             enum "194.67500" {
               description "194.67500 THz/1539.96 nm 6.25/12.5/75GHz spacing";
             }
             enum "194.68125" {
               description "194.68125 THz/1539.91 nm 6.25GHz spacing";
             }
             enum "194.68750" {
               description "194.68750 THz/1539.86 nm 6.25/12.5GHz spacing";
             }
             enum "194.69375" {
               description "194.69375 THz/1539.82 nm 6.25GHz spacing";
             }
             enum "194.70000" {
               description "194.70000 THz/1539.77 nm 6.25/12.5/50/100GHz spacing";
             }
             enum "194.70625" {
               description "194.70625 THz/1539.72 nm 6.25GHz spacing";
             }
             enum "194.71250" {
               description "194.71250 THz/1539.67 nm 6.25/12.5GHz spacing";
             }
             enum "194.71875" {
               description "194.71875 THz/1539.62 nm 6.25GHz spacing";
             }
             enum "194.72500" {
               description "194.72500 THz/1539.57 nm 6.25/12.5GHz spacing";
             }
             enum "194.73125" {
               description "194.73125 THz/1539.52 nm 6.25GHz spacing";
             }
             enum "194.73750" {
               description "194.73750 THz/1539.47 nm 6.25/12.5GHz spacing";
             }
             enum "194.74375" {
               description "194.74375 THz/1539.42 nm 6.25GHz spacing";
             }
             enum "194.75000" {
               description "194.75000 THz/1539.37 nm 6.25/12.5/50/75GHz spacing";
             }
             enum "194.75625" {
               description "194.75625 THz/1539.32 nm 6.25GHz spacing";
             }
             enum "194.76250" {
               description "194.76250 THz/1539.27 nm 6.25/12.5GHz spacing";
             }
             enum "194.76875" {
               description "194.76875 THz/1539.22 nm 6.25GHz spacing";
             }
             enum "194.77500" {
               description "194.77500 THz/1539.17 nm 6.25/12.5GHz spacing";
             }
             enum "194.78125" {
               description "194.78125 THz/1539.12 nm 6.25GHz spacing";
             }
             enum "194.78750" {
               description "194.78750 THz/1539.07 nm 6.25/12.5GHz spacing";
             }
             enum "194.79375" {
               description "194.79375 THz/1539.03 nm 6.25GHz spacing";
             }
             enum "194.80000" {
               description "194.80000 THz/1538.98 nm 6.25/12.5/50/100GHz spacing";
             }
             enum "194.80625" {
               description "194.80625 THz/1538.93 nm 6.25GHz spacing";
             }
             enum "194.81250" {
               description "194.81250 THz/1538.88 nm 6.25/12.5GHz spacing";
             }
             enum "194.81875" {
               description "194.81875 THz/1538.83 nm 6.25GHz spacing";
             }
             enum "194.82500" {
               description "194.82500 THz/1538.78 nm 6.25/12.5/75GHz spacing";
             }
             enum "194.83125" {
               description "194.83125 THz/1538.73 nm 6.25GHz spacing";
             }
             enum "194.83750" {
               description "194.83750 THz/1538.68 nm 6.25/12.5GHz spacing";
             }
             enum "194.84375" {
               description "194.84375 THz/1538.63 nm 6.25GHz spacing";
             }
             enum "194.85000" {
               description "194.85000 THz/1538.58 nm 6.25/12.5/50GHz spacing";
             }
             enum "194.85625" {
               description "194.85625 THz/1538.53 nm 6.25GHz spacing";
             }
             enum "194.86250" {
               description "194.86250 THz/1538.48 nm 6.25/12.5GHz spacing";
             }
             enum "194.86875" {
               description "194.86875 THz/1538.43 nm 6.25GHz spacing";
             }
             enum "194.87500" {
               description "194.87500 THz/1538.38 nm 6.25/12.5GHz spacing";
             }
             enum "194.88125" {
               description "194.88125 THz/1538.33 nm 6.25GHz spacing";
             }
             enum "194.88750" {
               description "194.88750 THz/1538.28 nm 6.25/12.5GHz spacing";
             }
             enum "194.89375" {
               description "194.89375 THz/1538.24 nm 6.25GHz spacing";
             }
             enum "194.90000" {
               description "194.90000 THz/1538.19 nm 6.25/12.5/50/75/100GHz spacing";
             }
             enum "194.90625" {
               description "194.90625 THz/1538.14 nm 6.25GHz spacing";
             }
             enum "194.91250" {
               description "194.91250 THz/1538.09 nm 6.25/12.5GHz spacing";
             }
             enum "194.91875" {
               description "194.91875 THz/1538.04 nm 6.25GHz spacing";
             }
             enum "194.92500" {
               description "194.92500 THz/1537.99 nm 6.25/12.5GHz spacing";
             }
             enum "194.93125" {
               description "194.93125 THz/1537.94 nm 6.25GHz spacing";
             }
             enum "194.93750" {
               description "194.93750 THz/1537.89 nm 6.25/12.5GHz spacing";
             }
             enum "194.94375" {
               description "194.94375 THz/1537.84 nm 6.25GHz spacing";
             }
             enum "194.95000" {
               description "194.95000 THz/1537.79 nm 6.25/12.5/50GHz spacing";
             }
             enum "194.95625" {
               description "194.95625 THz/1537.74 nm 6.25GHz spacing";
             }
             enum "194.96250" {
               description "194.96250 THz/1537.69 nm 6.25/12.5GHz spacing";
             }
             enum "194.96875" {
               description "194.96875 THz/1537.64 nm 6.25GHz spacing";
             }
             enum "194.97500" {
               description "194.97500 THz/1537.59 nm 6.25/12.5/75GHz spacing";
             }
             enum "194.98125" {
               description "194.98125 THz/1537.55 nm 6.25GHz spacing";
             }
             enum "194.98750" {
               description "194.98750 THz/1537.50 nm 6.25/12.5GHz spacing";
             }
             enum "194.99375" {
               description "194.99375 THz/1537.45 nm 6.25GHz spacing";
             }
             enum "195.00000" {
               description "195.00000 THz/1537.40 nm 6.25/12.5/50/100GHz spacing";
             }
             enum "195.00625" {
               description "195.00625 THz/1537.35 nm 6.25GHz spacing";
             }
             enum "195.01250" {
               description "195.01250 THz/1537.30 nm 6.25/12.5GHz spacing";
             }
             enum "195.01875" {
               description "195.01875 THz/1537.25 nm 6.25GHz spacing";
             }
             enum "195.02500" {
               description "195.02500 THz/1537.20 nm 6.25/12.5GHz spacing";
             }
             enum "195.03125" {
               description "195.03125 THz/1537.15 nm 6.25GHz spacing";
             }
             enum "195.03750" {
               description "195.03750 THz/1537.10 nm 6.25/12.5GHz spacing";
             }
             enum "195.04375" {
               description "195.04375 THz/1537.05 nm 6.25GHz spacing";
             }
             enum "195.05000" {
               description "195.05000 THz/1537.00 nm 6.25/12.5/50/75GHz spacing";
             }
             enum "195.05625" {
               description "195.05625 THz/1536.95 nm 6.25GHz spacing";
             }
             enum "195.06250" {
               description "195.06250 THz/1536.90 nm 6.25/12.5GHz spacing";
             }
             enum "195.06875" {
               description "195.06875 THz/1536.86 nm 6.25GHz spacing";
             }
             enum "195.07500" {
               description "195.07500 THz/1536.81 nm 6.25/12.5GHz spacing";
             }
             enum "195.08125" {
               description "195.08125 THz/1536.76 nm 6.25GHz spacing";
             }
             enum "195.08750" {
               description "195.08750 THz/1536.71 nm 6.25/12.5GHz spacing";
             }
             enum "195.09375" {
               description "195.09375 THz/1536.66 nm 6.25GHz spacing";
             }
             enum "195.10000" {
               description "195.10000 THz/1536.61 nm 6.25/12.5/50/100GHz spacing";
             }
             enum "195.10625" {
               description "195.10625 THz/1536.56 nm 6.25GHz spacing";
             }
             enum "195.11250" {
               description "195.11250 THz/1536.51 nm 6.25/12.5GHz spacing";
             }
             enum "195.11875" {
               description "195.11875 THz/1536.46 nm 6.25GHz spacing";
             }
             enum "195.12500" {
               description "195.12500 THz/1536.41 nm 6.25/12.5/75GHz spacing";
             }
             enum "195.13125" {
               description "195.13125 THz/1536.36 nm 6.25GHz spacing";
             }
             enum "195.13750" {
               description "195.13750 THz/1536.31 nm 6.25/12.5GHz spacing";
             }
             enum "195.14375" {
               description "195.14375 THz/1536.26 nm 6.25GHz spacing";
             }
             enum "195.15000" {
               description "195.15000 THz/1536.22 nm 6.25/12.5/50GHz spacing";
             }
             enum "195.15625" {
               description "195.15625 THz/1536.17 nm 6.25GHz spacing";
             }
             enum "195.16250" {
               description "195.16250 THz/1536.12 nm 6.25/12.5GHz spacing";
             }
             enum "195.16875" {
               description "195.16875 THz/1536.07 nm 6.25GHz spacing";
             }
             enum "195.17500" {
               description "195.17500 THz/1536.02 nm 6.25/12.5GHz spacing";
             }
             enum "195.18125" {
               description "195.18125 THz/1535.97 nm 6.25GHz spacing";
             }
             enum "195.18750" {
               description "195.18750 THz/1535.92 nm 6.25/12.5GHz spacing";
             }
             enum "195.19375" {
               description "195.19375 THz/1535.87 nm 6.25GHz spacing";
             }
             enum "195.20000" {
               description "195.20000 THz/1535.82 nm 6.25/12.5/50/75/100GHz spacing";
             }
             enum "195.20625" {
               description "195.20625 THz/1535.77 nm 6.25GHz spacing";
             }
             enum "195.21250" {
               description "195.21250 THz/1535.72 nm 6.25/12.5GHz spacing";
             }
             enum "195.21875" {
               description "195.21875 THz/1535.67 nm 6.25GHz spacing";
             }
             enum "195.22500" {
               description "195.22500 THz/1535.63 nm 6.25/12.5GHz spacing";
             }
             enum "195.23125" {
               description "195.23125 THz/1535.58 nm 6.25GHz spacing";
             }
             enum "195.23750" {
               description "195.23750 THz/1535.53 nm 6.25/12.5GHz spacing";
             }
             enum "195.24375" {
               description "195.24375 THz/1535.48 nm 6.25GHz spacing";
             }
             enum "195.25000" {
               description "195.25000 THz/1535.43 nm 6.25/12.5/50GHz spacing";
             }
             enum "195.25625" {
               description "195.25625 THz/1535.38 nm 6.25GHz spacing";
             }
             enum "195.26250" {
               description "195.26250 THz/1535.33 nm 6.25/12.5GHz spacing";
             }
             enum "195.26875" {
               description "195.26875 THz/1535.28 nm 6.25GHz spacing";
             }
             enum "195.27500" {
               description "195.27500 THz/1535.23 nm 6.25/12.5/75GHz spacing";
             }
             enum "195.28125" {
               description "195.28125 THz/1535.18 nm 6.25GHz spacing";
             }
             enum "195.28750" {
               description "195.28750 THz/1535.13 nm 6.25/12.5GHz spacing";
             }
             enum "195.29375" {
               description "195.29375 THz/1535.08 nm 6.25GHz spacing";
             }
             enum "195.30000" {
               description "195.30000 THz/1535.04 nm 6.25/12.5/50/100GHz spacing";
             }
             enum "195.30625" {
               description "195.30625 THz/1534.99 nm 6.25GHz spacing";
             }
             enum "195.31250" {
               description "195.31250 THz/1534.94 nm 6.25/12.5GHz spacing";
             }
             enum "195.31875" {
               description "195.31875 THz/1534.89 nm 6.25GHz spacing";
             }
             enum "195.32500" {
               description "195.32500 THz/1534.84 nm 6.25/12.5GHz spacing";
             }
             enum "195.33125" {
               description "195.33125 THz/1534.79 nm 6.25GHz spacing";
             }
             enum "195.33750" {
               description "195.33750 THz/1534.74 nm 6.25/12.5GHz spacing";
             }
             enum "195.34375" {
               description "195.34375 THz/1534.69 nm 6.25GHz spacing";
             }
             enum "195.35000" {
               description "195.35000 THz/1534.64 nm 6.25/12.5/50/75GHz spacing";
             }
             enum "195.35625" {
               description "195.35625 THz/1534.59 nm 6.25GHz spacing";
             }
             enum "195.36250" {
               description "195.36250 THz/1534.54 nm 6.25/12.5GHz spacing";
             }
             enum "195.36875" {
               description "195.36875 THz/1534.50 nm 6.25GHz spacing";
             }
             enum "195.37500" {
               description "195.37500 THz/1534.45 nm 6.25/12.5GHz spacing";
             }
             enum "195.38125" {
               description "195.38125 THz/1534.40 nm 6.25GHz spacing";
             }
             enum "195.38750" {
               description "195.38750 THz/1534.35 nm 6.25/12.5GHz spacing";
             }
             enum "195.39375" {
               description "195.39375 THz/1534.30 nm 6.25GHz spacing";
             }
             enum "195.40000" {
               description "195.40000 THz/1534.25 nm 6.25/12.5/50/100GHz spacing";
             }
             enum "195.40625" {
               description "195.40625 THz/1534.20 nm 6.25GHz spacing";
             }
             enum "195.41250" {
               description "195.41250 THz/1534.15 nm 6.25/12.5GHz spacing";
             }
             enum "195.41875" {
               description "195.41875 THz/1534.10 nm 6.25GHz spacing";
             }
             enum "195.42500" {
               description "195.42500 THz/1534.05 nm 6.25/12.5/75GHz spacing";
             }
             enum "195.43125" {
               description "195.43125 THz/1534.00 nm 6.25GHz spacing";
             }
             enum "195.43750" {
               description "195.43750 THz/1533.96 nm 6.25/12.5GHz spacing";
             }
             enum "195.44375" {
               description "195.44375 THz/1533.91 nm 6.25GHz spacing";
             }
             enum "195.45000" {
               description "195.45000 THz/1533.86 nm 6.25/12.5/50GHz spacing";
             }
             enum "195.45625" {
               description "195.45625 THz/1533.81 nm 6.25GHz spacing";
             }
             enum "195.46250" {
               description "195.46250 THz/1533.76 nm 6.25/12.5GHz spacing";
             }
             enum "195.46875" {
               description "195.46875 THz/1533.71 nm 6.25GHz spacing";
             }
             enum "195.47500" {
               description "195.47500 THz/1533.66 nm 6.25/12.5GHz spacing";
             }
             enum "195.48125" {
               description "195.48125 THz/1533.61 nm 6.25GHz spacing";
             }
             enum "195.48750" {
               description "195.48750 THz/1533.56 nm 6.25/12.5GHz spacing";
             }
             enum "195.49375" {
               description "195.49375 THz/1533.51 nm 6.25GHz spacing";
             }
             enum "195.50000" {
               description "195.50000 THz/1533.47 nm 6.25/12.5/50/75/100GHz spacing";
             }
             enum "195.50625" {
               description "195.50625 THz/1533.42 nm 6.25GHz spacing";
             }
             enum "195.51250" {
               description "195.51250 THz/1533.37 nm 6.25/12.5GHz spacing";
             }
             enum "195.51875" {
               description "195.51875 THz/1533.32 nm 6.25GHz spacing";
             }
             enum "195.52500" {
               description "195.52500 THz/1533.27 nm 6.25/12.5GHz spacing";
             }
             enum "195.53125" {
               description "195.53125 THz/1533.22 nm 6.25GHz spacing";
             }
             enum "195.53750" {
               description "195.53750 THz/1533.17 nm 6.25/12.5GHz spacing";
             }
             enum "195.54375" {
               description "195.54375 THz/1533.12 nm 6.25GHz spacing";
             }
             enum "195.55000" {
               description "195.55000 THz/1533.07 nm 6.25/12.5/50GHz spacing";
             }
             enum "195.55625" {
               description "195.55625 THz/1533.02 nm 6.25GHz spacing";
             }
             enum "195.56250" {
               description "195.56250 THz/1532.98 nm 6.25/12.5GHz spacing";
             }
             enum "195.56875" {
               description "195.56875 THz/1532.93 nm 6.25GHz spacing";
             }
             enum "195.57500" {
               description "195.57500 THz/1532.88 nm 6.25/12.5/75GHz spacing";
             }
             enum "195.58125" {
               description "195.58125 THz/1532.83 nm 6.25GHz spacing";
             }
             enum "195.58750" {
               description "195.58750 THz/1532.78 nm 6.25/12.5GHz spacing";
             }
             enum "195.59375" {
               description "195.59375 THz/1532.73 nm 6.25GHz spacing";
             }
             enum "195.60000" {
               description "195.60000 THz/1532.68 nm 6.25/12.5/50/100GHz spacing";
             }
             enum "195.60625" {
               description "195.60625 THz/1532.63 nm 6.25GHz spacing";
             }
             enum "195.61250" {
               description "195.61250 THz/1532.58 nm 6.25/12.5GHz spacing";
             }
             enum "195.61875" {
               description "195.61875 THz/1532.53 nm 6.25GHz spacing";
             }
             enum "195.62500" {
               description "195.62500 THz/1532.49 nm 6.25/12.5GHz spacing";
             }
             enum "195.63125" {
               description "195.63125 THz/1532.44 nm 6.25GHz spacing";
             }
             enum "195.63750" {
               description "195.63750 THz/1532.39 nm 6.25/12.5GHz spacing";
             }
             enum "195.64375" {
               description "195.64375 THz/1532.34 nm 6.25GHz spacing";
             }
             enum "195.65000" {
               description "195.65000 THz/1532.29 nm 6.25/12.5/50/75GHz spacing";
             }
             enum "195.65625" {
               description "195.65625 THz/1532.24 nm 6.25GHz spacing";
             }
             enum "195.66250" {
               description "195.66250 THz/1532.19 nm 6.25/12.5GHz spacing";
             }
             enum "195.66875" {
               description "195.66875 THz/1532.14 nm 6.25GHz spacing";
             }
             enum "195.67500" {
               description "195.67500 THz/1532.09 nm 6.25/12.5GHz spacing";
             }
             enum "195.68125" {
               description "195.68125 THz/1532.04 nm 6.25GHz spacing";
             }
             enum "195.68750" {
               description "195.68750 THz/1532.00 nm 6.25/12.5GHz spacing";
             }
             enum "195.69375" {
               description "195.69375 THz/1531.95 nm 6.25GHz spacing";
             }
             enum "195.70000" {
               description "195.70000 THz/1531.90 nm 6.25/12.5/50/100GHz spacing";
             }
             enum "195.70625" {
               description "195.70625 THz/1531.85 nm 6.25GHz spacing";
             }
             enum "195.71250" {
               description "195.71250 THz/1531.80 nm 6.25/12.5GHz spacing";
             }
             enum "195.71875" {
               description "195.71875 THz/1531.75 nm 6.25GHz spacing";
             }
             enum "195.72500" {
               description "195.72500 THz/1531.70 nm 6.25/12.5/75GHz spacing";
             }
             enum "195.73125" {
               description "195.73125 THz/1531.65 nm 6.25GHz spacing";
             }
             enum "195.73750" {
               description "195.73750 THz/1531.60 nm 6.25/12.5GHz spacing";
             }
             enum "195.74375" {
               description "195.74375 THz/1531.56 nm 6.25GHz spacing";
             }
             enum "195.75000" {
               description "195.75000 THz/1531.51 nm 6.25/12.5/50GHz spacing";
             }
             enum "195.75625" {
               description "195.75625 THz/1531.46 nm 6.25GHz spacing";
             }
             enum "195.76250" {
               description "195.76250 THz/1531.41 nm 6.25/12.5GHz spacing";
             }
             enum "195.76875" {
               description "195.76875 THz/1531.36 nm 6.25GHz spacing";
             }
             enum "195.77500" {
               description "195.77500 THz/1531.31 nm 6.25/12.5GHz spacing";
             }
             enum "195.78125" {
               description "195.78125 THz/1531.26 nm 6.25GHz spacing";
             }
             enum "195.78750" {
               description "195.78750 THz/1531.21 nm 6.25/12.5GHz spacing";
             }
             enum "195.79375" {
               description "195.79375 THz/1531.16 nm 6.25GHz spacing";
             }
             enum "195.80000" {
               description "195.80000 THz/1531.12 nm 6.25/12.5/50/75/100GHz spacing";
             }
             enum "195.80625" {
               description "195.80625 THz/1531.07 nm 6.25GHz spacing";
             }
             enum "195.81250" {
               description "195.81250 THz/1531.02 nm 6.25/12.5GHz spacing";
             }
             enum "195.81875" {
               description "195.81875 THz/1530.97 nm 6.25GHz spacing";
             }
             enum "195.82500" {
               description "195.82500 THz/1530.92 nm 6.25/12.5GHz spacing";
             }
             enum "195.83125" {
               description "195.83125 THz/1530.87 nm 6.25GHz spacing";
             }
             enum "195.83750" {
               description "195.83750 THz/1530.82 nm 6.25/12.5GHz spacing";
             }
             enum "195.84375" {
               description "195.84375 THz/1530.77 nm 6.25GHz spacing";
             }
             enum "195.85000" {
               description "195.85000 THz/1530.72 nm 6.25/12.5/50GHz spacing";
             }
             enum "195.85625" {
               description "195.85625 THz/1530.68 nm 6.25GHz spacing";
             }
             enum "195.86250" {
               description "195.86250 THz/1530.63 nm 6.25/12.5GHz spacing";
             }
             enum "195.86875" {
               description "195.86875 THz/1530.58 nm 6.25GHz spacing";
             }
             enum "195.87500" {
               description "195.87500 THz/1530.53 nm 6.25/12.5/75GHz spacing";
             }
             enum "195.88125" {
               description "195.88125 THz/1530.48 nm 6.25GHz spacing";
             }
             enum "195.88750" {
               description "195.88750 THz/1530.43 nm 6.25/12.5GHz spacing";
             }
             enum "195.89375" {
               description "195.89375 THz/1530.38 nm 6.25GHz spacing";
             }
             enum "195.90000" {
               description "195.90000 THz/1530.33 nm 6.25/12.5/50/100GHz spacing";
             }
             enum "195.90625" {
               description "195.90625 THz/1530.29 nm 6.25GHz spacing";
             }
             enum "195.91250" {
               description "195.91250 THz/1530.24 nm 6.25/12.5GHz spacing";
             }
             enum "195.91875" {
               description "195.91875 THz/1530.19 nm 6.25GHz spacing";
             }
             enum "195.92500" {
               description "195.92500 THz/1530.14 nm 6.25/12.5GHz spacing";
             }
             enum "195.93125" {
               description "195.93125 THz/1530.09 nm 6.25GHz spacing";
             }
             enum "195.93750" {
               description "195.93750 THz/1530.04 nm 6.25/12.5GHz spacing";
             }
             enum "195.94375" {
               description "195.94375 THz/1529.99 nm 6.25GHz spacing";
             }
             enum "195.95000" {
               description "195.95000 THz/1529.94 nm 6.25/12.5/50/75GHz spacing";
             }
             enum "195.95625" {
               description "195.95625 THz/1529.89 nm 6.25GHz spacing";
             }
             enum "195.96250" {
               description "195.96250 THz/1529.85 nm 6.25/12.5GHz spacing";
             }
             enum "195.96875" {
               description "195.96875 THz/1529.80 nm 6.25GHz spacing";
             }
             enum "195.97500" {
               description "195.97500 THz/1529.75 nm 6.25/12.5GHz spacing";
             }
             enum "195.98125" {
               description "195.98125 THz/1529.70 nm 6.25GHz spacing";
             }
             enum "195.98750" {
               description "195.98750 THz/1529.65 nm 6.25/12.5GHz spacing";
             }
             enum "195.99375" {
               description "195.99375 THz/1529.60 nm 6.25GHz spacing";
             }
             enum "196.00000" {
               description "196.00000 THz/1529.55 nm 6.25/12.5/50/100GHz spacing";
             }
             enum "196.00625" {
               description "196.00625 THz/1529.50 nm 6.25GHz spacing";
             }
             enum "196.01250" {
               description "196.01250 THz/1529.46 nm 6.25/12.5GHz spacing";
             }
             enum "196.01875" {
               description "196.01875 THz/1529.41 nm 6.25GHz spacing";
             }
             enum "196.02500" {
               description "196.02500 THz/1529.36 nm 6.25/12.5/75GHz spacing";
             }
             enum "196.03125" {
               description "196.03125 THz/1529.31 nm 6.25GHz spacing";
             }
             enum "196.03750" {
               description "196.03750 THz/1529.26 nm 6.25/12.5GHz spacing";
             }
             enum "196.04375" {
               description "196.04375 THz/1529.21 nm 6.25GHz spacing";
             }
             enum "196.05000" {
               description "196.05000 THz/1529.16 nm 6.25/12.5/50GHz spacing";
             }
             enum "196.05625" {
               description "196.05625 THz/1529.11 nm 6.25GHz spacing";
             }
             enum "196.06250" {
               description "196.06250 THz/1529.07 nm 6.25/12.5GHz spacing";
             }
             enum "196.06875" {
               description "196.06875 THz/1529.02 nm 6.25GHz spacing";
             }
             enum "196.07500" {
               description "196.07500 THz/1528.97 nm 6.25/12.5GHz spacing";
             }
             enum "196.08125" {
               description "196.08125 THz/1528.92 nm 6.25GHz spacing";
             }
             enum "196.08750" {
               description "196.08750 THz/1528.87 nm 6.25/12.5GHz spacing";
             }
             enum "196.09375" {
               description "196.09375 THz/1528.82 nm 6.25GHz spacing";
             }
             enum "196.10000" {
               description "196.10000 THz/1528.77 nm 6.25/12.5/50/75/100GHz spacing";
             }
             enum "196.15040" {
               description "196.15040 THz/1528.38 nm 50Ghz spacing";
             }
           }
         }
       }
     }
     leaf tx-power {
       description "Transmit laser output power";
       units "dBm";
       type string {
       }
     }
     choice laser-enable-choice {
       leaf laser-enable {
         description "Enable transmit laser";
         type empty;
       }
       leaf no-laser-enable {
         description "Don't enable transmit laser";
         type empty;
       }
     }
   }
   grouping odu-attributes {
     description "Optical Data Unit configuration attributes";
     uses apply-advanced;
     leaf rate {
       description "Specific type of ODU, according to data rate";
       type enumeration {
         enum "odu4" {
           description "ODU4 for 100 Gbps";
         }
       }
     }
     choice is-ma-choice {
       leaf is-ma {
         description "Link is enabled for maintenance tasks, alarms are masked";
         type empty;
       }
       leaf no-is-ma {
         description "Don't link is enabled for maintenance tasks, alarms are masked";
         type empty;
       }
     }
     container tti {
       description "Configuration of OTU trail trace identifier";
       presence "enable tti";
       uses otn-tti-attributes;
     }
     container degrade {
       description "Configuration of OTU degrade defect detection";
       presence "enable degrade";
       uses otn-degrade;
     }
     leaf exp-payload-type {
       description "Expected OPU payload type";
       type union {
         type uint8;
         type string {
           pattern "<.*>|$.*";
         }
       }
     }
     container prbs {
       description "Configuration of framed pseudorandom binary sequence test signal";
       presence "enable prbs";
       uses prbs-config;
     }
   }
   grouping otn-degrade {
     description "Configuration of degrade defect detection";
     uses apply-advanced;
     leaf degm {
       description "Number of consecutive intervals error rate above threshold";
       type union {
         type string {
           pattern "<.*>|$.*";
         }
         type uint16 {
           range "2 .. 10";
         }
       }
     }
     leaf degthr {
       description "Threshold - percentage errored blocks, ex. 1.23 = 1.23%";
       type string {
       }
     }
   }
   grouping otn-tti-attributes {
     description "Configuration of OTN trail trace identifier";
     uses apply-advanced;
     leaf sapi {
       description "Transmitted source access point identifier field";
       type string {
         length "0 .. 15";
       }
     }
     leaf dapi {
       description "Transmitted destination access point identifier field";
       type string {
         length "0 .. 15";
       }
     }
     leaf operator {
       description "Transmitted operator field";
       type string {
         length "0 .. 32";
       }
     }
     leaf exp-sapi {
       description "Expected received source access point identifier field";
       type string {
         length "0 .. 15";
       }
     }
     leaf exp-dapi {
       description "Expected received destination access point identifier field";
       type string {
         length "0 .. 15";
       }
     }
     leaf tim-detect-mode {
       description "Trace input mismatch defect detection mode";
       type enumeration {
         enum "disabled" {
           description "Detection of trace input mismatch defect disabled";
         }
         enum "sapi-only" {
           description "Detection of trace input mismatch defect on SAPI field only";
         }
         enum "dapi-only" {
           description "Detection of trace input mismatch defect on DAPI field only";
         }
         enum "sapi-and-dapi" {
           description "Detection of trace input mismatch defect on both SAPI and DAPI fields";
         }
       }
     }
     choice tim-act-enable-choice {
       leaf tim-act-enable {
         description "Enable trace input mismatch consequential actions";
         type empty;
       }
       leaf no-tim-act-enable {
         description "Don't enable trace input mismatch consequential actions";
         type empty;
       }
     }
   }
   grouping otn_options_type {
     uses apply-advanced;
     choice laser-enable-choice {
       leaf laser-enable {
         description "Enable Laser";
         type empty;
       }
       leaf no-laser-enable {
         description "Don't enable Laser";
         type empty;
       }
     }
     choice is-ma-choice {
       leaf is-ma {
         description "Link is enabled with alarms masked";
         type empty;
       }
       leaf no-is-ma {
         description "Don't link is enabled with alarms masked";
         type empty;
       }
     }
     choice line-loopback-choice {
       leaf line-loopback {
         description "Enable line loopback";
         type empty;
       }
       leaf no-line-loopback {
         description "Don't enable line loopback";
         type empty;
       }
     }
     choice local-loopback-choice {
       leaf local-loopback {
         description "Enable local host loopback";
         type empty;
       }
       leaf no-local-loopback {
         description "Don't enable local host loopback";
         type empty;
       }
     }
     choice prbs-choice {
       leaf prbs {
         description "Enable otn payload prbs";
         type empty;
       }
       leaf no-prbs {
         description "Don't enable otn payload prbs";
         type empty;
       }
     }
     choice odu-ttim-action-enable-choice {
       leaf odu-ttim-action-enable {
         description "Enable consequent action for ODU TTIM";
         type empty;
       }
       leaf no-odu-ttim-action-enable {
         description "Don't enable consequent action for ODU TTIM";
         type empty;
       }
     }
     choice otu-ttim-action-enable-choice {
       leaf otu-ttim-action-enable {
         description "Enable consequent action for OTU TTIM";
         type empty;
       }
       leaf no-otu-ttim-action-enable {
         description "Don't enable consequent action for OTU TTIM";
         type empty;
       }
     }
     choice transport-monitoring-choice {
       leaf transport-monitoring {
         description "Enable transport monitoring";
         type empty;
       }
       leaf no-transport-monitoring {
         description "Don't enable transport monitoring";
         type empty;
       }
     }
     container odu-delay-management {
       description "Set odu delay management";
       uses apply-advanced;
       choice monitor-end-point-choice {
         leaf monitor-end-point {
           description "Originate connection monitor end point";
           type empty;
         }
         leaf no-monitor-end-point {
           description "Don't originate connection monitor end point";
           type empty;
         }
       }
       choice start-measurement-choice {
         leaf start-measurement {
           description "Enable to start a dm measurement";
           type empty;
         }
         leaf no-start-measurement {
           description "Don't enable to start a dm measurement";
           type empty;
         }
       }
       choice bypass-choice {
         leaf bypass {
           description "Act as tandem passing dm value through node";
           type empty;
         }
         leaf no-bypass {
           description "Don't act as tandem passing dm value through node";
           type empty;
         }
       }
       leaf number-of-frames {
         description "Number of consequent frames to declare dm done";
         type union {
           type string {
             pattern "<.*>|$.*";
           }
           type uint32 {
             range "0 .. 255";
           }
         }
       }
       choice remote-loop-enable-choice {
         leaf remote-loop-enable {
           description "Enable remote DM loop on remote end";
           type empty;
         }
         leaf no-remote-loop-enable {
           description "Don't enable remote DM loop on remote end";
           type empty;
         }
       }
     }
     container signal-degrade {
       description "Signal degrade thresholds";
       uses apply-advanced;
       leaf interval {
         description "Time interval";
         default "10";
         units "milliseconds";
         type union {
           type string {
             pattern "<.*>|$.*";
           }
           type uint32 {
             range "1 .. 1000";
           }
         }
       }
       leaf ber-threshold-clear {
         description "Ber threshold for signal degrade clear (format: xe-n, example: 4.5e-3)";
         type string {
         }
       }
       leaf ber-threshold-signal-degrade {
         description "Ber threshold for signal-degrade (format: xe-n, example: 4.5e-3)";
         type string {
         }
       }
       leaf q-threshold-signal-degrade-clear {
         description "Q threshold for signal-degrade clear (e.g. 14.26)";
         units "dB";
         type string;
       }
       leaf q-threshold-signal-degrade {
         description "Q threshold for signal-degrade (e.g. 9.26)";
         units "dB";
         type string;
       }
     }
     container odu-signal-degrade {
       description "Signal degrade thresholds for ODU";
       uses apply-advanced;
       leaf interval {
         description "Time interval";
         default "10";
         units "milliseconds";
         type union {
           type string {
             pattern "<.*>|$.*";
           }
           type uint32 {
             range "1 .. 1000";
           }
         }
       }
       leaf ber-threshold-clear {
         description "Ber th for sd clear (format: xe-n, example: 4.5e-3)";
         default "1.0e-9";
         type string {
         }
       }
       leaf ber-threshold-signal-degrade {
         description "Ber th for sd (format: xe-n, example: 4.5e-3)";
         default "1.0e-6";
         type string {
         }
       }
     }
     container preemptive-fast-reroute {
       description "Preemptive fast reroute";
       uses apply-advanced;
       choice odu-signal-degrade-monitor-enable-choice {
         leaf odu-signal-degrade-monitor-enable {
           description "Enable ODU signal degrade monitoring";
           type empty;
         }
         leaf no-odu-signal-degrade-monitor-enable {
           description "Don't enable ODU signal degrade monitoring";
           type empty;
         }
       }
       choice odu-backward-frr-enable-choice {
         leaf odu-backward-frr-enable {
           description "Enable ODU backward frr insertion";
           type empty;
         }
         leaf no-odu-backward-frr-enable {
           description "Don't enable ODU backward frr insertion";
           type empty;
         }
       }
       choice signal-degrade-monitor-enable-choice {
         leaf signal-degrade-monitor-enable {
           description "Enable signal degrade monitoring";
           type empty;
         }
         leaf no-signal-degrade-monitor-enable {
           description "Don't enable signal degrade monitoring";
           type empty;
         }
       }
       choice backward-frr-enable-choice {
         leaf backward-frr-enable {
           description "Enable backward frr insertion";
           type empty;
         }
         leaf no-backward-frr-enable {
           description "Don't enable backward frr insertion";
           type empty;
         }
       }
     }
     leaf fec {
       description "Forward Error Correction mode";
       type enumeration {
         enum "none" {
           description "GFEC all 0's";
         }
         enum "gfec" {
           description "GFEC-Generic Forward Error Correction";
         }
         enum "efec" {
           description "EFEC-Enhanced Forward Error Correction";
         }
         enum "gfec-sdfec" {
           description "Both gfec and sdfec";
         }
         enum "ufec" {
           description "UFEC-Ultra Forward Error Correction";
         }
         enum "sdfec" {
           description "SDFEC-Soft Decision Forward Error Correction";
         }
         enum "hgfec" {
           description "HGFEC-High Gain Forward Error Correction";
         }
         enum "sdfec15" {
           description "SDFEC with 15 percent overhead - non-differential";
         }
       }
     }
     choice insert-odu-oci-choice {
       leaf insert-odu-oci {
         description "Force odu open connection indication";
         type empty;
       }
       leaf no-insert-odu-oci {
         description "Don't force odu open connection indication";
         type empty;
       }
     }
     choice insert-odu-lck-choice {
       leaf insert-odu-lck {
         description "Force odu locked maintenance signal";
         type empty;
       }
       leaf no-insert-odu-lck {
         description "Don't force odu locked maintenance signal";
         type empty;
       }
     }
     leaf rate {
       description "Optical Transmission Network mode";
       type enumeration {
         enum "pass-thru" {
           description "Pass through mode - No OTN framing";
         }
         enum "fixed-stuff-bytes" {
           description "Fixed Stuff Bytes 11.0957Gbps";
         }
         enum "no-fixed-stuff-bytes" {
           description "No Fixed Stuff Bytes 11.0491Gbps";
         }
         enum "oc192" {
           description "OTU2 for OC192 10.7Gbps";
         }
         enum "otu3" {
           description "OTU3 for 40Gbps";
         }
         enum "otu4" {
           description "OTU4/OTU4v for 100Gbps-127Gbps";
         }
       }
     }
     container bytes {
       description "Set OTN header bytes";
       uses apply-advanced;
       leaf transmit-payload-type {
         description "Transmit payload type";
         type union {
           type string {
             pattern "<.*>|$.*";
           }
           type uint32 {
             range "0 .. 255";
           }
         }
       }
     }
     container tti {
       description "Trace Identifier";
       uses apply-advanced;
       leaf otu-dapi {
         description "OTU Destination Access Point Identifier";
         type string;
       }
       leaf otu-sapi {
         description "OTU Source Access Point Identifier";
         type string;
       }
       leaf otu-expected-receive-dapi {
         description "OTU Expected Receive Destination Access Point Identifier";
         type string;
       }
       leaf otu-expected-receive-sapi {
         description "OTU Expected Receive Source Access Point Identifier";
         type string;
       }
       leaf odu-dapi {
         description "ODU Destination Access Point Identifier";
         type string;
       }
       leaf odu-sapi {
         description "ODU Source Access Point Identifier";
         type string;
       }
       leaf odu-expected-receive-dapi {
         description "ODU Expected Receive Destination Access Point Identifier";
         type string;
       }
       leaf odu-expected-receive-sapi {
         description "ODU Expected Receive Source Access Point Identifier";
         type string;
       }
       choice otu-dapi-first-byte-nul-choice {
         leaf otu-dapi-first-byte-nul {
           description "Insert all-0s to first byte";
           type empty;
         }
         leaf no-otu-dapi-first-byte-nul {
           description "Don't insert all-0s to first byte";
           type empty;
         }
       }
       choice otu-sapi-first-byte-nul-choice {
         leaf otu-sapi-first-byte-nul {
           description "Insert all-0s to first byte";
           type empty;
         }
         leaf no-otu-sapi-first-byte-nul {
           description "Don't insert all-0s to first byte";
           type empty;
         }
       }
       choice otu-expected-receive-dapi-first-byte-nul-choice {
         leaf otu-expected-receive-dapi-first-byte-nul {
           description "Insert all-0s to first byte";
           type empty;
         }
         leaf no-otu-expected-receive-dapi-first-byte-nul {
           description "Don't insert all-0s to first byte";
           type empty;
         }
       }
       choice otu-expected-receive-sapi-first-byte-nul-choice {
         leaf otu-expected-receive-sapi-first-byte-nul {
           description "Insert all-0s to first byte";
           type empty;
         }
         leaf no-otu-expected-receive-sapi-first-byte-nul {
           description "Don't insert all-0s to first byte";
           type empty;
         }
       }
       choice odu-dapi-first-byte-nul-choice {
         leaf odu-dapi-first-byte-nul {
           description "Insert all-0s to first byte";
           type empty;
         }
         leaf no-odu-dapi-first-byte-nul {
           description "Don't insert all-0s to first byte";
           type empty;
         }
       }
       choice odu-sapi-first-byte-nul-choice {
         leaf odu-sapi-first-byte-nul {
           description "Insert all-0s to first byte";
           type empty;
         }
         leaf no-odu-sapi-first-byte-nul {
           description "Don't insert all-0s to first byte";
           type empty;
         }
       }
       choice odu-expected-receive-dapi-first-byte-nul-choice {
         leaf odu-expected-receive-dapi-first-byte-nul {
           description "Insert all-0s to first byte";
           type empty;
         }
         leaf no-odu-expected-receive-dapi-first-byte-nul {
           description "Don't insert all-0s to first byte";
           type empty;
         }
       }
       choice odu-expected-receive-sapi-first-byte-nul-choice {
         leaf odu-expected-receive-sapi-first-byte-nul {
           description "Insert all-0s to first byte";
           type empty;
         }
         leaf no-odu-expected-receive-sapi-first-byte-nul {
           description "Don't insert all-0s to first byte";
           type empty;
         }
       }
     }
     container trigger {
       description "Defect triggers";
       uses apply-advanced;
       container oc-los {
         description "OC Loss Of Signal defect trigger";
         choice oc_los_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-lof {
         description "OC Loss Of Frame defect trigger";
         choice oc_lof_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-lom {
         description "OC Loss Of Multiframe defect trigger";
         choice oc_lom_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-wavelength-lock {
         description "OC Wavelength Lock defect trigger";
         choice oc_wavelength_lock_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-tsf {
         description "Oc tsf defect trigger";
         choice oc-tsf-choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-ais {
         description "OTU Alarm Indication Signal defect trigger";
         choice otu_ais_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-bdi {
         description "OTU Backward Defect Indication defect trigger";
         choice otu_bdi_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-iae {
         description "OTU Incoming Alignment defect trigger";
         choice otu_iae_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-ttim {
         description "OTU Trail Trace Identifier Mismatch defect trigger";
         choice otu_ttim_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-sd {
         description "OTU Signal Degrade defect trigger";
         choice otu_sd_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-fec-deg {
         description "OTU FEC Degrade defect trigger";
         choice otu_fec_deg_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-fec-exe {
         description "OTU FEC Excessive Error defect trigger";
         choice otu_fec_exe_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-ais {
         description "ODU Alarm Indication Signal defect trigger";
         choice odu_ais_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-bdi {
         description "ODU Backward Defect Indication defect trigger";
         choice odu_bdi_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-iae {
         description "Odu iae defect trigger";
         choice odu-iae-choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-bei {
         description "Odu backward error indication defect trigger";
         choice odu_bei_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-oci {
         description "ODU Open Connection Indication defect trigger";
         choice odu_oci_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-lck {
         description "ODU Locked defect trigger";
         choice odu_lck_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-ttim {
         description "ODU Trail Trace Identifier Mismatch defect trigger";
         choice odu_ttim_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-sd {
         description "ODU Signal Degrade defect trigger";
         choice odu_sd_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container opu-ptim {
         description "Payload Type Mismatch defect trigger";
         choice opu_ptm_choices {
           case case_1 {
             leaf ignore {
               description "Ignore the defect";
               type empty;
             }
           }
           case case_2 {
             container hold-time {
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
     }
     container tca {
       description "TCA - threshold crossing alerts";
       uses apply-advanced;
       container otu-tca-es {
         description "OTU Errored Seconds Threshold crossing defect trigger";
         choice enable-tca-choice {
           leaf enable-tca {
             description "Enable the OTU errored seconds threshold crossing alert";
             type empty;
           }
           leaf no-enable-tca {
             description "Don't enable the OTU errored seconds threshold crossing alert";
             type empty;
           }
         }
         leaf threshold {
           description "TCA threshold for OTU errored seconds in 15 minutes";
           default "135";
           type union {
             type string {
               pattern "<.*>|$.*";
             }
             type uint32 {
               range "1 .. 900";
             }
           }
         }
         leaf threshold-24hrs {
           description "TCA threshold for OTU errored seconds in 24 hours";
           default "162";
           type union {
             type string {
               pattern "<.*>|$.*";
             }
             type uint32 {
               range "1 .. 86400";
             }
           }
         }
       }
       container otu-tca-ses {
         description "OTU Severely Errored Seconds Threshold crossing defect trigger";
         choice enable-tca-choice {
           leaf enable-tca {
             description "Enable the OTU severely errored seconds threshold crossing alert";
             type empty;
           }
           leaf no-enable-tca {
             description "Don't enable the OTU severely errored seconds threshold crossing alert";
             type empty;
           }
         }
         leaf threshold {
           description "TCA threshold for OTU severely errored seconds in 15 minutes";
           default "90";
           type union {
             type string {
               pattern "<.*>|$.*";
             }
             type uint32 {
               range "1 .. 900";
             }
           }
         }
         leaf threshold-24hrs {
           description "TCA threshold for OTU severely errored seconds in 24 hours";
           default "108";
           type union {
             type string {
               pattern "<.*>|$.*";
             }
             type uint32 {
               range "1 .. 86400";
             }
           }
         }
       }
       container otu-tca-uas {
         description "OTU Unavailable Seconds Threshold crossing defect trigger";
         choice enable-tca-choice {
           leaf enable-tca {
             description "Enable the OTU unavailable seconds threshold crossing alert";
             type empty;
           }
           leaf no-enable-tca {
             description "Don't enable the OTU unavailable seconds threshold crossing alert";
             type empty;
           }
         }
         leaf threshold {
           description "TCA threshold for OTU unavailable seconds in 15 minutes";
           default "90";
           type union {
             type string {
               pattern "<.*>|$.*";
             }
             type uint32 {
               range "10 .. 900";
             }
           }
         }
         leaf threshold-24hrs {
           description "TCA threshold for OTU unavailable seconds in 24 hours";
           default "108";
           type union {
             type string {
               pattern "<.*>|$.*";
             }
             type uint32 {
               range "10 .. 86400";
             }
           }
         }
       }
       container otu-tca-bbe {
         description "OTU Background Block Error Threshold crossing defect trigger";
         choice enable-tca-choice {
           leaf enable-tca {
             description "Enable the OTU BBE threshold crossing alert";
             type empty;
           }
           leaf no-enable-tca {
             description "Don't enable the OTU BBE threshold crossing alert";
             type empty;
           }
         }
         leaf threshold {
           description "TCA threshold for OTU BBE in 15 minutes";
           default "800";
           type union {
             type string {
               pattern "<.*>|$.*";
             }
             type uint32 {
               range "1 .. 771000000";
             }
           }
         }
         leaf threshold-24hrs {
           description "TCA threshold for OTU BBE in 24 hours";
           default "960";
           type union {
             type string {
               pattern "<.*>|$.*";
             }
             type uint32 {
               range "1 .. 771000000";
             }
           }
         }
       }
       container otu-tca-es-fe {
         description "OTU far-end Errored Seconds Threshold crossing defect trigger";
         choice enable-tca-choice {
           leaf enable-tca {
             description "Enable the OTU far-end errored seconds threshold crossing alert";
             type empty;
           }
           leaf no-enable-tca {
             description "Don't enable the OTU far-end errored seconds threshold crossing alert";
             type empty;
           }
         }
         leaf threshold {
           description "TCA threshold for OTU far-end errored seconds in 15 minutes";
           default "135";
           type union {
             type string {
               pattern "<.*>|$.*";
             }
             type uint32 {
               range "1 .. 900";
             }
           }
         }
         leaf threshold-24hrs {
           description "TCA threshold for OTU far-end errored seconds in 24 hours";
           default "162";
           type union {
             type string {
               pattern "<.*>|$.*";
             }
             type uint32 {
               range "1 .. 86400";
             }
           }
         }
       }
       container otu-tca-ses-fe {
         description "OTU far-end Severely Errored Seconds Threshold crossing defect trigger";
         choice enable-tca-choice {
           leaf enable-tca {
             description "Enable the OTU far-end Unavailable Seconds threshold crossing alert";
             type empty;
           }
           leaf no-enable-tca {
             description "Don't enable the OTU far-end Unavailable Seconds threshold crossing alert";
             type empty;
           }
         }
         leaf threshold {
           description "TCA threshold for OTU far-end severely errored seconds in 15 minutes";
           default "90";
           type union {
             type string {
               pattern "<.*>|$.*";
             }
             type uint32 {
               range "1 .. 900";
             }
           }
         }
         leaf threshold-24hrs {
           description "TCA threshold for OTU far-end severely errored seconds in 24 hours";
           default "108";
           type union {
             type string {
               pattern "<.*>|$.*";
             }
             type uint32 {
               range "1 .. 86400";
             }
           }
         }
       }
       container otu-tca-uas-fe {
         description "OTU far-end Unavailable Seconds Threshold crossing defect trigger";
         choice enable-tca-choice {
           leaf enable-tca {
             description "Enable the OTU far end unavailabe second threshold crossing alert";
             type empty;
           }
           leaf no-enable-tca {
             description "Don't enable the OTU far end unavailabe second threshold crossing alert";
             type empty;
           }
         }
         leaf threshold {
           description "TCA threshold for OTU far-end unavailable seconds in 15 minutes";
           default "90";
           type union {
             type string {
               pattern "<.*>|$.*";
             }
             type uint32 {
               range "10 .. 900";
             }
           }
         }
         leaf threshold-24hrs {
           description "TCA threshold for OTU far-end unavailable seconds in 24 hours";
           default "108";
           type union {
             type string {
               pattern "<.*>|$.*";
             }
             type uint32 {
               range "10 .. 86400";
             }
           }
         }
       }
       container otu-tca-bbe-fe {
         description "OTU far-end Background Block Error (BEI) Threshold crossing defect trigger";
         choice enable-tca-choice {
           leaf enable-tca {
             description "Enable the OTU BBE (BEI) threshold crossing alert";
             type empty;
           }
           leaf no-enable-tca {
             description "Don't enable the OTU BBE (BEI) threshold crossing alert";
             type empty;
           }
         }
         leaf threshold {
           description "TCA threshold for OTU far-end BBE (BEI) in 15 minutes";
           default "800";
           type union {
             type string {
               pattern "<.*>|$.*";
             }
             type uint32 {
               range "1 .. 771000000";
             }
           }
         }
         leaf threshold-24hrs {
           description "TCA threshold for OTU far-end BBE (BEI) in 24 hours";
           default "960";
           type union {
             type string {
               pattern "<.*>|$.*";
             }
             type uint32 {
               range "1 .. 771000000";
             }
           }
         }
       }
       container odu-tca-es {
         description "ODU Errored Seconds Threshold crossing defect trigger";
         choice enable-tca-choice {
           leaf enable-tca {
             description "Enable the ODU errored seconds threshold crossing alert";
             type empty;
           }
           leaf no-enable-tca {
             description "Don't enable the ODU errored seconds threshold crossing alert";
             type empty;
           }
         }
         leaf threshold {
           description "TCA threshold for ODU errored seconds in 15 minutes";
           default "135";
           type union {
             type string {
               pattern "<.*>|$.*";
             }
             type uint32 {
               range "1 .. 900";
             }
           }
         }
         leaf threshold-24hrs {
           description "TCA threshold for ODU errored seconds in 24 hours";
           default "162";
           type union {
             type string {
               pattern "<.*>|$.*";
             }
             type uint32 {
               range "1 .. 86400";
             }
           }
         }
       }
       container odu-tca-ses {
         description "ODU Severely Errored Seconds Threshold crossing defect trigger";
         choice enable-tca-choice {
           leaf enable-tca {
             description "Enable the ODU severely errored seconds threshold crossing alert";
             type empty;
           }
           leaf no-enable-tca {
             description "Don't enable the ODU severely errored seconds threshold crossing alert";
             type empty;
           }
         }
         leaf threshold {
           description "TCA threshold for ODU severely errored seconds in 15 minutes";
           default "90";
           type union {
             type string {
               pattern "<.*>|$.*";
             }
             type uint32 {
               range "1 .. 900";
             }
           }
         }
         leaf threshold-24hrs {
           description "TCA threshold for ODU severely-errored seconds in 24 hours";
           default "108";
           type union {
             type string {
               pattern "<.*>|$.*";
             }
             type uint32 {
               range "1 .. 86400";
             }
           }
         }
       }
       container odu-tca-uas {
         description "ODU Unavailable Seconds Threshold crossing defect trigger";
         choice enable-tca-choice {
           leaf enable-tca {
             description "Enable the ODU unavailable seconds threshold crossing alert";
             type empty;
           }
           leaf no-enable-tca {
             description "Don't enable the ODU unavailable seconds threshold crossing alert";
             type empty;
           }
         }
         leaf threshold {
           description "TCA threshold for ODU unavailable seconds in 15 minutes";
           default "90";
           type union {
             type string {
               pattern "<.*>|$.*";
             }
             type uint32 {
               range "10 .. 900";
             }
           }
         }
         leaf threshold-24hrs {
           description "TCA threshold for ODU unavailable seconds in 24 hours";
           default "108";
           type union {
             type string {
               pattern "<.*>|$.*";
             }
             type uint32 {
               range "10 .. 86400";
             }
           }
         }
       }
       container odu-tca-bbe {
         description "ODU Background Block Error Threshold crossing defect trigger";
         choice enable-tca-choice {
           leaf enable-tca {
             description "Enable the ODU BBE threshold crossing alert";
             type empty;
           }
           leaf no-enable-tca {
             description "Don't enable the ODU BBE threshold crossing alert";
             type empty;
           }
         }
         leaf threshold {
           description "TCA threshold for ODU BBE in 15 minutes";
           default "800";
           type union {
             type string {
               pattern "<.*>|$.*";
             }
             type uint32 {
               range "1 .. 771000000";
             }
           }
         }
         leaf threshold-24hrs {
           description "TCA threshold for ODU backgrand block error in 24 hours";
           default "960";
           type union {
             type string {
               pattern "<.*>|$.*";
             }
             type uint32 {
               range "1 .. 771000000";
             }
           }
         }
       }
       container odu-tca-es-fe {
         description "ODU far-end Errored Seconds Threshold crossing defect trigger";
         choice enable-tca-choice {
           leaf enable-tca {
             description "Enable the ODU far-end errored seconds threshold crossing alert";
             type empty;
           }
           leaf no-enable-tca {
             description "Don't enable the ODU far-end errored seconds threshold crossing alert";
             type empty;
           }
         }
         leaf threshold {
           description "TCA threshold for ODU far-end errored seconds in 15 minutes";
           default "135";
           type union {
             type string {
               pattern "<.*>|$.*";
             }
             type uint32 {
               range "1 .. 900";
             }
           }
         }
         leaf threshold-24hrs {
           description "TCA threshold for ODU far-end errored seconds in 24 hours";
           default "162";
           type union {
             type string {
               pattern "<.*>|$.*";
             }
             type uint32 {
               range "1 .. 86400";
             }
           }
         }
       }
       container odu-tca-ses-fe {
         description "ODU far-end Severely Errored Seconds Threshold crossing defect trigger";
         choice enable-tca-choice {
           leaf enable-tca {
             description "Enable the ODU far-end Unavailable Seconds threshold crossing alert";
             type empty;
           }
           leaf no-enable-tca {
             description "Don't enable the ODU far-end Unavailable Seconds threshold crossing alert";
             type empty;
           }
         }
         leaf threshold {
           description "TCA threshold for ODU far-end severely errored seconds in 15 minutes";
           default "90";
           type union {
             type string {
               pattern "<.*>|$.*";
             }
             type uint32 {
               range "1 .. 900";
             }
           }
         }
         leaf threshold-24hrs {
           description "TCA threshold for ODU severely-errored seconds in 24 hours";
           default "108";
           type union {
             type string {
               pattern "<.*>|$.*";
             }
             type uint32 {
               range "1 .. 86400";
             }
           }
         }
       }
       container odu-tca-uas-fe {
         description "ODU far-end Unavailable Seconds Threshold crossing defect trigger";
         choice enable-tca-choice {
           leaf enable-tca {
             description "Enable the ODU far end unavailabe second threshold crossing alert";
             type empty;
           }
           leaf no-enable-tca {
             description "Don't enable the ODU far end unavailabe second threshold crossing alert";
             type empty;
           }
         }
         leaf threshold {
           description "TCA threshold for ODU far-end unavailable seconds in 15 minutes";
           default "90";
           type union {
             type string {
               pattern "<.*>|$.*";
             }
             type uint32 {
               range "10 .. 900";
             }
           }
         }
         leaf threshold-24hrs {
           description "TCA threshold for ODU far-end unavailable seconds in 24 hours";
           default "108";
           type union {
             type string {
               pattern "<.*>|$.*";
             }
             type uint32 {
               range "10 .. 86400";
             }
           }
         }
       }
       container odu-tca-bbe-fe {
         description "ODU far-end Background Block Error (BEI) Threshold crossing defect trigger";
         choice enable-tca-choice {
           leaf enable-tca {
             description "Enable the ODU BBE (BEI) threshold crossing alert";
             type empty;
           }
           leaf no-enable-tca {
             description "Don't enable the ODU BBE (BEI) threshold crossing alert";
             type empty;
           }
         }
         leaf threshold {
           description "TCA threshold for ODU far-end BBE (BEI) in 15 minutes";
           default "800";
           type union {
             type string {
               pattern "<.*>|$.*";
             }
             type uint32 {
               range "1 .. 771000000";
             }
           }
         }
         leaf threshold-24hrs {
           description "TCA threshold for ODU far-end backgrand block error in 24 hours";
           default "960";
           type union {
             type string {
               pattern "<.*>|$.*";
             }
             type uint32 {
               range "1 .. 771000000";
             }
           }
         }
       }
       container otu-tca-fec-ber {
         description "OTU Errored Seconds Threshold crossing defect trigger";
         choice enable-tca-choice {
           leaf enable-tca {
             description "Enable the OTU errored seconds threshold crossing alert";
             type empty;
           }
           leaf no-enable-tca {
             description "Don't enable the OTU errored seconds threshold crossing alert";
             type empty;
           }
         }
         leaf threshold {
           description "TCA threshold for BER value in format: xe-n, x is an integer or decimal number, n = 0..9";
           default "10e-3";
           type string {
           }
         }
         leaf threshold-24hrs {
           description "TCA threshold for BER value in format: xe-n, x is an integer or decimal number, n = 0..9";
           default "10e-3";
           type string {
           }
         }
       }
     }
   }
   grouping otu-attributes {
     description "Optical transmission unit configuration attributes";
     uses apply-advanced;
     leaf rate {
       description "Specific type of OTU, according to data rate";
       type enumeration {
         enum "otu4" {
           description "OTU4 for 100 Gbps";
         }
       }
     }
     choice is-ma-choice {
       leaf is-ma {
         description "Link is enabled for maintenance tasks, alarms are masked";
         type empty;
       }
       leaf no-is-ma {
         description "Don't link is enabled for maintenance tasks, alarms are masked";
         type empty;
       }
     }
     leaf fec {
       description "Forward error correction type";
       type enumeration {
         enum "none" {
           description "No forward error correction applied";
         }
         enum "gfec" {
           description "ITU-T G.709 standard forward error correction";
         }
         enum "hgfec" {
           description "High gain FEC";
         }
       }
     }
     leaf loopback {
       description "Enabled loopback mode";
       type enumeration {
         enum "none" {
           description "No loopback mode active";
         }
         enum "local" {
           description "Local loopback (host side)";
         }
         enum "line" {
           description "Line loopback (network side)";
         }
       }
     }
     container tti {
       description "Configuration of OTU trail trace identifier";
       presence "enable tti";
       uses otn-tti-attributes;
     }
     container degrade {
       description "Configuration of OTU degrade defect detection";
       presence "enable degrade";
       uses otn-degrade;
     }
   }
   grouping p2mp_ldp_lsp_nh_obj {
     uses apply-advanced;
     list root-address {
       key name;
       description "Configure the root address of P2MP LSP";
       leaf name {
         description "Root address of the P2MP LSP";
         type jt:ipaddr;
       }
       uses apply-advanced;
       leaf lsp-id {
         description "Configure the generic LSP identifier";
         type union {
           type string {
             pattern "<.*>|$.*";
           }
           type uint32 {
             range "1 .. 65535";
           }
         }
       }
       list group-address {
         key name;
         description "IPv4/Ipv6 group address for mLDP LSP";
         leaf name {
           description "IPv4/Ipv6 group address";
           type jt:ipaddr;
         }
         uses apply-advanced;
         list source-address {
           key name;
           description "IPv4/Ipv6 source address";
           leaf name {
             description "IPv4/Ipv6 source address for mLDP LSP";
             type jt:ipaddr;
           }
           uses apply-advanced;
         }
       }
     }
   }
   grouping pim_bootstrap_options_type {
     uses apply-advanced;
     leaf priority {
       description "Eligibility to be the bootstrap router";
       type union {
         type string {
           pattern "<.*>|$.*";
         }
         type uint32 {
           range "0 .. 255";
         }
       }
     }
     leaf-list import {
       ordered-by user;
       description "Bootstrap import policy";
       type jt:policy-algebra;
     }
     leaf-list export {
       ordered-by user;
       description "Bootstrap export policy";
       type jt:policy-algebra;
     }
   }
   grouping pim_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping pim_rp_group_range_type {
     leaf name {
       type jt:ipprefix;
     }
     uses apply-advanced;
     leaf nexthop-hold-time {
       description "Nexthop hold time in milliseconds";
       units "milliseconds";
       type union {
         type string {
           pattern "<.*>|$.*";
         }
         type uint32 {
           range "1 .. 1000";
         }
       }
     }
   }
   grouping ppp_options_type {
     uses apply-advanced;
     leaf dynamic-profile {
       description "Dynamic profile name";
       type string;
     }
     container chap {
       presence "enable chap";
       description "Challenge Handshake Authentication Protocol options";
       uses apply-advanced;
       choice access-data {
         case case_1 {
           leaf access-profile {
             description "Profile containing client list and access parameters";
             type string {
               length "1 .. 63";
             }
           }
         }
         case case_2 {
           leaf default-chap-secret {
             description "Default CHAP secret to be used when no matching access profile exists";
             type jt:unreadable;
           }
         }
       }
       leaf local-name {
         description "Name sent in CHAP-Challenge and CHAP-Response";
         type string;
       }
       leaf no-rfc2486 {
         description "RFC2486 compliance is not enforced";
         type empty;
       }
       leaf passive {
         description "Handle incoming CHAP requests only";
         type empty;
       }
       container challenge-length {
         description "CHAP challenge length";
         leaf minimum {
           description "Minimum CHAP challenge length";
           default "16";
           units "bytes";
           type union {
             type string {
               pattern "<.*>|$.*";
             }
             type uint8 {
               range "8 .. 63";
             }
           }
         }
         leaf maximum {
           description "Maximum CHAP challenge length";
           default "32";
           units "bytes";
           type union {
             type string {
               pattern "<.*>|$.*";
             }
             type uint8 {
               range "8 .. 63";
             }
           }
         }
       }
     }
     container pap {
       presence "enable pap";
       description "Password Authentication Protocol options";
       uses apply-advanced;
       choice access-data {
         case case_1 {
           leaf access-profile {
             description "Profile containing client list and access parameters";
             type string {
               length "1 .. 63";
             }
           }
         }
         case case_2 {
           leaf default-password {
             description "Default PAP password used in the absence of matching profile";
             type jt:unreadable;
           }
         }
       }
       leaf local-name {
         description "Name sent in PAP request packet";
         type string;
       }
       leaf no-rfc2486 {
         description "RFC2486 compliance is not enforced";
         type empty;
       }
       leaf local-password {
         description "Password sent in PAP request packet";
         type jt:unreadable;
       }
       leaf passive {
         description "Do not handle PAP authentication requests";
         type empty;
       }
     }
     leaf-list authentication {
       ordered-by user;
       description "Order in which PPP authentication protocols are negotiated";
       type enumeration {
         enum "pap" {
           description "Password Authentication Protocol";
         }
         enum "chap" {
           description "Challenge Handshake Authentication Protocol";
         }
       }
     }
     container compression {
       description "Set compression options";
       leaf acfc {
         description "Negotiate Address/Control field compression";
         type empty;
       }
       leaf pfc {
         description "Negotiate Protocol field compression";
         type empty;
       }
     }
     leaf lcp-restart-timer {
       description "LCP restart timer";
       units "milliseconds";
       type union {
         type string {
           pattern "<.*>|$.*";
         }
         type uint16 {
           range "20 .. 10000";
         }
       }
     }
     leaf ncp-restart-timer {
       description "NCP restart timer";
       units "milliseconds";
       type union {
         type string {
           pattern "<.*>|$.*";
         }
         type uint16 {
           range "500 .. 10000";
         }
       }
     }
     leaf no-termination-request {
       description "Don't send PPP termination requests";
       type empty;
     }
     leaf loopback-clear-timer {
       description "Loopback clear timer";
       units "seconds";
       type union {
         type string {
           pattern "<.*>|$.*";
         }
         type uint8 {
           range "1 .. 60";
         }
       }
     }
     leaf lcp-max-conf-req {
       description "Maximum LCP Conf-Req to be sent, 0 means infinite";
       type union {
         type string {
           pattern "<.*>|$.*";
         }
         type uint32 {
           range "0 .. 65535";
         }
       }
     }
     leaf ncp-max-conf-req {
       description "Maximum NCP Conf-Req to be sent, 0 means infinite";
       type union {
         type string {
           pattern "<.*>|$.*";
         }
         type uint32 {
           range "0 .. 65535";
         }
       }
     }
     leaf on-demand-ip-address {
       description "Enable On-Demand IPv4 address allocation and de-allocation";
       type empty;
     }
     leaf aaa-options {
       description "Attach AAA options name to dynamic-profile";
       type string {
         length "1 .. 63";
       }
     }
     container initiate-ncp {
       description "Enable server initiated NCP";
       uses apply-advanced;
       leaf ip {
         description "Enable server initiated IPNCP";
         type empty;
       }
       leaf ipv6 {
         description "Enable server initiated IPv6NCP";
         type empty;
       }
       leaf dual-stack-passive {
         description "Disable server initiated IPNCP/IPv6NCP for dual-stack client";
         type empty;
       }
     }
     leaf mru {
       description "The Maximum Receive Unit size in bytes";
       type union {
         type string {
           pattern "<.*>|$.*";
         }
         type uint32 {
           range "64 .. 9192";
         }
       }
     }
     leaf mtu {
       description "The Maximum Transfer Unit size in bytes";
       type string;
     }
     leaf peer-ip-address-optional {
       description "Set Peer IP Address Optional in IP NCP Negotiations";
       type empty;
     }
     leaf ipcp-suggest-dns-option {
       description "Suggest peer to negotiate with DNS Addresses options";
       type empty;
     }
     leaf ignore-magic-number-mismatch {
       description "Ignore magic-number validation failure in LCP keepalive";
       type empty;
     }
     container local-authentication {
       description "Local Authentication Protocol options";
       uses local_auth_type;
     }
     leaf lcp-connection-update {
       description "Enable LCP connection update request to peer";
       type empty;
     }
   }
   grouping local_auth_type {
     description "Local authentication";
     uses apply-advanced;
     leaf password {
       description "Username password";
       type string {
         length "1 .. 64";
       }
     }
     container username-include {
       description "Add username options";
       uses apply-advanced;
       leaf mac-address {
         description "Include MAC address";
         type empty;
       }
       leaf circuit-id {
         description "Include circuit-id ";
         type empty;
       }
       leaf remote-id {
         description "Include remote-id ";
         type empty;
       }
       leaf domain-name {
         description "Domain name";
         type string {
           length "1 .. 64";
         }
       }
       leaf delimiter {
         description "Delimiter/separator character";
         type string {
           length 1;
         }
       }
     }
   }
   grouping pppoe_options_type {
     uses apply-advanced;
     leaf underlying-interface {
       description "Underlying interface name";
       type string;
     }
     leaf idle-timeout {
       description "Time for which session can be idle (0 = forever)";
       units "seconds";
       type union {
         type string {
           pattern "<.*>|$.*";
         }
         type uint32 {
           range "0 .. 4294967295";
         }
       }
     }
     leaf access-concentrator {
       description "Name of the access concentrator (PPPoE server)";
       type string;
     }
     leaf service-name {
       description "Service to be requested (from PPPoE server)";
       type string;
     }
     leaf auto-reconnect {
       description "Time to reconnect after session terminates (0 = never)";
       units "seconds";
       type union {
         type string {
           pattern "<.*>|$.*";
         }
         type uint32 {
           range "0 .. 4294967295";
         }
       }
     }
     choice pppoe-mode {
       case case_1 {
         leaf server {
           description "PPPoE operates in server mode";
           type empty;
         }
       }
       case case_2 {
         leaf client {
           description "PPPoE operates in client mode";
           type empty;
         }
       }
     }
     leaf ppp-max-payload {
       description "Specify the value of ppp-max-payload tag";
       type union {
         type string {
           pattern "<.*>|$.*";
         }
         type uint32 {
           range "1492 .. 9192";
         }
       }
     }
   }
   grouping pppoe_underlying_options_type {
     uses apply-advanced;
     leaf access-concentrator {
       description "Name of the access concentrator (PPPoE server)";
       type string {
         length "1 .. 64";
       }
     }
     leaf direct-connect {
       description "Ignore received VS tags for PPPoE sessions";
       type empty;
     }
     leaf duplicate-protection {
       description "Disallow multiple PPPoE sessions to a single client";
       type empty;
     }
     leaf dynamic-profile {
       description "Attach dynamic-profile to interface";
       type string {
         length "1 .. 64";
       }
     }
     leaf max-sessions {
       description "Maximum number of PPPoE sessions allowed on underlying interface";
       type union {
         type string {
           pattern "<.*>|$.*";
         }
         type uint32;
       }
     }
     leaf max-sessions-vsa-ignore {
       description "Ignore the max-sessions VSA";
       type empty;
     }
     leaf service-name-table {
       description "Attach Service Name Table to interface";
       type string {
         length "1 .. 32";
       }
     }
     container short-cycle-protection {
       presence "enable short-cycle-protection";
       description "Enable short cycle protection on underlying interface";
       uses apply-advanced;
       leaf lockout-time-min {
         description "Minimum lockout time";
         units "seconds";
         type union {
           type string {
             pattern "<.*>|$.*";
           }
           type uint32 {
             range "1 .. 86400";
           }
         }
       }
       leaf lockout-time-max {
         description "Maximum lockout time";
         units "seconds";
         type union {
           type string {
             pattern "<.*>|$.*";
           }
           type uint32 {
             range "1 .. 86400";
           }
         }
       }
       leaf filter {
         description "Granularity of blocking filter";
         type enumeration {
           enum "aci" {
             description "Block by Agent Circuit ID";
           }
         }
       }
     }
   }
   grouping prbs-config {
     description "Configuration of pseudorandom binary sequence test signal";
     uses apply-advanced;
     choice enable-prbs-choice {
       leaf enable-prbs {
         description "Enable PRBS test pattern generation and monitoring";
         type empty;
       }
       leaf no-enable-prbs {
         description "Don't enable PRBS test pattern generation and monitoring";
         type empty;
       }
     }
     leaf direction {
       description "Direction of generated and received PRBS test signal";
       default "line";
       type enumeration {
         enum "local" {
           description "Test signal generated towards and received from host-side";
         }
         enum "line" {
           description "Test signal generated towards and received from network-side";
         }
       }
     }
     leaf pattern {
       description "Pattern to use for PRBS test signal";
       default "prbs-31";
       type enumeration {
         enum "prbs-31" {
           description "2^31 polynomial PRBS test signal, as per G.709";
         }
         enum "prbs-23" {
           description "2^23 polynomial PRBS test signal, SONET/SDH framed";
         }
         enum "prbs-15" {
           description "2^15 polynomial PRBS test signal";
         }
         enum "prbs-7" {
           description "2^7 polynomial PRBS test signal";
         }
       }
     }
     choice invert-choice {
       leaf invert {
         description "Invert the test pattern";
         type empty;
       }
       leaf no-invert {
         description "Don't invert the test pattern";
         type empty;
       }
     }
   }
   grouping prefix_action {
     leaf name {
       description "Prefix action name";
       type string {
       }
     }
     uses apply-advanced;
     leaf policer {
       description "Police the packet using a set of named policer";
       type string {
       }
     }
     leaf count {
       description "Enable counters";
       type empty;
     }
     leaf filter-specific {
       description "Filter specific, else term specific";
       type empty;
     }
     leaf subnet-prefix-length {
       description "Prefix length for the total address range";
       type union {
         type string {
           pattern "<.*>|$.*";
         }
         type uint32 {
           range "0 .. 32";
         }
       }
     }
     choice source_or_dest {
       case case_1 {
         leaf source-prefix-length {
           description "Source prefix range";
           type union {
             type string {
               pattern "<.*>|$.*";
             }
             type uint32 {
               range "0 .. 32";
             }
           }
         }
       }
       case case_2 {
         leaf destination-prefix-length {
           description "Destination prefix range";
           type union {
             type string {
               pattern "<.*>|$.*";
             }
             type uint32 {
               range "0 .. 32";
             }
           }
         }
       }
     }
   }
   grouping prefix_list_items {
     leaf name {
       description "Address prefix";
       type jt:ipprefix-only;
     }
     uses apply-advanced;
   }
   grouping qualified_nh_obj {
     leaf name {
       description "Next hop to destination";
       type union {
         type jt:ipaddr-or-interface;
         type string {
           pattern "<.*>|$.*";
         }
       }
     }
     uses apply-advanced;
     leaf preference {
       description "Preference of qualified next hop";
       type union {
         type uint32;
         type string {
           pattern "<.*>|$.*";
         }
       }
     }
     leaf metric {
       description "Metric of qualified next hop";
       type union {
         type uint32;
         type string {
           pattern "<.*>|$.*";
         }
       }
     }
     leaf interface {
       description "Interface of qualified next hop";
       type union {
         type jt:interface-name;
         type string {
           pattern "<.*>|$.*";
         }
       }
     }
     leaf mac-address {
       description "Next-hop Mac Address";
       type jt:mac-unicast;
     }
     leaf order {
       description "Order of qualified next hop";
       type union {
         type string {
           pattern "<.*>|$.*";
         }
         type uint16 {
           range "1 .. 65535";
         }
       }
     }
     leaf tag {
       description "Tag string";
       type union {
         type uint32;
         type string {
           pattern "<.*>|$.*";
         }
       }
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       leaf inline-disable {
         description "Disable inline mode for this BFD session";
         type empty;
       }
       leaf pdu-size {
         description "BFD transport protocol payload size";
         default "24";
         type union {
           type string {
             pattern "<.*>|$.*";
           }
           type uint32 {
             range "24 .. 9000";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           type string;
         }
         leaf algorithm {
           description "Algorithm name";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       container echo {
         description "Echo mode parameters";
         uses apply-advanced;
         leaf minimum-interval {
           description "Minimum transmit and receive interval";
           units "milliseconds";
           type union {
             type string {
               pattern "<.*>|$.*";
             }
             type uint32 {
               range "100 .. 255000";
             }
           }
         }
       }
       container echo-lite {
         description "Echo-lite more parameters";
         uses apply-advanced;
         leaf minimum-interval {
           description "Minimum transmit and receive interval";
           units "milliseconds";
           type union {
             type string {
               pattern "<.*>|$.*";
             }
             type uint32 {
               range "100 .. 255000";
             }
           }
         }
       }
       leaf neighbor {
         description "BFD neighbor address";
         type jt:ipaddr;
       }
       leaf local-address {
         description "BFD local address (for multihop only)";
         type jt:ipaddr;
       }
       leaf holddown-interval {
         description "Time to hold the session-UP notification to the client";
         units "milliseconds";
         type union {
           type string {
             pattern "<.*>|$.*";
           }
           type uint32 {
             range "0 .. 255000";
           }
         }
       }
       leaf minimum-receive-ttl {
         description "Minimum receive TTL below which to drop";
         type union {
           type string {
             pattern "<.*>|$.*";
           }
           type uint8 {
             range "1 .. 255";
           }
         }
       }
     }
   }
   grouping radius_options_vlan_type {
     uses apply-advanced;
     list nas-port-options {
       key name;
       ordered-by user;
       description "Attach NAS Port options to VLAN/SVLAN ranges";
       max-elements 16;
       leaf name {
         description "Profile name";
         type string;
       }
       uses apply-advanced;
       leaf nas-port-type {
         description "Configure NAS port type";
         type string;
       }
       container nas-port-extended-format {
         description "Configure NAS port format";
         uses apply-advanced;
         leaf ae-width {
           description "Number of bits for the  aggregated ethernet identifier field";
           units "bits";
           type union {
             type string {
               pattern "<.*>|$.*";
             }
             type uint32 {
               range "0 .. 32";
             }
           }
         }
         leaf slot {
           description "Value to write to the slot field";
           type union {
             type string {
               pattern "<.*>|$.*";
             }
             type uint32 {
               range "0 .. 255";
             }
           }
         }
         leaf slot-width {
           description "Number of bits for the slot field";
           units "bits";
           type union {
             type string {
               pattern "<.*>|$.*";
             }
             type uint32 {
               range "0 .. 32";
             }
           }
         }
         leaf adapter {
           description "Value to write to the adapter field";
           type union {
             type string {
               pattern "<.*>|$.*";
             }
             type uint32 {
               range "0 .. 255";
             }
           }
         }
         leaf adapter-width {
           description "Number of bits for the adapter field";
           units "bits";
           type union {
             type string {
               pattern "<.*>|$.*";
             }
             type uint32 {
               range "0 .. 32";
             }
           }
         }
         leaf port {
           description "Value to write to the port field";
           type union {
             type string {
               pattern "<.*>|$.*";
             }
             type uint32 {
               range "0 .. 255";
             }
           }
         }
         leaf port-width {
           description "Number of bits for the port field";
           units "bits";
           type union {
             type string {
               pattern "<.*>|$.*";
             }
             type uint32 {
               range "0 .. 32";
             }
           }
         }
         leaf pw-width {
           description "Number of bits for the pseudo-wire field";
           units "bits";
           type union {
             type string {
               pattern "<.*>|$.*";
             }
             type uint32 {
               range "0 .. 32";
             }
           }
         }
         leaf stacked-vlan-width {
           description "Number of bits for the S-VLAN subinterface field";
           units "bits";
           type union {
             type string {
               pattern "<.*>|$.*";
             }
             type uint32 {
               range "0 .. 32";
             }
           }
         }
         leaf vlan-width {
           description "Number of bits for the VLAN subinterface field";
           units "bits";
           type union {
             type string {
               pattern "<.*>|$.*";
             }
             type uint32 {
               range "0 .. 32";
             }
           }
         }
         leaf stacked {
           description "Include the S-VLAN ID for subscribers on interfaces";
           type empty;
         }
         leaf vpi-width {
           description "Number of bits for the ATM VPI field";
           units "bits";
           type union {
             type string {
               pattern "<.*>|$.*";
             }
             type uint32 {
               range "0 .. 32";
             }
           }
         }
         leaf vci-width {
           description "Number of bits for the ATM VCI field";
           units "bits";
           type union {
             type string {
               pattern "<.*>|$.*";
             }
             type uint32 {
               range "0 .. 32";
             }
           }
         }
       }
       list stacked-vlan-ranges {
         key name;
         ordered-by user;
         description "Configure interface based on stacked-vlan range";
         leaf name {
           description "SVLAN range: [any | <low-tag>-<high-tag>],[any | <low-tag>-<high-tag>]";
           type string {
           }
         }
         uses apply-advanced;
       }
       list vlan-ranges {
         key name;
         ordered-by user;
         description "Configure interface based on vlan range";
         leaf name {
           description "VLAN range: [any | <low-tag>-<high-tag>]";
           type string {
           }
         }
         uses apply-advanced;
       }
     }
   }
   grouping rib_aggregate_type {
     uses apply-advanced;
     container defaults {
       description "Global route options";
       uses apply-advanced;
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
       container algorithm {
         description "Algorithm number";
         leaf number {
           description "Algorithm number";
           type union {
             type string {
               pattern "<.*>|$.*";
             }
             type uint32 {
               range "0 .. 255";
             }
           }
         }
       }
     }
     leaf protocol-instance-name {
       description "Name of protocol instance under routing instance";
       type string;
     }
     list route {
       key name;
       description "Individual route options";
       leaf name {
         description "Destination prefix";
         type jt:ipprefix;
       }
       uses apply-advanced;
       leaf description {
         description "Description for aggregate routes";
         type string {
         }
       }
       leaf-list policy {
         ordered-by user;
         description "Policy filter";
         type jt:policy-algebra;
       }
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
       container algorithm {
         description "Algorithm number";
         leaf number {
           description "Algorithm number";
           type union {
             type string {
               pattern "<.*>|$.*";
             }
             type uint32 {
               range "0 .. 255";
             }
           }
         }
       }
     }
   }
   grouping rib_group_type {
     uses apply-advanced;
     leaf inet-old-style {
       description "Name of the IPv4 routing table group";
       status deprecated;
       type string;
     }
     leaf inet {
       description "Name of the IPv4 routing table group";
       type string;
     }
     leaf inet3 {
       description "Name of the IPv4 inet.3 routing table group";
       type string;
     }
     leaf inet6 {
       description "Name of the IPv6 routing table group";
       type string;
     }
     leaf inet63 {
       description "Name of the IPv6 inet6.3 routing table group";
       type string;
     }
   }
   grouping rib_static_metric_type {
     leaf metric-value {
       description "Metric value";
       type union {
         type uint32;
         type string {
           pattern "<.*>|$.*";
         }
       }
     }
     leaf type {
       description "Metric type";
       type union {
         type string {
           pattern "<.*>|$.*";
         }
         type uint32 {
           range "1 .. 16";
         }
       }
     }
   }
   grouping sfw_addr_object {
     leaf name {
       description "Match IP address";
       type string;
     }
     leaf except {
       description "Match address not in this prefix";
       type empty;
     }
   }
   grouping sonet_options_type {
     uses apply-advanced;
     leaf vtmapping {
       description "VT mapping mode";
       type enumeration {
         enum "klm" {
           description "KLM mode";
         }
         enum "itu-t" {
           description "ITU-T mode";
         }
       }
     }
     leaf fcs {
       description "Frame checksum";
       type enumeration {
         enum "32" {
           description "32-bit mode";
         }
         enum "16" {
           description "16-bit mode";
         }
       }
     }
     leaf path-trace {
       description "Path trace string";
       type string;
     }
     leaf loopback {
       description "Loopback mode";
       type enumeration {
         enum "local" {
           description "Local loopback";
         }
         enum "remote" {
           description "Remote loopback";
         }
       }
     }
     container trigger {
       description "Defect triggers";
       uses apply-advanced;
       container lol {
         description "LOL defect trigger";
         choice lol_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container pll {
         description "PLL defect trigger";
         choice pll_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lof {
         description "LOF defect trigger";
         choice lof_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container los {
         description "LOS defect trigger";
         choice los_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ais-l {
         description "AIS-L defect trigger";
         choice ais_l_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container rfi-l {
         description "RFI-L defect trigger";
         choice rfi_l_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ber-sd {
         description "BER-SD defect trigger";
         uses apply-advanced;
         choice ber_sd_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ber-sf {
         description "BER-SF defect trigger";
         uses apply-advanced;
         choice ber_sf_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ais-p {
         description "AIS-P defect trigger";
         choice ais_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lop-p {
         description "LOP-P defect trigger";
         choice lop_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container rfi-p {
         description "RFI-P defect trigger";
         choice rfi_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container uneq-p {
         description "UNEQ-P defect trigger";
         choice uneq_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container plm-p {
         description "PLM-P defect trigger";
         choice plm_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container locd {
         description "LOCD defect trigger (ATM only)";
         choice locd_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lcdp {
         description "LCD-P defect trigger (Ethernet WAN only)";
         choice lcdp_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
     }
     container aps {
       description "Automatic Protection Switching";
       uses aps_type;
     }
     choice payload_scrambler_choices {
       case case_1 {
         container payload-scrambler {
           presence "enable payload-scrambler";
           description "Enable payload scrambling";
           choice payload-choice {
           }
         }
       }
       case case_2 {
         leaf no-payload-scrambler {
           description "Do not enable payload scrambling";
           type empty;
         }
       }
     }
     choice z0-increment-choice {
       leaf z0-increment {
         description "Increment Z0 in SDH mode";
         type empty;
       }
       leaf no-z0-increment {
         description "Don't increment Z0 in SDH mode";
         type empty;
       }
     }
     choice loop-timing-choice {
       leaf loop-timing {
         description "Set loop timing for STM-1";
         type empty;
       }
       leaf no-loop-timing {
         description "Don't set loop timing for STM-1";
         type empty;
       }
     }
     container bytes {
       description "Set SONET header bytes";
       uses apply-advanced;
       leaf e1-quiet {
         description "E1-quiet value";
         type union {
           type string {
             pattern "<.*>|$.*";
           }
           type uint32 {
             range "0 .. 255";
           }
         }
       }
       leaf f1 {
         description "F1 user value";
         type union {
           type string {
             pattern "<.*>|$.*";
           }
           type uint32 {
             range "0 .. 255";
           }
         }
       }
       leaf f2 {
         description "F2 user value";
         type union {
           type string {
             pattern "<.*>|$.*";
           }
           type uint32 {
             range "0 .. 255";
           }
         }
       }
       leaf s1 {
         description "S1/Z1 value (stratum clock by convention)";
         type union {
           type string {
             pattern "<.*>|$.*";
           }
           type uint32 {
             range "0 .. 255";
           }
         }
       }
       leaf z3 {
         description "Z3 user value";
         type union {
           type string {
             pattern "<.*>|$.*";
           }
           type uint32 {
             range "0 .. 255";
           }
         }
       }
       leaf z4 {
         description "Z4 user value";
         type union {
           type string {
             pattern "<.*>|$.*";
           }
           type uint32 {
             range "0 .. 255";
           }
         }
       }
       leaf c2 {
         description "C2 user value";
         type union {
           type string {
             pattern "<.*>|$.*";
           }
           type uint32 {
             range "0 .. 255";
           }
         }
       }
     }
     leaf rfc-2615 {
       description "RFC 2615 compliance";
       type empty;
     }
     leaf aggregate {
       description "Join a SONET aggregate";
       type union {
         type jt:interface-device;
         type string {
           pattern "<.*>|$.*";
         }
       }
     }
     container mpls {
       description "MPLS options";
       uses mpls_ifd_options;
     }
   }
   grouping springte_lsp_nh_obj {
     uses apply-advanced;
     leaf nexthop {
       description "SPRING-TE LSP to use to reach destination";
       type string {
         length "1 .. 128";
       }
     }
     container lsp-source {
       description "Source of tunnel creation";
       uses apply-advanced;
       choice lsp-src-choice {
         case case_1 {
           leaf pcep {
             description "Path computation element protocol";
             type empty;
           }
         }
         case case_2 {
           leaf static {
             description "Static configuration";
             type empty;
           }
         }
         case case_3 {
           leaf dtm {
             description "Dynamic tunnel module";
             type empty;
           }
         }
         case case_4 {
           leaf bgp {
             description "BGP SRTE";
             type empty;
           }
         }
       }
     }
   }
   grouping tdm_options_type {
     uses apply-advanced;
     leaf sfp-type {
       description "Smart SFP type";
       type enumeration {
         enum "T1" {
           description "T1 smart SFP";
         }
         enum "E1" {
           description "E1 smart SFP";
         }
         enum "DS3" {
           description "DS3 smart SFP";
         }
         enum "STM1" {
           description "STM1 smart SFP";
         }
         enum "STM4" {
           description "STM4 smart SFP";
         }
         enum "STM16" {
           description "STM16 smart SFP";
         }
       }
     }
     leaf tdm-in-loop {
       description "Configure port in TDM IN-LOOP mode";
       type empty;
     }
     leaf tdm-out-loop {
       description "Configure port in TDM OUT-LOOP mode";
       type empty;
     }
     leaf ces-psn-port-dmac-check-enable {
       description "Enable DMAC check on smart SFP";
       type empty;
     }
     container iwf-params {
       description "TDM interworking functionality (IWF) parameters";
       uses apply-advanced;
       leaf decap-ecid {
         description "ECID for decapsulation";
         type union {
           type string {
             pattern "<.*>|$.*";
           }
           type uint32 {
             range "0 .. 1048575";
           }
         }
       }
       leaf encap-ecid {
         description "ECID for encapsulation";
         type union {
           type string {
             pattern "<.*>|$.*";
           }
           type uint32 {
             range "0 .. 1048575";
           }
         }
       }
     }
     container ces-psn-channel {
       description "CES PSN channel parameters";
       uses apply-advanced;
       leaf dmac-address {
         description "Destination MAC-address to be paired with the Smart SFP";
         type jt:mac-addr;
       }
       leaf mode {
         description "PSN encapsulation mode";
         type enumeration {
           enum "MEF8" {
             description "MEF8 encapsulation";
           }
           enum "MPLS" {
             description "MPLS Encapsulation";
           }
         }
       }
       leaf vlan-id-1 {
         description "VLAN ID for encapsulation";
         type union {
           type string {
             pattern "<.*>|$.*";
           }
           type uint32 {
             range "0 .. 4094";
           }
         }
       }
       leaf vlan-id-2 {
         description "Outer VLAN ID for encapsulation";
         type union {
           type string {
             pattern "<.*>|$.*";
           }
           type uint32 {
             range "0 .. 4094";
           }
         }
       }
     }
   }
   grouping three-color-policer-type {
     description "Three-color policer";
     leaf name {
       description "Policer name";
       type string {
       }
     }
     uses apply-advanced;
     leaf filter-specific {
       description "Three color policer is filter-specific";
       type empty;
     }
     leaf logical-interface-policer {
       description "Policer is logical interface policer";
       type empty;
     }
     leaf physical-interface-policer {
       description "Policer is physical interface policer";
       type empty;
     }
     leaf shared-bandwidth-policer {
       description "Share policer bandwidth among bundle links";
       type empty;
     }
     container action {
       description "Action for three-color policer";
       uses apply-advanced;
       list loss-priority {
         key name;
         ordered-by user;
         description "Loss priority for packet";
         uses three-color-policer-action;
       }
     }
     choice rate-type-choice {
       case case_1 {
         container single-rate {
           description "Single-rate policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-rate {
             description "Bandwidth allowed for committed traffic";
             units "bits per second";
             type string;
           }
           leaf committed-burst-size {
             description "Burst size allowed for committed traffic";
             units "bytes";
             type string;
           }
           leaf excess-burst-size {
             description "Burst size allowed for excess traffic";
             units "bytes";
             type string;
           }
         }
       }
       case case_2 {
         container single-packet-rate {
           presence "enable single-packet-rate";
           description "Single-rate packet policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-pps {
             description "PPS allowed for committed traffic";
             units "packets per second";
             type string;
           }
           leaf committed-packet-burst {
             description "Packet burst allowed for committed traffic";
             units "packets";
             type string;
           }
           leaf excess-packet-burst {
             description "Packet burst allowed for excess traffic";
             units "packets";
             type string;
           }
         }
       }
       case case_3 {
         container two-rate {
           presence "enable two-rate";
           description "Two-rate policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-rate {
             description "Bandwidth allowed for committed traffic";
             units "bits per second";
             type string;
           }
           leaf committed-burst-size {
             description "Burst size allowed for committed traffic  ";
             units "bytes";
             type string;
           }
           leaf peak-information-rate {
             description "Bandwidth allowed for peak traffic";
             units "bits per second";
             type string;
           }
           leaf peak-burst-size {
             description "Burst size allowed for peak traffic  ";
             units "bytes";
             type string;
           }
           container aggregate-policing {
             presence "enable aggregate-policing";
             description "Configure Aggregate Policer";
             uses apply-advanced;
             list policer {
               key name;
               ordered-by user;
               description "Two-color policer to be used as aggregate";
               max-elements 1;
               leaf name {
                 description "Name of two-color policer to use to aggregate police";
                 type string;
               }
               uses apply-advanced;
               leaf aggregate-sharing-mode {
                 description "Hierarchical Metering model";
                 type enumeration {
                   enum "hybrid" {
                     description "Child policer CIR rates are guaranteed rates and PIR rate are peak rates for member flow";
                   }
                 }
               }
             }
           }
         }
       }
       case case_4 {
         container two-packet-rate {
           presence "enable two-packet-rate";
           description "Two-rate packet policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-pps {
             description "PPS allowed for committed traffic";
             units "packets per second";
             type string;
           }
           leaf committed-packet-burst {
             description "Packet burst allowed for committed traffic  ";
             units "packets";
             type string;
           }
           leaf peak-information-pps {
             description "PPS allowed for peak traffic";
             units "packets per second";
             type string;
           }
           leaf peak-packet-burst {
             description "Packet burst allowed for peak traffic  ";
             units "packets";
             type string;
           }
         }
       }
     }
   }
   grouping three-color-policer-action {
     description "Action for three-color policer";
     leaf name {
       description "Loss priority for packet";
       type enumeration {
         enum "high" {
           description "High loss priority";
         }
       }
     }
     uses apply-advanced;
     container then {
       description "Action to take if the rate limits are exceeded";
       uses apply-advanced;
       leaf discard {
         description "Discard the packet";
         type empty;
       }
     }
   }
   grouping time-format-object {
     uses apply-advanced;
     leaf year {
       description "Year in time format for syslog";
       type empty;
     }
     leaf millisecond {
       description "Millisecond in time format for syslog";
       type empty;
     }
   }
   grouping to_fabric_object {
     description "Match traffic going to fabric";
     uses apply-advanced;
     leaf except {
       description "Match traffic switched locally and not going to fabric";
       type empty;
     }
   }
   grouping tunnel_end_point {
     description "Define a tunnel end point";
     leaf name {
       description "Tunnel end-point identifier (ASCII string)";
       type string {
       }
     }
     uses apply-advanced;
     choice l3-protocol {
       case case_1 {
         container ipv6 {
           presence "enable ipv6";
           description "Enter an IPv6 tunnel";
           uses apply-advanced;
           leaf source-address {
             description "Tunnel source address";
             type jt:ipv6addr;
           }
           leaf destination-address {
             description "Tunnel destination address";
             type jt:ipv6prefix;
           }
         }
       }
       case case_2 {
         container ipv4 {
           presence "enable ipv4";
           description "Enter an IPv4 tunnel";
           uses apply-advanced;
           leaf source-address {
             description "Tunnel source address";
             type jt:ipv4addr;
           }
           leaf destination-address {
             description "Tunnel destination address";
             type jt:ipv4prefix;
           }
         }
       }
     }
     choice tunnel-protocol {
       case case_1 {
         container gre {
           presence "enable gre";
           description "Tunnel is GRE";
           uses apply-advanced;
           leaf key {
             description "Key for authentication";
             type union {
               type uint32;
               type string {
                 pattern "<.*>|$.*";
               }
             }
           }
         }
       }
       case case_2 {
         container gre-in-udp {
           presence "enable gre-in-udp";
           description "Tunnel is GRE-in-UDP";
           uses apply-advanced;
           leaf source-port {
             description "UDP source port";
             type union {
               type string {
                 pattern "<.*>|$.*";
               }
               type uint32 {
                 range "0 .. 65535";
               }
             }
           }
           leaf destination-port {
             description "UDP destination port";
             type union {
               type string {
                 pattern "<.*>|$.*";
               }
               type uint32 {
                 range "0 .. 65535";
               }
             }
           }
           leaf key {
             description "GRE key for authentication";
             type union {
               type uint32;
               type string {
                 pattern "<.*>|$.*";
               }
             }
           }
         }
       }
     }
   }
   grouping vlan_map {
     description "IEEE 802.1q Virtual LAN (VLAN) Tag mapping";
     uses apply-advanced;
     choice operation_choices {
       case case_1 {
         leaf push {
           description "Push a VLAN tag";
           type empty;
         }
       }
       case case_2 {
         leaf swap {
           description "Swap a VLAN tag";
           type empty;
         }
       }
       case case_3 {
         leaf pop {
           description "Pop a VLAN tag";
           type empty;
         }
       }
       case case_4 {
         leaf push-push {
           description "Push two VLAN tags";
           type empty;
         }
       }
       case case_5 {
         leaf swap-push {
           description "Swap VLAN tag and push a new VLAN tag";
           type empty;
         }
       }
       case case_6 {
         leaf swap-swap {
           description "Swap both outer and inner VLAN tags";
           type empty;
         }
       }
       case case_7 {
         leaf pop-swap {
           description "Pop outer VLAN tag and swap inner VLAN tag";
           type empty;
         }
       }
       case case_8 {
         leaf pop-pop {
           description "Pop both outer and inner VLAN tags";
           type empty;
         }
       }
     }
     leaf tag-protocol-id {
       description "IEEE 802.1q Tag Protocol Identifier to rewrite";
       type string {
       }
     }
     leaf inner-tag-protocol-id {
       description "IEEE 802.1q Tag Protocol ID to rewrite for inner tag";
       type string;
     }
     leaf vlan-id {
       description "VLAN ID to rewrite";
       type string;
     }
     leaf inner-vlan-id {
       description "VLAN ID to rewrite for inner tag";
       type string;
     }
   }
   grouping vpls_filter {
     description "Define an VPLS firewall filter";
     leaf name {
       description "Filter name";
       type string {
       }
     }
     uses apply-advanced;
     leaf-list accounting-profile {
       ordered-by user;
       description "Accounting profile name";
       type string;
     }
     leaf interface-specific {
       description "Defined counters are interface specific";
       type empty;
     }
     leaf physical-interface-filter {
       description "Filter is physical interface filter";
       type empty;
     }
     leaf instance-shared {
       description "Filter is routing-instance shared";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         choice ether-type_choice {
           case case_1 {
             leaf-list ether-type {
               ordered-by user;
               type string;
             }
           }
           case case_2 {
             leaf-list ether-type-except {
               ordered-by user;
               type string;
             }
           }
         }
         choice vlan-ether-type_choice {
           case case_1 {
             leaf-list vlan-ether-type {
               ordered-by user;
               type string;
             }
           }
           case case_2 {
             leaf-list vlan-ether-type-except {
               ordered-by user;
               type string;
             }
           }
         }
         list destination-mac-address {
           key name;
           ordered-by user;
           description "Destination MAC address";
           uses firewall_mac_addr_object;
         }
         list source-mac-address {
           key name;
           ordered-by user;
           description "Source MAC address";
           uses firewall_mac_addr_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice learn-vlan-id_choice {
           case case_1 {
             leaf-list learn-vlan-id {
               ordered-by user;
               description "Learn-vlan-id range (0..4095)";
               type string {
               }
             }
           }
           case case_2 {
             leaf-list learn-vlan-id-except {
               ordered-by user;
               description "Learn-vlan-id range (0..4095)";
               type string {
               }
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice user-vlan-id_choice {
           case case_1 {
             leaf-list user-vlan-id {
               ordered-by user;
               description "User-vlan-id range (0..4095)";
               type string {
               }
             }
           }
           case case_2 {
             leaf-list user-vlan-id-except {
               ordered-by user;
               description "User-vlan-id range (0..4095)";
               type string {
               }
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         choice learn-vlan-dei_choice {
           case case_1 {
             leaf-list learn-vlan-dei {
               ordered-by user;
               description "DEI value 0-1";
               type union {
                 type string {
                   pattern "<.*>|$.*";
                 }
                 type uint32 {
                   range "0 .. 1";
                 }
               }
             }
           }
           case case_2 {
             leaf-list learn-vlan-dei-except {
               ordered-by user;
               description "DEI value 0-1";
               type union {
                 type string {
                   pattern "<.*>|$.*";
                 }
                 type uint32 {
                   range "0 .. 1";
                 }
               }
             }
           }
         }
         choice traffic-type_choice {
           case case_1 {
             leaf-list traffic-type {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
           case case_2 {
             leaf-list traffic-type-except {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
         }
         list ip-source-address {
           key name;
           ordered-by user;
           description "Match IP source address";
           uses firewall_addr_object;
         }
         list ip-destination-address {
           key name;
           ordered-by user;
           description "Match IP destination address";
           uses firewall_addr_object;
         }
         list ip-address {
           key name;
           ordered-by user;
           description "Match IP source or destination address";
           uses firewall_addr_object;
         }
         choice ip-protocol_choice {
           case case_1 {
             leaf-list ip-protocol {
               ordered-by user;
               type string;
             }
           }
           case case_2 {
             leaf-list ip-protocol-except {
               ordered-by user;
               type string;
             }
           }
         }
         choice dscp_choice {
           case case_1 {
             leaf-list dscp {
               ordered-by user;
               type string;
             }
           }
           case case_2 {
             leaf-list dscp-except {
               ordered-by user;
               type string;
             }
           }
         }
         choice ip-precedence_choice {
           case case_1 {
             leaf-list ip-precedence {
               ordered-by user;
               type string;
             }
           }
           case case_2 {
             leaf-list ip-precedence-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-flags {
           description "Match TCP flags";
           type string;
         }
         choice icmp-code_choice {
           case case_1 {
             leaf-list icmp-code {
               ordered-by user;
               type string;
             }
           }
           case case_2 {
             leaf-list icmp-code-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         list interface {
           key name;
           ordered-by user;
           description "Match interface name";
           uses match_interface_object;
         }
         list interface-set {
           key name;
           ordered-by user;
           description "Match interface in set";
           uses match_interface_set_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         list ipv6-destination-address {
           key name;
           ordered-by user;
           description "Match IPv6 destination address";
           uses firewall_addr6_object;
         }
         list ipv6-source-address {
           key name;
           ordered-by user;
           description "Match IPv6 source address";
           uses firewall_addr6_object;
         }
         list ipv6-address {
           key name;
           ordered-by user;
           description "Match IPv6 address";
           uses firewall_addr6_object;
         }
         choice ipv6-next-header_choice {
           case case_1 {
             leaf-list ipv6-next-header {
               ordered-by user;
               type string;
             }
           }
           case case_2 {
             leaf-list ipv6-next-header-except {
               ordered-by user;
               type string;
             }
           }
         }
         choice ipv6-payload-protocol_choice {
           case case_1 {
             leaf-list ipv6-payload-protocol {
               ordered-by user;
               type string;
             }
           }
           case case_2 {
             leaf-list ipv6-payload-protocol-except {
               ordered-by user;
               type string;
             }
           }
         }
         choice ipv6-traffic-class_choice {
           case case_1 {
             leaf-list ipv6-traffic-class {
               ordered-by user;
               type string;
             }
           }
           case case_2 {
             leaf-list ipv6-traffic-class-except {
               ordered-by user;
               type string;
             }
           }
         }
         list ipv6-source-prefix-list {
           key name;
           ordered-by user;
           description "Match IPV6 source prefixes in named list";
           uses firewall_prefix_list;
         }
         list ipv6-destination-prefix-list {
           key name;
           ordered-by user;
           description "Match IPV6 destination prefixes in named list";
           uses firewall_prefix_list;
         }
         list ipv6-prefix-list {
           key name;
           ordered-by user;
           description "Match IP source or destination prefixes in named list";
           uses firewall_prefix_list;
         }
         choice flex-mask_choice {
           case case_1 {
             container flexible-match-mask {
               description "Match flexible mask";
               presence "enable flexible-match-mask";
               uses match_L2_flexible_mask;
             }
           }
         }
         choice flex-range_choice {
           case case_1 {
             container flexible-match-range {
               description "Match flexible range";
               presence "enable flexible-match-range";
               uses match_L2_flexible_range;
             }
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
             leaf hierarchical-policer {
               description "Name of hierarchical policer to use to rate-limit traffic";
               type string {
               }
             }
           }
           case case_4 {
             container enhanced-hierarchical-policer {
               description "Police the packet using enhanced-hierarchical-policer";
               uses apply-advanced;
               leaf enhanced-hierarchical-policer-name {
                 description "Name of enhanced hierarchical policer to use to rate-limit traffic";
                 type string {
                 }
               }
               leaf traffic-priority {
                 description "Traffic priority based on hierarchy level";
                 type enumeration {
                   enum "high" {
                     description "Hierarchical policer high traffic-priority";
                   }
                   enum "medium-high" {
                     description "Hierarchical policer medium-high traffic-priority";
                   }
                   enum "medium-low" {
                     description "Hierarchical policer medium-low traffic-priority";
                   }
                   enum "low" {
                     description "Hierarchical policer low traffic-priority";
                   }
                 }
               }
             }
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         leaf count {
           description "Count the packet in the named counter";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf port-mirror-instance {
           description "Port-mirror the packet to specified instance";
           type string {
           }
         }
         leaf port-mirror {
           description "Port-mirror the packet";
           type empty;
         }
         leaf inline-monitoring-instance {
           description "Inline monitoring to specified instance";
           type string {
           }
         }
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf next-hop-group {
           description "Use specified next-hop group";
           type string;
         }
         leaf sample {
           description "Sample the packet";
           type empty;
         }
         leaf log {
           description "Log the packet";
           type empty;
         }
         leaf syslog {
           description "System log (syslog) information about the packet";
           type empty;
         }
       }
     }
   }
   grouping vrrp-group {
     description "Virtual Router Redundancy Protocol group";
     leaf name {
       description "Identifier for VRRP group";
       type union {
         type string {
           pattern "<.*>|$.*";
         }
         type uint32 {
           range "0 .. 255";
         }
       }
     }
     uses apply-advanced;
     choice address {
       case case_1 {
         leaf-list virtual-address {
           ordered-by user;
           description "One or more virtual IPv4 addresses";
           type jt:ipv4addr;
         }
       }
       case case_2 {
         leaf-list virtual-inet6-address {
           ordered-by user;
           description "One or more virtual inet6 addresses";
           type jt:ipv6addr;
         }
       }
     }
     leaf virtual-link-local-address {
       description "Virtual link-local addresses";
       type jt:ipv6addr;
     }
     leaf priority {
       description "Virtual router election priority";
       type union {
         type string {
           pattern "<.*>|$.*";
         }
         type uint32 {
           range "0 .. 255";
         }
       }
     }
     leaf preferred {
       description "Preferred group on subnet";
       type empty;
     }
     choice advertisement_type {
       case case_1 {
         leaf advertise-interval {
           description "Advertisement interval";
           units "seconds";
           type union {
             type string {
               pattern "<.*>|$.*";
             }
             type uint32 {
               range "1 .. 255";
             }
           }
         }
       }
       case case_2 {
         leaf fast-interval {
           description "Fast advertisement interval";
           units "milliseconds";
           type union {
             type string {
               pattern "<.*>|$.*";
             }
             type uint32 {
               range "10 .. 40950";
             }
           }
         }
       }
       case case_3 {
         leaf inet6-advertise-interval {
           description "Inet6 advertisement interval";
           units "milliseconds";
           type union {
             type string {
               pattern "<.*>|$.*";
             }
             type uint32 {
               range "100 .. 40000";
             }
           }
         }
       }
     }
     choice preempt_type {
       case case_1 {
         container preempt {
           presence "enable preempt";
           description "Allow preemption";
           uses apply-advanced;
           leaf hold-time {
             description "Preemption hold time";
             units "seconds";
             type union {
               type string {
                 pattern "<.*>|$.*";
               }
               type uint32 {
                 range "0 .. 3600";
               }
             }
           }
         }
       }
       case case_2 {
         leaf no-preempt {
           description "Don't allow preemption";
           type empty;
         }
       }
     }
     choice accept_type {
       case case_1 {
         leaf accept-data {
           description "Accept packets destined for virtual IP address";
           type empty;
         }
       }
       case case_2 {
         leaf no-accept-data {
           description "Don't accept packets destined for virtual IP address";
           type empty;
         }
       }
     }
     leaf authentication-type {
       description "Authentication type";
       type enumeration {
         enum "md5" {
           description "HMAC-MD5-96";
         }
         enum "simple" {
           description "Simple password";
         }
       }
     }
     leaf authentication-key {
       description "Authentication key";
       type jt:unreadable;
     }
     container track {
       description "Interfaces to track for VRRP group";
       uses apply-advanced;
       leaf priority-hold-time {
         description "Priority hold time";
         units "seconds";
         type union {
           type string {
             pattern "<.*>|$.*";
           }
           type uint32 {
             range "0 .. 3600";
           }
         }
       }
       list interface {
         key name;
         ordered-by user;
         description "Interface to track in VRRP group";
         leaf name {
           description "Name of interface";
           type union {
             type jt:interface-unit;
             type string {
               pattern "<.*>|$.*";
             }
           }
         }
         uses apply-advanced;
         list bandwidth-threshold {
           key name;
           description "Track bandwidth of interface";
           leaf name {
             description "Interface speed below which priority cost is incurred";
             units "bits per second";
             type string;
           }
           leaf priority-cost {
             description "Value subtracted from priority when bandwidth is below threshold";
             type union {
               type string {
                 pattern "<.*>|$.*";
               }
               type uint32 {
                 range "1 .. 254";
               }
             }
           }
         }
         leaf priority-cost {
           description "Value to subtract from priority when interface is down";
           type union {
             type string {
               pattern "<.*>|$.*";
             }
             type uint32 {
               range "1 .. 254";
             }
           }
         }
       }
       list route {
         key "route_address routing-instance";
         ordered-by user;
         description "Route to track in VRRP group";
         leaf route_address {
           description "Route address";
           type jt:ipprefix-mandatory;
         }
         leaf routing-instance {
           description "Routing instance to which route belongs, or 'default'";
           type string {
           }
         }
         leaf priority-cost {
           description "Value to subtract from priority when route is down";
           type union {
             type string {
               pattern "<.*>|$.*";
             }
             type uint32 {
               range "1 .. 254";
             }
           }
         }
       }
     }
     container vrrp-inherit-from {
       description "VRRP group to follow for this VRRP group";
       uses apply-advanced;
       leaf active-interface {
         description "Interface name of VRRP active group";
         type union {
           type jt:interface-unit;
           type string {
             pattern "<.*>|$.*";
           }
         }
       }
       leaf active-group {
         description "Identifier for VRRP active group";
         type union {
           type string {
             pattern "<.*>|$.*";
           }
           type uint32 {
             range "0 .. 255";
           }
         }
       }
     }
     leaf advertisements-threshold {
       description "Number of vrrp advertisements missed before declaring master down";
       type union {
         type string {
           pattern "<.*>|$.*";
         }
         type uint32 {
           range "1 .. 15";
         }
       }
     }
   }
 }
