/*
 * Copyright (c) 2024 Juniper Networks, Inc.
 * All rights reserved.
 */
 module junos-nfx-conf-poe {
   namespace "http://yang.juniper.net/junos-nfx/conf/poe";

   prefix jc-poe;

   import junos-common-types {
     prefix jt;
     revision-date 2023-01-01;
   }

   import junos-nfx-conf-root {
     prefix jc;
     revision-date 2023-01-01;
   }

   organization "Juniper Networks, Inc.";

   contact "yang-support@juniper.net";

   description "Junos poe configuration module";

   revision 2023-01-01 {
     description "Junos: 23.4R2.13";
   }

   augment /jc:configuration {
     uses poe-group;
   }
   augment /jc:configuration/jc:groups {
     uses poe-group;
   }
   grouping poe-group {
     container poe {
       description "Power over Ethernet options";
       uses apply-advanced;
       leaf management {
         description "Power management mode for Power over Ethernet";
         default "class";
         type enumeration {
           enum "static" {
             description "Static power allocation method";
           }
           enum "class" {
             description "Class based power allocation method";
           }
           enum "high-power" {
             description "High power allocation method";
           }
         }
       }
       leaf guard-band {
         description "Guard band for Power over Ethernet";
         default "0";
         units "watts";
         type union {
           type string {
             pattern "<.*>|$.*";
           }
           type uint32 {
             range "0 .. 19";
           }
         }
       }
       container notification-control {
         description "Notification control for Power over Ethernet traps";
         uses apply-advanced;
         list fpc {
           key name;
           ordered-by user;
           description "FPC slot number";
           leaf name {
             description "FPC slot number";
             type union {
               type string {
                 pattern "<.*>|$.*";
               }
               type uint32;
             }
           }
           uses apply-advanced;
           leaf disable {
             description "Disable Power over Ethernet notification";
             type empty;
           }
         }
       }
       leaf lldp-priority {
         description "PoE controller LLDP priority";
         type empty;
       }
       leaf fast-poe {
         description "Fast Power over Ethernet";
         type empty;
       }
       leaf perpetual-poe {
         description "Perpetual Power over Ethernet";
         type empty;
       }
       list interface {
         key name;
         ordered-by user;
         description "Interface configuration for Power over Ethernet";
         leaf name {
           description "Name of interface";
           type string;
         }
         uses apply-advanced;
         leaf disable {
           description "Disable interface";
           type empty;
         }
         leaf priority {
           description "Priority options";
           default "low";
           type enumeration {
             enum "low" {
               description "Low priority";
             }
             enum "high" {
               description "High priority";
             }
           }
         }
         leaf maximum-power {
           description "Maximum power";
           default "30.0";
           units "watts";
           type decimal64 {
             fraction-digits 9;
           }
         }
         container telemetries {
           presence "enable telemetries";
           description "Telemetries settings";
           uses apply-advanced;
           leaf disable {
             description "Disable telemetries";
             type empty;
           }
           leaf interval {
             description "Interval at which data should be recorded";
             default "5";
             units "minutes";
             type union {
               type string {
                 pattern "<.*>|$.*";
               }
               type uint32 {
                 range "1 .. 30";
               }
             }
           }
           leaf duration {
             description "Duration to continue recording of data";
             default "1";
             units "hours";
             type union {
               type string {
                 pattern "<.*>|$.*";
               }
               type uint32 {
                 range "1 .. 24";
               }
             }
           }
         }
         leaf af-mode {
           description "Enable 802.3af";
           type empty;
         }
         leaf high-power {
           description "Enable high power on interface ";
           type empty;
         }
         leaf ultrahigh-power {
           description "Enable ultra high power on interface";
           type empty;
         }
         leaf legacy-pd {
           description "Enable legacy pd support on interface";
           type empty;
         }
       }
       list fpc {
         key name;
         ordered-by user;
         description "FPC slot number";
         leaf name {
           description "FPC slot number";
           type string;
         }
         uses apply-advanced;
         leaf maximum-power {
           description "Maximum FPC power limit";
           units "watts";
           type union {
             type string {
               pattern "<.*>|$.*";
             }
             type uint32 {
               range "0 .. 500";
             }
           }
         }
         leaf priority {
           description "Priority level(high/low)";
           type enumeration {
             enum "low" {
               description "Priority low";
             }
             enum "high" {
               description "Priority high";
             }
           }
         }
         leaf management {
           description "PoE management mode";
           default "class";
           type enumeration {
             enum "static" {
               description "Static power allocation method";
             }
             enum "class" {
               description "Power allocation class";
             }
           }
         }
         leaf guard-band {
           description "Guard band for PoE";
           default "0";
           units "watts";
           type union {
             type string {
               pattern "<.*>|$.*";
             }
             type uint32 {
               range "0 .. 15";
             }
           }
         }
         leaf lldp-priority {
           description "PoE controller LLDP priority";
           type empty;
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping macro-data-type {
     leaf name {
       description "Keyword part of the keyword-value pair";
       type string;
     }
     leaf value {
       description "Value part of the keyword-value pair";
       type string;
     }
   }
 }
