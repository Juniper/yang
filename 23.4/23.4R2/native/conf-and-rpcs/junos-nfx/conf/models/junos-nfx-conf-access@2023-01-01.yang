/*
 * Copyright (c) 2024 Juniper Networks, Inc.
 * All rights reserved.
 */
 module junos-nfx-conf-access {
   namespace "http://yang.juniper.net/junos-nfx/conf/access";

   prefix jc-access;

   import junos-common-types {
     prefix jt;
     revision-date 2023-01-01;
   }

   import junos-nfx-conf-root {
     prefix jc;
     revision-date 2023-01-01;
   }

   organization "Juniper Networks, Inc.";

   contact "yang-support@juniper.net";

   description "Junos access configuration module";

   revision 2023-01-01 {
     description "Junos: 23.4R2.13";
   }

   augment /jc:configuration {
     uses access-group;
   }
   augment /jc:configuration/jc:groups {
     uses access-group;
   }
   grouping access-group {
     container access {
       description "Network access configuration";
       uses juniper-access-options;
     }
   }
   grouping juniper-access-options {
     uses apply-advanced;
     container address-pool-manager {
       presence "enable address-pool-manager";
       description "APM server configuration";
       uses apply-advanced;
       leaf inet {
         description "Address-pool-manager IPv4 address";
         type jt:ipaddr;
       }
       leaf port {
         description "Address-pool-manager IPv4 port";
         type union {
           type uint16;
           type string {
             pattern "<.*>|$.*";
           }
         }
       }
       leaf system-identifier {
         description "Address-pool-manager system identifier for this entity";
         type string;
       }
       leaf source-address {
         description "Source IP address to use for this entity";
         type jt:ipaddr;
       }
       container secrets {
         presence "enable secrets";
         uses apply-advanced;
         leaf certificate {
           description "Address-pool-manager certificate file name";
           type string;
         }
         leaf key {
           description "Address-pool-manager private-key file name";
           type string;
         }
         leaf ca-cert {
           description "Address-pool-manager authority-certification file name";
           type string;
         }
       }
     }
     list radius-server {
       key name;
       ordered-by user;
       description "RADIUS server configuration";
       uses access-radius-server-object;
     }
     list radius-server-name {
       key name;
       ordered-by user;
       description "RADIUS server FQDN configuration";
       uses access-radius-server-name-object;
     }
     leaf radius-disconnect-port {
       description "Server port on which to access disconnect requests from RADIUS client";
       default "1700";
       type union {
         type uint16;
         type string {
           pattern "<.*>|$.*";
         }
       }
     }
     list radius-disconnect {
       key name;
       ordered-by user;
       description "RADIUS-initiated disconnect configuration for dynamic termination of user sessions by external entity";
       uses radius-disconnect-object;
     }
     list domain-name-server {
       key name;
       ordered-by user;
       description "Default DNS server's IPv4 address";
       leaf name {
         description "Address";
         type jt:ipv4addr;
       }
       uses apply-advanced;
     }
     list domain-name-server-inet {
       key name;
       ordered-by user;
       description "DNS server's IPv4 address";
       leaf name {
         description "Address";
         type jt:ipv4addr;
       }
       uses apply-advanced;
     }
     list domain-name-server-inet6 {
       key name;
       ordered-by user;
       description "DNS server's IPv6 address";
       leaf name {
         description "Address";
         type jt:ipv6addr;
       }
       uses apply-advanced;
     }
     list wins-server {
       key name;
       ordered-by user;
       description "Default WINS server's IPv4 address";
       leaf name {
         description "Address";
         type jt:ipv4addr;
       }
       uses apply-advanced;
     }
     list address-pool {
       key name;
       ordered-by user;
       description "Address pool";
       uses address-pool-object;
     }
     list group-profile {
       key name;
       ordered-by user;
       description "Group profile to use for this client";
       uses group-profile-object;
     }
     list profile {
       key name;
       ordered-by user;
       description "Set of attributes that define access";
       leaf name {
         description "Profile name";
         type string {
           length "1 .. 63";
         }
       }
       uses apply-advanced;
       leaf-list accounting-order {
         ordered-by user;
         description "Order in which accounting mechanisms are used";
         type enumeration {
           enum "radius" {
             description "Remote Authentication Dial-In User Service";
           }
         }
       }
       leaf-list authentication-order {
         ordered-by user;
         description "Order in which authentication mechanisms are used";
         type enumeration {
           enum "radius" {
             description "Remote Authentication Dial-In User Service";
           }
           enum "password" {
             description "Locally configured password in access profile";
           }
           enum "none" {
             description "No authentication performed";
           }
           enum "nasreq" {
             description "Diameter based authentication and authorization using NASREQ application protocol";
           }
           enum "nas-5g" {
             description "Authentication and authorization using 3GPP N1 and N2 signaling";
           }
           enum "ldap" {
             description "Lightweight Directory Access Protocol";
           }
           enum "securid" {
             description "RSA SecurID Authentication";
           }
           enum "s6a" {
             description "S6a Authentication";
           }
         }
       }
       leaf-list authorization-order {
         ordered-by user;
         description "Order in which authorization mechanisms are used";
         type enumeration {
           enum "jsrc" {
             description "Diameter based authorization using Juniper's SRC application protocol";
           }
           enum "nasreq" {
             description "Diameter based authorization using NASREQ application protocol";
           }
           enum "none" {
             description "No authorization performed";
           }
         }
       }
       leaf provisioning-order {
         description "Order in which provisioning mechanisms are used";
         type enumeration {
           enum "jsrc" {
             description "Address authorization via SRC";
           }
           enum "gx-plus" {
             description "Policy/service provisioning via GXPLUS";
           }
           enum "pcrf" {
             description "Policy/service provisioning via PCRF";
           }
         }
       }
       leaf-list preauthentication-order {
         ordered-by user;
         description "Order in which preauthentication mechanisms are used";
         type enumeration {
           enum "radius" {
             description "Remote Authentication Dial-In User Service";
           }
         }
       }
       leaf-list charging-service-list {
         ordered-by user;
         description "List of used 3gpp charging servicess";
         type enumeration {
           enum "ocs" {
             description "Online charging service";
           }
         }
       }
       list domain-name-server {
         key name;
         ordered-by user;
         description "Default DNS server's IPv4 address";
         leaf name {
           description "Address";
           type jt:ipv4addr;
         }
         uses apply-advanced;
       }
       list domain-name-server-inet {
         key name;
         ordered-by user;
         description "DNS server's IPv4 address";
         leaf name {
           description "Address";
           type jt:ipv4addr;
         }
         uses apply-advanced;
       }
       list domain-name-server-inet6 {
         key name;
         ordered-by user;
         description "DNS server's IPv6 address";
         leaf name {
           description "Address";
           type jt:ipv6addr;
         }
         uses apply-advanced;
       }
       list wins-server {
         key name;
         ordered-by user;
         description "Default WINS server's IPv4 address";
         leaf name {
           description "Address";
           type jt:ipv4addr;
         }
         uses apply-advanced;
       }
       list client {
         key name;
         description "Entity requesting access";
         uses access-client-object;
       }
       container address-assignment {
         description "Address assignment pool";
         uses apply-advanced;
         leaf pool {
           description "Name of address-assignment pool";
           type string {
             length "1 .. 63";
           }
         }
         leaf inet6-pool {
           description "Name of address-assignment pool for family inet6";
           type string {
             length "1 .. 63";
           }
         }
       }
       leaf session-limit-per-username {
         description "Maximum number of sessions allowed per username";
         type union {
           type string {
             pattern "<.*>|$.*";
           }
           type uint32 {
             range "1 .. 16";
           }
         }
       }
       container local {
         description "Set configuration for local reporting - obsolete config";
         status deprecated;
         uses apply-advanced;
         leaf flat-file-profile {
           description "Specifies that the service accounting will be reported as per flat-file profile";
           type string;
         }
       }
       container radius {
         description "Set of RADIUS configurations";
         uses apply-advanced;
         leaf-list authentication-server {
           ordered-by user;
           description "The authentication server list to use in the specified order to send authentication messages";
           type jt:ipaddr;
         }
         leaf-list accounting-server {
           ordered-by user;
           description "The accounting server list to use in the specified order to send accounting messages";
           type jt:ipaddr;
         }
         leaf-list preauthentication-server {
           ordered-by user;
           description "The preauthentication server list to use in the specified order to send preauthentication messages";
           type jt:ipaddr;
         }
         leaf authentication-server-name {
           description "The authentication server to use to send authentication messages";
           type string {
             length "4 .. 255";
           }
         }
         leaf accounting-server-name {
           description "The accounting server to use to send accounting messages";
           type string {
             length "4 .. 255";
           }
         }
         container options {
           description "Specifies the RADIUS options";
           uses apply-advanced;
           leaf ethernet-port-type-virtual {
             description "Type of physical port to authenticate the user is virtual (RADIUS attribute 61)";
             type empty;
           }
           container interface-description-format {
             description "Interface description in the NAS-port-ID attribute";
             uses apply-advanced;
             leaf exclude-sub-interface {
               description "Exclude sub-interface from interface description";
               type empty;
             }
             leaf exclude-adapter {
               description "Exclude adapter from interface description";
               type empty;
             }
             leaf exclude-channel {
               description "Exclude channel from interface description";
               type empty;
             }
           }
           leaf nas-identifier {
             description "NAS-Identifier to be used for authentication and accounting requests (RADIUS attribute 32)";
             type string {
               length "1 .. 64";
             }
           }
           container nas-port-extended-format {
             description "RADIUS client's use of an extended format for RADIUS attribute 5";
             uses apply-advanced;
             leaf ae-width {
               description "Number of bits for the aggregated ethernet identifier field";
               units "bits";
               type union {
                 type string {
                   pattern "<.*>|$.*";
                 }
                 type uint32 {
                   range "0 .. 32";
                 }
               }
             }
             leaf slot-width {
               description "Number of bits for the slot field";
               units "bits";
               type union {
                 type string {
                   pattern "<.*>|$.*";
                 }
                 type uint32 {
                   range "0 .. 32";
                 }
               }
             }
             leaf adapter-width {
               description "Number of bits for the adapter field";
               units "bits";
               type union {
                 type string {
                   pattern "<.*>|$.*";
                 }
                 type uint32 {
                   range "0 .. 32";
                 }
               }
             }
             leaf port-width {
               description "Number of bits for the port field";
               units "bits";
               type union {
                 type string {
                   pattern "<.*>|$.*";
                 }
                 type uint32 {
                   range "0 .. 32";
                 }
               }
             }
             leaf pw-width {
               description "Number of bits for the pseudo-wire field";
               units "bits";
               type union {
                 type string {
                   pattern "<.*>|$.*";
                 }
                 type uint32 {
                   range "0 .. 32";
                 }
               }
             }
             leaf stacked-vlan-width {
               description "Number of bits for the S-VLAN subinterface field";
               units "bits";
               type union {
                 type string {
                   pattern "<.*>|$.*";
                 }
                 type uint32 {
                   range "0 .. 32";
                 }
               }
             }
             leaf vlan-width {
               description "Number of bits for the VLAN subinterface field";
               units "bits";
               type union {
                 type string {
                   pattern "<.*>|$.*";
                 }
                 type uint32 {
                   range "0 .. 32";
                 }
               }
             }
             container atm {
               description "ATM specific parameters for NAS Port";
               uses apply-advanced;
               leaf slot-width {
                 description "Number of bits for the ATM slot field";
                 units "bits";
                 type union {
                   type string {
                     pattern "<.*>|$.*";
                   }
                   type uint32 {
                     range "0 .. 32";
                   }
                 }
               }
               leaf adapter-width {
                 description "Number of bits for the ATM adapter field";
                 units "bits";
                 type union {
                   type string {
                     pattern "<.*>|$.*";
                   }
                   type uint32 {
                     range "0 .. 32";
                   }
                 }
               }
               leaf port-width {
                 description "Number of bits for the ATM port field";
                 units "bits";
                 type union {
                   type string {
                     pattern "<.*>|$.*";
                   }
                   type uint32 {
                     range "0 .. 32";
                   }
                 }
               }
               leaf vpi-width {
                 description "Number of bits for the ATM VPI field";
                 units "bits";
                 type union {
                   type string {
                     pattern "<.*>|$.*";
                   }
                   type uint32 {
                     range "0 .. 32";
                   }
                 }
               }
               leaf vci-width {
                 description "Number of bits for the ATM VCI field";
                 units "bits";
                 type union {
                   type string {
                     pattern "<.*>|$.*";
                   }
                   type uint32 {
                     range "0 .. 32";
                   }
                 }
               }
             }
           }
           leaf nas-port-id-delimiter {
             description "Single character delimiter character to use in the NAS-Port-Id";
             type string {
               length 1;
             }
           }
           container nas-port-id-format {
             description "Format methods for building the NAS-Port-Id radius attribute";
             uses apply-advanced;
             leaf nas-identifier {
               description "Include the nas-identifier value";
               type empty;
             }
             leaf interface-description {
               description "Include the interface-description value";
               type empty;
             }
             leaf agent-circuit-id {
               description "Include (ACI) agent-circuit-id value";
               type empty;
             }
             leaf agent-remote-id {
               description "Include (ARI) agent-remote-id value";
               type empty;
             }
             leaf postpend-vlan-tags {
               description "Include the vlan tag(s) using :<outer>-<inner>";
               type empty;
             }
             leaf interface-text-description {
               description "Include the interfaces description string";
               type empty;
             }
             leaf-list concatenated-vlan-tags {
               ordered-by user;
               description "Include the vlan tag(s) as a concatenated string";
               type enumeration {
                 enum "fixed-size-outer-tag" {
                   description "Fixed size outer VLAN tag value of 4 octets";
                 }
                 enum "fixed-size-inner-tag" {
                   description "Fixed size inner VLAN tag value of 4 octets";
                 }
               }
             }
             leaf-list order {
               ordered-by user;
               description "Order of options for appearance in the NAS-Port-Id string";
               type enumeration {
                 enum "nas-identifier" {
                   description "Include the nas-identifier value";
                 }
                 enum "agent-circuit-id" {
                   description "Include (ACI) agent-circuit-id value";
                 }
                 enum "agent-remote-id" {
                   description "Include (ARI) agent-remote-id value";
                 }
                 enum "interface-description" {
                   description "Include the interface-description value";
                 }
                 enum "interface-text-description" {
                   description "Include the interface's description string";
                 }
                 enum "postpend-vlan-tags" {
                   description "Include the vlan tag(s) using :<outer>-<inner>";
                 }
               }
             }
           }
           container nas-port-type {
             description "Translation mechanism for changing the NAS-Port-Type radius attribute";
             uses apply-advanced;
             leaf ethernet {
               description "Translation mechanism for changing the Ethernet value";
               type string;
             }
           }
           leaf calling-station-id-delimiter {
             description "Single character separator for calling-station-id";
             type string {
               length 1;
             }
           }
           container calling-station-id-format {
             description "Format method for building the calling-station-id";
             uses apply-advanced;
             leaf nas-identifier {
               description "Include the nas-identifier value";
               type empty;
             }
             leaf interface-description {
               description "Include the interface-description value";
               type empty;
             }
             leaf agent-circuit-id {
               description "Include agent-circuit-id value";
               type empty;
             }
             leaf agent-remote-id {
               description "Include agent-remote-id value";
               type empty;
             }
             leaf mac-address {
               description "Include mac-address value";
               type empty;
             }
             leaf interface-text-description {
               description "Include the interfaces description string";
               type empty;
             }
             leaf stacked-vlan {
               description "Include the stacked vlan tag value";
               type empty;
             }
             leaf vlan {
               description "Include the vlan tag value";
               type empty;
             }
           }
           leaf remote-circuit-id-delimiter {
             description "Single delimiter character to use in the remote-circuit-id";
             type string {
               length 1;
             }
           }
           container remote-circuit-id-format {
             description "Format method for building the remote-circuit-id attribute";
             uses apply-advanced;
             leaf agent-circuit-id {
               description "Include agent-circuit-id (ACI) value";
               type empty;
             }
             leaf agent-remote-id {
               description "Include agent-remote-id (ARI) value";
               type empty;
             }
           }
           leaf remote-circuit-id-fallback {
             description "Configure the fallback for remote-circuit-id attribute";
             type enumeration {
               enum "default" {
                 description "Fallback to default underlying-interface";
               }
               enum "configured-calling-station-id" {
                 description "Fallback to configured calling-station-id";
               }
             }
           }
           container override {
             description "Configure RADIUS to override the standard use of an attribute";
             uses apply-advanced;
             container calling-station-id {
               description "Configure RADIUS value for calling-station-id attribute";
               leaf remote-circuit-id {
                 description "Configure RADIUS to use remote-circuit-id";
                 type empty;
               }
             }
             leaf nas-port {
               description "Configure override RADIUS nas-port with";
               type enumeration {
                 enum "tunnel-client-nas-port" {
                   description "Tunnel-client-nas-port";
                 }
               }
             }
             leaf nas-port-type {
               description "Configure override RADIUS nas-port-type with";
               type enumeration {
                 enum "tunnel-client-nas-port-type" {
                   description "Tunnel-client-nas-port-type";
                 }
               }
             }
             leaf nas-ip-address {
               description "Configure override RADIUS nas-ip-address with";
               type enumeration {
                 enum "tunnel-client-gateway-address" {
                   description "Tunnel-client-gateway-address";
                 }
               }
             }
           }
           leaf accounting-session-id-format {
             description "Decimal format or description format for the accounting session ID";
             type enumeration {
               enum "decimal" {
                 description "Decimal-session-identifier";
               }
               enum "description" {
                 description "Description Format: <jnpr> <interface-type> <interface-specifier>:<session-identifier>";
               }
             }
           }
           leaf accounting-session-id-strict {
             description "Enforce exact match of accounting-session-id in CoA processing";
             type empty;
           }
           leaf revert-interval {
             description "Time after which to revert to primary server";
             units "seconds";
             type union {
               type string {
                 pattern "<.*>|$.*";
               }
               type uint32 {
                 range "0 .. 604800";
               }
             }
           }
           leaf vlan-nas-port-stacked-format {
             description "Include the S-VLAN ID, in addition to the VLAN ID, for subscribers on Ethernet interfaces";
             type empty;
           }
           leaf client-authentication-algorithm {
             description "Algorithm to access the RADIUS servers for authentication";
             type enumeration {
               enum "direct" {
                 description "Contacts the first AAA server on the list for each request, the second AAA server if the first one fails, and so on";
               }
               enum "round-robin" {
                 description "Contacts the first AAA server for the first request, the second AAA server for the second request, and so on";
               }
             }
           }
           leaf client-accounting-algorithm {
             description "Algorithm to access the RADIUS servers for accounting";
             type enumeration {
               enum "direct" {
                 description "Contacts the first AAA server on the list for each request, the second AAA server if the first one fails, and so on";
               }
               enum "round-robin" {
                 description "Contacts the first AAA server for the first request, the second AAA server for the second request, and so on";
               }
             }
           }
           leaf juniper-access-line-attributes {
             description "Include the Juniper (IANA 4874) access line VSAs in requests to RADIUS servers";
             type empty;
           }
           container ip-address-change-notify {
             presence "enable ip-address-change-notify";
             description "Include IPv4-Release-Control VSA (26-164) in requests to RADIUS server";
             leaf message {
               description "Message to be added in IPv4-Release-Control VSA (26-164)";
               type string {
                 length "1 .. 32";
               }
             }
           }
           leaf coa-dynamic-variable-validation {
             description "Enable strict dynamic variable validation (no undefined variable) in CoA processing";
             type empty;
           }
           leaf chap-challenge-in-request-authenticator {
             description "Use 16-byte CHAP challenge as Request Authenticator";
             type empty;
           }
           container service-activation {
             description "Service activation requirement for successful login";
             uses apply-advanced;
             leaf extensible-service {
               description "Service activation of extensible services requirement for successful login";
               default "optional-at-login";
               type enumeration {
                 enum "required-at-login" {
                   description "Service activation must succeed to allow subscriber login";
                 }
                 enum "optional-at-login" {
                   description "Service activation success is not required to allow subscriber login";
                 }
               }
             }
             leaf dynamic-profile {
               description "Service activation of dynamic-profile services requirement for successful login";
               default "required-at-login";
               type enumeration {
                 enum "required-at-login" {
                   description "Service activation must succeed to allow subscriber login";
                 }
                 enum "optional-at-login" {
                   description "Service activation success is not required to allow subscriber login";
                 }
               }
             }
           }
           leaf accounting-username-original {
             description "Use orignal (un-modified) username in accounting messages";
             type empty;
           }
         }
         container attributes {
           description "Specifies how RADIUS attributes should be handled";
           uses apply-advanced;
           container ignore {
             description "Ignores the specified attribute in RADIUS Access-Accept messages";
             uses apply-advanced;
             leaf output-filter {
               description "Juniper (IANA 4874) Output-filter / Egress-Policy-Name (VSA 26-11)";
               type empty;
             }
             leaf input-filter {
               description "Juniper (IANA 4874) Input-filter / Ingress-Policy-Name (VSA 26-10)";
               type empty;
             }
             leaf framed-ip-netmask {
               description "Framed-IP-Netmask (attribute 9)";
               type empty;
             }
             leaf logical-system-routing-instance {
               description "Juniper (IANA 4874) Logical-system-routing-instance / Virtual-Router (VSA 26-1)";
               type empty;
             }
             leaf dynamic-iflset-name {
               description "Juniper (IANA 4874) Dynamic interface set / Qos-Set-Name (VSA 26-130)";
               type empty;
             }
             leaf idle-timeout {
               description "Idle-Timeout (attribute 28)";
               type empty;
             }
             leaf session-timeout {
               description "Session-Timeout (attribute 27)";
               type empty;
             }
             leaf-list standard-attribute {
               ordered-by user;
               description "RADIUS standard attribute number";
               type union {
                 type string {
                   pattern "<.*>|$.*";
                 }
                 type uint32 {
                   range "1 .. 255";
                 }
               }
             }
             list vendor-id {
               key name;
               ordered-by user;
               description "Specify the vendor-identifier for a vendor-specific attribute (VSA)";
               leaf name {
                 description "Vendor IANA enterprise number";
                 type union {
                   type string {
                     pattern "<.*>|$.*";
                   }
                   type uint32 {
                     range "1 .. 16777215";
                   }
                 }
               }
               uses apply-advanced;
               leaf-list vendor-attribute {
                 ordered-by user;
                 description "Vendor specific attribute number";
                 type union {
                   type string {
                     pattern "<.*>|$.*";
                   }
                   type uint32 {
                     range "1 .. 255";
                   }
                 }
               }
             }
           }
           container exclude {
             description "Configures the exclusion of RADIUS attributes in RADIUS messages";
             uses apply-advanced;
             list standard-attribute {
               key name;
               ordered-by user;
               description "Specify RADIUS standard attribute number";
               leaf name {
                 description "RADIUS standard attribute number";
                 type union {
                   type string {
                     pattern "<.*>|$.*";
                   }
                   type uint32 {
                     range "1 .. 255";
                   }
                 }
               }
               uses apply-advanced;
               leaf-list packet-type {
                 ordered-by user;
                 description "Specify packet types to be excluded";
                 type enumeration {
                   enum "access-request" {
                     description "RADIUS Access-Request message";
                   }
                   enum "accounting-on" {
                     description "RADIUS Accounting-On Message";
                   }
                   enum "accounting-off" {
                     description "RADIUS Accounting-Off message";
                   }
                   enum "accounting-start" {
                     description "RADIUS Accounting-Start message";
                   }
                   enum "accounting-stop" {
                     description "RADIUS Accounting-Stop message";
                   }
                 }
               }
             }
             list vendor-id {
               key name;
               ordered-by user;
               description "Specify the vendor-identifier for a vendor-specific attribute (VSA)";
               leaf name {
                 description "Vendor IANA enterprise number";
                 type union {
                   type string {
                     pattern "<.*>|$.*";
                   }
                   type uint32 {
                     range "1 .. 16777215";
                   }
                 }
               }
               uses apply-advanced;
               list vendor-attribute {
                 key name;
                 ordered-by user;
                 description "Specify vendor specific attribute number";
                 leaf name {
                   description "Vendor specific attribute number";
                   type union {
                     type string {
                       pattern "<.*>|$.*";
                     }
                     type uint32 {
                       range "1 .. 255";
                     }
                   }
                 }
                 uses apply-advanced;
                 leaf-list packet-type {
                   ordered-by user;
                   description "Specify packet types to be excluded";
                   type enumeration {
                     enum "access-request" {
                       description "RADIUS Access-Request message";
                     }
                     enum "accounting-on" {
                       description "RADIUS Accounting-On Message";
                     }
                     enum "accounting-off" {
                       description "RADIUS Accounting-Off message";
                     }
                     enum "accounting-start" {
                       description "RADIUS Accounting-Start message";
                     }
                     enum "accounting-stop" {
                       description "RADIUS Accounting-Stop message";
                     }
                   }
                 }
               }
             }
             leaf-list accounting-authentic {
               ordered-by user;
               description "Excludes RADIUS attribute 45, Acct-Authentic";
               type enumeration {
                 enum "accounting-on" {
                   description "RADIUS Accounting-On Message";
                 }
                 enum "accounting-off" {
                   description "RADIUS Accounting-Off message";
                 }
                 enum "accounting-start" {
                   description "RADIUS Accounting-Start message";
                 }
                 enum "accounting-stop" {
                   description "RADIUS Accounting-Stop message";
                 }
               }
             }
             leaf-list accounting-delay-time {
               ordered-by user;
               description "Excludes RADIUS attribute 41, Acct-Delay-Time";
               type enumeration {
                 enum "accounting-on" {
                   description "RADIUS Accounting-On Message";
                 }
                 enum "accounting-off" {
                   description "RADIUS Accounting-Off message";
                 }
                 enum "accounting-start" {
                   description "RADIUS Accounting-Start message";
                 }
                 enum "accounting-stop" {
                   description "RADIUS Accounting-Stop message";
                 }
               }
             }
             leaf-list accounting-session-id {
               ordered-by user;
               description "Excludes RADIUS attribute 44, Acct-Session-ID";
               type enumeration {
                 enum "access-request" {
                   description "RADIUS Access-Request message";
                 }
               }
             }
             leaf-list accounting-terminate-cause {
               ordered-by user;
               description "Excludes RADIUS attribute 49, Acct-Terminate-Cause";
               type enumeration {
                 enum "accounting-off" {
                   description "RADIUS Accounting-Off message";
                 }
               }
             }
             leaf-list called-station-id {
               ordered-by user;
               description "Excludes RADIUS attribute 30, Called-Station-ID";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list calling-station-id {
               ordered-by user;
               description "Excludes RADIUS attribute 31, Calling-Station-ID";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list class {
               ordered-by user;
               description "Excludes RADIUS attribute 25, Class";
               type enumeration {
                 enum "accounting-start" {
                   description "RADIUS Accounting-Start message";
                 }
                 enum "accounting-stop" {
                   description "RADIUS Accounting-Stop message";
                 }
               }
             }
             leaf-list delegated-ipv6-prefix {
               ordered-by user;
               description "Excludes RADIUS attribute 123, Delegated-IPv6-Prefix";
               type enumeration {
                 enum "accounting-start" {
                   description "RADIUS Accounting-Start message";
                 }
                 enum "accounting-stop" {
                   description "RADIUS Accounting-Stop message";
                 }
               }
             }
             leaf-list dhcp-options {
               ordered-by user;
               description "Excludes RADIUS attribute 26-55, DHCP-Options";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dhcp-gi-address {
               ordered-by user;
               description "Excludes RADIUS attribute 26-57, DHCP-GI-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dhcp-mac-address {
               ordered-by user;
               description "Excludes RADIUS attribute 26-56, DHCP-MAC-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list output-filter {
               ordered-by user;
               description "Excludes RADIUS attribute 26-11, Egress-Policy-Name";
               type enumeration {
                 enum "accounting-start" {
                   description "RADIUS Accounting-Start message";
                 }
                 enum "accounting-stop" {
                   description "RADIUS Accounting-Stop message";
                 }
               }
             }
             leaf-list event-time-stamp {
               ordered-by user;
               description "Excludes RADIUS attribute 55, Event-Timestamp";
               type enumeration {
                 enum "accounting-on" {
                   description "RADIUS Accounting-On Message";
                 }
                 enum "accounting-off" {
                   description "RADIUS Accounting-Off message";
                 }
                 enum "accounting-start" {
                   description "RADIUS Accounting-Start message";
                 }
                 enum "accounting-stop" {
                   description "RADIUS Accounting-Stop message";
                 }
               }
             }
             leaf-list filter-id {
               ordered-by user;
               description "Excludes RADIUS attribute 11, Filter-Id";
               type enumeration {
                 enum "accounting-start" {
                   description "RADIUS Accounting-Start message";
                 }
                 enum "accounting-stop" {
                   description "RADIUS Accounting-Stop message";
                 }
               }
             }
             leaf-list framed-ip-address {
               ordered-by user;
               description "Excludes RADIUS attribute 8, Framed-IP-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list framed-ip-netmask {
               ordered-by user;
               description "Excludes RADIUS attribute 9, Framed-IP-Netmask";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list framed-ip-route {
               ordered-by user;
               description "Excludes RADIUS attribute 22, Framed-Route";
               type enumeration {
                 enum "accounting-start" {
                   description "RADIUS Accounting-Start message";
                 }
                 enum "accounting-stop" {
                   description "RADIUS Accounting-Stop message";
                 }
               }
             }
             leaf-list framed-ipv6-address {
               ordered-by user;
               description "Excludes RADIUS attribute 168, Framed-IPV6-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list framed-ipv6-pool {
               ordered-by user;
               description "Excludes RADIUS attribute 100, Framed-IPv6-Pool";
               type enumeration {
                 enum "accounting-start" {
                   description "RADIUS Accounting-Start message";
                 }
                 enum "accounting-stop" {
                   description "RADIUS Accounting-Stop message";
                 }
               }
             }
             leaf-list framed-ipv6-prefix {
               ordered-by user;
               description "Excludes RADIUS attribute 97, Framed-IPv6-Prefix";
               type enumeration {
                 enum "accounting-start" {
                   description "RADIUS Accounting-Start message";
                 }
                 enum "accounting-stop" {
                   description "RADIUS Accounting-Stop message";
                 }
               }
             }
             leaf-list framed-ipv6-route {
               ordered-by user;
               description "Excludes RADIUS attribute 99, Framed-IPv6-Route";
               type enumeration {
                 enum "accounting-start" {
                   description "RADIUS Accounting-Start message";
                 }
                 enum "accounting-stop" {
                   description "RADIUS Accounting-Stop message";
                 }
               }
             }
             leaf-list framed-pool {
               ordered-by user;
               description "Excludes RADIUS attribute 88, Framed-Pool";
               type enumeration {
                 enum "accounting-start" {
                   description "RADIUS Accounting-Start message";
                 }
                 enum "accounting-stop" {
                   description "RADIUS Accounting-Stop message";
                 }
               }
             }
             leaf-list input-filter {
               ordered-by user;
               description "Excludes RADIUS attribute 26-10, Ingress-Policy-Name";
               type enumeration {
                 enum "accounting-start" {
                   description "RADIUS Accounting-Start message";
                 }
                 enum "accounting-stop" {
                   description "RADIUS Accounting-Stop message";
                 }
               }
             }
             leaf-list input-gigapackets {
               ordered-by user;
               description "Excludes Juniper (IANA 4874) VSA  26-42, Acct-Input-Gigapackets";
               type enumeration {
                 enum "accounting-stop" {
                   description "RADIUS Accounting-Stop message";
                 }
               }
             }
             leaf-list input-gigawords {
               ordered-by user;
               description "Excludes RADIUS attribute 52, Acct-Input-Gigawords";
               type enumeration {
                 enum "accounting-stop" {
                   description "RADIUS Accounting-Stop message";
                 }
               }
             }
             leaf-list input-ipv6-packets {
               ordered-by user;
               description "Excludes Juniper (IANA 4874) VSA  26-153, Acct-Input-IPv6-Packets";
               type enumeration {
                 enum "accounting-stop" {
                   description "RADIUS Accounting-Stop message";
                 }
               }
             }
             leaf-list input-ipv6-gigawords {
               ordered-by user;
               description "Excludes Juniper (IANA 4874) VSA  26-155, Acct-Input-IPv6-Gigawords";
               type enumeration {
                 enum "accounting-stop" {
                   description "RADIUS Accounting-Stop message";
                 }
               }
             }
             leaf-list input-ipv6-octets {
               ordered-by user;
               description "Excludes Juniper (IANA 4874) VSA  26-151, Acct-Input-IPv6-Octets";
               type enumeration {
                 enum "accounting-stop" {
                   description "RADIUS Accounting-Stop message";
                 }
               }
             }
             leaf-list interface-description {
               ordered-by user;
               description "Excludes RADIUS attribute 26-63, Interface-Desc";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list nas-identifier {
               ordered-by user;
               description "Excludes RADIUS attribute 32, NAS-identifier";
               type enumeration {
                 enum "access-request" {
                   description "RADIUS Access-Request message";
                 }
                 enum "accounting-on" {
                   description "RADIUS Accounting-On Message";
                 }
                 enum "accounting-off" {
                   description "RADIUS Accounting-Off message";
                 }
                 enum "accounting-start" {
                   description "RADIUS Accounting-Start message";
                 }
                 enum "accounting-stop" {
                   description "RADIUS Accounting-Stop message";
                 }
               }
             }
             leaf-list nas-port {
               ordered-by user;
               description "Excludes RADIUS attribute 5, NAS-Port";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list nas-port-id {
               ordered-by user;
               description "Excludes RADIUS attribute 87, NAS-Port-ID";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list nas-port-type {
               ordered-by user;
               description "Excludes RADIUS attribute 61, NAS-Port-Type";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list output-gigapackets {
               ordered-by user;
               description "Excludes Juniper (IANA 4874) VSA  26-43, Acct-Output-Gigapackets";
               type enumeration {
                 enum "accounting-stop" {
                   description "RADIUS Accounting-Stop message";
                 }
               }
             }
             leaf-list output-gigawords {
               ordered-by user;
               description "Excludes RADIUS attribute 53, Acct-Output-Gigawords";
               type enumeration {
                 enum "accounting-stop" {
                   description "RADIUS Accounting-Stop message";
                 }
               }
             }
             leaf-list output-ipv6-packets {
               ordered-by user;
               description "Excludes Juniper (IANA 4874) VSA  26-154, Acct-Output-IPv6-Packets";
               type enumeration {
                 enum "accounting-stop" {
                   description "RADIUS Accounting-Stop message";
                 }
               }
             }
             leaf-list output-ipv6-gigawords {
               ordered-by user;
               description "Excludes Juniper (IANA 4874) VSA  26-156, Acct-Output-IPv6-Gigawords";
               type enumeration {
                 enum "accounting-stop" {
                   description "RADIUS Accounting-Stop message";
                 }
               }
             }
             leaf-list output-ipv6-octets {
               ordered-by user;
               description "Excludes Juniper (IANA 4874) VSA  26-152, Acct-Output-IPv6-Octets";
               type enumeration {
                 enum "accounting-stop" {
                   description "RADIUS Accounting-Stop message";
                 }
               }
             }
             leaf-list dynamic-iflset-name {
               ordered-by user;
               description "Excludes RADIUS attribute 26-130, Dynamic-Iflset-Name";
               type enumeration {
                 enum "accounting-start" {
                   description "RADIUS Accounting-Start message";
                 }
                 enum "accounting-stop" {
                   description "RADIUS Accounting-Stop message";
                 }
               }
             }
             leaf-list dsl-forum-attributes {
               ordered-by user;
               description "Excludes DSL Forum RADIUS attributes (RFC 4679)";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list l2c-upstream-data {
               ordered-by user;
               description "Excludes Juniper (IANA 4874) DSL VSA 26-92, L2C-Upstream-Data";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list l2c-downstream-data {
               ordered-by user;
               description "Excludes Juniper (IANA 4874) DSL VSA 26-93, L2C-Downstream-Data";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acc-loop-cir-id {
               ordered-by user;
               description "Excludes Juniper (IANA 4874) DSL VSA 26-110, Acc-Loop-Cir-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acc-aggr-cir-id-bin {
               ordered-by user;
               description "Excludes Juniper (IANA 4874) DSL VSA 26-111, Acc-Aggr-Cir-Id-Bin";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acc-aggr-cir-id-asc {
               ordered-by user;
               description "Excludes Juniper (IANA 4874) DSL VSA 26-112, Acc-Aggr-Cir-Id-Asc";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list act-data-rate-up {
               ordered-by user;
               description "Excludes Juniper (IANA 4874) DSL VSA 26-113, Act-Data-Rate-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list act-data-rate-dn {
               ordered-by user;
               description "Excludes Juniper (IANA 4874) DSL VSA 26-114, Act-Data-Rate-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list min-data-rate-up {
               ordered-by user;
               description "Excludes Juniper (IANA 4874) DSL VSA 26-115, Min-Data-Rate-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list min-data-rate-dn {
               ordered-by user;
               description "Excludes Juniper (IANA 4874) DSL VSA 26-116, Min-Data-Rate-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list att-data-rate-up {
               ordered-by user;
               description "Excludes Juniper (IANA 4874) DSL VSA 26-117, Att-Data-Rate-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list att-data-rate-dn {
               ordered-by user;
               description "Excludes Juniper (IANA 4874) DSL VSA 26-118, Att-Data-Rate-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list max-data-rate-up {
               ordered-by user;
               description "Excludes Juniper (IANA 4874) DSL VSA 26-119, Max-Data-Rate-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list max-data-rate-dn {
               ordered-by user;
               description "Excludes Juniper (IANA 4874) DSL VSA 26-120, Max-Data-Rate-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list min-lp-data-rate-up {
               ordered-by user;
               description "Excludes Juniper (IANA 4874) DSL VSA 26-121, Min-Lp-Data-Rate-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list min-lp-data-rate-dn {
               ordered-by user;
               description "Excludes Juniper (IANA 4874) DSL VSA 26-122, Min-Lp-Data-Rate-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list max-interlv-delay-up {
               ordered-by user;
               description "Excludes Juniper (IANA 4874) DSL VSA 26-123, Max-Interlv-Delay-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list act-interlv-delay-up {
               ordered-by user;
               description "Excludes Juniper (IANA 4874) DSL VSA 26-124, Act-Interlv-Delay-Up";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list max-interlv-delay-dn {
               ordered-by user;
               description "Excludes Juniper (IANA 4874) DSL VSA 26-125, Max-Interlv-Delay-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list act-interlv-delay-dn {
               ordered-by user;
               description "Excludes Juniper (IANA 4874) DSL VSA 26-126, Act-Interlv-Delay-Dn";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dsl-line-state {
               ordered-by user;
               description "Excludes Juniper (IANA 4874) DSL VSA 26-127, DSL-Line-State";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dsl-type {
               ordered-by user;
               description "Excludes Juniper (IANA 4874) DSL VSA 26-128, DSL-Type";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list downstream-calculated-qos-rate {
               ordered-by user;
               description "Excludes Juniper (IANA 4874) DSL VSA 26-141, Downstream-Calculated-QoS-Rate";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list upstream-calculated-qos-rate {
               ordered-by user;
               description "Excludes Juniper (IANA 4874) DSL VSA 26-142, Upstream-Calculated-QoS-Rate";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list cos-shaping-rate {
               ordered-by user;
               description "Excludes Juniper (IANA 4874) VSA 26-177, Cos-Shaping-Rate";
               type enumeration {
                 enum "accounting-start" {
                   description "RADIUS Accounting-Start message";
                 }
                 enum "accounting-stop" {
                   description "RADIUS Accounting-Stop message";
                 }
               }
             }
             leaf-list framed-interface-id {
               ordered-by user;
               description "Excludes RADIUS attribute 96, Framed-Interface-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list chargeable-user-identity {
               ordered-by user;
               description "Excludes RADIUS attribute 89, Chargeable-User-Identity";
               type enumeration {
                 enum "access-request" {
                   description "RADIUS Access-Request message";
                 }
               }
             }
             leaf-list l2tp-tx-connect-speed {
               ordered-by user;
               description "Excludes Juniper (IANA 4874) VSA 26-162, , L2TP-Tx-Connect-Speed";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list l2tp-rx-connect-speed {
               ordered-by user;
               description "Excludes Juniper (IANA 4874) VSA 26-163, , L2TP-Rx-Connect-Speed";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-type {
               ordered-by user;
               description "Excludes RADIUS attribute 64, Tunnel-Type";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-medium-type {
               ordered-by user;
               description "Excludes RADIUS attribute 65, Tunnel-Medium-Type";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-client-endpoint {
               ordered-by user;
               description "Excludes RADIUS attribute 66, Tunnel-Client-Endpoint";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-server-endpoint {
               ordered-by user;
               description "Excludes RADIUS attribute 67, Tunnel-Server-Endpoint";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-assignment-id {
               ordered-by user;
               description "Excludes RADIUS attribute 82, Tunnel-Assignment-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-client-auth-id {
               ordered-by user;
               description "Excludes RADIUS attribute 90, Tunnel-Client-Auth-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list tunnel-server-auth-id {
               ordered-by user;
               description "Excludes RADIUS attribute 91, Tunnel-Server-Auth-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acct-tunnel-connection {
               ordered-by user;
               description "Excludes RADIUS attribute 68, Acct-Tunnel-Connection";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acc-loop-remote-id {
               ordered-by user;
               description "Excludes Juniper (IANA 4874) VSA 26-XXX, ERX-Acc-Loop-Remote-Id";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list acc-loop-encap {
               ordered-by user;
               description "Excludes Juniper (IANA 4874) VSA 26-182, ERX-Acc-Loop-Encap";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list pppoe-description {
               ordered-by user;
               description "Excludes RADIUS attribute 26-24, PPPOE-Description";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list virtual-router {
               ordered-by user;
               description "Excludes Juniper (IANA 4874) VSA 26-1, Virtual-Router";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list first-relay-ipv4-address {
               ordered-by user;
               description "Excludes RADIUS attribute 26-189, DHCP-First-Relay-IPv4-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list first-relay-ipv6-address {
               ordered-by user;
               description "Excludes RADIUS attribute 26-190, DHCP-First-Relay-IPv6-Address";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dhcpv6-options {
               ordered-by user;
               description "Excludes RADIUS attribute 26-207, DHCPv6-Options";
               type enumeration {
                 enum "access-request" {
                   description "RADIUS Access-Request message";
                 }
                 enum "accounting-start" {
                   description "RADIUS Accounting-Start message";
                 }
                 enum "accounting-stop" {
                   description "RADIUS Accounting-Stop message";
                 }
               }
             }
             leaf-list dhcp-header {
               ordered-by user;
               description "Excludes RADIUS attribute 26-208, DHCP-Header";
               type enumeration {
                 enum "access-request" {
                   description "RADIUS Access-Request message";
                 }
               }
             }
             leaf-list dhcpv6-header {
               ordered-by user;
               description "Excludes RADIUS attribute 26-209, DHCPv6-Header";
               type enumeration {
                 enum "access-request" {
                   description "RADIUS Access-Request message";
                 }
               }
             }
             leaf-list acct-request-reason {
               ordered-by user;
               description "Excludes RADIUS attribute 26-210, Acct-Request-Reason";
               type enumeration {
                 enum "accounting-start" {
                   description "RADIUS Accounting-Start message";
                 }
                 enum "accounting-stop" {
                   description "RADIUS Accounting-Stop message";
                 }
               }
             }
           }
         }
       }
       container session-options {
         description "Options for an authenticated client's session";
         uses apply-advanced;
         leaf-list client-group {
           ordered-by user;
           description "One or more groups to which client belongs";
           type string;
         }
         leaf client-idle-timeout {
           description "Time in minutes of idleness after which access is denied";
           units "minutes";
           type union {
             type string {
               pattern "<.*>|$.*";
             }
             type uint32 {
               range "10 .. 1440";
             }
           }
         }
         leaf client-idle-timeout-ingress-only {
           description "Idle timeout applies to ingress traffic only";
           type empty;
         }
         leaf client-session-timeout {
           description "Time in minutes since initial access after which access is denied";
           units "minutes";
           type union {
             type string {
               pattern "<.*>|$.*";
             }
             type uint32 {
               range "1 .. 527040";
             }
           }
         }
         container strip-user-name {
           description "Options for stripping user name string";
           uses apply-advanced;
           container delimiter {
             description "Allowable delimiter characters for strip user name separation";
             leaf characters {
               description "Sequence of characters without spaces and commas";
               type string {
                 length "1 .. 8";
               }
             }
           }
           container parse-direction {
             description "Strip user name parsing direction";
             choice direction {
               case case_1 {
                 leaf right-to-left {
                   description "Parse the username from right to left";
                   type empty;
                 }
               }
               case case_2 {
                 leaf left-to-right {
                   description "Parse the username field from left to right";
                   type empty;
                 }
               }
             }
           }
         }
         container pcc-context {
           description "Pcc context configurations";
           uses apply-advanced;
           leaf pcef-profile {
             description "Pcef profile name";
             type string;
           }
           leaf input-service-set {
             description "Input service-set name";
             type string;
           }
           leaf output-service-set {
             description "Output service-set name";
             type string;
           }
           leaf input-ipv6-service-set {
             description "Input ipv6 service set name";
             type string;
           }
           leaf output-ipv6-service-set {
             description "Output ipv6 service set name";
             type string;
           }
           leaf input-service-filter {
             description "Input service filter name";
             type string;
           }
           leaf output-service-filter {
             description "Output service filter name";
             type string;
           }
           leaf input-ipv6-service-filter {
             description "Input ipv6 service filter name";
             type string;
           }
           leaf output-ipv6-service-filter {
             description "Output ipv6 service filter name";
             type string;
           }
         }
       }
       container client-name-filter {
         description "Restrictions on client names";
         uses access-client-name-filter-object;
       }
       container ldap-options {
         description "Lightweight Directory Access Protocol options";
         uses access-ldap-options;
       }
       list ldap-server {
         key name;
         ordered-by user;
         description "Lightweight Directory Access Protocol server";
         uses ldap-server-object;
       }
       list radius-server {
         key name;
         ordered-by user;
         description "RADIUS server configuration";
         uses profile-radius-server-object;
       }
       list radius-server-name {
         key name;
         ordered-by user;
         description "RADIUS server FQDN configuration";
         uses profile-radius-server-name-object;
       }
       container radius-options {
         description "RADIUS options";
         uses access-radius-options;
       }
       container accounting {
         description "Specifies the accounting options";
         uses apply-advanced;
         leaf-list order {
           ordered-by user;
           description "Order in which accounting mechanisms are used";
           type enumeration {
             enum "radius" {
               description "Remote authentication dial-in user service";
             }
           }
         }
         leaf accounting-stop-on-failure {
           description "Send an Acct-Stop message if a user fails authentication, but AAA-server grants access";
           type empty;
         }
         leaf accounting-stop-on-access-deny {
           description "Send an Acct-Stop message if AAA-server denies access";
           type empty;
         }
         leaf immediate-update {
           description "Send an Acct-Update message on receipt of a Acct-response for the Acct-Start message";
           type empty;
         }
         leaf coa-immediate-update {
           description "Send an Acct-Update message on completion of processing a change of authorization";
           type empty;
         }
         leaf address-change-immediate-update {
           description "Send an Acct-Update message to notify address change";
           type empty;
         }
         leaf update-interval {
           description "The interval in min btw accounting updates(Interim-stats off,if unspecified)";
           units "minutes";
           type union {
             type string {
               pattern "<.*>|$.*";
             }
             type uint32 {
               range "10 .. 1440";
             }
           }
         }
         leaf statistics {
           description "Reports set of statistics attributes based on reporting type";
           type enumeration {
             enum "volume-time" {
               description "Configures the option to report both volume and uptime";
             }
             enum "time" {
               description "Configures the option to report only uptime";
             }
           }
         }
         leaf wait-for-acct-on-ack {
           description "Wait for ACCT-ON-ACK";
           type empty;
         }
         leaf send-acct-status-on-config-change {
           description "Send ACCT-ON/OFF on config change";
           type empty;
         }
         leaf duplication {
           description "Send duplicated accounting reports if applied";
           type empty;
         }
         leaf-list duplication-filter {
           ordered-by user;
           description "Configure duplication filters";
           type enumeration {
             enum "interim-original" {
               description "Do not send original accounting interims";
             }
             enum "interim-duplicated" {
               description "Do not send duplicated accounting interims";
             }
             enum "exclude-attributes" {
               description "Use duplication access profile exclude attributes";
             }
           }
         }
         container duplication-vrf {
           description "Duplication vrf configurations";
           uses apply-advanced;
           leaf vrf-name {
             description "VRF name";
             type string {
               length "1 .. 257";
             }
           }
           leaf-list access-profile-name {
             ordered-by user;
             description "Access profile name";
             type string {
               length "1 .. 63";
             }
             max-elements 5;
           }
         }
         leaf-list duplication-attribute-format {
           ordered-by user;
           description "Use attribute format defined under duplication accouting access-profile";
           type enumeration {
             enum "username" {
               description "Username";
             }
           }
         }
         leaf ancp-speed-change-immediate-update {
           description "Send an Acct-Update message when ANCP speed change is detected";
           type empty;
         }
         leaf family-state-change-immediate-update {
           description "Send an Acct-Update message to notify address family activation state change";
           type empty;
         }
       }
       container service {
         description "Subscriber service configurations";
         uses apply-advanced;
         leaf accounting-order {
           description "Order in which accounting mechanism service is used";
           type enumeration {
             enum "activation-protocol" {
               description "Send service accounting reports via service activation protocol";
             }
             enum "radius" {
               description "Send service accounting reports via radius protocol";
             }
             enum "local" {
               description "Send service accounting for local reporting - obsolete config";
             }
           }
         }
         container accounting {
           description "Specifies the service accounting options";
           uses apply-advanced;
           leaf update-interval {
             description "The interval in minutes between accounting updates(Interim-stats off, if not specified)";
             units "minutes";
             type union {
               type string {
                 pattern "<.*>|$.*";
               }
               type uint32 {
                 range "10 .. 1440";
               }
             }
           }
           leaf statistics {
             description "Reports set of statistics attributes based on reporting type";
             type enumeration {
               enum "time" {
                 description "Configures the option to report only uptime";
               }
               enum "volume-time" {
                 description "Configures the option to report both volume and uptime";
               }
             }
           }
         }
       }
       container jsrc {
         description "Set of JSRC configurations";
         uses apply-advanced;
         container attributes {
           description "Specifies how JSRC attributes should be handled";
           uses apply-advanced;
           container exclude {
             description "Configures the exclusion of JSRC attributes in DIAMETER messages";
             uses apply-advanced;
             leaf-list user-name {
               ordered-by user;
               description "Excludes Diameter attribute 1, User-Name";
               type enumeration {
                 enum "authorization-request" {
                   description "Authorization AA-Request message";
                 }
                 enum "provisioning-request" {
                   description "Provisioning AA-Request message";
                 }
               }
             }
           }
         }
       }
       list subscriber {
         key name;
         description "Locally authenticated subscriber configuration";
         uses localauth-subscriber-object;
       }
     }
     container address-assignment {
       description "Address assignment configuration";
       uses address-assignment-type;
     }
     container address-protection {
       presence "enable address-protection";
       description "Initiate Duplicate Address Protection";
       uses apply-advanced;
       leaf reassign-on-match {
         description "Disconnect owning session and reassign to this session";
         type empty;
       }
     }
     container address-preservation {
       description "Enable address preservation";
       uses apply-advanced;
       leaf address-types {
         description "Address preservation address types";
         type enumeration {
           enum "delegated-prefix" {
             description "Address preservation delegated prefix";
           }
         }
       }
       leaf aging-time {
         description "Time to hold address reservation";
         default "86400";
         units "seconds";
         type union {
           type string {
             pattern "<.*>|$.*";
           }
           type uint32 {
             range "3600 .. 604800";
           }
         }
       }
     }
     leaf linked-pool-aggregation {
       description "Enable linked pools aggregation";
       type empty;
     }
     list tunnel-profile {
       key name;
       ordered-by user;
       description "Set of attributes that define tunnel access";
       leaf name {
         description "Tunnel profile name";
         type string {
           length "1 .. 63";
         }
       }
       uses apply-advanced;
       list tunnel {
         key name;
         ordered-by user;
         description "Tunnel id 1 to 31";
         leaf name {
           description "Tunnel indicator";
           type union {
             type string {
               pattern "<.*>|$.*";
             }
             type int32 {
               range "1 .. 31";
             }
           }
         }
         uses apply-advanced;
         leaf preference {
           description "Preference value";
           default "2000";
           type union {
             type string {
               pattern "<.*>|$.*";
             }
             type uint32 {
               range "0 .. 2000";
             }
           }
         }
         container remote-gateway {
           description "Tunnel remote gateway";
           uses apply-advanced;
           leaf address {
             description "IP address";
             type jt:ipv4addr;
           }
           leaf gateway-name {
             description "Gateway name";
             type string;
           }
         }
         container source-gateway {
           description "Tunnel source gateway";
           uses apply-advanced;
           leaf address {
             description "IP address";
             type jt:ipv4addr;
           }
           leaf gateway-name {
             description "Tunnel source name";
             type string;
           }
         }
         choice ri_or_ls {
           case case_1 {
             leaf routing-instance {
               description "Routing instance to be used for tunneled subscriber";
               type string;
             }
           }
           case case_2 {
             list logical-system {
               key name;
               ordered-by user;
               description "Logical system to be used for tunneled subscriber";
               max-elements 1;
               leaf name {
                 description "Logical system name";
                 type string;
               }
               uses apply-advanced;
               leaf routing-instance {
                 description "Routing instance to be used for tunneled subscriber";
                 type string;
               }
             }
           }
         }
         leaf secret {
           description "Tunnel password sent to remote gateway";
           type string {
             length "1 .. 64";
           }
         }
         leaf medium {
           description "Tunnel medium";
           default "ipv4";
           type enumeration {
             enum "ipv4" {
               description "Internet protocol version 4";
             }
           }
         }
         leaf tunnel-type {
           description "Tunnel type";
           default "l2tp";
           type enumeration {
             enum "l2tp" {
               description "Layer 2 tunnel protocol";
             }
           }
         }
         leaf identification {
           description "Tunnel assignment identification";
           type string;
         }
         leaf max-sessions {
           description "Maximum number of sessions per tunnel";
           default "0";
           type union {
             type string {
               pattern "<.*>|$.*";
             }
             type uint32 {
               range "0 .. 60000";
             }
           }
         }
         leaf nas-port-method {
           description "Tunnel network access server port method";
           type enumeration {
             enum "cisco-avp" {
               description "Limited Cisco vendor specific mechanism";
             }
           }
         }
       }
     }
     list tunnel-switch-profile {
       key name;
       ordered-by user;
       description "Tunnel switch profile name";
       leaf name {
         description "Tunnel switch profile name";
         type string {
           length "1 .. 63";
         }
       }
       uses apply-advanced;
       container avp {
         description "L2TP AVPs action configuration";
         uses apply-advanced;
         leaf calling-number {
           description "Action for L2TP AVP calling number";
           type enumeration {
             enum "regenerate" {
               description "Regenerate L2TP AVP";
             }
             enum "relay" {
               description "Relay L2TP AVP";
             }
             enum "drop" {
               description "Drop L2TP AVP";
             }
           }
         }
         leaf bearer-type {
           description "Action for L2TP AVP bearer type";
           type enumeration {
             enum "regenerate" {
               description "Regenerate L2TP AVP";
             }
             enum "relay" {
               description "Relay L2TP AVP";
             }
             enum "drop" {
               description "Drop L2TP AVP";
             }
           }
         }
         leaf cisco-nas-port-info {
           description "Action for L2TP AVP Cisco NAS port information";
           type enumeration {
             enum "regenerate" {
               description "Regenerate L2TP AVP";
             }
             enum "relay" {
               description "Relay L2TP AVP";
             }
             enum "drop" {
               description "Drop L2TP AVP";
             }
           }
         }
       }
       leaf tunnel-profile {
         description "Tunnel profile name";
         type string {
           length "1 .. 63";
         }
       }
     }
     container domain {
       description "Domain map configuration";
       uses domain-map-type;
     }
     container ppp-options {
       presence "enable ppp-options";
       description "Point-to-Point Protocol (PPP) specific options";
       uses apply-advanced;
       container compliance {
         description "Standards compliance definition";
         uses apply-advanced;
         leaf-list rfc {
           ordered-by user;
           description "Enforce compliance with RFC standards";
           type enumeration {
             enum "2486" {
               description "RFC 2486 compliant";
             }
           }
         }
       }
     }
     container gx-plus {
       description "GX-PLUS configuration";
       uses gx-plus-definition;
     }
     container pcrf {
       description "PCRF configuration";
       uses pcrf-definition;
     }
     container ocs {
       description "OCS configuration";
       uses ocs-definition;
     }
     container radsec {
       description "RADSEC configuration";
       uses radsec-definition;
     }
     container s6a {
       description "S6a configuration";
       uses s6a-definition;
     }
     leaf report-interface-descriptions {
       description "Support reporting of interface descriptions";
       type empty;
     }
     container nasreq {
       description "Nasreq configuration";
       uses nasreq-definition;
     }
     container nas-5g {
       description "NAS-5G configuration";
       uses nas-5g-definition;
     }
     list protocol-attributes {
       key name;
       ordered-by user;
       description "Protocol specific attribute configuration";
       uses protocol-attribute-type;
     }
     list aaa-options {
       key name;
       ordered-by user;
       description "AAA option configurations";
       leaf name {
         description "AAA options name";
         type string {
           length "1 .. 63";
         }
       }
       uses apply-advanced;
       leaf access-profile {
         description "Access profile name";
         type string {
           length "1 .. 63";
         }
       }
       leaf aaa-context {
         description "AAA context";
         type string;
       }
       leaf subscriber-context {
         description "Subscriber context";
         type string;
       }
     }
     leaf disable-tenant-access {
       description "Disable access to root lsys profiles for tenants";
       type empty;
     }
     container radius-options {
       description "RADIUS options";
       uses access-radius-options;
     }
     container ldap-options {
       description "Lightweight Directory Access Protocol options";
       uses access-ldap-options;
     }
     list ldap-server {
       key name;
       ordered-by user;
       description "Lightweight Directory Access Protocol server options";
       uses ldap-server-object;
     }
     list securid-server {
       key name;
       ordered-by user;
       description "SecurID server configuration";
       max-elements 1;
       uses securid-server-object;
     }
     container accounting-backup-options {
       description "Pending accounting backup-options ";
       uses apply-advanced;
       leaf max-pending-accounting-stops {
         description "Max pending accouting stops";
         type union {
           type string {
             pattern "<.*>|$.*";
           }
           type uint32 {
             range "1 .. 168000";
           }
         }
       }
       leaf max-withhold-time {
         description "Maximum time in mins to hold the pending accounting stops";
         units "minutes";
         type union {
           type string {
             pattern "<.*>|$.*";
           }
           type uint32 {
             range "60 .. 1440";
           }
         }
       }
     }
     container terminate-code {
       description "Terminate code mapping configuration";
       uses apply-advanced;
       container aaa {
         description "AAA terminate-code mapping configuration";
         uses apply-advanced;
         container deny {
           description "Terminate-code specification";
           uses apply-advanced;
           container authentication-denied {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-resources {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container server-request-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container service-shutdown {
           description "Terminate-code specification";
           uses apply-advanced;
           container network-logout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container remote-reset {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container subscriber-logout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container time-limit {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container volume-limit {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container shutdown {
           description "Terminate-code specification";
           uses apply-advanced;
           container administrative-reset {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container idle-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container reassign-on-match {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container remote-reset {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container session-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
       }
       container dhcp {
         description "DHCP terminate-code mapping configuration";
         uses apply-advanced;
         container client-request {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container lost-carrier {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container nak {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container nas-logout {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container no-offers {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
       }
       container hybrid-access {
         description "HYBRID-ACCESS terminate-code mapping configuration";
         uses apply-advanced;
         container admin-down {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container client-request {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container lost-carrier {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container nak {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container nas-logout {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container no-resource {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
       }
       container l2tp {
         description "L2TP terminate-code mapping configuration";
         uses apply-advanced;
         container issu {
           description "Terminate-code specification";
           uses apply-advanced;
           container in-progress {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container session {
           description "Terminate-code specification";
           uses apply-advanced;
           container access-interface-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container administrative-close {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container administrative-drain {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container call-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container call-failed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container create-failed {
             description "Terminate-code specification";
             uses apply-advanced;
             container icrq-to-initiator-tunnel {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container invalid-config {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container limit-reached {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container single-shot-tunnel-already-fired {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container too-busy {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container failover-protocol-resync-disconnect {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container hardware-unavailable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-resources-server-port {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container not-ready {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container receive-cdn {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-duplicate-value-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-result-code {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-iccn {
             description "Terminate-code specification";
             uses apply-advanced;
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-framing-type {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-proxy-authen-type {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-unsupported-proxy-authen-type {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-connect-speed {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-framing-type {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-proxy-authen-challenge {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-proxy-authen-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-proxy-authen-name {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-proxy-authen-response {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container unexpected {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-icrp {
             description "Terminate-code specification";
             uses apply-advanced;
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-duplicate-value-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container unexpected {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-icrq {
             description "Terminate-code specification";
             uses apply-advanced;
             container administrative-close {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container authenticate-failed-host {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-bearer-type {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-cisco-nas-port {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-duplicate-value-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-call-serial-number {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container unexpected {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-occn {
             description "Terminate-code specification";
             uses apply-advanced;
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-framing-type {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-connect-speed {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-framing-type {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container unexpected {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-ocrp {
             description "Terminate-code specification";
             uses apply-advanced;
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-duplicate-value-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container unexpected {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-ocrq {
             description "Terminate-code specification";
             uses apply-advanced;
             container administrative-close {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container authenticate-failed-host {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-bearer-type {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-framing-type {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-duplicate-value-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-bearer-type {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-call-serial-number {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-called-number {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-framing-type {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-maximum-bps {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-minimum-bps {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container unexpected {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container unsupported {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-sli {
             description "Terminate-code specification";
             uses apply-advanced;
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-accm {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-accm {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-unexpected-packet {
             description "Terminate-code specification";
             uses apply-advanced;
             container lac-incoming {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container lac-outgoing {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container lns-incoming {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container lns-outgoing {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-unknown-session-id {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container receive-wen {
             description "Terminate-code specification";
             uses apply-advanced;
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-call-errors {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container timeout-connection {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container timeout-inactivity {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container timeout-session {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container timeout-upper-create {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container transmit-speed-unavailable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container tunnel-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container tunnel-failed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container tunnel-switch-profile-deleted {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container tunneled-interface-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container unknown-cause {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container upper-create-failed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container upper-removed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container warmstart-not-operational {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container warmstart-recovery-error {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container warmstart-uppper-not-restacked {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container session-eracheck-failed {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container session-mappedswitchedsession-down {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container session-rx-csurq-avp-unknown {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container session-rx-icrq-issu-in-progress {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container session-rx-ocrq-issu-in-progress {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container session-sdb-release {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container session-stray-ifl-association {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container session-tunnelswitch-error {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container session-uptimer-expiry {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container tunnel {
           description "Terminate-code specification";
           uses apply-advanced;
           container administrative-close {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container administrative-drain {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container control-channel-failed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container created-no-sessions {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container destination-address-changed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container destination-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container failover-protocol {
             description "Terminate-code specification";
             uses apply-advanced;
             container no-resources-for-recovery-tunnel {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources-for-session-resync {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container not-supported {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container not-supported-by-peer {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container recovery-control-channel-failed {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container recovery-tunnel-failed {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container recovery-tunnel-finished {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container recovery-tunnel-primary-down {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container session-resync-failed {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container host-profile-changed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container host-profile-deleted {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container receive-fsq {
             description "Terminate-code specification";
             uses apply-advanced;
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-failover-session-state {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container session-id-not-null {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-fsr {
             description "Terminate-code specification";
             uses apply-advanced;
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-failover-session-state {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container session-id-not-null {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-recovery-scccn {
             description "Terminate-code specification";
             uses apply-advanced;
             container authenticate-failed-challenge {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-challenge-response {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-challenge-response {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unexpected-challenge-response {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container session-id-not-null {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-recovery-scccp {
             description "Terminate-code specification";
             uses apply-advanced;
             container avp-unexpected-challenge-response {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-recovery-scccp-avp-bad-value-challenge-response {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container receive-recovery-scccp-avp-missing-challenge-response {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container receive-recovery-sccrp {
             description "Terminate-code specification";
             uses apply-advanced;
             container authenticate-failed-challenge {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-bearer-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-challenge {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-framing-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-protocol-version {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-receive-window-size {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-suggested-control-sequence {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-duplicate-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-mismatched-host-name {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-mismatched-vendor-name {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-framing-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-host-name {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-protocol-version {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unexpected-challenge-without-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container session-id-not-null {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-recovery-sccrq {
             description "Terminate-code specification";
             uses apply-advanced;
             container administrative-close {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-bearer-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-challenge {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-framing-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-protocol-version {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-receive-window-size {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-tunnel {
               description "Terminate-code specification";
               uses apply-advanced;
               container recovery {
                 description "Terminate-code specification";
                 uses apply-advanced;
                 container radius {
                   description "Radius Acct-Terminate-Cause configuration";
                   leaf acct-terminate-cause {
                     description "Set value";
                     type union {
                       type string {
                         pattern "<.*>|$.*";
                       }
                       type uint32 {
                         range "1 .. 4294967295";
                       }
                     }
                   }
                 }
               }
             }
             container avp-duplicate-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-duplicate-value-tie-breaker {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-mismatched-host-name {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-mismatched-vendor-name {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-framing-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-host-name {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-protocol-version {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-tunnel {
               description "Terminate-code specification";
               uses apply-advanced;
               container recovery {
                 description "Terminate-code specification";
                 uses apply-advanced;
                 container radius {
                   description "Radius Acct-Terminate-Cause configuration";
                   leaf acct-terminate-cause {
                     description "Set value";
                     type union {
                       type string {
                         pattern "<.*>|$.*";
                       }
                       type uint32 {
                         range "1 .. 4294967295";
                       }
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-tie-breaker {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unexpected-challenge-without-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources-max-tunnels {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container session-id-not-null {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container tunnel-id-not-null {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-recovery-stopccn {
             description "Terminate-code specification";
             uses apply-advanced;
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-duplicate-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-result-code {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container session-id-not-null {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-recovery-unexpected-packet {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container receive-recovery-unknown-packet {
             description "Terminate-code specification";
             uses apply-advanced;
             container message-type-indecipherable {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container message-type-unrecognized {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-scccn {
             description "Terminate-code specification";
             uses apply-advanced;
             container authenticate-failed-challenge {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-challenge-response {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-challenge-response {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unexpected-challenge-response {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container session-id-not-null {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container unexpected {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-sccrp {
             description "Terminate-code specification";
             uses apply-advanced;
             container authenticate-failed-challenge {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container authenticate-failed-host {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-bearer-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-challenge {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-challenge-response {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-failover-capability {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-framing-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-protocol-version {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-receive-window-size {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-duplicate-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-challenge-response {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-framing-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-host-name {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-protocol-version {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unexpected-challenge-response {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unexpected-challenge-without-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container session-id-not-null {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container unexpected {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-sccrq {
             description "Terminate-code specification";
             uses apply-advanced;
             container administrative-close {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container authenticate-failed-host {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-bearer-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-challenge {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-failover-capability {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-framing-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-protocol-version {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-receive-window-size {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-duplicate-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-framing-capabilities {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-host-name {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-protocol-version {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unexpected-challenge-without-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container bad-address {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container invalid-ns {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources-max-tunnels {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container session-id-not-null {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container unexpected {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-session-packet {
             description "Terminate-code specification";
             uses apply-advanced;
             container null-session-id-invalid {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container null-session-id-without-assigned-session-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-stopccn {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
             container avp-bad-hidden {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-bad-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-duplicate-value-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-bad-length {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-malformed-truncated {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-assigned-tunnel-id {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-mandatory-result-code {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-random-vector {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-missing-secret {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container avp-unknown {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container no-resources {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container session-id-not-null {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-unexpected-packet {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
             container for-session {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container receive-unknown-packet {
             description "Terminate-code specification";
             uses apply-advanced;
             container message-type-indecipherable {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container message-type-unrecognized {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container timeout-connection {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container timeout-connection-recovery-tunnel {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container timeout-idle {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container unknown-cause {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container warmstart-not-operational {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container warmstart-recovery-error {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
       }
       container ppp {
         description "PPP terminate-code mapping configuration";
         uses apply-advanced;
         container admin-logout {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container admin-reconnect-request {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container authenticate {
           description "Terminate-code specification";
           uses apply-advanced;
           container authenticator-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container challenge-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container chap-no-resources {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container chap-peer-authenticator-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container chap-peer-challenge-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container deny-by-peer {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container eap-challenge-larger-than-mtu {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container eap-peer-authenticator-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container eap-request-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container inactivity-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-requests {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-authenticator {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-resources {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container pap-peer-authenticator-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container pap-request-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container session-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container too-many-requests {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container tunnel-fail-immediate {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container tunnel-unsupported-tunnel-type {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container bridging {
           description "Terminate-code specification";
           uses apply-advanced;
           container admin-disable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container failed-to-activate-family-bridging {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container inhibited-by-authentication {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container link-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-configure-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-passive-retries-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-sevice-disable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-ieee802-tagged-frame-format {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-mac-frame-format {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-ieee802-tagged-frame-format {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-mac-fram-fromat {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-service {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container renegotiate-rx-conf-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container renegotiate-rx-conf-nak {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container renegotiate-rx-conf-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container renegotiate-rx-conf-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container stale-stacking {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container terminate-code-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container terminate-term-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container terminate-term-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container bundle {
           description "Terminate-code specification";
           uses apply-advanced;
           container fail-activation {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-create {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-engine-add {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-fragment-size-mismatch {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-fragmentation-location {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-fragmentation-mismatch {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-hash-link-selection-mismatch {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-join {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-local-mped-not-set-yet {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-local-mrru-mismatch {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-local-mru-mismatch {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-peer-endpoint-discriminator-mismatch {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-peer-mrru-mismatch {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-profile-nak {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-reassembly-location {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-reassembly-mismatch {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-record-network {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-server-location-mismatch {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-static-link {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container fail-unrecoverable-ifl {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container dynamic-profile-instantiation-failed {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container failover-during-authentication {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container interface-admin-disable {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container interface-no-hardware {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container ip {
           description "Terminate-code specification";
           uses apply-advanced;
           container admin-disable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container failed-to-activate-family-inet {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container failed-to-activate-services {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container failed-to-add-access-internal-route {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container inhibited-by-authentication {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container link-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-configure-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-passive-retries-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-ip-address {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-ip-address-mask {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-primary-dns-address {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-primary-nbns-address {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-secondary-dns-address {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-secondary-nbns-address {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-ip-address {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-ip-address-mask {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-primary-dns-address {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-primary-nbns-address {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-secondary-dns-address {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-secondary-nbns-address {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-service {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-nak {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-code-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-term-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-term-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container service-disable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container stale-stacking {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container ipv6 {
           description "Terminate-code specification";
           uses apply-advanced;
           container admin-disable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container failed-to-activate-family-inet6 {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container failed-to-activate-services {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container inhibited-by-authentication {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container link-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container local-and-peer-interface-ids-identical {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-configure-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-passive-retries-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-ipv6-interface-id {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-ipv6-interface-id {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-service {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-nak {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-code-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-term-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-term-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container service-disable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container stale-stacking {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container l2tp-session {
           description "Terminate-code specification";
           uses apply-advanced;
           container apply-link-attribute-failed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container lcp {
           description "Terminate-code specification";
           uses apply-advanced;
           container authenticate-terminate-hold {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container configured-mrru-too-small {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container configured-mru-invalid {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container configured-mru-too-small {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container dynamic-interface-hold {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container failed-to-activate-services {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container keepalive-failure {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container loopback-rx-conf-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container loopback-rx-echo-reply {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container loopback-rx-echo-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-configure-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-passive-retries-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container mru-changed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container negotiation-timeout {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-accm {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-acfc {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-authentication {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-endpoint-discriminator {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-magic-number {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-mrru {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-mru {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-pfc {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-accm {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-acfc {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-authentication {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-endpoint-discriminator {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-magic-number {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-mrru {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-mru {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-pfc {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-nak {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-code-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-protocol-reject {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-term-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-term-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container tunnel-disconnected {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container tunnel-failed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container license-limit-exceeded {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container link-interface-no-hardware {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container lower-interface-attach-failed {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container lower-interface-down {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container lower-interface-teardown {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container mpls {
           description "Terminate-code specification";
           uses apply-advanced;
           container admin-disable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container failed-to-activate-family-mpls {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container link-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-configure-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-passive-retries-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-service {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-nak {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-code-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-term-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-term-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container service-disable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container stale-stacking {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container network-interface-admin-disable {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container no-bundle {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container no-interface {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container no-link-interface {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container no-ncps-available {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container no-network-interface {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container no-upper-interface {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container osi {
           description "Terminate-code specification";
           uses apply-advanced;
           container admin-disable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container failed-to-activate-family-osi {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container link-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-configure-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container max-passive-retries-exceeded {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-local-align-npdu {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-peer-align-npdu {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container no-service {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-nak {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-renegotiate-rx-conf-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-code-rej {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-term-ack {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container peer-terminate-term-req {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container service-disable {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container stale-stacking {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container recovery {
           description "Terminate-code specification";
           uses apply-advanced;
           container active-state-cleanup {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container configured-state-cleanup {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container init-state-cleanup {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container terminated-state-cleanup {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container terminating-state-cleanup {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
         container session-init-failed {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container subscriber-mgr {
           description "Terminate-code specification";
           uses apply-advanced;
           container activation-failed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container get-credentials-failed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container link-interface-not-found {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container set-state-active-failed {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
         }
       }
       container vlan {
         description "VLAN terminate-code mapping configuration";
         uses apply-advanced;
         container admin-logout {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container admin-reconnect {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container other {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container out-of-band {
           description "Terminate-code specification";
           uses apply-advanced;
           container access-interface-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container admin-access-interface-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container admin-core-interface-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container ancp {
             description "Terminate-code specification";
             uses apply-advanced;
             container port-down {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
             container port-vlan-id-change {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
           container core-interface-down {
             description "Terminate-code specification";
             uses apply-advanced;
             container radius {
               description "Radius Acct-Terminate-Cause configuration";
               leaf acct-terminate-cause {
                 description "Set value";
                 type union {
                   type string {
                     pattern "<.*>|$.*";
                   }
                   type uint32 {
                     range "1 .. 4294967295";
                   }
                 }
               }
             }
           }
           container l2-wholesale {
             description "Terminate-code specification";
             uses apply-advanced;
             container no-free-vlans {
               description "Terminate-code specification";
               uses apply-advanced;
               container radius {
                 description "Radius Acct-Terminate-Cause configuration";
                 leaf acct-terminate-cause {
                   description "Set value";
                   type union {
                     type string {
                       pattern "<.*>|$.*";
                     }
                     type uint32 {
                       range "1 .. 4294967295";
                     }
                   }
                 }
               }
             }
           }
         }
         container profile-request-error {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container sdb-error {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
         container subscriber-activate-error {
           description "Terminate-code specification";
           uses apply-advanced;
           container radius {
             description "Radius Acct-Terminate-Cause configuration";
             leaf acct-terminate-cause {
               description "Set value";
               type union {
                 type string {
                   pattern "<.*>|$.*";
                 }
                 type uint32 {
                   range "1 .. 4294967295";
                 }
               }
             }
           }
         }
       }
     }
     container diameter-profiles {
       description "Diameter application configurations";
       uses aaa-diameter-profiles;
     }
     container firewall-authentication {
       description "Type of firewall authentication";
       uses apply-advanced;
       container pass-through {
         description "Pass-through firewall authentication settings";
         uses apply-advanced;
         leaf default-profile {
           description "Name of default profile";
           type string {
             length "1 .. 250";
           }
         }
         container ftp {
           description "FTP banners";
           uses banner-object;
         }
         container telnet {
           description "Telnet banners";
           uses banner-object;
         }
         container http {
           description "HTTP banners";
           uses banner-object;
         }
       }
       container web-authentication {
         description "Web-authentication settings";
         uses apply-advanced;
         leaf default-profile {
           description "Name of profile to use for web-authentication";
           type string {
             length "1 .. 250";
           }
         }
         container banner {
           uses apply-advanced;
           leaf success {
             description "The message that will be displayed on successful login";
             type string {
               length "1 .. 250";
             }
           }
           leaf fail {
             description "The message that will be displayed on failed login";
             type string {
               length "1 .. 250";
             }
           }
           leaf logout {
             description "The message that will be displayed on logout";
             type string {
               length "1 .. 250";
             }
           }
         }
         leaf logo {
           description "Path to logo file";
           type string;
         }
         leaf timeout {
           description "Web-authentication timeout value in seconds";
           type union {
             type string {
               pattern "<.*>|$.*";
             }
             type int32 {
               range "5 .. 60";
             }
           }
         }
       }
       container traceoptions {
         description "Firewall authentication tracing options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "configuration" {
                 description "Trace configuration events";
               }
               enum "setup" {
                 description "Trace setup of firewall authentication service";
               }
               enum "authentication" {
                 description "Trace authentication events";
               }
               enum "mnha" {
                 description "Trace fwauth mnha connectivity events";
               }
               enum "all" {
                 description "Trace with all flags enabled";
               }
             }
           }
         }
       }
       leaf-list trusted-sites {
         ordered-by user;
         description "List of trusted websites";
         type string;
       }
     }
     container radius {
       description "RADIUS server and network-element configuration";
       uses juniper-radius;
     }
     container diameter {
       description "Diameter server and network-element configuration";
       uses juniper-mobile-diameter;
     }
   }
   grouping aaa-diameter-profiles {
     uses apply-advanced;
     list gy-profile {
       key name;
       ordered-by user;
       description "Diameter Gy application profile configuration";
       uses aaa-diameter-profile-type-gy;
     }
     list gx-profile {
       key name;
       ordered-by user;
       description "Diameter Gx application profile configuration";
       uses aaa-diameter-profile-type-gx;
     }
   }
   grouping aaa-diameter-profile-type-gx {
     leaf name {
       description "Diameter profile name";
       type string {
         length "1 .. 63";
       }
     }
     uses apply-advanced;
     list targets {
       key name;
       ordered-by user;
       description "AAA diameter target configurations";
       uses aaa-diameter-target;
     }
     leaf request-timeout {
       description "Profile request timeout";
       units "seconds";
       type union {
         type string {
           pattern "<.*>|$.*";
         }
         type uint32 {
           range "0 .. 65535";
         }
       }
     }
     container attributes {
       description "Diameter AVP attributes for Gx application";
       uses aaa-diameter-gx-profile-attr-type;
     }
   }
   grouping aaa-diameter-gx-profile-attr-type {
     uses apply-advanced;
     container include {
       description "Specify AVP options to be included";
       uses apply-advanced;
       leaf gx-capability-list {
         description "Include Gx Capability list AVP";
         type union {
           type uint32;
           type string {
             pattern "<.*>|$.*";
           }
         }
       }
       leaf rule-suggestion {
         description "Include rule-suggestion AVP";
         type string {
           length "1 .. 63";
         }
       }
       leaf rai {
         description "Include RAI AVP";
         type empty;
       }
       leaf qos-negotiation {
         description "Include QoS negotiation AVP";
         type empty;
       }
       leaf qos-upgrade {
         description "Include QoS upgrade AVP";
         type empty;
       }
     }
     container exclude {
       description "Specify AVP options to be excluded";
       uses apply-advanced;
       leaf packet-filter-information {
         description "Exclude packet filter information AVP";
         type empty;
       }
       leaf packet-filter-operation {
         description "Exclude packet filter operation AVP";
         type empty;
       }
       leaf rat-type {
         description "Exclude rat-type AVP";
         type empty;
       }
       leaf default-eps-bearer-qos {
         description "Exclude default EPS bearer QOS AVP";
         type empty;
       }
       leaf an-gw-address {
         description "Exclude an-gw-address AVP";
         type empty;
       }
       leaf network-request-support {
         description "Exclude network request support AVP";
         type empty;
       }
       leaf event-trigger {
         description "Exclude event trigger AVP";
         type empty;
       }
       leaf threegpp-rat-type {
         description "Exclude 3GPP-RAT-type AVP";
         type empty;
       }
       leaf offline {
         description "Exclude offline AVP";
         type empty;
       }
       leaf qos-negotiation {
         description "Exclude QoS negotiation AVP";
         type empty;
       }
       leaf qos-upgrade {
         description "Exclude QoS upgrade AVP";
         type empty;
       }
     }
   }
   grouping aaa-diameter-profile-type-gy {
     leaf name {
       description "Diameter profile name";
       type string {
         length "1 .. 63";
       }
     }
     uses apply-advanced;
     list targets {
       key name;
       ordered-by user;
       description "AAA diameter target configurations";
       uses aaa-diameter-target;
     }
     leaf request-timeout {
       description "Profile request timeout";
       units "seconds";
       type union {
         type string {
           pattern "<.*>|$.*";
         }
         type uint32 {
           range "0 .. 65535";
         }
       }
     }
     container attributes {
       description "Diameter AVP attributes for Gy application";
       uses aaa-diameter-gy-profile-attr-type;
     }
   }
   grouping aaa-diameter-gy-profile-attr-type {
     uses apply-advanced;
     container include {
       description "Specify AVP options to be included";
       uses apply-advanced;
       leaf cumulative-used-service-unit {
         description "Include cumulative-used-service-unit AVP";
         type empty;
       }
       leaf credit-instance-id {
         description "Include credit-instance-id AVP";
         type empty;
       }
       leaf service-start-timestamp {
         description "Include service-start-timestamp AVP";
         type empty;
       }
       leaf mscc-qos-information {
         description "Include mscc-qos-information AVP";
         type empty;
       }
       leaf framed-ip-address {
         description "Include framed ip address AVP";
         type empty;
       }
       leaf framed-ipv6-prefix {
         description "Include framed IPV6 Prefix AVP";
         type empty;
       }
       leaf gprs-negotiated-qos {
         description "Include GPRS negotiated QOS AVP";
         type empty;
       }
     }
     container exclude {
       description "Specify AVP options to be excluded";
       uses apply-advanced;
       leaf ps-information {
         description "Exclude PS Information AVP. If excluded, all the 3GPP AVPs will be sent at command level ";
         type empty;
       }
       leaf username {
         description "Exclude Username AVP";
         type empty;
       }
       leaf user-equipment-info {
         description "Exclude user equipment info AVP";
         type empty;
       }
       leaf all-3gpp-avps {
         description "Exclude all 3GPP AVPs";
         type empty;
       }
       leaf qos-information {
         description "Exclude QOS information AVP";
         type empty;
       }
       leaf pdn-connection-id {
         description "Exclude PDN connection id AVP";
         type empty;
       }
       leaf dynamic-address-flag {
         description "Exclude dynamic address flag AVP";
         type empty;
       }
       leaf serving-node-type {
         description "Exclude serving node type AVP";
         type empty;
       }
       leaf cc-selection-mode {
         description "Exclude charging characteristics selection mode AVP";
         type empty;
       }
       leaf start-time {
         description "Exclude start time AVP";
         type empty;
       }
       leaf stop-time {
         description "Exclude stop time AVP";
         type empty;
       }
       leaf user-location-information {
         description "Exclude user location information AVP";
         type empty;
       }
     }
   }
   grouping aaa-diameter-target {
     description "Diameter target configuration";
     leaf name {
       description "Diameter target name";
       type string {
         length "1 .. 31";
       }
     }
     uses apply-advanced;
     leaf destination-realm {
       description "Destination realm associated with this target";
       type string {
         length "1 .. 255";
       }
     }
     leaf destination-host {
       description "Destination host associated with this target";
       type string {
         length "1 .. 255";
       }
     }
     leaf priority {
       description "Target priority";
       type union {
         type string {
           pattern "<.*>|$.*";
         }
         type uint32 {
           range "1 .. 65535";
         }
       }
     }
     leaf network-element {
       description "Specify the diameter network element for this target";
       type string {
         length "1 .. 31";
       }
     }
   }
   grouping access-client-name-filter-object {
     description "Restrictions on client names authenticated on this server";
     uses apply-advanced;
     leaf domain-name {
       description "Domain name to match (must be part of username)";
       type string;
     }
     leaf separator {
       description "Separator character in domain name";
       type string {
         length 1;
       }
     }
     leaf count {
       description "Number of separator instances";
       default "0";
       type union {
         type string {
           pattern "<.*>|$.*";
         }
         type uint8 {
           range "0 .. 255";
         }
       }
     }
   }
   grouping access-client-object {
     leaf name {
       description "Name of entity requesting access";
       type string;
     }
     uses apply-advanced;
     leaf no-rfc2486 {
       description "RFC2486 compliance is not enforced";
       type empty;
     }
     leaf chap-secret {
       description "CHAP secret";
       type jt:unreadable;
     }
     leaf pap-password {
       description "PAP password";
       type jt:unreadable;
     }
     choice client_type {
       case case_1 {
         container ppp {
           presence "enable ppp";
           description "Configuration for Point-to-Point Protocol";
           uses apply-advanced;
           leaf framed-pool {
             description "Address pool used to assign an address for the user";
             type string {
               length "1 .. 63";
             }
           }
           leaf idle-timeout {
             description "Idle timeout before termination of session";
             default "0";
             units "seconds";
             type union {
               type string {
                 pattern "<.*>|$.*";
               }
               type uint32 {
                 range "0 .. 4294967295";
               }
             }
           }
           container ppp-options {
             presence "enable ppp-options";
             description "Point-to-Point Protocol interface-specific options";
             uses apply-advanced;
             leaf pap {
               description "Password Authentication Protocol";
               type empty;
             }
             leaf chap {
               description "Challenge Handshake Authentication Protocol";
               type empty;
             }
           }
           leaf keepalive {
             description "PPP keepalive interval";
             default "10";
             units "seconds";
             type union {
               type string {
                 pattern "<.*>|$.*";
               }
               type uint16 {
                 range "0 .. 32767";
               }
             }
           }
           leaf primary-dns {
             description "Primary DNS server name";
             type string;
           }
           leaf secondary-dns {
             description "Secondary DNS server name";
             type string;
           }
           leaf primary-wins {
             description "Primary wins server name";
             type string;
           }
           leaf secondary-wins {
             description "Secondary wins server name";
             type string;
           }
           leaf encapsulation-overhead {
             description "Encapsulation overhead for Class of Service calculation";
             type union {
               type string {
                 pattern "<.*>|$.*";
               }
               type int8 {
                 range "-63 .. 64";
               }
             }
           }
           leaf cell-overhead {
             description "ATM cell overhead for Class of Service calculation";
             type empty;
           }
           leaf interface-id {
             description "Interface identifier to look up session information";
             type string {
               length "1 .. 63";
             }
           }
           leaf framed-ip-address {
             description "Address to be configured for the user";
             type jt:ipv4prefix;
           }
           leaf keepalive-retries {
             description "PPP keepalive retries";
             default "10";
             type union {
               type string {
                 pattern "<.*>|$.*";
               }
               type uint16 {
                 range "3 .. 32767";
               }
             }
           }
         }
       }
       case case_2 {
         container l2tp {
           presence "enable l2tp";
           description "Configuration for Layer 2 Tunneling Protocol";
           uses apply-advanced;
           leaf maximum-sessions {
             description "Maximum number of sessions per client";
             type union {
               type uint32;
               type string {
                 pattern "<.*>|$.*";
               }
             }
           }
           leaf maximum-sessions-per-tunnel {
             description "Maximum number of sessions per L2TP tunnel";
             default "0";
             type union {
               type uint16;
               type string {
                 pattern "<.*>|$.*";
               }
             }
           }
           leaf service-profile {
             description "Dynamic service profile(s) to be applied to this session";
             type string;
           }
           leaf interface-id {
             description "Interface identifier for PPP users missing one";
             type string {
               length "1 .. 63";
             }
           }
           leaf lcp-renegotiation {
             description "Force renegotiation of LCP options";
             type empty;
           }
           leaf local-chap {
             description "Force local CHAP challenge";
             type empty;
           }
           container override-result-code {
             description "Override result code with admin value in CDN message at LNS";
             uses apply-advanced;
             leaf session-out-of-resource {
               description "Override result code for session out-of-resource due to permanent or temporary condition with admin value in CDN message at LNS";
               type empty;
             }
           }
           leaf aaa-access-profile {
             description "AAA access profile name";
             type string {
               length "1 .. 63";
             }
           }
           container multilink {
             description "Multilink Point-to-Point Protocol command options";
             presence "enable multilink";
             uses multilink-object;
           }
           leaf session-limit-group {
             description "Session limit group name";
             type string;
           }
           leaf ppp-authentication {
             description "Method for authenticating client";
             type enumeration {
               enum "chap" {
                 description "Challenge Handshake Authentication Protocol";
               }
               enum "pap" {
                 description "Password Authentication Protocol";
               }
             }
           }
           leaf shared-secret {
             description "Shared secret for authenticating peer";
             type string {
               length "1 .. 64";
             }
           }
           leaf ppp-profile {
             description "User profile name";
             type string;
           }
           leaf dynamic-profile {
             description "Dynamic profile name";
             type string;
           }
         }
       }
     }
     leaf group-profile {
       description "Group profile name";
       type string;
     }
     leaf user-group-profile {
       description "User group profile name";
       type string;
     }
     container xauth {
       description "Configure xauth attributes";
       uses apply-advanced;
       leaf ip-address {
         description "Specify the ip-address for client";
         type jt:ipv4prefix;
       }
     }
     leaf-list client-group {
       ordered-by user;
       description "One or more groups to which the client belongs";
       type string;
     }
     container firewall-user {
       description "Client is configured as a firewall user";
       uses apply-advanced;
       leaf password {
         description "Password for user";
         type string {
           length "1 .. 128";
         }
       }
     }
   }
   grouping access-ldap-options {
     uses apply-advanced;
     leaf revert-interval {
       description "Time after which to revert to primary server";
       default "600";
       units "seconds";
       type union {
         type string {
           pattern "<.*>|$.*";
         }
         type uint32 {
           range "60 .. 4294967295";
         }
       }
     }
     leaf base-distinguished-name {
       description "Suffix when assembling user distinguished name (DN) or base DN under which to search for user DN";
       type string;
     }
     choice search_type {
       case case_1 {
         container assemble {
           presence "enable assemble";
           description "Derive user distinguished name from 'common-name' and 'base-distinguished-name'";
           uses apply-advanced;
           leaf common-name {
             description "Prefix in user distinguished name (for example, 'cn' or 'uid')";
             default "cn";
             type string;
           }
         }
       }
       case case_2 {
         container search {
           presence "enable search";
           description "Search for user's distinguished name";
           uses apply-advanced;
           leaf search-filter {
             description "Filter to use in search (examples: 'cn=' or 'givenName=')";
             type string;
           }
           container admin-search {
             presence "enable admin-search";
             description "Perform an administrator search to find user's distinguished name";
             uses apply-advanced;
             leaf distinguished-name {
               description "Administrator's distinguished name";
               type string;
             }
             leaf password {
               description "Administrator password";
               type jt:unreadable;
             }
           }
         }
       }
     }
     list allowed-groups {
       key name;
       ordered-by user;
       description "LDAP allowed groups configuration";
       uses ldap-allowed-groups-object;
     }
   }
   grouping access-radius-options {
     uses apply-advanced;
     leaf revert-interval {
       description "Time after which to revert to primary server";
       default "60";
       units "seconds";
       type union {
         type string {
           pattern "<.*>|$.*";
         }
         type uint32 {
           range "0 .. 604800";
         }
       }
     }
     leaf timeout-grace {
       description "The period after a RADIUS server times out before marking the server as dead";
       default "10";
       units "seconds";
       type union {
         type string {
           pattern "<.*>|$.*";
         }
         type uint32 {
           range "0 .. 30";
         }
       }
     }
     leaf request-rate {
       description "Maximum number of RADIUS requests sent per second";
       default "500";
       type union {
         type string {
           pattern "<.*>|$.*";
         }
         type uint32 {
           range "100 .. 4000";
         }
       }
     }
     leaf interim-rate {
       description "Maximum number of RADIUS requests sent per second";
       default "500";
       type union {
         type string {
           pattern "<.*>|$.*";
         }
         type uint32 {
           range "50 .. 4000";
         }
       }
     }
     leaf interim-update-tolerance {
       description "Maximum tolerance for Interim Updates to RADIUS";
       status deprecated;
       default "60";
       units "seconds";
       type union {
         type string {
           pattern "<.*>|$.*";
         }
         type uint32 {
           range "1 .. 600";
         }
       }
     }
     container unique-nas-port {
       presence "enable unique-nas-port";
       description "Use unique value for NAS-Port radius attribute";
       uses apply-advanced;
       leaf chassis-id {
         description "Configure chassis identifier field of NAS-Port";
         type union {
           type string {
             pattern "<.*>|$.*";
           }
           type uint32 {
             range "0 .. 127";
           }
         }
       }
       leaf chassis-id-width {
         description "Number of bits for the chassis identifier field of NAS-Port";
         units "bits";
         type union {
           type string {
             pattern "<.*>|$.*";
           }
           type uint32 {
             range "1 .. 7";
           }
         }
       }
     }
   }
   grouping access-radius-server-name-object {
     leaf name {
       description "Fully qualified domain name of the RADIUS server";
       type string {
         length "4 .. 255";
       }
     }
     uses apply-advanced;
     leaf dns-query-interval {
       description "Frequency of RADIUS server name resolution";
       default "60";
       units "minutes";
       type union {
         type string {
           pattern "<.*>|$.*";
         }
         type uint16 {
           range "10 .. 1440";
         }
       }
     }
     leaf accounting-port {
       description "RADIUS server accounting port number";
       default "1813";
       type union {
         type string {
           pattern "<.*>|$.*";
         }
         type uint16 {
           range "1 .. 65535";
         }
       }
     }
     leaf radsec-destination {
       description "RADSEC destination";
       type union {
         type uint32;
         type string {
           pattern "<.*>|$.*";
         }
       }
     }
     leaf port {
       description "RADIUS server authentication port number";
       default "1812";
       type union {
         type string {
           pattern "<.*>|$.*";
         }
         type uint16 {
           range "1 .. 65535";
         }
       }
     }
     leaf preauthentication-port {
       description "RADIUS server preauthentication port number";
       type union {
         type string {
           pattern "<.*>|$.*";
         }
         type uint16 {
           range "1 .. 65535";
         }
       }
     }
     leaf dynamic-request-port {
       description "RADIUS client dynamic request port number";
       default "3799";
       type union {
         type string {
           pattern "<.*>|$.*";
         }
         type uint16 {
           range "1 .. 65535";
         }
       }
     }
     leaf secret {
       description "Shared secret with the RADIUS server";
       type jt:unreadable;
     }
     leaf preauthentication-secret {
       description "Shared secret with the RADIUS server";
       type jt:unreadable;
     }
     leaf timeout {
       description "Request timeout period";
       default "3";
       units "seconds";
       type union {
         type string {
           pattern "<.*>|$.*";
         }
         type uint32 {
           range "1 .. 1000";
         }
       }
     }
     leaf retry {
       description "Retry attempts";
       default "3";
       type union {
         type string {
           pattern "<.*>|$.*";
         }
         type uint32 {
           range "1 .. 100";
         }
       }
     }
     leaf accounting-timeout {
       description "Accounting request timeout period";
       default "0";
       units "seconds";
       type union {
         type string {
           pattern "<.*>|$.*";
         }
         type uint32 {
           range "0 .. 1000";
         }
       }
     }
     leaf accounting-retry {
       description "Accounting retry attempts";
       default "0";
       type union {
         type string {
           pattern "<.*>|$.*";
         }
         type uint32 {
           range "0 .. 100";
         }
       }
     }
     leaf max-outstanding-requests {
       description "Maximum requests in flight to server";
       default "1000";
       type union {
         type string {
           pattern "<.*>|$.*";
         }
         type uint32 {
           range "0 .. 2000";
         }
       }
     }
     leaf source-address {
       description "Use specified address as source address";
       type jt:ipaddr;
     }
     leaf routing-instance {
       description "Use specified routing instance";
       type string;
     }
   }
   grouping access-radius-server-object {
     leaf name {
       description "RADIUS server address";
       type jt:ipaddr;
     }
     uses apply-advanced;
     leaf port {
       description "RADIUS server authentication port number";
       default "1812";
       type union {
         type string {
           pattern "<.*>|$.*";
         }
         type uint16 {
           range "1 .. 65535";
         }
       }
     }
     leaf preauthentication-port {
       description "RADIUS server preauthentication port number";
       type union {
         type string {
           pattern "<.*>|$.*";
         }
         type uint16 {
           range "1 .. 65535";
         }
       }
     }
     leaf accounting-port {
       description "Port number to send RADIUS accounting messages";
       default "1813";
       type union {
         type string {
           pattern "<.*>|$.*";
         }
         type uint16 {
           range "1 .. 65535";
         }
       }
     }
     leaf dynamic-request-port {
       description "RADIUS client dynamic request port number";
       default "3799";
       type union {
         type string {
           pattern "<.*>|$.*";
         }
         type uint16 {
           range "1 .. 65535";
         }
       }
     }
     leaf secret {
       description "Shared secret with the RADIUS server";
       type jt:unreadable;
     }
     leaf preauthentication-secret {
       description "Shared secret with the RADIUS server";
       type jt:unreadable;
     }
     leaf timeout {
       description "Request timeout period";
       default "3";
       units "seconds";
       type union {
         type string {
           pattern "<.*>|$.*";
         }
         type uint32 {
           range "1 .. 1000";
         }
       }
     }
     leaf retry {
       description "Retry attempts";
       default "3";
       type union {
         type string {
           pattern "<.*>|$.*";
         }
         type uint32 {
           range "1 .. 100";
         }
       }
     }
     leaf accounting-timeout {
       description "Accounting request timeout period";
       default "0";
       units "seconds";
       type union {
         type string {
           pattern "<.*>|$.*";
         }
         type uint32 {
           range "0 .. 1000";
         }
       }
     }
     leaf accounting-retry {
       description "Accounting retry attempts";
       default "0";
       type union {
         type string {
           pattern "<.*>|$.*";
         }
         type uint32 {
           range "0 .. 100";
         }
       }
     }
     leaf max-outstanding-requests {
       description "Maximum requests in flight to server";
       default "1000";
       type union {
         type string {
           pattern "<.*>|$.*";
         }
         type uint32 {
           range "0 .. 2000";
         }
       }
     }
     leaf source-address {
       description "Use specified address as source address";
       type jt:ipaddr;
     }
     leaf routing-instance {
       description "Use specified routing instance";
       type string;
     }
     leaf radsec-destination {
       description "RADSEC destination";
       type union {
         type uint32;
         type string {
           pattern "<.*>|$.*";
         }
       }
     }
   }
   grouping address-assignment-type {
     description "Address assignment configuration";
     uses apply-advanced;
     container neighbor-discovery-router-advertisement {
       description "Designated NDRA pool for this instance";
       leaf ndra-name {
         description "Designated NDRA pool name";
         type string {
           length "1 .. 63";
         }
       }
     }
     leaf high-utilization {
       description "Generate an SNMP trap when address pool use surpasses this percentage";
       type union {
         type string {
           pattern "<.*>|$.*";
         }
         type uint16 {
           range "2 .. 99";
         }
       }
     }
     leaf abated-utilization {
       description "Generate an SNMP clear trap when address pool use falls below this percentage";
       type union {
         type string {
           pattern "<.*>|$.*";
         }
         type uint16 {
           range "1 .. 98";
         }
       }
     }
     leaf high-utilization-v6 {
       description "Generate an SNMP trap when address pool use surpasses this percentage";
       type union {
         type string {
           pattern "<.*>|$.*";
         }
         type uint16 {
           range "2 .. 99";
         }
       }
     }
     leaf abated-utilization-v6 {
       description "Generate an SNMP clear trap when address pool use falls below this percentage";
       type union {
         type string {
           pattern "<.*>|$.*";
         }
         type uint16 {
           range "1 .. 98";
         }
       }
     }
     list dynamic-pool {
       key name;
       ordered-by user;
       description "Dynamic address pool";
       leaf name {
         description "Dynamic address pool name";
         type string {
           length "1 .. 63";
         }
       }
       uses apply-advanced;
       container family {
         presence "enable family";
         description "Address family";
         uses apply-advanced;
         container inet6 {
           description "IPv6";
           uses apply-advanced;
           leaf delegated-prefix-length {
             description "Delegated IPv6 network prefix length";
             type union {
               type string {
                 pattern "<.*>|$.*";
               }
               type uint32 {
                 range "1 .. 64";
               }
             }
           }
           leaf prefix-identifier {
             description "Prefix identifier to use for delegated prefix";
             type jt:ipv6addr;
           }
           leaf from-interface {
             description "Get prefix from interface name";
             type union {
               type jt:interface-name;
               type string {
                 pattern "<.*>|$.*";
               }
             }
           }
           list range {
             key name;
             ordered-by user;
             description "IPv6 address range";
             leaf name {
               description "Range name";
               type string {
                 length "1 .. 63";
               }
             }
             uses apply-advanced;
             leaf masked-low {
               description "Lower limit of ipv6 address range";
               type jt:ipv6prefix-mandatory;
             }
             leaf masked-high {
               description "Upper limit of ipv6 address range";
               type jt:ipv6prefix-mandatory;
             }
             leaf prefix-length {
               description "IPv6 delegated prefix length";
               type union {
                 type string {
                   pattern "<.*>|$.*";
                 }
                 type uint32 {
                   range "1 .. 64";
                 }
               }
             }
           }
           container dhcp-attributes {
             description "DHCP options and match criteria";
             uses dynamic-dhcp-attribute-type;
           }
         }
       }
     }
     list pool {
       key name;
       ordered-by user;
       description "Address pool";
       leaf name {
         description "Address pool name";
         type string {
           length "1 .. 63";
         }
       }
       uses apply-advanced;
       leaf active-drain {
         description "Notify client of pool active drain mode";
         type empty;
       }
       leaf hold-down {
         description "Place pool in passive drain mode";
         type empty;
       }
       leaf link {
         description "Address pool link name";
         type string {
           length "1 .. 63";
         }
       }
       container family {
         presence "enable family";
         description "Address family";
         choice family_type {
           case case_1 {
             container inet {
               presence "enable inet";
               description "IPv4";
               uses apply-advanced;
               leaf network {
                 description "Network address";
                 type jt:ipv4prefix;
               }
               list range {
                 key name;
                 ordered-by user;
                 description "Address range";
                 max-elements 1;
                 leaf name {
                   description "Range name";
                   type string {
                     length "1 .. 63";
                   }
                 }
                 uses apply-advanced;
                 leaf low {
                   description "Lower limit of address range";
                   type jt:ipv4addr;
                 }
                 leaf high {
                   description "Upper limit of address range";
                   type jt:ipv4addr;
                 }
               }
               container dhcp-attributes {
                 description "DHCP options and match criteria";
                 uses dhcp-attribute-type;
               }
               container xauth-attributes {
                 description "Configure xauth attributes";
                 uses apply-advanced;
                 leaf primary-dns {
                   description "Specify the primary-dns IP address";
                   type jt:ipv4prefix;
                 }
                 leaf secondary-dns {
                   description "Specify the secondary-dns IP address";
                   type jt:ipv4prefix;
                 }
                 leaf primary-wins {
                   description "Specify the primary-wins IP address";
                   type jt:ipv4prefix;
                 }
                 leaf secondary-wins {
                   description "Specify the secondary-wins IP address";
                   type jt:ipv4prefix;
                 }
               }
               list host {
                 key name;
                 ordered-by user;
                 description "Hostname for static reservations";
                 leaf name {
                   description "Hostname";
                   type string {
                     length "1 .. 256";
                   }
                 }
                 uses apply-advanced;
                 leaf hardware-address {
                   description "Hardware address";
                   type jt:mac-addr;
                 }
                 leaf ip-address {
                   description "Reserved address";
                   type jt:ipv4addr;
                 }
                 choice host-identifier-type {
                   case case_1 {
                     leaf user-name {
                       description "Set subscriber user name as host identifier";
                       type empty;
                     }
                   }
                 }
               }
               list excluded-address {
                 key name;
                 ordered-by user;
                 description "Excluded Addresses";
                 max-elements 20;
                 leaf name {
                   description "Excluded address";
                   type jt:ipv4addr;
                 }
                 uses apply-advanced;
               }
               list excluded-range {
                 key name;
                 ordered-by user;
                 description "Excluded address range";
                 max-elements 20;
                 leaf name {
                   description "Range name";
                   type string {
                     length "1 .. 63";
                   }
                 }
                 uses apply-advanced;
                 leaf low {
                   description "Lower limit of excluded address range";
                   type jt:ipv4addr;
                 }
                 leaf high {
                   description "Upper limit of excluded address range";
                   type jt:ipv4addr;
                 }
               }
             }
           }
           case case_2 {
             container inet6 {
               presence "enable inet6";
               description "IPv6";
               uses apply-advanced;
               leaf prefix {
                 description "IPv6 network prefix";
                 type jt:ipv6prefix-mandatory;
               }
               list range {
                 key name;
                 ordered-by user;
                 description "IPv6 address range";
                 leaf name {
                   description "Range name";
                   type string {
                     length "1 .. 63";
                   }
                 }
                 uses apply-advanced;
                 leaf low {
                   description "Lower limit of ipv6 address range";
                   type jt:ipv6prefix-mandatory;
                 }
                 leaf high {
                   description "Upper limit of ipv6 address range";
                   type jt:ipv6prefix-mandatory;
                 }
                 leaf prefix-length {
                   description "IPv6 delegated prefix length";
                   type union {
                     type string {
                       pattern "<.*>|$.*";
                     }
                     type uint32 {
                       range "1 .. 128";
                     }
                   }
                 }
               }
               container dhcp-attributes {
                 description "DHCP options and match criteria";
                 uses dhcp-attribute-type;
               }
               container xauth-attributes {
                 description "Configure xauth ipv6 attributes";
                 uses apply-advanced;
                 leaf primary-dns-ipv6 {
                   description "Specify the primary-dns IPv6 address";
                   type jt:ipv6addr;
                 }
                 leaf secondary-dns-ipv6 {
                   description "Specify the secondary-dns IPv6 address";
                   type jt:ipv6addr;
                 }
               }
               list host {
                 key name;
                 ordered-by user;
                 description "Hostname for static reservations";
                 leaf name {
                   description "Hostname";
                   type string {
                     length "1 .. 256";
                   }
                 }
                 uses apply-advanced;
                 leaf hardware-address {
                   description "Hardware address";
                   type jt:mac-addr;
                 }
                 leaf ip-address {
                   description "Reserved address";
                   type jt:ipv6addr;
                 }
                 choice host-identifier-type {
                   case case_1 {
                     leaf user-name {
                       description "Set subscriber user name as host identifier";
                       type empty;
                     }
                   }
                 }
               }
               list excluded-address {
                 key name;
                 ordered-by user;
                 description "Excluded Addresses";
                 max-elements 20;
                 leaf name {
                   description "Excluded address";
                   type jt:ipv6addr;
                 }
                 uses apply-advanced;
               }
               list excluded-range {
                 key name;
                 ordered-by user;
                 description "Excluded address range";
                 max-elements 20;
                 leaf name {
                   description "Range name";
                   type string {
                     length "1 .. 63";
                   }
                 }
                 uses apply-advanced;
                 leaf low {
                   description "Lower limit of excluded address range";
                   type jt:ipv6addr;
                 }
                 leaf high {
                   description "Upper limit of excluded address range";
                   type jt:ipv6addr;
                 }
               }
             }
           }
         }
       }
     }
     list location-pool {
       key name;
       ordered-by user;
       description "Location-based IP address pool";
       max-elements 10;
       leaf name {
         description "Pool name";
         type string {
           length "1 .. 64";
         }
       }
       uses apply-advanced;
       container family {
         presence "enable family";
         description "Address family";
         container inet {
           description "IPv4 location pool";
           uses apply-advanced;
           list location {
             key name;
             description "Relative location of router";
             max-elements 32;
             leaf name {
               description "Location number";
               type union {
                 type string {
                   pattern "<.*>|$.*";
                 }
                 type uint32 {
                   range "1 .. 32";
                 }
               }
             }
             uses apply-advanced;
             leaf address {
               description "IP address/destination prefix";
               type jt:ipv4prefix;
             }
           }
         }
       }
     }
     list domain-profile {
       key name;
       ordered-by user;
       description "Address domain profile";
       leaf name {
         description "Pool domain profile name";
         type string {
           length "1 .. 63";
         }
       }
       uses apply-advanced;
       container family {
         presence "enable family";
         description "Network family to which this configuration belongs";
         uses apply-advanced;
         choice family_type {
           case case_1 {
             container inet {
               description "The IPv4 internet family";
               uses apply-advanced;
               leaf preferred-prefix-length {
                 description "Preferred prefix length";
                 type union {
                   type string {
                     pattern "<.*>|$.*";
                   }
                   type uint32 {
                     range "8 .. 30";
                   }
                 }
               }
               leaf source-partition-qualifier {
                 description "Prefix source qualifier appended to location for partition name";
                 type string {
                   length "1 .. 63";
                 }
               }
               container excluded-address {
                 description "Excluded addresses from allocation";
                 leaf-list last-octet {
                   ordered-by user;
                   description "Last octet of the excluded address";
                   type union {
                     type string {
                       pattern "<.*>|$.*";
                     }
                     type uint8 {
                       range "0 .. 255";
                     }
                   }
                 }
               }
               container install-discard-routes {
                 presence "enable install-discard-routes";
                 description "Install discard route domain pool prefix";
                 uses apply-advanced;
                 leaf tag {
                   description "Route tag";
                   type union {
                     type string {
                       pattern "<.*>|$.*";
                     }
                     type uint32 {
                       range "0 .. 4294967295";
                     }
                   }
                 }
                 leaf backup-tag {
                   description "Backup route tag";
                   type union {
                     type string {
                       pattern "<.*>|$.*";
                     }
                     type uint32 {
                       range "0 .. 4294967295";
                     }
                   }
                 }
               }
               leaf dhcp-gateway-address-last-octet {
                 description "DHCP host address component to be excluded and passed to DHCP";
                 type union {
                   type string {
                     pattern "<.*>|$.*";
                   }
                   type uint8 {
                     range "1 .. 8";
                   }
                 }
               }
               leaf protocol-attributes {
                 description "Access protocol-attributes name";
                 type string {
                   length "1 .. 63";
                 }
               }
             }
           }
           case case_2 {
             container inet6 {
               description "The IPv6 internet family";
               uses apply-advanced;
               leaf partition-type {
                 description "Partition type";
                 type enumeration {
                   enum "non-temporary-address" {
                     description "Address to advertise in DHCPv6";
                   }
                   enum "delegated-prefix" {
                     description "Prefix to advertise in DHCPv6";
                   }
                   enum "router-advertisement" {
                     description "Prefix for router advertisement";
                   }
                 }
               }
               leaf preferred-prefix-length {
                 description "Preferred prefix length";
                 type union {
                   type string {
                     pattern "<.*>|$.*";
                   }
                   type uint32 {
                     range "8 .. 126";
                   }
                 }
               }
               leaf allocation-length {
                 description "Per-allocation length";
                 default "128";
                 type union {
                   type string {
                     pattern "<.*>|$.*";
                   }
                   type uint32 {
                     range "8 .. 128";
                   }
                 }
               }
               leaf source-partition-qualifier {
                 description "Prefix source qualifier appended to location for partition name";
                 type string {
                   length "1 .. 63";
                 }
               }
               container install-discard-routes {
                 presence "enable install-discard-routes";
                 description "Install discard route domain pool prefix";
                 uses apply-advanced;
                 leaf tag {
                   description "Route tag";
                   type union {
                     type string {
                       pattern "<.*>|$.*";
                     }
                     type uint32 {
                       range "0 .. 4294967295";
                     }
                   }
                 }
                 leaf backup-tag {
                   description "Backup route tag";
                   type union {
                     type string {
                       pattern "<.*>|$.*";
                     }
                     type uint32 {
                       range "0 .. 4294967295";
                     }
                   }
                 }
               }
               leaf protocol-attributes {
                 description "Access protocol-attributes name";
                 type string {
                   length "1 .. 63";
                 }
               }
             }
           }
         }
       }
     }
     container subscriber-group-default-tags {
       presence "enable subscriber-group-default-tags";
       description "Route tags to advertise for statically assigned subscriber addresses and prefixes";
       uses apply-advanced;
       leaf tag {
         description "Route tag to advertise for the active user-plane of the subscriber group";
         type union {
           type string {
             pattern "<.*>|$.*";
           }
           type uint32 {
             range "0 .. 4294967295";
           }
         }
       }
       leaf backup-tag {
         description "Route tag to advertise for the backup user-plane of the subscriber group";
         type union {
           type string {
             pattern "<.*>|$.*";
           }
           type uint32 {
             range "0 .. 4294967295";
           }
         }
       }
     }
     list address-pools {
       key name;
       ordered-by user;
       description "Address pools for subscribers";
       max-elements 10000;
       uses sm-ippool-pool;
     }
   }
   grouping address-pool-object {
     leaf name {
       description "Address pool name";
       type string {
         length "1 .. 63";
       }
     }
     uses apply-advanced;
     choice address_choice {
       case case_1 {
         leaf address {
           description "Address or address prefix";
           type jt:ipv4prefix;
         }
       }
       case case_2 {
         container address-range {
           presence "enable address-range";
           description "Range of addresses for pool";
           leaf low {
             description "Lower limit of address range";
             type jt:ipv4addr;
           }
           leaf high {
             description "Upper limit of address range";
             type jt:ipv4addr;
           }
           uses apply-advanced;
           leaf mask {
             description "Netmask for address pool";
             type jt:ipv4addr;
           }
         }
       }
     }
     leaf primary-dns {
       description "Name of primary DNS server";
       type jt:hostname;
     }
     leaf secondary-dns {
       description "Name of secondary DNS server";
       type jt:hostname;
     }
     leaf primary-wins {
       description "Name of primary WINS server";
       type jt:hostname;
     }
     leaf secondary-wins {
       description "Name of secondary WINS server";
       type jt:hostname;
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping banner-object {
     uses apply-advanced;
     container banner {
       description "Banners that are prompted during authentication";
       uses apply-advanced;
       leaf login {
         description "The message that will be displayed before login";
         type string {
           length "1 .. 250";
         }
       }
       leaf success {
         description "The message that will be displayed on successful login";
         type string {
           length "1 .. 250";
         }
       }
       leaf fail {
         description "The message that will be displayed after failed user login";
         type string {
           length "1 .. 250";
         }
       }
     }
   }
   grouping dhcp-attribute-type {
     uses apply-advanced;
     container option-match {
       description "Match";
       uses apply-advanced;
       container option-82 {
         uses apply-advanced;
         list circuit-id {
           key name;
           ordered-by user;
           description "Circuit ID portion of the option 82";
           leaf name {
             type string;
           }
           leaf range {
             description "Range name";
             type string;
           }
         }
         list remote-id {
           key name;
           ordered-by user;
           description "Remote ID portion of the option 82";
           leaf name {
             type string;
           }
           leaf range {
             description "Range name";
             type string;
           }
         }
       }
     }
     leaf maximum-lease-time {
       description "Maximum lease time advertised to clients";
       units "seconds";
       type string;
     }
     leaf next-server {
       description "Next server that clients need to contact";
       type jt:ipv4addr;
     }
     leaf server-identifier {
       description "Server Identifier - IP address value";
       type jt:ipv4addr;
     }
     leaf grace-period {
       description "Grace period for leases";
       units "seconds";
       type union {
         type uint32;
         type string {
           pattern "<.*>|$.*";
         }
       }
     }
     leaf domain-name {
       description "Domain name advertised to clients";
       type string {
       }
     }
     list name-server {
       key name;
       ordered-by user;
       description "Domain name servers available to the client";
       leaf name {
         description "DNS server's IPv4 address";
         type jt:ipv4addr;
       }
       uses apply-advanced;
     }
     list wins-server {
       key name;
       ordered-by user;
       description "WINS name servers";
       leaf name {
         description "WINS server's IPv4 address";
         type jt:ipv4addr;
       }
       uses apply-advanced;
     }
     list router {
       key name;
       description "Routers advertised to clients";
       leaf name {
         description "Router's IPv4 address";
         type jt:ipv4addr;
       }
       uses apply-advanced;
     }
     leaf boot-file {
       description "Boot filename advertised to clients";
       type string;
     }
     leaf boot-server {
       description "Boot server advertised to clients";
       type string {
       }
     }
     leaf tftp-server {
       description "TFTP server IP address advertised to clients";
       type jt:ipv4addr;
     }
     container sip-server {
       description "SIP servers to clients";
       uses apply-advanced;
       list name {
         key name;
         description "SIP server domain name available to clients";
         leaf name {
           description "SIP server name";
           type string;
         }
         uses apply-advanced;
       }
       list ip-address {
         key name;
         description "SIP servers list of IPv4 addresses available to the client";
         leaf name {
           description "SIP server's IPv4 address";
           type jt:ipv4addr;
         }
         uses apply-advanced;
       }
     }
     leaf netbios-node-type {
       description "Type of NETBIOS node advertised to clients";
       type enumeration {
         enum "b-node" {
           description "Broadcast node";
         }
         enum "p-node" {
           description "Peer-to-peer node";
         }
         enum "m-node" {
           description "Mixed Node";
         }
         enum "h-node" {
           description "Hybrid node";
         }
       }
     }
     leaf sip-server-domain-name {
       description "SIP server domain name available to clients";
       type string {
       }
     }
     list sip-server-address {
       key name;
       ordered-by user;
       description "SIP Servers list of IPv6 addresses available to the client";
       leaf name {
         description "SIP Server's IPv6 address";
         type jt:ipv6addr;
       }
       uses apply-advanced;
     }
     list dns-server {
       key name;
       ordered-by user;
       description "Domain name servers available to the client";
       leaf name {
         description "DNS server's IPv6 address";
         type jt:ipv6addr;
       }
       uses apply-advanced;
     }
     leaf propagate-settings {
       description "Interface name for propagating TCP/IP Settings to pool";
       type string;
     }
     leaf-list propagate-ppp-settings {
       ordered-by user;
       description "PPP interface name for propagating DNS/WINS settings";
       type union {
         type jt:interface-name;
         type string {
           pattern "<.*>|$.*";
         }
       }
       max-elements 8;
     }
     list option {
       key name;
       ordered-by user;
       description "DHCP option";
       leaf name {
         description "DHCP option identifier code";
         type union {
           type uint32;
           type string {
             pattern "<.*>|$.*";
           }
         }
       }
       choice option-type-choice {
         case case_1 {
           leaf flag {
             description "Boolean flag value";
             type enumeration {
               enum "true" {
                 description "True value";
               }
               enum "false" {
                 description "False value";
               }
               enum "on" {
                 description "On value";
               }
               enum "off" {
                 description "Off value";
               }
             }
           }
         }
         case case_2 {
           leaf byte {
             description "Unsigned 8-bit value";
             type union {
               type uint8;
               type string {
                 pattern "<.*>|$.*";
               }
             }
           }
         }
         case case_3 {
           leaf short {
             description "Signed 16-bit numeric value";
             type union {
               type int16;
               type string {
                 pattern "<.*>|$.*";
               }
             }
           }
         }
         case case_4 {
           leaf unsigned-short {
             description "Unsigned 16-bit numeric value";
             type union {
               type uint16;
               type string {
                 pattern "<.*>|$.*";
               }
             }
           }
         }
         case case_5 {
           leaf integer {
             description "Signed 32-bit numeric value";
             type union {
               type int32;
               type string {
                 pattern "<.*>|$.*";
               }
             }
           }
         }
         case case_6 {
           leaf unsigned-integer {
             description "Unsigned 32-bit numeric value";
             type union {
               type uint32;
               type string {
                 pattern "<.*>|$.*";
               }
             }
           }
         }
         case case_7 {
           leaf hex-string {
             description "Hexadecimal string";
             type string {
               length "1 .. 510";
             }
           }
         }
         case case_8 {
           leaf string {
             description "Character string value";
             type string {
               length "1 .. 254";
             }
           }
         }
         case case_9 {
           leaf ip-address {
             description "IP address value";
             type jt:ipv4addr;
           }
         }
         case case_10 {
           leaf ipv6-address {
             description "IPV6 address value";
             type jt:ipv6addr;
           }
         }
         case case_11 {
           container array {
             presence "enable array";
             description "Array of values";
             uses apply-advanced;
             choice option-type-array-choice {
               case case_1 {
                 leaf-list flag {
                   ordered-by user;
                   description "Array of boolean flag values";
                   type enumeration {
                     enum "true" {
                       description "True value";
                     }
                     enum "false" {
                       description "False value";
                     }
                     enum "on" {
                       description "On value";
                     }
                     enum "off" {
                       description "Off value";
                     }
                   }
                 }
               }
               case case_2 {
                 leaf-list byte {
                   ordered-by user;
                   description "Array of unsigned 8-bit values";
                   type union {
                     type uint8;
                     type string {
                       pattern "<.*>|$.*";
                     }
                   }
                 }
               }
               case case_3 {
                 leaf-list short {
                   ordered-by user;
                   description "Array of signed 16-bit numeric values";
                   type union {
                     type int16;
                     type string {
                       pattern "<.*>|$.*";
                     }
                   }
                 }
               }
               case case_4 {
                 leaf-list unsigned-short {
                   ordered-by user;
                   description "Array of 16-bit numeric values";
                   type union {
                     type uint16;
                     type string {
                       pattern "<.*>|$.*";
                     }
                   }
                 }
               }
               case case_5 {
                 leaf-list integer {
                   ordered-by user;
                   description "Array of signed 32-bit numeric values";
                   type union {
                     type int32;
                     type string {
                       pattern "<.*>|$.*";
                     }
                   }
                 }
               }
               case case_6 {
                 leaf-list unsigned-integer {
                   ordered-by user;
                   description "Array of unsigned 32-bit numeric values";
                   type union {
                     type uint32;
                     type string {
                       pattern "<.*>|$.*";
                     }
                   }
                 }
               }
               case case_7 {
                 leaf-list hex-string {
                   ordered-by user;
                   description "Hexadecimal string";
                   type string {
                     length "1 .. 510";
                   }
                 }
               }
               case case_8 {
                 leaf-list string {
                   ordered-by user;
                   description "Array of character string values";
                   type string {
                     length "1 .. 254";
                   }
                 }
               }
               case case_9 {
                 leaf-list ip-address {
                   ordered-by user;
                   description "Array of IP address values";
                   type jt:ipv4addr;
                 }
               }
               case case_10 {
                 leaf-list ipv6-address {
                   ordered-by user;
                   description "Array of IPv6 address values";
                   type jt:ipv6addr;
                 }
               }
             }
           }
         }
       }
     }
     leaf valid-lifetime {
       description "Valid lifetime advertised to clients";
       units "seconds";
       type string;
     }
     leaf preferred-lifetime {
       description "Preferred lifetime advertised to clients";
       units "seconds";
       type string;
     }
     leaf t1-percentage {
       description "T1 time as percentage of preferred lifetime or max lease";
       units "percent";
       type union {
         type string {
           pattern "<.*>|$.*";
         }
         type uint32 {
           range "0 .. 100";
         }
       }
     }
     leaf t2-percentage {
       description "T2 time as percentage of preferred lifetime or max lease";
       units "percent";
       type union {
         type string {
           pattern "<.*>|$.*";
         }
         type uint32 {
           range "0 .. 100";
         }
       }
     }
     leaf exclude-prefix-len {
       description "Length of IPv6 prefix to be excluded from delegated prefix";
       type union {
         type string {
           pattern "<.*>|$.*";
         }
         type uint32 {
           range "1 .. 128";
         }
       }
     }
     leaf t1-renewal-time {
       description "T1 renewal time";
       units "seconds";
       type union {
         type uint32;
         type string {
           pattern "<.*>|$.*";
         }
       }
     }
     leaf t2-rebinding-time {
       description "T2 rebinding time";
       units "seconds";
       type union {
         type uint32;
         type string {
           pattern "<.*>|$.*";
         }
       }
     }
   }
   grouping domain-map-type {
     description "Domain map configuration";
     uses apply-advanced;
     list map {
       key name;
       ordered-by user;
       description "Domain map definitions";
       leaf name {
         description "Domain map name";
         type string {
           length "1 .. 64";
         }
       }
       uses apply-advanced;
       choice aaa_ri_or_ls {
         case case_1 {
           leaf aaa-routing-instance {
             description "Routing instance to be used for applying AAA services";
             type string;
           }
         }
         case case_2 {
           list aaa-logical-system {
             key name;
             ordered-by user;
             description "Logical system to be used for applying AAA services";
             max-elements 1;
             leaf name {
               description "Logical system name";
               type string;
             }
             uses apply-advanced;
             leaf aaa-routing-instance {
               description "Routing instance to be used for applying AAA services";
               type string;
             }
           }
         }
       }
       leaf access-profile {
         description "Access profile to be used for applying AAA services";
         type string {
           length "1 .. 63";
         }
       }
       leaf address-pool {
         description "Address pool to use for providing address-allocation services";
         type string {
           length "1 .. 63";
         }
       }
       leaf dynamic-profile {
         description "Dynamic profile to be used for this client's session";
         type string;
       }
       leaf override-password {
         description "Use this password for authentication";
         type string {
           length "1 .. 64";
         }
       }
       leaf override-chap-password {
         description "Use this CHAP password for authentication";
         type string {
           length "1 .. 64";
         }
       }
       leaf using-user-password {
         description "Send overridden CHAP-Password using User-Password";
         type empty;
       }
       list padn {
         key name;
         ordered-by user;
         description "PPPoE Active Discovery Network parameters to apply for this client's session";
         status deprecated;
         max-elements 16;
         leaf name {
           description "Destination IP address";
           type jt:ipv4addr;
         }
         uses apply-advanced;
         leaf mask {
           description "Destination mask";
           type jt:ipv4addr;
         }
         leaf metric {
           description "Metric value";
           type union {
             type string {
               pattern "<.*>|$.*";
             }
             type uint16 {
               range "0 .. 255";
             }
           }
         }
       }
       choice target_ri_or_ls {
         case case_1 {
           leaf target-routing-instance {
             description "Routing instance the client's session will be mapped to";
             type string;
           }
         }
         case case_2 {
           list target-logical-system {
             key name;
             ordered-by user;
             description "Logical system the client's session will be mapped to";
             max-elements 1;
             leaf name {
               description "Logical system name";
               type string;
             }
             uses apply-advanced;
             leaf target-routing-instance {
               description "Routing instance the client's session will be mapped to";
               type string;
             }
           }
         }
       }
       leaf strip-domain {
         description "Enable domain name stripping from the username";
         type empty;
       }
       container strip-username {
         presence "enable strip-username";
         description "Enable user name stripping from the username";
         choice direction {
           case case_1 {
             leaf right-to-left {
               description "Strip to first domain delimiter on the right";
               type empty;
             }
           }
           case case_2 {
             leaf left-to-right {
               description "Strip to first domain delimiter on the left";
               type empty;
             }
           }
         }
       }
       leaf tunnel-profile {
         description "Tunnel profile to be used for this client's session";
         type string;
       }
       leaf tunnel-switch-profile {
         description "Tunnel switch profile";
         type string;
       }
       list sub-domain {
         key name;
         ordered-by user;
         description "Sub-Domain definitions";
         max-elements 16;
         leaf name {
           description "Sub-Domain name";
           type string {
             length "1 .. 64";
           }
         }
         uses apply-advanced;
         choice aaa_ri_or_ls {
           case case_1 {
             leaf aaa-routing-instance {
               description "Routing instance to be used for applying AAA services";
               type string;
             }
           }
           case case_2 {
             list aaa-logical-system {
               key name;
               ordered-by user;
               description "Logical system to be used for applying AAA services";
               max-elements 1;
               leaf name {
                 description "Logical system name";
                 type string;
               }
               uses apply-advanced;
               leaf aaa-routing-instance {
                 description "Routing instance to be used for applying AAA services";
                 type string;
               }
             }
           }
         }
         leaf access-profile {
           description "Access profile to be used for applying AAA services";
           type string {
             length "1 .. 63";
           }
         }
         leaf address-pool {
           description "Address pool to use for providing address-allocation services";
           type string {
             length "1 .. 63";
           }
         }
         leaf dynamic-profile {
           description "Dynamic profile to be used for this client's session";
           type string;
         }
         leaf override-password {
           description "Use this password for authentication";
           type string {
             length "1 .. 64";
           }
         }
         leaf override-chap-password {
           description "Use this CHAP password for authentication";
           type string {
             length "1 .. 64";
           }
         }
         leaf using-user-password {
           description "Send overridden CHAP-Password using User-Password";
           type empty;
         }
         list padn {
           key name;
           ordered-by user;
           description "PPPoE Active Discovery Network parameters to apply for this client's session";
           status deprecated;
           max-elements 16;
           leaf name {
             description "Destination IP address";
             type jt:ipv4addr;
           }
           uses apply-advanced;
           leaf mask {
             description "Destination mask";
             type jt:ipv4addr;
           }
           leaf metric {
             description "Metric value";
             type union {
               type string {
                 pattern "<.*>|$.*";
               }
               type uint16 {
                 range "0 .. 255";
               }
             }
           }
         }
         choice target_ri_or_ls {
           case case_1 {
             leaf target-routing-instance {
               description "Routing instance the client's session will be mapped to";
               type string;
             }
           }
           case case_2 {
             list target-logical-system {
               key name;
               ordered-by user;
               description "Logical system the client's session will be mapped to";
               max-elements 1;
               leaf name {
                 description "Logical system name";
                 type string;
               }
               uses apply-advanced;
               leaf target-routing-instance {
                 description "Routing instance the client's session will be mapped to";
                 type string;
               }
             }
           }
         }
         leaf strip-domain {
           description "Enable domain name stripping from the username";
           type empty;
         }
         container strip-username {
           presence "enable strip-username";
           description "Enable user name stripping from the username";
           choice direction {
             case case_1 {
               leaf right-to-left {
                 description "Strip to first domain delimiter on the right";
                 type empty;
               }
             }
             case case_2 {
               leaf left-to-right {
                 description "Strip to first domain delimiter on the left";
                 type empty;
               }
             }
           }
         }
         leaf tunnel-profile {
           description "Tunnel profile to be used for this client's session";
           type string;
         }
         leaf tunnel-switch-profile {
           description "Tunnel switch profile";
           type string;
         }
         container qualifier {
           description "Qualifier definition for sub-domain";
           uses apply-advanced;
           choice sub_domain_qualifier_choice {
             case case_1 {
               leaf-list vlan-id-list {
                 description "Apply access-profile only for the vlan-id specified in the vlan-id-list";
                 type jt:vlan-range;
               }
             }
           }
         }
       }
     }
     container parse-order {
       description "Order in which search parsing is conducted (i.e. look for domain-namd or realm-name first)";
       choice order {
         case case_1 {
           leaf domain-first {
             description "Search for domain name in username field before searching for realm name";
             type empty;
           }
         }
         case case_2 {
           leaf realm-first {
             description "Search for realm name in username field before searching for domain name";
             type empty;
           }
         }
       }
     }
     container delimiter {
       description "Allowable delimiter characters for domain name separation";
       leaf characters {
         description "Sequence of characters without spaces and commas";
         type string {
           length "1 .. 8";
         }
       }
     }
     container parse-direction {
       description "Domain name parsing direction";
       choice direction {
         case case_1 {
           leaf right-to-left {
             description "Parse the username from right to left";
             type empty;
           }
         }
         case case_2 {
           leaf left-to-right {
             description "Parse the username field from left to right to find domain name";
             type empty;
           }
         }
       }
     }
     container realm-delimiter {
       description "Allowable delimiter characters for realm name separation";
       leaf characters {
         description "Sequence of characters without spaces and commas";
         type string {
           length "1 .. 8";
         }
       }
     }
     container realm-parse-direction {
       description "Realm name parsing direction";
       choice direction {
         case case_1 {
           leaf left-to-right {
             description "Parse the username field from left to right to find realm name";
             type empty;
           }
         }
         case case_2 {
           leaf right-to-left {
             description "Parse the username field from right to left to find realm name";
             type empty;
           }
         }
       }
     }
   }
   grouping dynamic-dhcp-attribute-type {
     uses apply-advanced;
     leaf maximum-lease-time {
       description "Maximum lease time advertised to clients";
       units "seconds";
       type string;
     }
     leaf valid-lifetime {
       description "Preferred lifetime";
       units "seconds";
       type string;
     }
     leaf preferred-lifetime {
       description "Preferred lifetime";
       units "seconds";
       type string;
     }
     list dns-server {
       key name;
       ordered-by user;
       description "Domain name servers available to the client";
       leaf name {
         description "DNS server's IPv6 address";
         type jt:ipv6addr;
       }
       uses apply-advanced;
     }
     leaf t1-percentage {
       description "T1 time as percentage of preferred lifetime advertised to clients";
       units "percent";
       type union {
         type string {
           pattern "<.*>|$.*";
         }
         type uint32 {
           range "0 .. 100";
         }
       }
     }
     leaf t2-percentage {
       description "T2 time as percentage of preferred lifetime advertised to clients";
       units "percent";
       type union {
         type string {
           pattern "<.*>|$.*";
         }
         type uint32 {
           range "0 .. 100";
         }
       }
     }
   }
   grouping group-profile-object {
     leaf name {
       description "Group profile name";
       type string {
         length "1 .. 63";
       }
     }
     uses apply-advanced;
     container ppp {
       presence "enable ppp";
       description "Configuration for Point-to-Point Protocol";
       uses apply-advanced;
       leaf framed-pool {
         description "Address pool used to assign an address for the user";
         type string {
           length "1 .. 63";
         }
       }
       leaf idle-timeout {
         description "Idle timeout before termination of session";
         default "0";
         units "seconds";
         type union {
           type string {
             pattern "<.*>|$.*";
           }
           type uint32 {
             range "0 .. 4294967295";
           }
         }
       }
       container ppp-options {
         presence "enable ppp-options";
         description "Point-to-Point Protocol interface-specific options";
         uses apply-advanced;
         leaf pap {
           description "Password Authentication Protocol";
           type empty;
         }
         leaf chap {
           description "Challenge Handshake Authentication Protocol";
           type empty;
         }
         leaf mru {
           description "The Maximum Receive Unit size in bytes";
           type union {
             type string {
               pattern "<.*>|$.*";
             }
             type uint32 {
               range "64 .. 9192";
             }
           }
         }
         leaf mtu {
           description "The Maximum Transfer Unit size in bytes";
           type string;
         }
         container initiate-ncp {
           description "Enable server initiated NCP";
           uses apply-advanced;
           leaf ip {
             description "Enable server initiated IPNCP";
             type empty;
           }
           leaf ipv6 {
             description "Enable server initiated IPv6NCP";
             type empty;
           }
           leaf dual-stack-passive {
             description "Disable server initiated IPNCP/IPv6NCP for dual-stack client";
             type empty;
           }
         }
         leaf peer-ip-address-optional {
           description "Set Peer IP Address Optional in IP NCP Negotiations";
           type empty;
         }
         leaf ipcp-suggest-dns-option {
           description "Suggest peer to negotiate with DNS Addresses options";
           type empty;
         }
         leaf ignore-magic-number-mismatch {
           description "Ignore magic-number validation failure in LCP keepalive";
           type empty;
         }
         leaf aaa-options {
           description "Attach AAA options name to group-profile";
           type string {
             length "1 .. 63";
           }
         }
       }
       leaf keepalive {
         description "PPP keepalive interval";
         default "10";
         units "seconds";
         type union {
           type string {
             pattern "<.*>|$.*";
           }
           type uint16 {
             range "0 .. 32767";
           }
         }
       }
       leaf primary-dns {
         description "Primary DNS server name";
         type string;
       }
       leaf secondary-dns {
         description "Secondary DNS server name";
         type string;
       }
       leaf primary-wins {
         description "Primary wins server name";
         type string;
       }
       leaf secondary-wins {
         description "Secondary wins server name";
         type string;
       }
       leaf encapsulation-overhead {
         description "Encapsulation overhead for Class of Service calculation";
         type union {
           type string {
             pattern "<.*>|$.*";
           }
           type int8 {
             range "-63 .. 64";
           }
         }
       }
       leaf cell-overhead {
         description "ATM cell overhead for Class of Service calculation";
         type empty;
       }
       leaf interface-id {
         description "Interface identifier to look up session information";
         type string {
           length "1 .. 63";
         }
       }
     }
     container l2tp {
       presence "enable l2tp";
       description "Configuration for Layer 2 Tunneling Protocol";
       uses apply-advanced;
       leaf maximum-sessions {
         description "Maximum number of sessions per client";
         type union {
           type uint32;
           type string {
             pattern "<.*>|$.*";
           }
         }
       }
       leaf maximum-sessions-per-tunnel {
         description "Maximum number of sessions per L2TP tunnel";
         default "0";
         type union {
           type uint16;
           type string {
             pattern "<.*>|$.*";
           }
         }
       }
       leaf service-profile {
         description "Dynamic service profile(s) to be applied to this session";
         type string;
       }
       leaf interface-id {
         description "Interface identifier for PPP users missing one";
         type string {
           length "1 .. 63";
         }
       }
       leaf lcp-renegotiation {
         description "Force renegotiation of LCP options";
         type empty;
       }
       leaf local-chap {
         description "Force local CHAP challenge";
         type empty;
       }
       container override-result-code {
         description "Override result code with admin value in CDN message at LNS";
         uses apply-advanced;
         leaf session-out-of-resource {
           description "Override result code for session out-of-resource due to permanent or temporary condition with admin value in CDN message at LNS";
           type empty;
         }
       }
       container multilink {
         description "Multilink Point-to-Point Protocol command options";
         presence "enable multilink";
         uses multilink-object;
       }
     }
   }
   grouping gx-plus-definition {
     description "GX-PLUS configuration definition";
     uses apply-advanced;
     list partition {
       key name;
       ordered-by user;
       description "GX-PLUS partition configuration";
       leaf name {
         description "GX-PLUS partition name";
         type string {
           length "1 .. 63";
         }
       }
       uses apply-advanced;
       leaf diameter-instance {
         description "GX-PLUS diameter instance";
         type string {
           length "1 .. 63";
         }
       }
       leaf destination-realm {
         description "GX-PLUS destination realm";
         type string {
           length "1 .. 255";
         }
       }
       leaf destination-host {
         description "GX-PLUS destination host";
         type string {
           length "1 .. 255";
         }
       }
     }
     container global {
       presence "enable global";
       description "GX-PLUS global parameters";
       uses apply-advanced;
       leaf include-ipv6 {
         description "Send provisioning request for IPv6-only subscribers";
         type empty;
       }
       leaf max-outstanding-requests {
         description "Maximum number of outstanding requests";
         default "40";
         type union {
           type string {
             pattern "<.*>|$.*";
           }
           type uint32 {
             range "2 .. 40";
           }
         }
       }
     }
   }
   grouping juniper-mobile-diameter {
     description "Diameter protocol layer";
     uses apply-advanced;
     container traceoptions {
       description "Trace options related to DIAMETER servers";
       uses diameter-traceoptions;
     }
     container origin {
       presence "enable origin";
       description "Origin attributes of this diameter instance";
       uses apply-advanced;
       leaf realm {
         description "Origin realm of this diameter instance";
         type string {
           length "1 .. 255";
         }
       }
       leaf host {
         description "Origin host of this diameter instance";
         type string {
           length "1 .. 255";
         }
       }
     }
     leaf vendor-id {
       description "Vendor-Id to advertize in Capability-Exchange";
       default "2636";
       type union {
         type string {
           pattern "<.*>|$.*";
         }
         type uint32 {
           range "1 .. 4294967295";
         }
       }
     }
     leaf firmware-revision {
       description "Firmware-Revision to advertize in Capability-Exchange";
       default "0";
       type union {
         type string {
           pattern "<.*>|$.*";
         }
         type uint32 {
           range "0 .. 4294967295";
         }
       }
     }
     leaf product-name {
       description "Product-Name to advertize in Capability-Exchange";
       type string {
         length "1 .. 127";
       }
     }
     list network-element {
       key name;
       ordered-by user;
       description "Network element of this diameter instance";
       leaf name {
         description "Name for this network element";
         type string {
           length "1 .. 31";
         }
       }
       uses apply-advanced;
       leaf-list function {
         ordered-by user;
         description "Diameter function associated with by this network element";
         type enumeration {
           enum "pcc-gx" {
             description "Policy and Charging Control Application Gx function";
           }
           enum "dcca-gy" {
             description "Diameter Credit Control Application Gy function";
           }
         }
         max-elements 3;
       }
       list peer {
         key name;
         ordered-by user;
         description "Peer associated with this network element";
         leaf name {
           description "Name of a peer associated with this network element";
           type string {
             length "1 .. 31";
           }
         }
         uses apply-advanced;
         leaf priority {
           description "Peer priority with this network element";
           type union {
             type string {
               pattern "<.*>|$.*";
             }
             type uint32 {
               range "1 .. 65535";
             }
           }
         }
         leaf timeout {
           description "Peer timeout with this network element in seconds";
           default "4";
           type union {
             type string {
               pattern "<.*>|$.*";
             }
             type uint32 {
               range "1 .. 100";
             }
           }
         }
       }
     }
     list transport {
       key name;
       ordered-by user;
       description "Diameter transport configuration";
       max-elements 31;
       leaf name {
         description "Name for this transport definition";
         type string {
           length "1 .. 31";
         }
       }
       uses apply-advanced;
       leaf address {
         description "Source IP address for a peer";
         type jt:ipaddr;
       }
       choice instance {
         case case_1 {
           container logical-system {
             description "Logical system to be used by transport";
             status deprecated;
             leaf logical-system-name {
               description "Name of logical system";
               type string {
               }
             }
             leaf routing-instance {
               description "Routing instance to be used by transport";
               type union {
                 type string {
                   pattern "default";
                 }
                 type string {
                 }
               }
             }
           }
         }
         case case_2 {
           leaf routing-instance {
             description "Routing instance of server to which to forward";
             type union {
               type string {
                 pattern "default";
               }
               type string {
               }
             }
           }
         }
       }
     }
     list peer {
       key name;
       ordered-by user;
       description "Diameter peer configuration";
       max-elements 31;
       leaf name {
         description "Name for this Diameter peer";
         type string {
           length "1 .. 31";
         }
       }
       uses apply-advanced;
       leaf address {
         description "IP Address of Diameter peer";
         type jt:ipaddr;
       }
       container connect-actively {
         presence "enable connect-actively";
         uses apply-advanced;
         leaf transport {
           description "Name of transport";
           type string {
             length "1 .. 31";
           }
         }
         leaf port {
           description "Peer port";
           default "3868";
           type union {
             type string {
               pattern "<.*>|$.*";
             }
             type uint16 {
               range "1 .. 65535";
             }
           }
         }
         leaf capabilities-exchange-timeout {
           description "Time to wait in Wait-I-CEA state";
           default "10";
           units "seconds";
           type union {
             type string {
               pattern "<.*>|$.*";
             }
             type uint32 {
               range "1 .. 65535";
             }
           }
         }
         leaf repeat-timeout {
           description "Timer to reconnect after getting DO_NOT_WANT_TO_TALK_TO_YOU in DPR";
           default "0";
           units "seconds";
           type union {
             type string {
               pattern "<.*>|$.*";
             }
             type uint32 {
               range "0 .. 65535";
             }
           }
         }
         leaf retry-timeout {
           description "Time to wait between connection attempts";
           default "30";
           units "seconds";
           type union {
             type string {
               pattern "<.*>|$.*";
             }
             type uint32 {
               range "1 .. 65535";
             }
           }
         }
         leaf timeout {
           description "Time to wait in Wait-Conn-Ack state";
           default "10";
           units "seconds";
           type union {
             type string {
               pattern "<.*>|$.*";
             }
             type uint32 {
               range "1 .. 65535";
             }
           }
         }
       }
       container incoming-queue {
         presence "enable incoming-queue";
         description "Incoming queue properties of this peer";
         uses apply-advanced;
         leaf size {
           description "Incoming queue size for this peer";
           type union {
             type string {
               pattern "<.*>|$.*";
             }
             type uint32 {
               range "1 .. 65535";
             }
           }
         }
       }
       container outgoing-queue {
         presence "enable outgoing-queue";
         description "Outgoing queue properties of this peer";
         uses apply-advanced;
         leaf size {
           description "Outgoing queue size for this peer";
           type union {
             type string {
               pattern "<.*>|$.*";
             }
             type uint32 {
               range "1 .. 65535";
             }
           }
         }
         leaf low-watermark {
           description "Low watermark in percentage for outgoing queue of this peer";
           default "60";
           type union {
             type string {
               pattern "<.*>|$.*";
             }
             type uint16 {
               range "1 .. 100";
             }
           }
         }
         leaf high-watermark {
           description "High watermark in percentage for outgoing queue of this peer";
           default "80";
           type union {
             type string {
               pattern "<.*>|$.*";
             }
             type uint16 {
               range "1 .. 100";
             }
           }
         }
       }
       leaf watchdog-timeout {
         description "Time to wait for Device-Watchdog-Answer";
         default "30";
         units "seconds";
         type union {
           type string {
             pattern "<.*>|$.*";
           }
           type uint32 {
             range "1 .. 65535";
           }
         }
       }
       leaf connection-timeout {
         description "Time to wait in Wait-Conn-Ack state";
         status deprecated;
         default "10";
         units "seconds";
         type union {
           type string {
             pattern "<.*>|$.*";
           }
           type uint32 {
             range "1 .. 65535";
           }
         }
       }
       leaf connection-repeat-timeout {
         description "Timer to reconnect after getting DO_NOT_WANT_TO_TALK_TO_YOU in DPR";
         status deprecated;
         default "0";
         units "seconds";
         type union {
           type string {
             pattern "<.*>|$.*";
           }
           type uint32 {
             range "0 .. 65535";
           }
         }
       }
       leaf capabilities-exchange-timeout {
         description "Time to wait in Wait-I-CEA state";
         status deprecated;
         default "10";
         units "seconds";
         type union {
           type string {
             pattern "<.*>|$.*";
           }
           type uint32 {
             range "1 .. 65535";
           }
         }
       }
       leaf disconnect-peer-timeout {
         description "Time to wait in Closing state";
         default "10";
         units "seconds";
         type union {
           type string {
             pattern "<.*>|$.*";
           }
           type uint32 {
             range "1 .. 65535";
           }
         }
       }
       leaf connection-retry-timeout {
         description "Time to wait between connection attempts";
         status deprecated;
         default "30";
         units "seconds";
         type union {
           type string {
             pattern "<.*>|$.*";
           }
           type uint32 {
             range "1 .. 65535";
           }
         }
       }
       leaf origin-host-prefix {
         description "Peer-specific prefix for local Origin-Host";
         type string {
           length "1 .. 255";
         }
       }
     }
     container applications {
       presence "enable applications";
       description "Diameter applications related configuration";
       uses apply-advanced;
       container pcc-gx {
         presence "enable pcc-gx";
         description "Policy and Charging Control Application Gx configuration";
         uses apply-advanced;
         leaf maximum-pending-requests {
           description "Maximum pending requests for this application";
           default "40000";
           type union {
             type string {
               pattern "<.*>|$.*";
             }
             type uint16 {
               range "1000 .. 65535";
             }
           }
         }
       }
       container dcca-gy {
         presence "enable dcca-gy";
         description "Diameter Credit Control Application Gy configuration";
         uses apply-advanced;
         leaf maximum-pending-requests {
           description "Maximum pending requests for this application";
           default "40000";
           type union {
             type string {
               pattern "<.*>|$.*";
             }
             type uint16 {
               range "1000 .. 65535";
             }
           }
         }
       }
     }
   }
   grouping diameter-traceoptions {
     description "Trace options related to DIAMETER peers";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "send" {
             description "Trace transmitted packets";
           }
           enum "send-detail" {
             description "Trace transmitted packets in detail";
           }
           enum "receive" {
             description "Trace received packets";
           }
           enum "receive-detail" {
             description "Trace received packets in detail";
           }
           enum "timeout" {
             description "Trace timeout events";
           }
           enum "state" {
             description "Trace DIAMTER peer state changes";
           }
           enum "all" {
             description "Trace everything";
           }
         }
       }
     }
     list peer {
       key name;
       ordered-by user;
       description "Trace packet sent to or received from the peer[s]";
       leaf name {
         description "Trace packet sent to or received from the peer";
         type string {
           length "1 .. 31";
         }
       }
       uses apply-advanced;
     }
   }
   grouping juniper-radius {
     uses apply-advanced;
     container traceoptions {
       description "Trace options related to RADIUS servers";
       uses radius-traceoptions;
     }
     list servers {
       key name;
       ordered-by user;
       description "RADIUS server configuration";
       uses juniper-radius-server;
     }
     list clients {
       key name;
       ordered-by user;
       description "RADIUS client configuration";
       uses juniper-radius-client;
     }
     list network-elements {
       key name;
       ordered-by user;
       description "Network element configuration";
       uses juniper-radius-network-element;
     }
     list network-element-groups {
       key name;
       ordered-by user;
       description "Network element group configuration";
       uses juniper-radius-network-element-group;
     }
     list snoop-segments {
       key name;
       ordered-by user;
       description "Radius snooping segments";
       uses juniper-radius-snoop-segment;
     }
   }
   grouping juniper-radius-client {
     description "RADIUS client configuration";
     leaf name {
       description "Name to identify the client[s]";
       type string {
         length "1 .. 31";
       }
     }
     uses apply-advanced;
     leaf address {
       description "RADIUS client ipv4address/prefix";
       type jt:ipv4prefix;
     }
     container source-interface {
       description "Source interface in which RADIUS packets will be rcvd";
       leaf interface-name {
         description "Interface name";
         type union {
           type jt:interface-name;
           type string {
             pattern "<.*>|$.*";
           }
         }
       }
       leaf ipv4-address {
         description "Source IPv4 address to be used";
         type jt:ipv4addr;
       }
     }
     leaf prefer-framed-ip-address {
       description "Prefer framed-ip-address/framed-netmask attributes over framed-route attribute";
       type empty;
     }
     leaf prefer-framed-ipv6-prefix {
       description "Prefer framed-ipv6-prefix attrbiute over delegated-ipv6-prefix attribute";
       type empty;
     }
     container accounting {
       presence "enable accounting";
       description "Accounting parameters";
       uses apply-advanced;
       leaf secret {
         description "Shared secret with RADIUS client for accounting";
         type string {
           length "1 .. 64";
         }
       }
       leaf response-cache-timeout {
         description "Accounting response Cache timeout period";
         default "3";
         units "seconds";
         type union {
           type string {
             pattern "<.*>|$.*";
           }
           type uint32 {
             range "1 .. 30";
           }
         }
       }
       leaf port {
         description "Radius clients accounting server port number";
         default "1813";
         type union {
           type string {
             pattern "<.*>|$.*";
           }
           type uint16 {
             range "1 .. 65535";
           }
         }
       }
     }
   }
   grouping juniper-radius-network-element {
     description "Network element configuration";
     leaf name {
       description "Network element name";
       type string {
         length "1 .. 31";
       }
     }
     uses apply-advanced;
     list server {
       key name;
       ordered-by user;
       description "RADIUS server and its priority";
       leaf name {
         description "RADIUS server name";
         type string {
           length "1 .. 31";
         }
       }
       leaf priority {
         description "Server priority";
         default "1";
         type union {
           type string {
             pattern "<.*>|$.*";
           }
           type uint32 {
             range "1 .. 16";
           }
         }
       }
     }
     leaf maximum-pending-reqs-limit {
       description "Maximum number of pending requests queued to the network-element";
       type union {
         type string {
           pattern "<.*>|$.*";
         }
         type uint32 {
           range "512 .. 8192";
         }
       }
     }
     leaf pending-queue-watermark {
       description "Watermark in percentage at which flow-control for pending queue           of this network-element is turned on";
       type union {
         type string {
           pattern "<.*>|$.*";
         }
         type uint32 {
           range "1 .. 99";
         }
       }
     }
     leaf pending-queue-watermark-abate {
       description "Watermark in percentage at which flow-control for pending queue          of this network-element is turned off";
       type union {
         type string {
           pattern "<.*>|$.*";
         }
         type uint32 {
           range "1 .. 99";
         }
       }
     }
   }
   grouping juniper-radius-network-element-group {
     description "Network element group configuration";
     leaf name {
       description "Network element group name";
       type string {
         length "1 .. 31";
       }
     }
     uses apply-advanced;
     list network-element {
       key name;
       ordered-by user;
       description "Specify the network-elements in this group";
       max-elements 4;
       leaf name {
         description "Network element name";
         type string {
           length "1 .. 31";
         }
       }
       leaf mandatory {
         description "This network-element must respond to the request";
         type empty;
       }
     }
     leaf broadcast {
       description "Send the request to all network-elements in the group";
       type empty;
     }
   }
   grouping juniper-radius-server {
     description "RADIUS server configuration";
     leaf name {
       description "Name to identify the server";
       type string {
         length "1 .. 31";
       }
     }
     uses apply-advanced;
     leaf address {
       description "RADIUS server address";
       type jt:ipv4addr;
     }
     leaf port {
       description "RADIUS server authentication port number";
       default "1812";
       type union {
         type string {
           pattern "<.*>|$.*";
         }
         type uint16 {
           range "1 .. 65535";
         }
       }
     }
     leaf preauthentication-port {
       description "RADIUS server preauthentication port number";
       type union {
         type string {
           pattern "<.*>|$.*";
         }
         type uint16 {
           range "1 .. 65535";
         }
       }
     }
     leaf accounting-port {
       description "RADIUS server accounting port number";
       default "1813";
       type union {
         type string {
           pattern "<.*>|$.*";
         }
         type uint16 {
           range "1 .. 65535";
         }
       }
     }
     leaf dynamic-request-port {
       description "RADIUS client dynamic request port number";
       default "3799";
       type union {
         type string {
           pattern "<.*>|$.*";
         }
         type uint16 {
           range "1 .. 65535";
         }
       }
     }
     leaf secret {
       description "Shared secret with RADIUS server";
       type string {
         length "1 .. 64";
       }
     }
     leaf accounting-secret {
       description "Shared secret with RADIUS server for accounting";
       type string {
         length "1 .. 64";
       }
     }
     leaf allow-dynamic-requests {
       description "Allows dynamic-requests to be received from the radius server";
       type empty;
     }
     leaf dynamic-request-secret {
       description "Shared secret with RADIUS client for dynamic-requests";
       type string {
         length "1 .. 64";
       }
     }
     leaf timeout {
       description "Request timeout period";
       default "3";
       units "seconds";
       type union {
         type string {
           pattern "<.*>|$.*";
         }
         type uint32 {
           range "1 .. 90";
         }
       }
     }
     leaf retry {
       description "Retry attempts";
       default "3";
       type union {
         type string {
           pattern "<.*>|$.*";
         }
         type uint32 {
           range "1 .. 10";
         }
       }
     }
     container dead-criteria {
       description "Dead server detection criteria";
       leaf retries {
         description "Number of retransmits before marking the server dead";
         type union {
           type string {
             pattern "<.*>|$.*";
           }
           type uint16 {
             range "10 .. 65535";
           }
         }
       }
       leaf interval {
         description "Interval during which the number of retries are tracked";
         units "seconds";
         type union {
           type string {
             pattern "<.*>|$.*";
           }
           type uint16 {
             range "5 .. 300";
           }
         }
       }
       leaf revert-interval {
         description "Rervert-interval period";
         default "300";
         units "seconds";
         type union {
           type string {
             pattern "<.*>|$.*";
           }
           type uint32 {
             range "0 .. 4294967295";
           }
         }
       }
     }
     container source-interface {
       description "Source interface from which RADIUS packets will be sent";
       leaf interface-name {
         description "Interface name";
         type union {
           type jt:interface-name;
           type string {
             pattern "<.*>|$.*";
           }
         }
       }
       leaf ipv4-address {
         description "Source IPv4 address to be used";
         type jt:ipv4addr;
       }
     }
   }
   grouping juniper-radius-snoop-segment {
     description "Radius snooping segment configuration";
     leaf name {
       description "Name to identify radius snoop segment[s]";
       type string {
         length "1 .. 32";
       }
     }
     uses apply-advanced;
     leaf destination-ip-address {
       description "Destination address of snoop segment";
       type jt:ipv4addr;
     }
     leaf source-ip-address {
       description "Source address of snoop segment";
       type jt:ipv4addr;
     }
     leaf destination-port {
       description "Destination port of snoop segment";
       default "1813";
       type union {
         type string {
           pattern "<.*>|$.*";
         }
         type uint16 {
           range "1 .. 65535";
         }
       }
     }
     leaf shared-secret {
       description "Shared secret between source and destination of snoop segment";
       type string {
         length "1 .. 64";
       }
     }
     container source-interface {
       description "Source interface on which packets have to be snooped";
       leaf interface-name {
         description "Interface name";
         type union {
           type jt:interface-name;
           type string {
             pattern "<.*>|$.*";
           }
         }
       }
     }
     leaf request-cache-timeout {
       description "Time duration to cache request";
       default "30";
       units "seconds";
       type union {
         type string {
           pattern "<.*>|$.*";
         }
         type uint32 {
           range "1 .. 30";
         }
       }
     }
   }
   grouping ldap-allowed-groups-object {
     leaf name {
       description "LDAP Group name";
       type string {
         length "1 .. 63";
       }
     }
     uses apply-advanced;
     container address-assignment {
       description "Address assignment pool";
       uses apply-advanced;
       leaf pool {
         description "Name of address-assignment pool";
         type string {
           length "1 .. 63";
         }
       }
       leaf inet6-pool {
         description "Name of address-assignment pool for family inet6";
         type string {
           length "1 .. 63";
         }
       }
     }
   }
   grouping ldap-server-object {
     leaf name {
       description "Hostname or IPv4 address of LDAP server";
       type string {
       }
     }
     uses apply-advanced;
     leaf port {
       description "LDAP server port number";
       default "389";
       type union {
         type string {
           pattern "<.*>|$.*";
         }
         type uint16 {
           range "1 .. 65535";
         }
       }
     }
     leaf source-address {
       description "Use specified address as source address";
       type jt:ipv4addr;
     }
     leaf routing-instance {
       description "Use specified routing instance";
       type string;
     }
     leaf retry {
       description "Number of times to resend requests";
       default "3";
       type union {
         type string {
           pattern "<.*>|$.*";
         }
         type uint32 {
           range "1 .. 10";
         }
       }
     }
     leaf timeout {
       description "Delay before resending unacknowledged request";
       default "5";
       units "seconds";
       type union {
         type string {
           pattern "<.*>|$.*";
         }
         type uint32 {
           range "3 .. 90";
         }
       }
     }
     leaf tls-type {
       type enumeration {
         enum "start-tls" {
           description "Negotiate start-tls for connection";
         }
       }
     }
     leaf tls-timeout {
       description "Limit on tls handshake time";
       default "5";
       units "seconds";
       type union {
         type string {
           pattern "<.*>|$.*";
         }
         type uint32 {
           range "3 .. 90";
         }
       }
     }
     leaf tls-min-version {
       default "v1.2";
       type enumeration {
         enum "v1.1" {
           description "Require tls 1.1 and 1.2";
         }
         enum "v1.2" {
           description "Require tls 1.2";
         }
       }
     }
     leaf no-tls-certificate-check {
       description "Do not validate peer certificate";
       type empty;
     }
     leaf tls-peer-name {
       description "Expected peer fdqn";
       type string {
         length "1 .. 255";
       }
     }
   }
   grouping localauth-subscriber-object {
     leaf name {
       description "Subscriber username";
       type string;
     }
     uses apply-advanced;
     leaf password {
       description "Password for the subscriber";
       type string {
         length "1 .. 64";
       }
     }
     leaf framed-ip-address {
       description "IP address to assign to the subscriber";
       type jt:ipv4addr;
     }
     leaf framed-pool {
       description "Pool name to assign an IP address to the subscriber";
       type string {
         length "1 .. 63";
       }
     }
     leaf delegated-pool {
       description "Pool name to assign an IPv6 delegated prefix to the subscriber";
       type string {
         length "1 .. 64";
       }
     }
     leaf framed-ipv6-pool {
       description "Pool name to assign an IPv6 address or NDRA prefix to the subscriber";
       type string {
         length "1 .. 64";
       }
     }
     choice ri_or_ls {
       case case_1 {
         leaf target-routing-instance {
           description "Routing instance to be assigned to the subscriber";
           type string;
         }
       }
       case case_2 {
         container target-logical-system {
           presence "enable target-logical-system";
           description "Logical system to be assigned to the subscriber";
           uses apply-advanced;
           leaf logical-system-name {
             description "Logical system name";
             type string;
           }
           leaf target-routing-instance {
             description "Routing instance ";
             type string;
           }
         }
       }
     }
   }
   grouping macro-data-type {
     leaf name {
       description "Keyword part of the keyword-value pair";
       type string;
     }
     leaf value {
       description "Value part of the keyword-value pair";
       type string;
     }
   }
   grouping multilink-object {
     description "Configuration for Multilink";
     uses apply-advanced;
     leaf fragment-threshold {
       description "Fragmentation threshold";
       units "bytes";
       type union {
         type string {
           pattern "<.*>|$.*";
         }
         type uint16 {
           range "128 .. 9192";
         }
       }
     }
     leaf drop-timeout {
       description "Drop timeout";
       default "0";
       units "milliseconds";
       type union {
         type string {
           pattern "<.*>|$.*";
         }
         type uint16 {
           range "0 .. 2000";
         }
       }
     }
   }
   grouping nas-5g-definition {
     description "NAS-5G configuration definition";
     uses apply-advanced;
     leaf max-outstanding-requests {
       description "Number of unanswered NAS-5G signalling requests";
       default "40";
       type union {
         type string {
           pattern "<.*>|$.*";
         }
         type uint32 {
           range "20 .. 2000";
         }
       }
     }
     leaf request-retry {
       description "Number of times to retry a NAS-5G signalling request that fails or times-out";
       default "0";
       type union {
         type string {
           pattern "<.*>|$.*";
         }
         type uint32 {
           range "0 .. 3";
         }
       }
     }
     leaf timeout {
       description "Time period that a NAS-5G signalling request waits before failing";
       default "20";
       units "seconds";
       type union {
         type string {
           pattern "<.*>|$.*";
         }
         type uint32 {
           range "5 .. 30";
         }
       }
     }
   }
   grouping nasreq-definition {
     description "NASREQ configuration definition";
     uses apply-advanced;
     list partition {
       key name;
       ordered-by user;
       description "NASREQ partition definition";
       leaf name {
         description "NASREQ partition name";
         type string {
           length "1 .. 63";
         }
       }
       uses apply-advanced;
       leaf diameter-instance {
         description "NASREQ diameter instance";
         type string {
           length "1 .. 63";
         }
       }
       leaf destination-realm {
         description "NASREQ destination realm";
         type string {
           length "1 .. 255";
         }
       }
       leaf destination-host {
         description "NASREQ destination host";
         type string {
           length "1 .. 255";
         }
       }
     }
     leaf timeout {
       description "Time period that a NASREQ request waits on the transmit queue before failing";
       default "20";
       units "seconds";
       type union {
         type string {
           pattern "<.*>|$.*";
         }
         type uint32 {
           range "5 .. 30";
         }
       }
     }
     leaf request-retry {
       description "Number of times to retry NASREQ request when DIAMETER fails with timeout.";
       default "0";
       type union {
         type string {
           pattern "<.*>|$.*";
         }
         type uint32 {
           range "0 .. 3";
         }
       }
     }
     leaf max-outstanding-requests {
       description "Number of unanswered NASREQ requests sent to server";
       default "40";
       type union {
         type string {
           pattern "<.*>|$.*";
         }
         type uint32 {
           range "20 .. 2000";
         }
       }
     }
   }
   grouping ocs-definition {
     description "OCS configuration definition";
     uses apply-advanced;
     list partition {
       key name;
       ordered-by user;
       description "OCS partition configuration";
       max-elements 1;
       leaf name {
         description "OCS partition name";
         type string {
           length "1 .. 63";
         }
       }
       uses apply-advanced;
       leaf alternative-partition-name {
         description "Alternative diameter partition";
         type string {
           length "1 .. 63";
         }
       }
       leaf called-station-id {
         description "OCS called station id";
         type string {
           length "1 .. 255";
         }
       }
       container backup {
         description "OCS Backup feature";
         uses apply-advanced;
         leaf limit {
           description "Maximium number of subscriber in backup";
           default "1024";
           type union {
             type string {
               pattern "<.*>|$.*";
             }
             type uint32 {
               range "256 .. 262144";
             }
           }
         }
         leaf overflow {
           description "Backup overflow action";
           default "deny-login";
           type enumeration {
             enum "deny-login" {
               description "Deny login for new subscribers in backup overlow state";
             }
             enum "drop-oldest" {
               description "Drop oldest backup entries in backup overlow state";
             }
           }
         }
         leaf timeout {
           description "Backup timeout";
           default "3600";
           type union {
             type string {
               pattern "<.*>|$.*";
             }
             type uint32 {
               range "600 .. 86400";
             }
           }
         }
       }
       leaf charging-id {
         description "OCS charging id";
         type union {
           type uint32;
           type string {
             pattern "<.*>|$.*";
           }
         }
       }
       leaf destination-realm {
         description "OCS destination realm";
         type string {
           length "1 .. 255";
         }
       }
       leaf destination-host {
         description "OCS destination host";
         type string {
           length "1 .. 255";
         }
       }
       leaf diameter-instance {
         description "OCS diameter instance";
         type string {
           length "1 .. 63";
         }
       }
       leaf draining {
         description "Set this PCRF partiton to draining state";
         type empty;
       }
       leaf draining-response-timeout {
         description "Final response timeout in draining mode";
         default "30";
         units "seconds";
         type union {
           type string {
             pattern "<.*>|$.*";
           }
           type uint32 {
             range "1 .. 86400";
           }
         }
       }
       leaf force-continue {
         description "Expect/force 'continue' as cc-failure-handling value";
         type empty;
       }
       leaf ggsn-address {
         description "Value of ggsn-address avp reported to ocs";
         type jt:ipaddr;
       }
       leaf ggsn-mcc-mnc {
         description "Value of 3gpp-ggsn-mcc-mnc avp reported to ocs";
         type string;
       }
       leaf final-response-timeout {
         description "Final response timeout";
         default "86400";
         units "seconds";
         type union {
           type string {
             pattern "<.*>|$.*";
           }
           type uint32 {
             range "1 .. 86400";
           }
         }
       }
       leaf max-outstanding-requests {
         description "Maximum number of outstanding requests";
         default "40";
         type union {
           type string {
             pattern "<.*>|$.*";
           }
           type uint32 {
             range "2 .. 40";
           }
         }
       }
       leaf send-origin-state-id {
         description "Include origin-state-id avp";
         type empty;
       }
       container sftp-backup {
         description "Add sftp-backup options";
         uses apply-advanced;
         leaf address {
           description "IP address of sftp server";
           type jt:ipaddr;
         }
         leaf accumulation-count {
           description "Number of CCR-Ts accumulated before file transmission";
           default "256";
           type union {
             type string {
               pattern "<.*>|$.*";
             }
             type uint32 {
               range "10 .. 4096";
             }
           }
         }
         leaf accumulation-size {
           description "Max size of sftp file";
           default "102400";
           type union {
             type string {
               pattern "<.*>|$.*";
             }
             type uint32 {
               range "10240 .. 409600";
             }
           }
         }
         leaf accumulation-timeout {
           description "Accumulation delay before stfp file transmission";
           default "120";
           type union {
             type string {
               pattern "<.*>|$.*";
             }
             type uint32 {
               range "10 .. 3600";
             }
           }
         }
         leaf directory {
           description "Configure directory";
           type string {
             length "1 .. 255";
           }
         }
         leaf file-name-prefix {
           description "File for sftp destination";
           type string {
             length "1 .. 255";
           }
         }
         choice instance {
           case case_1 {
             container logical-system {
               description "Logical system to be used by sftp";
               leaf logical-system-name {
                 description "Name of logical system";
                 type string {
                 }
               }
               leaf routing-instance {
                 description "Routing instance to be used by sftp";
                 type union {
                   type string {
                     pattern "default";
                   }
                   type string {
                   }
                 }
               }
             }
           }
           case case_2 {
             leaf routing-instance {
               description "Routing instance to be used by sftp";
               type union {
                 type string {
                   pattern "default";
                 }
                 type string {
                 }
               }
             }
           }
         }
         leaf node-ipv4-address {
           description "IPv4 address of sending node to be included in the file";
           type jt:ipv4addr;
         }
         leaf node-ipv6-address {
           description "IPv6 address of sending node to be included in the file";
           type jt:ipv6addr;
         }
         leaf port {
           description "Port on sftp server";
           default "22";
           type union {
             type string {
               pattern "<.*>|$.*";
             }
             type uint16 {
               range "1 .. 65535";
             }
           }
         }
         leaf response-timeout {
           description "Timeout for sftp command response";
           default "30";
           type union {
             type string {
               pattern "<.*>|$.*";
             }
             type uint32 {
               range "10 .. 1200";
             }
           }
         }
         leaf retry-interval {
           description "Interval for retry after failed stfp file transmission";
           default "600";
           type union {
             type string {
               pattern "<.*>|$.*";
             }
             type uint32 {
               range "30 .. 1200";
             }
           }
         }
         leaf ssh-connection-linger {
           description "Underlying ssh session connection linger";
           default "30";
           type union {
             type string {
               pattern "<.*>|$.*";
             }
             type uint32 {
               range "10 .. 144000";
             }
           }
         }
         leaf ssh-login {
           description "Ssh login name";
           type string {
             length "1 .. 1024";
           }
         }
         leaf ssh-passphrase {
           description "Passphrase for underlying ssh session";
           type string {
             length "1 .. 1024";
           }
         }
         leaf ssh-log-verbose {
           description "Run ssh subprocess with verbose log";
           type empty;
         }
       }
       container user-name-include {
         description "Add user-name options";
         uses apply-advanced;
         leaf delimiter {
           description "Change delimiter/separator character";
           type string {
             length 1;
           }
         }
         leaf domain-name {
           description "Domain name";
           type string {
             length "1 .. 64";
           }
         }
         leaf interface-name {
           description "Include interface-name";
           type empty;
         }
         leaf base-interface-name {
           description "Include base-interface-name";
           type empty;
         }
         leaf mac-address {
           description "Include MAC address";
           type empty;
         }
         leaf nas-port-id {
           description "Include nas-port-id";
           type empty;
         }
         leaf origin-host {
           description "Include origin-host";
           type empty;
         }
         leaf origin-realm {
           description "Include origin-host";
           type empty;
         }
         leaf user-prefix {
           description "Add user defined prefix";
           type string {
             length "1 .. 64";
           }
         }
         leaf user-name {
           description "Include user-name";
           type empty;
         }
       }
     }
     container global {
       description "OCS global parameters";
       uses apply-advanced;
       leaf service-context-id {
         description "Service context-id for OCS";
         type string {
           length "1 .. 255";
         }
       }
     }
   }
   grouping pcrf-definition {
     description "PCRF configuration definition";
     uses apply-advanced;
     list partition {
       key name;
       ordered-by user;
       description "PCRF partition configuration";
       max-elements 1;
       leaf name {
         description "PCRF partition name";
         type string {
           length "1 .. 63";
         }
       }
       uses apply-advanced;
       leaf accept-sdr {
         description "Accept service discovery requests";
         type empty;
       }
       leaf destination-realm {
         description "PCRF destination realm";
         type string {
           length "1 .. 255";
         }
       }
       leaf destination-host {
         description "PCRF destination host";
         type string {
           length "1 .. 255";
         }
       }
       leaf diameter-instance {
         description "PCRF diameter instance";
         type string {
           length "1 .. 63";
         }
       }
       leaf draining {
         description "Set this PCRF partiton to draining state";
         type empty;
       }
       leaf draining-response-timeout {
         description "Logout response timeout in draining mode";
         default "30";
         units "seconds";
         type union {
           type string {
             pattern "<.*>|$.*";
           }
           type uint32 {
             range "1 .. 86400";
           }
         }
       }
       leaf ip-can-type {
         description "Value of IP-CAN-Type AVP for this PCRF partition";
         default "77";
         type union {
           type string {
             pattern "<.*>|$.*";
           }
           type uint32 {
             range "1 .. 2147483647";
           }
         }
       }
       container local-decision {
         description "Local decision configuration";
         uses apply-advanced;
         choice permission {
           case case_1 {
             leaf grant {
               description "Grant user connection by default";
               type empty;
             }
           }
           case case_2 {
             leaf deny {
               description "Deny user connection by default";
               type empty;
             }
           }
         }
         leaf reinit-on-failure {
           description "Reinit from local-active state on receiving result 5012";
           type empty;
         }
         leaf reinit-on-rar {
           description "Reinit from local-active state on received rar";
           type empty;
         }
         leaf reinit-timeout {
           description "Local reinit timeout";
           default "10";
           units "seconds";
           type union {
             type string {
               pattern "<.*>|$.*";
             }
             type uint32 {
               range "1 .. 90";
             }
           }
         }
         leaf timeout {
           description "Local decision timeout";
           default "90";
           units "seconds";
           type union {
             type string {
               pattern "<.*>|$.*";
             }
             type uint32 {
               range "1 .. 90";
             }
           }
         }
       }
       leaf logout-response-timeout {
         description "Logout response timeout";
         default "86400";
         units "seconds";
         type union {
           type string {
             pattern "<.*>|$.*";
           }
           type uint32 {
             range "1 .. 86400";
           }
         }
       }
       leaf max-outstanding-requests {
         description "Maximum number of outstanding requests";
         default "40";
         type union {
           type string {
             pattern "<.*>|$.*";
           }
           type uint32 {
             range "2 .. 40";
           }
         }
       }
       leaf report-local-rule {
         description "Report installed local rule to PCRF";
         type empty;
       }
       leaf report-resource-allocation {
         description "Report rule installation failuresto PCRF";
         type empty;
       }
       leaf report-successful-resource-allocation {
         description "Report rule installation successes to PCRF";
         type empty;
       }
       leaf send-dyn-subscription-indicator {
         description "Include Juniper-Dyn-Subscription-Indidicator into ccr-i";
         type empty;
       }
       leaf send-network-family-indicator {
         description "Include Juniper-Network-Family-Indidicator into ccr-i";
         type empty;
       }
       leaf send-origin-state-id {
         description "Include origin-state-id avp";
         type empty;
       }
       leaf subscription-id-type {
         description "Value of subscription-id-type AVP for this PCRF partition";
         type union {
           type string {
             pattern "<.*>|$.*";
           }
           type uint32 {
             range "1 .. 2147483647";
           }
         }
       }
       container subscription-id-data-include {
         description "Add subscription-id-data options";
         uses apply-advanced;
         leaf delimiter {
           description "Change delimiter/separator character";
           type string {
             length 1;
           }
         }
         leaf domain-name {
           description "Domain name";
           type string {
             length "1 .. 64";
           }
         }
         leaf interface-name {
           description "Include interface-name";
           type empty;
         }
         leaf vlan-tags {
           description "Include interface vlan tags (svlan-vlan)";
           type empty;
         }
         leaf base-interface-name {
           description "Include base-interface-name";
           type empty;
         }
         leaf mac-address {
           description "Include MAC address";
           type empty;
         }
         leaf nas-port-id {
           description "Include nas-port-id";
           type empty;
         }
         leaf origin-host {
           description "Include origin-host";
           type empty;
         }
         leaf origin-realm {
           description "Include origin-host";
           type empty;
         }
         leaf user-prefix {
           description "Add user defined prefix";
           type string {
             length "1 .. 64";
           }
         }
         leaf user-name {
           description "Include user-name";
           type empty;
         }
       }
       leaf use-session-stamp {
         description "Use session init timestamp as part of session-id";
         type empty;
       }
       leaf update-response-timeout {
         description "Update response timeout";
         default "3600";
         units "seconds";
         type union {
           type string {
             pattern "<.*>|$.*";
           }
           type uint32 {
             range "1 .. 86400";
           }
         }
       }
     }
     container global {
       description "PCRF global parameters";
       uses apply-advanced;
       list rule-param {
         key name;
         ordered-by user;
         description "Charging juniper-param avp configuraion";
         leaf name {
           description "Code for this juniper-param avp";
           type union {
             type string {
               pattern "<.*>|$.*";
             }
             type uint32 {
               range "12000 .. 12019";
             }
           }
         }
         uses apply-advanced;
         leaf param-name {
           description "Name associatated with this juniper-param avp";
           type string {
             length "1 .. 255";
           }
         }
         leaf log-name {
           description "Log-name associatated with this juniper-param avp";
           type string {
             length "1 .. 255";
           }
         }
       }
     }
   }
   grouping profile-radius-server-name-object {
     leaf name {
       description "Fully qualified domain name of the RADIUS server";
       type string {
         length "4 .. 255";
       }
     }
     uses apply-advanced;
     leaf dns-query-interval {
       description "Frequency of RADIUS server name resolution";
       default "60";
       units "minutes";
       type union {
         type string {
           pattern "<.*>|$.*";
         }
         type uint16 {
           range "10 .. 1440";
         }
       }
     }
     leaf accounting-port {
       description "RADIUS server accounting port number";
       default "1813";
       type union {
         type string {
           pattern "<.*>|$.*";
         }
         type uint16 {
           range "1 .. 65535";
         }
       }
     }
     leaf radsec-destination {
       description "RADSEC destination";
       type union {
         type uint32;
         type string {
           pattern "<.*>|$.*";
         }
       }
     }
     leaf port {
       description "RADIUS server authentication port number";
       default "1812";
       type union {
         type string {
           pattern "<.*>|$.*";
         }
         type uint16 {
           range "1 .. 65535";
         }
       }
     }
     leaf preauthentication-port {
       description "RADIUS server preauthentication port number";
       type union {
         type string {
           pattern "<.*>|$.*";
         }
         type uint16 {
           range "1 .. 65535";
         }
       }
     }
     leaf dynamic-request-port {
       description "RADIUS client dynamic request port number";
       default "3799";
       type union {
         type string {
           pattern "<.*>|$.*";
         }
         type uint16 {
           range "1 .. 65535";
         }
       }
     }
     leaf secret {
       description "Shared secret with the RADIUS server";
       type jt:unreadable;
     }
     leaf preauthentication-secret {
       description "Shared secret with the RADIUS server";
       type jt:unreadable;
     }
     leaf timeout {
       description "Request timeout period";
       default "3";
       units "seconds";
       type union {
         type string {
           pattern "<.*>|$.*";
         }
         type uint32 {
           range "1 .. 1000";
         }
       }
     }
     leaf retry {
       description "Retry attempts";
       default "3";
       type union {
         type string {
           pattern "<.*>|$.*";
         }
         type uint32 {
           range "1 .. 100";
         }
       }
     }
     leaf accounting-timeout {
       description "Accounting request timeout period";
       default "0";
       units "seconds";
       type union {
         type string {
           pattern "<.*>|$.*";
         }
         type uint32 {
           range "0 .. 1000";
         }
       }
     }
     leaf accounting-retry {
       description "Accounting retry attempts";
       default "0";
       type union {
         type string {
           pattern "<.*>|$.*";
         }
         type uint32 {
           range "0 .. 100";
         }
       }
     }
     leaf max-outstanding-requests {
       description "Maximum requests in flight to server";
       default "1000";
       type union {
         type string {
           pattern "<.*>|$.*";
         }
         type uint32 {
           range "0 .. 2000";
         }
       }
     }
     leaf source-address {
       description "Use specified address as source address";
       type jt:ipaddr;
     }
     leaf routing-instance {
       description "Use specified routing instance";
       type string;
     }
   }
   grouping profile-radius-server-object {
     leaf name {
       description "RADIUS server address";
       type jt:ipaddr;
     }
     uses apply-advanced;
     leaf port {
       description "RADIUS server authentication port number";
       default "1812";
       type union {
         type string {
           pattern "<.*>|$.*";
         }
         type uint16 {
           range "1 .. 65535";
         }
       }
     }
     leaf preauthentication-port {
       description "RADIUS server preauthentication port number";
       type union {
         type string {
           pattern "<.*>|$.*";
         }
         type uint16 {
           range "1 .. 65535";
         }
       }
     }
     leaf accounting-port {
       description "Port number to which to send RADIUS accounting messages";
       default "1813";
       type union {
         type string {
           pattern "<.*>|$.*";
         }
         type uint16 {
           range "1 .. 65535";
         }
       }
     }
     leaf dynamic-request-port {
       description "RADIUS client dynamic request port number";
       default "3799";
       type union {
         type string {
           pattern "<.*>|$.*";
         }
         type uint16 {
           range "1 .. 65535";
         }
       }
     }
     leaf secret {
       description "Shared secret with the RADIUS server";
       type jt:unreadable;
     }
     leaf preauthentication-secret {
       description "Shared secret with the RADIUS server";
       type jt:unreadable;
     }
     leaf timeout {
       description "Request timeout period";
       default "3";
       units "seconds";
       type union {
         type string {
           pattern "<.*>|$.*";
         }
         type uint32 {
           range "1 .. 1000";
         }
       }
     }
     leaf retry {
       description "Retry attempts";
       default "3";
       type union {
         type string {
           pattern "<.*>|$.*";
         }
         type uint32 {
           range "1 .. 100";
         }
       }
     }
     leaf accounting-timeout {
       description "Accounting request timeout period";
       default "0";
       units "seconds";
       type union {
         type string {
           pattern "<.*>|$.*";
         }
         type uint32 {
           range "0 .. 1000";
         }
       }
     }
     leaf accounting-retry {
       description "Accounting retry attempts";
       default "0";
       type union {
         type string {
           pattern "<.*>|$.*";
         }
         type uint32 {
           range "0 .. 100";
         }
       }
     }
     leaf max-outstanding-requests {
       description "Maximum requests in flight to server";
       default "1000";
       type union {
         type string {
           pattern "<.*>|$.*";
         }
         type uint32 {
           range "0 .. 2000";
         }
       }
     }
     leaf source-address {
       description "Use specified address as source address";
       type jt:ipaddr;
     }
     leaf routing-instance {
       description "Use specified routing instance";
       type string;
     }
     leaf radsec-destination {
       description "RADSEC destination";
       type union {
         type uint32;
         type string {
           pattern "<.*>|$.*";
         }
       }
     }
   }
   grouping protocol-attribute-type {
     description "Protocol specific attribute configuration";
     leaf name {
       description "Name for this protocol attribute group";
       type string {
         length "1 .. 63";
       }
     }
     uses apply-advanced;
     container dhcp {
       description "DHCPv4 configurable attributes";
       uses dhcp-attribute-type;
     }
     container dhcpv6 {
       description "DHCPv6 configurable attributes";
       uses dhcp-attribute-type;
     }
   }
   grouping radius-disconnect-object {
     leaf name {
       description "Address of RADIUS client from which to accept disconnect requests";
       type jt:ipv4addr;
     }
     uses apply-advanced;
     leaf secret {
       description "Secret with which to authenticate RADIUS client sending disconnect requests";
       type jt:unreadable;
     }
   }
   grouping radius-traceoptions {
     description "Trace options related to RADIUS";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "send" {
             description "Trace transmitted packets";
           }
           enum "send-detail" {
             description "Trace transmitted packets in detail";
           }
           enum "receive" {
             description "Trace received packets";
           }
           enum "receive-detail" {
             description "Trace received packets in detail";
           }
           enum "timeout" {
             description "Trace timeout events";
           }
           enum "state" {
             description "Trace RADIUS server state changes";
           }
           enum "all" {
             description "Trace everything";
           }
         }
       }
     }
     list server {
       key name;
       ordered-by user;
       description "Trace packet sent to or received from the server[s]";
       leaf name {
         description "Trace packet sent to or received from the server";
         type string {
           length "1 .. 31";
         }
       }
       uses apply-advanced;
     }
     list client {
       key name;
       ordered-by user;
       description "Trace packet sent to or received from the client[s]";
       leaf name {
         description "Trace packet sent to or received from the client";
         type string {
           length "1 .. 31";
         }
       }
       uses apply-advanced;
     }
     list snoop-segment {
       key name;
       ordered-by user;
       description "Trace packet related to snoop-segment";
       leaf name {
         description "Trace snooped packet";
         type string {
           length "1 .. 32";
         }
       }
       uses apply-advanced;
     }
   }
   grouping radsec-definition {
     description "RADSEC configuration definition";
     uses apply-advanced;
     list destination {
       key name;
       ordered-by user;
       description "RADSEC destination configuration";
       max-elements 16;
       leaf name {
         description "RADSEC destination id";
         type union {
           type string {
             pattern "<.*>|$.*";
           }
           type uint32 {
             range "1 .. 65535";
           }
         }
       }
       uses apply-advanced;
       leaf address {
         description "Destination IP address";
         type jt:ipaddr;
       }
       container dynamic-requests {
         presence "enable dynamic-requests";
         description "Accept dynamic requests";
         uses apply-advanced;
         leaf source-address {
           description "Source address for dynamic requests";
           type jt:ipaddr;
         }
         leaf source-port {
           description "Source port for dynamic requests";
           default "2083";
           type union {
             type string {
               pattern "<.*>|$.*";
             }
             type uint16 {
               range "1 .. 65535";
             }
           }
         }
         choice source-lsri-instance {
           case case_1 {
             container logical-system {
               description "Logical system for dynamic requests";
               leaf logical-system-name {
                 description "Name of logical system for dynamic requests";
                 type string {
                 }
               }
               leaf routing-instance {
                 description "Routing instance for dynamic requests";
                 type union {
                   type string {
                     pattern "default";
                   }
                   type string {
                   }
                 }
               }
             }
           }
           case case_2 {
             leaf routing-instance {
               description "Routing instance for dynamic requests";
               type union {
                 type string {
                   pattern "default";
                 }
                 type string {
                 }
               }
             }
           }
         }
       }
       leaf id-reuse-timeout {
         description "Radius id may be reused after this timeout";
         default "120";
         type union {
           type string {
             pattern "<.*>|$.*";
           }
           type uint32 {
             range "60 .. 3600";
           }
         }
       }
       choice lsri-instance {
         case case_1 {
           container logical-system {
             description "Logical system to be used";
             leaf logical-system-name {
               description "Name of logical system";
               type string {
               }
             }
             leaf routing-instance {
               description "Routing instance to be used";
               type union {
                 type string {
                   pattern "default";
                 }
                 type string {
                 }
               }
             }
           }
         }
         case case_2 {
           leaf routing-instance {
             description "Routing instance to be used";
             type union {
               type string {
                 pattern "default";
               }
               type string {
               }
             }
           }
         }
       }
       leaf max-tx-buffers {
         description "Maximum number of tx-buffers";
         default "100";
         type union {
           type string {
             pattern "<.*>|$.*";
           }
           type uint32 {
             range "32 .. 3200";
           }
         }
       }
       leaf port {
         description "Desitnaion port";
         default "2083";
         type union {
           type string {
             pattern "<.*>|$.*";
           }
           type uint16 {
             range "1 .. 65535";
           }
         }
       }
       leaf source-address {
         description "Source IP address for destination";
         type jt:ipaddr;
       }
       leaf tls-certificate {
         description "TLS certificate";
         type string {
           length "1 .. 255";
         }
       }
       leaf tls-force-ciphers {
         type enumeration {
           enum "medium" {
             description "Add medium grade ciphers. (Do not use!)";
           }
           enum "low" {
             description "Add medium and low grade ciphers. (Do not use!)";
           }
         }
       }
       leaf tls-min-version {
         default "v1.2";
         type enumeration {
           enum "v1.1" {
             description "Require tls 1.1 and 1.2";
           }
           enum "v1.2" {
             description "Require tls 1.2";
           }
         }
       }
       leaf tls-peer-name {
         description "Expected peer fdqn";
         type string {
           length "1 .. 255";
         }
       }
       leaf tls-timeout {
         description "Limit on tls handshake time";
         default "5";
         units "seconds";
         type union {
           type string {
             pattern "<.*>|$.*";
           }
           type uint32 {
             range "3 .. 90";
           }
         }
       }
     }
   }
   grouping s6a-definition {
     description "S6a configuration definition";
     uses apply-advanced;
     list partition {
       key name;
       ordered-by user;
       description "S6A partition configuration";
       max-elements 1;
       leaf name {
         description "S6a partition name";
         type string {
           length "1 .. 63";
         }
       }
       uses apply-advanced;
       leaf destination-realm {
         description "S6A destination realm";
         type string {
           length "1 .. 255";
         }
       }
       leaf destination-host {
         description "S6A destination host";
         type string {
           length "1 .. 255";
         }
       }
       leaf diameter-instance {
         description "S6A diameter instance";
         type string {
           length "1 .. 63";
         }
       }
       leaf max-outstanding-requests {
         description "Maximum number of outstanding requests";
         default "40";
         type union {
           type string {
             pattern "<.*>|$.*";
           }
           type uint32 {
             range "2 .. 1024";
           }
         }
       }
       leaf response-timeout {
         description "Response timeout";
         default "15";
         units "seconds";
         type union {
           type string {
             pattern "<.*>|$.*";
           }
           type uint32 {
             range "1 .. 30";
           }
         }
       }
     }
   }
   grouping securid-server-object {
     leaf name {
       description "Name of the SecurID server";
       type string;
     }
     uses apply-advanced;
     leaf configuration-file {
       description "Path to the SecurID server configuration (sdconf.rec) file";
       type string {
         length "1 .. 1024";
       }
     }
   }
   grouping sm-ippool-pool {
     description "Address pool configuration";
     leaf name {
       description "Address pool name";
       type string {
         length "1 .. 64";
       }
     }
     uses apply-advanced;
     leaf service-mode {
       description "Service mode";
       type enumeration {
         enum "maintenance" {
           description "Maintenance mode";
         }
       }
     }
     container family {
       presence "enable family";
       description "Address family";
       choice family_type {
         case case_1 {
           container inet {
             presence "enable inet";
             description "IPv4 address pool configuration";
             uses apply-advanced;
             list network {
               key name;
               ordered-by user;
               description "Specify IPv4 network prefix";
               leaf name {
                 description "IPv4 network prefix";
                 type jt:ipv4prefix-only;
               }
               uses apply-advanced;
               leaf external-assigned {
                 description "Assigned by an external authority";
                 type empty;
               }
               leaf allocation-prefix-length {
                 description "Size of address allocation block";
                 type union {
                   type string {
                     pattern "<.*>|$.*";
                   }
                   type uint8 {
                     range "22 .. 32";
                   }
                 }
               }
               list range {
                 key name;
                 ordered-by user;
                 description "Specify ranges within the prefix";
                 leaf name {
                   description "Range name";
                   type string {
                     length "1 .. 64";
                   }
                 }
                 uses apply-advanced;
                 leaf low {
                   description "Lower limit of the range";
                   type jt:ipv4addr;
                 }
                 leaf high {
                   description "Upper limit of the range";
                   type jt:ipv4addr;
                 }
                 leaf external-assigned {
                   description "Assigned by an external authority";
                   type empty;
                 }
               }
             }
           }
         }
         case case_2 {
           container inet6 {
             presence "enable inet6";
             description "IPv6 address pool configuration";
             uses apply-advanced;
             list network {
               key name;
               ordered-by user;
               description "Specify IPv6 network prefix";
               leaf name {
                 description "IPv6 network prefix";
                 type jt:ipv6prefix-only;
               }
               uses apply-advanced;
               leaf external-assigned {
                 description "Assigned by an external authority";
                 type empty;
               }
               leaf allocation-prefix-length {
                 description "Size of address allocation block";
                 type union {
                   type string {
                     pattern "<.*>|$.*";
                   }
                   type uint8 {
                     range "54 .. 64";
                   }
                 }
               }
               list range {
                 key name;
                 ordered-by user;
                 description "Specify ranges within the prefix";
                 leaf name {
                   description "Range name";
                   type string {
                     length "1 .. 64";
                   }
                 }
                 uses apply-advanced;
                 leaf low {
                   description "Lower limit of the range";
                   type jt:ipv6prefix-only;
                 }
                 leaf high {
                   description "Upper limit of the range";
                   type jt:ipv6prefix-only;
                 }
                 leaf external-assigned {
                   description "Addresses in this range are assigned to the client by an external authority";
                   type empty;
                 }
               }
             }
           }
         }
       }
     }
     leaf ageing-window {
       description "Time in sec when the address should not be re-used";
       default "2";
       units "seconds";
       type union {
         type string {
           pattern "<.*>|$.*";
         }
         type uint16 {
           range "1 .. 65535";
         }
       }
     }
     leaf pool-prefetch-threshold {
       description "Pool usage threshold to prefetch more addresses";
       default "80";
       units "percent";
       type union {
         type string {
           pattern "<.*>|$.*";
         }
         type uint8 {
           range "1 .. 100";
         }
       }
     }
     leaf pool-snmp-trap-threshold {
       description "Pool usage threshold to generate SNMP trap";
       default "80";
       units "percent";
       type union {
         type string {
           pattern "<.*>|$.*";
         }
         type uint8 {
           range "1 .. 100";
         }
       }
     }
     leaf default-pool {
       description "Pool usage as one of default pools or APN(s) specific";
       type empty;
     }
   }
 }
