/*
 * Copyright (c) 2024 Juniper Networks, Inc.
 * All rights reserved.
 */
 module junos-qfx-conf-chassis {
   namespace "http://yang.juniper.net/junos-qfx/conf/chassis";

   prefix jc-chassis;

   import junos-common-types {
     prefix jt;
     revision-date 2023-01-01;
   }

   import junos-qfx-conf-root {
     prefix jc;
     revision-date 2023-01-01;
   }

   organization "Juniper Networks, Inc.";

   contact "yang-support@juniper.net";

   description "Junos chassis configuration module";

   revision 2023-01-01 {
     description "Junos: 23.4R2.13";
   }

   augment /jc:configuration {
     uses chassis-group;
   }
   augment /jc:configuration/jc:groups {
     uses chassis-group;
   }
   grouping chassis-group {
     container chassis {
       description "Chassis configuration";
       uses chassis_type;
     }
   }
   grouping chassis_type {
     uses apply-advanced;
     container nssu {
       presence "enable nssu";
       description "Nonstop Software Upgrade settings";
       uses apply-advanced;
       list upgrade-group {
         key name;
         ordered-by user;
         description "Nonstop Software Upgrade group";
         leaf name {
           type string {
             length "1 .. 254";
           }
         }
         uses apply-advanced;
         leaf-list fpcs {
           description "FPCs associated with update-group";
           type union {
             type string {
               pattern "<.*>|$.*";
             }
             type uint32;
           }
           max-elements 16;
         }
       }
       leaf rcp-count {
         description "Parallel rcp count";
         type union {
           type string {
             pattern "<.*>|$.*";
           }
           type int32 {
             range "1 .. 8";
           }
         }
       }
       leaf lc-reboot-delay {
         description "Delay between linecard reboot during NSSU";
         type union {
           type string {
             pattern "<.*>|$.*";
           }
           type int32 {
             range "0 .. 600";
           }
         }
       }
     }
     leaf no-psu-redundancy {
       description "Disable N+1 Redundancy for PSUs";
       type empty;
     }
     leaf no-power-budget {
       description "Disable Chassis Power Budget";
       type empty;
     }
     container psu {
       description "Power Supply Unit redundancy configuration";
       uses apply-advanced;
       container redundancy {
         description "PSU Redundancy settings";
         uses apply-advanced;
         leaf n-plus-n {
           description "PSU redundancy: N+N configuration";
           type empty;
         }
       }
     }
     leaf fpc-resync {
       description "Send and receive Nchip cells for newly onlined FPC";
       type empty;
     }
     leaf craft-lockout {
       description "Disable craft interface input";
       type empty;
     }
     choice source-route-choice {
       leaf source-route {
         description "Enable IP source-route processing";
         status deprecated;
         type empty;
       }
       leaf no-source-route {
         description "Don't enable IP source-route processing";
         status deprecated;
         type empty;
       }
     }
     choice packet-scheduling-choice {
       leaf packet-scheduling {
         description "Enable DX2.0 packet scheduling";
         type empty;
       }
       leaf no-packet-scheduling {
         description "Don't enable DX2.0 packet scheduling";
         type empty;
       }
     }
     container icmp {
       description "ICMP protocol";
       uses apply-advanced;
     }
     container icmp6 {
       description "ICMP version 6 protocol";
       uses apply-advanced;
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
         }
         enum "192" {
           description "Maximum 192 ECMP routes";
         }
         enum "224" {
           description "Maximum 224 ECMP routes";
         }
         enum "256" {
           description "Maximum 256 ECMP routes";
         }
         enum "288" {
           description "Maximum 288 ECMP routes";
         }
         enum "320" {
           description "Maximum 320 ECMP routes";
         }
         enum "352" {
           description "Maximum 352 ECMP routes";
         }
         enum "384" {
           description "Maximum 384 ECMP routes";
         }
         enum "416" {
           description "Maximum 416 ECMP routes";
         }
         enum "448" {
           description "Maximum 448 ECMP routes";
         }
         enum "480" {
           description "Maximum 480 ECMP routes";
         }
         enum "512" {
           description "Maximum 512 ECMP routes";
         }
       }
     }
     container redundancy {
       description "Redundancy settings";
       uses chassis_redundancy_type;
     }
     container routing-engine {
       description "Routing Engine settings";
       uses chassis_routing_engine_type;
     }
     container aggregated-devices {
       description "Aggregated devices configuration";
       uses chassis_agg_dev_type;
     }
     list disk-partition {
       key name;
       ordered-by user;
       description "Chassis disk monitor configuration";
       leaf name {
         description "Choose disk partition to monitor";
         type enumeration {
           enum "/var" {
             description "Monitor /var partition";
           }
           enum "/config" {
             description "Monitor /config partition";
           }
         }
       }
       uses apply-advanced;
       list level {
         key name;
         ordered-by user;
         description "Threshold level";
         leaf name {
           type enumeration {
             enum "high" {
               description "Set high level of threshold";
             }
             enum "full" {
               description "Set full level of threshold";
             }
           }
         }
         uses apply-advanced;
         container free-space {
           description "Enter threshold value & choose the metric";
           leaf thres-free {
             description "Enter free space threshold value";
             type union {
               type string {
                 pattern "<.*>|$.*";
               }
               type uint32 {
                 range "0 .. 100";
               }
             }
           }
           choice thres-metric {
             case case_1 {
               leaf percent {
                 description "Free space threshold in %";
                 type empty;
               }
             }
             case case_2 {
               leaf mb {
                 description "Free space threshold in MB";
                 type empty;
               }
             }
           }
         }
       }
     }
     container container-devices {
       description "Container devices configuration";
       uses chassisd_agg_container_type;
     }
     container pseudowire-service {
       description "Pseudowire L3 termination device configuration";
       presence "enable pseudowire-service";
       uses chassis-pw-type;
     }
     container redundancy-group {
       description "Redundancy group configuration";
       uses chassisd-redundancy-group-type;
     }
     container fabric {
       description "Switch fabric settings";
       uses chassis_fabric_type;
     }
     list fpc {
       key name;
       description "Flexible PIC Concentrator parameters";
       uses chassis_fpc_type;
     }
     leaf node-id {
       description "Chassis identifier";
       type union {
         type string {
           pattern "<.*>|$.*";
         }
         type uint64 {
           range "1 .. 18446744073709551615";
         }
       }
     }
     list cb {
       key name;
       description "Control Board parameters";
       uses chassis_cb_type;
     }
     leaf disable-fm {
       description "Disable Fabric Manager";
       type empty;
     }
     container fpc-feb-connectivity {
       description "Connectivity between Flexible PIC Concentrators and Forwarding Engine Boards";
       uses apply-advanced;
       list fpc {
         key name;
         leaf name {
           description "FPC slot number";
           type union {
             type string {
               pattern "<.*>|$.*";
             }
             type uint32;
           }
         }
         uses apply-advanced;
         container feb {
           description "FEB slot number";
           choice feb-slot-choice {
             case case_1 {
               leaf none {
                 description "FPC not connected to any FEB";
                 type empty;
               }
             }
             case case_2 {
               leaf feb-slot {
                 description "FEB slot number";
                 type union {
                   type string {
                     pattern "<.*>|$.*";
                   }
                   type uint32;
                 }
               }
             }
           }
         }
       }
     }
     container pem {
       description "Power supply (PEM) parameters";
       uses chassis_pem_type;
     }
     container sib {
       description "Switch Interface Board parameters";
       uses chassis_sib_type;
     }
     container feb {
       description "Forwarding Engine Board parameters";
       uses chassis_feb_type;
     }
     container tfeb {
       description "Taz Forwarding Engine Board parameters";
       uses chassis_feb_type;
     }
     container alarm {
       description "Global alarm settings";
       uses chassis_alarm_type;
     }
     leaf slow-pfe-alarm {
       description "Enable slow (potential) PFE alarm";
       type empty;
     }
     leaf fpc-ifl-ae-statistics {
       description "Enable fpc ifl ae child statistics";
       type empty;
     }
     leaf ambient-temperature {
       description "Chassis ambient-temperature value in degree celsius";
       type enumeration {
         enum "55C" {
           description "55 degree celsius";
         }
         enum "40C" {
           description "40 degree celsius";
         }
         enum "25C" {
           description "25 degree celsius";
         }
         enum "32C" {
           description "32 degree celsius";
         }
       }
     }
     leaf network-services {
       description "Chassis network services configuration";
       type enumeration {
         enum "ip" {
           description "IP network services";
         }
         enum "ethernet" {
           description "Ethernet network services";
         }
         enum "enhanced-ip" {
           description "Enhanced IP network services";
         }
         enum "enhanced-ethernet" {
           description "Enhanced ethernet network services";
         }
         enum "enhanced-mode" {
           description "Enhanced network services";
         }
         enum "lan" {
           description "Ethernet LAN services";
         }
       }
     }
     container alarm-port {
       description "Craft-interface parameters";
       uses chassis_alarm_port_op_type;
     }
     container usb {
       description "USB control flags";
       uses apply-advanced;
       container storage {
         description "USB storage flags";
         uses apply-advanced;
         leaf disable {
           description "Disable USB storage";
           type empty;
         }
       }
     }
     container serdes {
       presence "enable serdes";
       description "Serdes test mode for link training";
       uses apply-advanced;
       leaf test-mode {
         description "Serdes test mode";
         type string;
       }
     }
     list lcc {
       key name;
       description "Line-card chassis configuration";
       leaf name {
         description "LCC number";
         type union {
           type string {
             pattern "<.*>|$.*";
           }
           type uint32;
         }
       }
       uses apply-advanced;
       list fpc {
         key name;
         description "Flexible PIC Concentrator parameters";
         uses chassis_fpc_type;
       }
       container pem {
         description "Power supply (PEM) parameters";
         uses chassis_pem_type;
       }
       choice state {
         case case_1 {
           leaf online-expected {
             description "LCC is expected to be online";
             type empty;
           }
         }
         case case_2 {
           leaf offline {
             description "LCC is expected to be offline";
             type empty;
           }
         }
       }
     }
     container synchronization {
       description "Clock synchronization options";
       uses apply-advanced;
       leaf switchover-mode {
         description "Should system revert to higher priority valid source";
         default "revertive";
         type enumeration {
           enum "non-revertive" {
             description "System uses current source as long as it is valid";
           }
           enum "revertive" {
             description "Automatically switch to higher priority valid source";
           }
         }
       }
       leaf switching-mode {
         description "Should system revert to higher priority valid source";
         default "non-revertive";
         type enumeration {
           enum "non-revertive" {
             description "System uses current source as long as it is valid";
           }
           enum "revertive" {
             description "Automatically switch to higher priority valid source";
           }
         }
       }
       leaf network-option {
         description "EEC synchronization networking type";
         type enumeration {
           enum "option-1" {
             description "Option 1 (EEC1) synchronization networking";
           }
           enum "option-2" {
             description "Option 2 (EEC2) synchronization networking";
           }
         }
       }
       leaf selection-mode {
         description "Selection mode for incoming ESMC quality";
         default "configured-quality";
         type enumeration {
           enum "configured-quality" {
             description "Use source's configured ESMC quality";
           }
           enum "received-quality" {
             description "Use source's received ESMC quality";
           }
         }
       }
       leaf clock-mode {
         description "Synchronous Ethernet Clock selection mode";
         type enumeration {
           enum "free-run" {
             description "Use the free-running local oscillator";
           }
           enum "auto-select" {
             description "Select best clock source";
           }
         }
       }
       leaf quality-mode-enable {
         description "Enable Synchronous Ethernet ESMC Quality mode";
         type empty;
       }
       leaf max-transmit-quality-level {
         description "Maximum transmit quality level";
         type enumeration {
           enum "ePRTC" {
             description "Time quality of enhanced primary reference time clock";
           }
           enum "PRTC" {
             description "Time quality of primary reference time clock";
           }
           enum "ePRC" {
             description "Time quality of enhanced primary reference clock";
           }
           enum "eEEC" {
             description "Time quality of enhanced ethernet equipment clock";
           }
           enum "prc" {
             description "Timing quality of a primary reference clock (option-1 only)";
           }
           enum "ssu-a" {
             description "Timing quality of a type I or IV slave clock (option-1 only)";
           }
           enum "ssu-b" {
             description "Timing quality of a type VI slave clock (option-1 only)";
           }
           enum "sec" {
             description "Timing quality of SDH equipment clock (option-1 only)";
           }
           enum "prs" {
             description "Clock traceable to primary reference source (option-2 only)";
           }
           enum "stu" {
             description "Clock traceable to unknown quality (option-2 only)";
           }
           enum "st2" {
             description "Clock traceable to stratum 2 (option-2 only)";
           }
           enum "tnc" {
             description "Clock traceable to transit node clock (option-2 only)";
           }
           enum "st3e" {
             description "Clock traceable to stratum 3E (option-2 only)";
           }
         }
       }
       leaf enable-extended-ql-tlv {
         description "Enable enhanced ESMC QL support";
         type empty;
       }
       leaf global-wait-to-restore {
         description "Global Port signal up state time before opening for ESMC";
         units "min";
         type union {
           type string {
             pattern "<.*>|$.*";
           }
           type uint32 {
             range "0 .. 12";
           }
         }
       }
       leaf minimum-quality {
         description "Minimum quality threshold";
         type enumeration {
           enum "prc" {
             description "Timing quality of a primary reference clock (option-1 only)";
           }
           enum "ssu-a" {
             description "Timing quality of a type I or IV slave clock (option-1 only)";
           }
           enum "ssu-b" {
             description "Timing quality of a type VI slave clock (option-1 only)";
           }
           enum "sec" {
             description "Timing quality of SDH equipment clock (option-1 only)";
           }
           enum "prs" {
             description "Clock traceable to primary reference source (option-2 only)";
           }
           enum "st2" {
             description "Clock traceable to stratum 2 (option-2 only)";
           }
           enum "tnc" {
             description "Clock traceable to transit node clock (option-2 only)";
           }
           enum "st3e" {
             description "Clock traceable to stratum 3E (option-2 only)";
           }
           enum "st3" {
             description "Clock traceable to stratum 3 (option-2 only)";
           }
           enum "st4" {
             description "Clock traceable to stratum 4 free-run (option-2 only)";
           }
           enum "smc" {
             description "Clock traceable to self-timed SONET (option-2 only)";
           }
           enum "stu" {
             description "Clock traceable to unknown quality (option-2 only)";
           }
         }
       }
       list port {
         key name;
         description "Clock synchronization ports";
         leaf name {
           type enumeration {
             enum "auxiliary" {
               description "Auxiliary port";
             }
             enum "gnss" {
               description "Global Navigation Satellite System - GPS or GLONASS port";
             }
             enum "time-of-day" {
               description "Time of Day(TOD) port";
             }
           }
         }
         uses apply-advanced;
         container client {
           presence "enable client";
           description "Port client receiving external signals";
           uses apply-advanced;
           container time-of-day-format {
             description "Time-of-day format as received on this port";
             uses apply-advanced;
             choice format {
               case case_1 {
                 leaf ascii {
                   description "ASCII Time-of-day message format string";
                   type string {
                     length "1 .. 80";
                   }
                 }
               }
               case case_2 {
                 leaf nmea-custom-format {
                   description "Customized NMEA format used when interfacing with GRU GPS Receiver Unit";
                   type empty;
                 }
               }
               case case_3 {
                 leaf no-protocol {
                   description "Used when interfacing with GRU GPS Receiver Unit to process PPS with no Time Of Day";
                   type empty;
                 }
               }
             }
           }
           leaf cable-length-compensation {
             description "Antenna cable length compensation in nanoseconds";
             type union {
               type uint32;
               type string {
                 pattern "<.*>|$.*";
               }
             }
           }
           leaf cable-delay-compensation {
             description "GPS Receiver Unit to Router delay compensation in nanoseconds";
             type union {
               type string {
                 pattern "<.*>|$.*";
               }
               type int32 {
                 range "-100000000 .. 100000000";
               }
             }
           }
           leaf antenna-voltage {
             description "Configure antenna voltage";
             type enumeration {
               enum "3.3" {
                 description "3.3 units";
               }
               enum "5" {
                 description "5 units";
               }
             }
           }
           leaf alarm-filter {
             description "Set alarm filter window";
             default "36";
             type union {
               type string {
                 pattern "<.*>|$.*";
               }
               type int32 {
                 range "1 .. 60";
               }
             }
           }
           leaf constellation {
             description "Configure constellation of satellites to use";
             type enumeration {
               enum "gps" {
                 description "Global Positioning Satellite(GPS) for clock recovery";
               }
               enum "glonass" {
                 description "Global Navigation Satellite System(GLONASS) constellation";
               }
               enum "gps-and-glonass" {
                 description "All constellations";
               }
               enum "beidou" {
                 description "BEIDOU for clock recovery constellations";
               }
               enum "gps-beidou" {
                 description "GPS and BEIDOU for clock recovery";
               }
               enum "gps-beidou-qzss" {
                 description "GPS ,BEIDOU and qzss for clock recovery";
               }
               enum "galileo" {
                 description "GALILEO for clock recovery";
               }
               enum "gps-galileo" {
                 description "GPS and GALILEO for clock recovery";
               }
               enum "gps-qzss" {
                 description "GPS and QZSS for clock recovery";
               }
               enum "gps-glonass-qzss" {
                 description "GPS,GLONASS and QZSS for clock recovery";
               }
               enum "gps-galileo-qzss" {
                 description "GPS , GALILEO and QZSS for clock recovery";
               }
             }
           }
           leaf anti-jamming {
             description "Enable anti-jamming feature";
             type empty;
           }
           leaf pps-loopback {
             description "Enable 1PPS loopback mode";
             type empty;
           }
           leaf dump-gpsstats {
             description "Enable dumping gnss data";
             type empty;
           }
         }
       }
       list interfaces {
         key name;
         description "Interface(s) with upstream clock source";
         leaf name {
           type enumeration {
             enum "external" {
               description "External clock interface";
             }
             enum "external-0/0" {
               description "External clock interface on SCB-0";
             }
             enum "external-0/1" {
               description "External clock interface on SCB-0";
             }
             enum "external-1/0" {
               description "External clock interface on SCB-1";
             }
             enum "external-1/1" {
               description "External clock interface on SCB-1";
             }
             enum "external-a" {
               description "External-A clock interface";
             }
             enum "external-b" {
               description "External-B clock interface";
             }
             enum "external-0" {
               description "External-0 clock interface";
             }
             enum "external-1" {
               description "External-1 clock interface";
             }
             enum "external-2" {
               description "External-2 clock interface";
             }
             enum "bits" {
               description "External BITS interface configuration";
             }
             enum "bits-a" {
               description "External BITS interface A configuration";
             }
             enum "bits-b" {
               description "External BITS interface B configuration";
             }
             enum "gps-0" {
               description "External GPS interface A configuration";
             }
             enum "gps-1" {
               description "External GPS interface B configuration";
             }
           }
         }
         uses apply-advanced;
         leaf signal-type {
           description "Frequency for provided reference clocks";
           type enumeration {
             enum "1mhz" {
               description "1 MHz clock signal";
             }
             enum "5mhz" {
               description "5 MHz clock signal";
             }
             enum "10mhz" {
               description "10 MHz clock signal";
             }
             enum "2048khz" {
               description "E1 unframed 2048Khz G.703 signal";
             }
             enum "e1" {
               description "E1-coded 2048 KHz signal on 120 ohm balanced line";
             }
             enum "t1" {
               description "T1-coded 1.544 MHz signal on 100 ohm balanced line";
             }
             enum "cc-8k" {
               description "Composite Clock 64kHz+8kHz";
             }
             enum "cc-8k-400" {
               description "Composite Clock 64kHz+8kHz+400Hz";
             }
             enum "6312k" {
               description "Japanese Standard 6312kHz";
             }
           }
         }
         leaf pulse-per-second-enable {
           description "Enable pulse-per-second (PPS) receive on the interface";
           type empty;
         }
         container e1-options {
           description "E1 interface-specific options";
           uses apply-advanced;
           leaf line-encoding {
             description "Line encoding";
             default "hdb3";
             type enumeration {
               enum "ami" {
                 description "Automatic mark inversion";
               }
               enum "hdb3" {
                 description "High-density bipolar 3 code";
               }
             }
           }
           leaf framing {
             description "Framing mode";
             default "g704";
             type enumeration {
               enum "g704" {
                 description "G.704 framing format for E1 interfaces";
               }
               enum "g704-no-crc4" {
                 description "G.704 framing without CRC4 for E1 interfaces";
               }
             }
           }
           leaf sabit {
             description "The sabit used for exchanging SSM quality";
             default "4";
             type union {
               type string {
                 pattern "<.*>|$.*";
               }
               type uint32 {
                 range "4 .. 8";
               }
             }
           }
         }
         container t1-options {
           description "T1 interface-specific options";
           uses apply-advanced;
           leaf line-encoding {
             description "Line encoding";
             default "b8zs";
             type enumeration {
               enum "ami" {
                 description "Automatic mark inversion";
               }
               enum "b8zs" {
                 description "8-bit zero suppression";
               }
             }
           }
           leaf framing {
             description "Framing mode";
             default "esf";
             type enumeration {
               enum "esf" {
                 description "Extended Super Frame";
               }
               enum "sf" {
                 description "Super Frame";
               }
             }
           }
         }
       }
       container source {
         description "ESMC source(s) related";
         uses apply-advanced;
         container gps-0 {
           presence "enable gps-0";
           description "Global Positioning System input A";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container gps-1 {
           presence "enable gps-1";
           description "Global Positioning System input B";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container bits-a {
           presence "enable bits-a";
           description "External Building Integrated Timing Supply input A";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container bits-b {
           presence "enable bits-b";
           description "External Building Integrated Timing Supply input B";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container virtual-port {
           presence "enable virtual-port";
           description "Virtual port";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         list interfaces {
           key name;
           description "Interface(s) with upstream clock source";
           leaf name {
             type string;
           }
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf no-ssm-support {
             description "No SSM support available for this interface";
             type empty;
           }
           leaf hold-off-time {
             description "Port signal down state time before closing for ESMC";
             units "milliseconds";
             type union {
               type string {
                 pattern "<.*>|$.*";
               }
               type uint32 {
                 range "300 .. 1800";
               }
             }
           }
           leaf aggregated-ether {
             description "Aggregated sources group name";
             type string;
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
       }
       container esmc-transmit {
         description "ESMC transmit parameters";
         uses apply-advanced;
         list interfaces {
           key name;
           ordered-by user;
           description "Interface(s) on which to permit ESMC transmit messages";
           leaf name {
             type string;
           }
           uses apply-advanced;
           container squelch {
             presence "enable squelch";
             description "Squelch a interface";
             uses apply-advanced;
             leaf method {
               description "Type of Squelch to be done";
               type enumeration {
                 enum "ais" {
                   description "Send AIS";
                 }
                 enum "ql-dnu" {
                   description "Send DNU Quality level out";
                 }
                 enum "rai" {
                   description "Method RAI";
                 }
                 enum "shut" {
                   description "Shutdown";
                 }
               }
             }
             leaf quality-level {
               description "ESMC Quality level below which output is squelched";
               type enumeration {
                 enum "ePRTC" {
                   description "Time quality of enhanced primary reference time clock";
                 }
                 enum "PRTC" {
                   description "Time quality of primary reference time clock";
                 }
                 enum "ePRC" {
                   description "Time quality of enhanced primary reference clock";
                 }
                 enum "eEEC" {
                   description "Time quality of enhanced ethernet equipment clock";
                 }
                 enum "prc" {
                   description "Timing quality of a primary reference clock (option-1 only)";
                 }
                 enum "ssu-a" {
                   description "Timing quality of a type I or IV slave clock (option-1 only)";
                 }
                 enum "ssu-b" {
                   description "Timing quality of a type VI slave clock (option-1 only)";
                 }
                 enum "sec" {
                   description "Timing quality of SDH equipment clock (option-1 only)";
                 }
                 enum "prs" {
                   description "Clock traceable to primary reference source (option-2 only)";
                 }
                 enum "st2" {
                   description "Clock traceable to stratum 2 (option-2 only)";
                 }
                 enum "tnc" {
                   description "Clock traceable to transit node clock (option-2 only)";
                 }
                 enum "st3e" {
                   description "Clock traceable to stratum 3E (option-2 only)";
                 }
                 enum "st3" {
                   description "Clock traceable to stratum 3 (option-2 only)";
                 }
                 enum "st4" {
                   description "Clock traceable to stratum 4 free-run (option-2 only)";
                 }
                 enum "smc" {
                   description "Clock traceable to self-timed SONET (option-2 only)";
                 }
                 enum "stu" {
                   description "Clock traceable to unknown quality (option-2 only)";
                 }
               }
             }
           }
         }
       }
       container hold-interval {
         description "Hold interval";
         uses apply-advanced;
         leaf switchover {
           description "Switchover wait time after clock recovery";
           default "30";
           units "sec";
           type union {
             type string {
               pattern "<.*>|$.*";
             }
             type uint32 {
               range "30 .. 60";
             }
           }
         }
         leaf configuration-change {
           description "Clock select wait time after change in config";
           default "15";
           units "sec";
           type union {
             type string {
               pattern "<.*>|$.*";
             }
             type uint32 {
               range "15 .. 60";
             }
           }
         }
         leaf restart {
           description "Clock select wait time after reboot";
           default "120";
           units "sec";
           type union {
             type string {
               pattern "<.*>|$.*";
             }
             type uint32 {
               range "60 .. 180";
             }
           }
         }
       }
       leaf signal-type {
         description "Frequency for provided reference clocks";
         default "t1";
         type enumeration {
           enum "e1" {
             description "E1-coded 2048 Khz signal on 120 ohm balanced line";
           }
           enum "t1" {
             description "T1-coded 1.544 Mhz signal on 100 ohm balanced line";
           }
           enum "cc-8k" {
             description "Composite Clock 64kHz+8kHz";
           }
           enum "cc-8k-400" {
             description "Composite Clock 64kHz+8kHz+400Hz";
           }
           enum "6312k" {
             description "Japanese Standard 6312kHz";
           }
         }
       }
       leaf primary {
         description "Best choice synchronization reference source list";
         type enumeration {
           enum "external-a" {
             description "Use external-a as a primary source";
           }
           enum "external-b" {
             description "Use external-b as a primary source";
           }
           enum "bits-a" {
             description "Use bits-a as a primary source";
           }
           enum "bits-b" {
             description "Use bits-b as a primary source";
           }
           enum "gps-0" {
             description "Use gps-0 as a primary source";
           }
           enum "gps-1" {
             description "Use gps-1 as a primary source";
           }
           enum "fpc-0" {
             description "Use fpc-0 as a primary source";
           }
           enum "fpc-1" {
             description "Use fpc-1 as a primary source";
           }
           enum "fpc-2" {
             description "Use fpc-2 as a primary source";
           }
           enum "fpc-3" {
             description "Use fpc-3 as a primary source";
           }
           enum "fpc-4" {
             description "Use fpc-4 as a primary source";
           }
           enum "fpc-5" {
             description "Use fpc-5 as a primary source";
           }
           enum "fpc-6" {
             description "Use fpc-6 as a primary source";
           }
           enum "fpc-7" {
             description "Use fpc-7 as a primary source";
           }
           enum "fpc-8" {
             description "Use fpc-8 as a primary source";
           }
           enum "fpc-9" {
             description "Use fpc-9 as a primary source";
           }
           enum "fpc-10" {
             description "Use fpc-10 as a primary source";
           }
           enum "fpc-11" {
             description "Use fpc-11 as a primary source";
           }
           enum "fpc-12" {
             description "Use fpc-12 as a primary source";
           }
           enum "fpc-13" {
             description "Use fpc-13 as a primary source";
           }
           enum "fpc-14" {
             description "Use fpc-14 as a primary source";
           }
           enum "fpc-15" {
             description "Use fpc-15 as a primary source";
           }
         }
       }
       leaf secondary {
         description "Alternative choice synchronization reference source list";
         type enumeration {
           enum "external-a" {
             description "Use external-a as a secondary source";
           }
           enum "external-b" {
             description "Use external-b as a secondary source";
           }
           enum "bits-a" {
             description "Use bits-a as a secondary source";
           }
           enum "bits-b" {
             description "Use bits-b as a secondary source";
           }
           enum "gps-0" {
             description "Use gps-0 as a secondary source";
           }
           enum "gps-1" {
             description "Use gps-1 as a secondary source";
           }
           enum "fpc-0" {
             description "Use fpc-0 as a secondary source";
           }
           enum "fpc-1" {
             description "Use fpc-1 as a secondary source";
           }
           enum "fpc-2" {
             description "Use fpc-2 as a secondary source";
           }
           enum "fpc-3" {
             description "Use fpc-3 as a secondary source";
           }
           enum "fpc-4" {
             description "Use fpc-4 as a secondary source";
           }
           enum "fpc-5" {
             description "Use fpc-5 as a secondary source";
           }
           enum "fpc-6" {
             description "Use fpc-6 as a secondary source";
           }
           enum "fpc-7" {
             description "Use fpc-7 as a secondary source";
           }
           enum "fpc-8" {
             description "Use fpc-8 as a secondary source";
           }
           enum "fpc-9" {
             description "Use fpc-9 as a secondary source";
           }
           enum "fpc-10" {
             description "Use fpc-10 as a secondary source";
           }
           enum "fpc-11" {
             description "Use fpc-11 as a secondary source";
           }
           enum "fpc-12" {
             description "Use fpc-12 as a secondary source";
           }
           enum "fpc-13" {
             description "Use fpc-13 as a secondary source";
           }
           enum "fpc-14" {
             description "Use fpc-14 as a secondary source";
           }
           enum "fpc-15" {
             description "Use fpc-15 as a secondary source";
           }
         }
       }
     }
     container lcd {
       description "Chassis LCD";
       status deprecated;
       uses apply-advanced;
       choice menu-item {
         case case_1 {
           leaf maintenance-menu {
             description "LCD maintenance menu";
             type empty;
           }
         }
       }
       choice enable-disable {
         case case_1 {
           leaf disable {
             description "Disable maintenance-menu";
             type empty;
           }
         }
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               type empty;
             }
             leaf unicast-in-lpm {
               description "Install unicast host entries in LPM table";
               type empty;
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:32K, needs reboot for VC; restarts PFE if standalone";
           }
         }
         case case_8 {
           container vxlan-gbp-l2-profile {
             presence "enable vxlan-gbp-l2-profile";
             description "MAC: 64K L3-host: 32K LPM: 16K EM:16K, needs reboot for VC; restarts PFE if standalone";
           }
         }
         case case_9 {
           container vxlan-gbp-l3-profile {
             presence "enable vxlan-gbp-l3-profile";
             description "MAC: 32K L3-host: 64K LPM: 16K EM:16K, needs reboot for VC; restarts PFE if standalone";
           }
         }
         case case_10 {
           container em-hw-profile {
             presence "enable em-hw-profile";
             description "MAC: 48K L3-host: 48K LPM: 16K EM:32K, needs reboot for VC; restarts PFE if standalone";
           }
         }
         case case_11 {
           container default-profile {
             presence "enable default-profile";
             description "MAC: 64K L3-host: 32K LPM: 24K IFP: 12K, needs reboot for VC; restarts PFE if standalone";
           }
         }
         case case_12 {
           container ifp-profile {
             presence "enable ifp-profile";
             description "MAC: 64K L3-host: 32K LPM: 12K IFP: 18K, needs reboot for VC; restarts PFE if standalone";
           }
         }
         case case_13 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     leaf loopback-firewallv6-optimization {
       description "Increase ACL scale for loopback IPv6 filters; restarts PFE";
       type empty;
     }
     leaf input-firewall-optimized-profile {
       description "Optimal default filter usage when IFA/FCoe/FIPsnooping is not used; restarts PFE";
       type empty;
     }
     leaf ivacl-firewall-no-portrange-profile {
       description "L4 Src/Dst Port range optimize is not needed; restarts PFE";
       type empty;
     }
     leaf iracl-firewall-ipv4-profile {
       description "IPv6 address match is not needed for IRACL filters; restarts PFE";
       type empty;
     }
     leaf ipvacl-firewall-l2-profile {
       description "Only Src/Dst MAC,VLAN,EtherType match is needed for IPACL/IVACL filters; restarts PFE";
       type empty;
     }
     leaf loopback-firewall-optimization {
       description "Optimal TCAM use,restarts PFE(for IP rsrved multicast dest & IP ttl=0/1,config explicitly)";
       type empty;
     }
     leaf epacl-firewall-optimization {
       description "Maximizes Egress Port ACLs TCAM use and restarts PFE";
       type empty;
     }
     leaf per-logical-interface-firewall {
       description "Ingress port firewall can be supported per logical interface, restarts PFE";
       type empty;
     }
     leaf fru-poweron-sequence {
       description "FRUs power on sequence like 0 1 2 3 ... within double quotes";
       type string {
       }
     }
     container psm {
       description "Power supply module";
       uses apply-advanced;
       container redundancy {
         description "PSM Source/Feed Redundancy configuration";
         uses apply-advanced;
         leaf source-redundancy {
           description "Toggle source redundancy for PSM";
           type empty;
         }
         container feed-redundancy {
           description "Toggle feed redundancy for a PSM slot";
           uses apply-advanced;
           list slot {
             key name;
             description "PSM slot number";
             leaf name {
               description "Select PSM slot";
               type union {
                 type string {
                   pattern "<.*>|$.*";
                 }
                 type uint32;
               }
             }
             uses apply-advanced;
           }
         }
       }
     }
     leaf auto-image-upgrade {
       description "Auto image upgrade using DHCP";
       type empty;
     }
     container error {
       description "Error level configuration for all FPC";
       presence "enable error";
       uses chassis_fpc_error_type;
     }
     container oss-map {
       description "Translate Operation Supported System's requirements";
       uses apply-advanced;
       leaf model-name {
         description "Override chassis model name for specific show/snmp output";
         type enumeration {
           enum "t640" {
             description "Set to T640's model";
           }
           enum "t1600" {
             description "Set to T1600's model";
           }
         }
       }
     }
     container jnu-management {
       description "JNU Management configuration";
       uses apply-advanced;
       leaf mode {
         description "JNU Mode";
         type enumeration {
           enum "feature-rich" {
             description "Feature Rich Mode";
           }
           enum "bng-control-plane" {
             description "BNG control-plane mode";
           }
         }
       }
       leaf satellite-name {
         description "Satellite name";
         type string;
       }
       leaf device-group {
         description "Satellite device group";
         type string;
       }
       list device-group-map {
         key name;
         ordered-by user;
         description "Common groups mapping to device groups";
         leaf name {
           description "Satellite Device Group";
           type string;
         }
         uses apply-advanced;
         leaf-list include-groups {
           ordered-by user;
           description "Common groups list";
           type string;
         }
       }
       list satellite {
         key name;
         ordered-by user;
         description "List of satellites";
         leaf name {
           description "Satellite name";
           type string;
         }
         uses apply-advanced;
         leaf device-group {
           description "Satellite Device Group";
           type string;
         }
         leaf model {
           description "Satellite model";
           type string;
         }
         leaf version {
           description "Satellite version";
           type string {
           }
         }
       }
       leaf user {
         description "Satellite User Name";
         type string;
       }
       leaf controller {
         description "Controller Name";
         type string;
       }
       leaf authentication {
         description "Authentication string";
         type jt:unreadable;
       }
     }
     list satellite {
       key name;
       ordered-by user;
       description "List of available satellite configurations";
       leaf name {
         description "Satellite name";
         type string;
       }
       uses apply-advanced;
     }
     leaf auto-satellite-conversion {
       description "Enable remote conversion to satellite device-mode";
       type empty;
     }
     container satellite-management {
       presence "enable satellite-management";
       description "Satellite management configuration";
       uses apply-advanced;
       container designated-event-forwarding {
         presence "enable designated-event-forwarding";
         description "Designated event forwarding";
       }
       container traceoptions {
         description "Global satelite discovery and provisioning trace options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "parse" {
                 description "Trace configuration parsing";
               }
               enum "config-internal" {
                 description "Trace configuration internals";
               }
               enum "normal" {
                 description "Trace normal events";
               }
               enum "general" {
                 description "Trace general events";
               }
               enum "state" {
                 description "Trace state transitions";
               }
               enum "task" {
                 description "Trace SDPD task processing";
               }
               enum "timer" {
                 description "Trace SDPD task timer processing";
               }
               enum "krt" {
                 description "Trace communication over routing socket";
               }
               enum "lldp" {
                 description "Trace LLDP events";
               }
               enum "provision" {
                 description "Trace provisioning events";
               }
               enum "extended-port" {
                 description "Trace extended-port events";
               }
               enum "multi-chassis" {
                 description "Trace multi-chassis events";
               }
               enum "upgrade-group" {
                 description "Trace sw-update events";
               }
               enum "device" {
                 description "Trace device FSM events";
               }
               enum "tcp" {
                 description "Trace TCP events";
               }
               enum "interface" {
                 description "Trace interface events";
               }
               enum "cluster" {
                 description "Trace cluster events";
               }
               enum "all" {
                 description "Trace everything";
               }
             }
           }
           leaf disable {
             description "Disable this trace flag";
             type empty;
           }
         }
       }
       leaf cluster-policy {
         description "Cluster policy";
         type string;
       }
       list cluster {
         key name;
         description "Configure a satellite device cluster";
         leaf name {
           description "Satellite cluster name";
           type string {
             length "1 .. 16";
           }
         }
         uses apply-advanced;
         leaf cluster-id {
           description "Satellite cluster identifier";
           type union {
             type string {
               pattern "<.*>|$.*";
             }
             type uint32 {
               range "1 .. 32";
             }
           }
         }
         leaf-list cascade-ports {
           description "Cascade ports";
           type union {
             type jt:interface-device;
             type string {
               pattern "<.*>|$.*";
             }
           }
         }
         leaf cluster-policy {
           description "Candidate uplink policy";
           type string;
         }
         list fpc {
           key name;
           leaf name {
             description "Satellite slot identifier";
             type union {
               type string {
                 pattern "<.*>|$.*";
               }
               type uint32 {
                 range "65 .. 254";
               }
             }
           }
           uses apply-advanced;
           leaf alias {
             description "Satellite alias";
             type string {
               length "1 .. 16";
             }
           }
           leaf description {
             description "Satellite description";
             type string {
               length "1 .. 64";
             }
           }
           leaf member-id {
             description "Satellite member id";
             type union {
               type string {
                 pattern "<.*>|$.*";
               }
               type uint32 {
                 range "0 .. 62";
               }
             }
           }
           leaf system-id {
             description "Satellite system id";
             type jt:mac-addr;
           }
           leaf cluster-policy {
             description "Candidate uplink policy";
             type string;
           }
         }
       }
       list fpc {
         key name;
         description "FPC identifier for a satellite device";
         leaf name {
           description "Satellite slot identifier";
           type union {
             type string {
               pattern "<.*>|$.*";
             }
             type uint32 {
               range "65 .. 254";
             }
           }
         }
         uses apply-advanced;
         leaf serial-number {
           description "Satellite serial number";
           type string {
             length "1 .. 16";
           }
         }
         leaf system-id {
           description "Satellite system id";
           type jt:mac-addr;
         }
         leaf target-mode {
           description "Enable target mode forwarding for extended-ports";
           type empty;
         }
         leaf alias {
           description "Satellite alias";
           type string {
             length "1 .. 16";
           }
         }
         leaf description {
           description "Satellite description";
           type string {
             length "1 .. 64";
           }
         }
         container management-address {
           presence "enable management-address";
           description "Satellite Management Interface IP";
           uses apply-advanced;
           leaf address {
             description "Satellite Management Interface IP address";
             type jt:ipv4prefix;
           }
           leaf gateway {
             description "Satellite Management Interface Gateway IP address";
             type jt:ipv4addr;
           }
         }
         leaf-list cascade-ports {
           description "Cascade ports";
           type union {
             type jt:interface-device;
             type string {
               pattern "<.*>|$.*";
             }
           }
         }
         leaf extended-ports-template {
           description "Extended ports template";
           type string;
         }
         choice ufd_type {
           case case_1 {
             container uplink-failure-detection {
               presence "enable uplink-failure-detection";
               description "Enable uplink-failure-detection";
               uses apply-advanced;
               leaf candidate-uplink-policy {
                 description "Candidate uplink policy";
                 type string;
               }
             }
           }
         }
         leaf environment-monitoring-policy {
           description "Environment monitoring policy";
           type string;
         }
         choice forwarding-policy-type {
           case case_1 {
             container forwarding-policy {
               presence "enable forwarding-policy";
               description "Enable a forwarding policy";
               uses apply-advanced;
               leaf forwarding-policy-alias {
                 description "Define forwarding policy alias";
                 type string;
               }
             }
           }
         }
       }
       leaf extended-ports-policy {
         description "Extended ports policy";
         type string;
       }
       choice ufd_type {
         case case_1 {
           container uplink-failure-detection {
             presence "enable uplink-failure-detection";
             description "Enable uplink-failure-detection";
             uses apply-advanced;
             leaf candidate-uplink-policy {
               description "Candidate uplink policy";
               type string;
             }
           }
         }
       }
       container psu {
         description "Power Supply Unit redundancy configuration";
         uses apply-advanced;
         container redundancy {
           description "PSU Redundancy settings";
           uses apply-advanced;
           leaf n-plus-n {
             description "PSU redundancy: N+N configuration";
             type empty;
           }
         }
       }
       container environment-monitoring-policy {
         presence "enable environment-monitoring-policy";
         description "Environment monitoring policy";
         uses apply-advanced;
         leaf policy-name {
           description "Default environment monitoring policy";
           type string;
         }
       }
       choice forwarding-policy-type {
         case case_1 {
           container forwarding-policy {
             presence "enable forwarding-policy";
             description "Enable a forwarding policy";
             uses apply-advanced;
             leaf forwarding-policy-alias {
               description "Define forwarding policy alias";
               type string;
             }
           }
         }
       }
       container redundancy-groups {
         description "Redundancy groups configuration";
         uses apply-advanced;
         leaf chassis-id {
           description "Chassis identifier";
           type union {
             type string {
               pattern "<.*>|$.*";
             }
             type uint32 {
               range "1 .. 4";
             }
           }
         }
         list rg-group {
           key name;
           ordered-by user;
           description "Redundancy groups";
           uses redundancy-group-type;
         }
       }
       container upgrade-groups {
         description "Upgrade group configuration";
         uses apply-advanced;
         list upgrade-group {
           key name;
           description "Upgrade group";
           uses upgrade-group-type;
         }
       }
       container auto-satellite-conversion {
         description "Enable automatic satellite conversion";
         uses apply-advanced;
         leaf-list satellite {
           ordered-by user;
           description "Satellite slot-id or range or all";
           type string {
             length "1 .. 100";
           }
         }
       }
       container single-home {
         description "Devices are connected to local aggregation device only";
         uses apply-advanced;
         leaf-list satellite {
           ordered-by user;
           description "Satellite slot-id or range or all";
           type string {
             length "1 .. 100";
           }
         }
       }
       leaf aging-timer {
         description "Aging-timer";
         units "minutes";
         type union {
           type string {
             pattern "<.*>|$.*";
           }
           type uint32 {
             range "2 .. 60000";
           }
         }
       }
       leaf block-console-access {
         description "Block console access";
         type empty;
       }
       container firewall {
         description "Define a firewall configuration";
         uses apply-advanced;
         container family {
           description "Protocol family";
           container bridge {
             description "Protocol family BRIDGE for firewall filter";
             uses apply-advanced;
             list filter {
               key name;
               ordered-by user;
               uses satellite-bridge-filter;
             }
           }
           container ethernet-switching {
             description "Protocol family Ethernet Switching for firewall filter";
             uses apply-advanced;
             list filter {
               key name;
               ordered-by user;
               description "Define an Ethernet Switching firewall filter";
               uses satellite-bridge-filter;
             }
           }
         }
       }
     }
     container periodic {
       description "Chassisd periodic options";
       uses apply-advanced;
       leaf ch-power-check-interval {
         description "Chassis power check interval, 0=default";
         default "0";
         units "seconds";
         type union {
           type string {
             pattern "<.*>|$.*";
           }
           type uint32 {
             range "0 .. 60";
           }
         }
       }
       leaf re-check-interval {
         description "Chassis RE check interval, 0=default";
         default "0";
         units "seconds";
         type union {
           type string {
             pattern "<.*>|$.*";
           }
           type uint32 {
             range "0 .. 60";
           }
         }
       }
     }
     container thermal-health-check {
       presence "enable thermal-health-check";
       description "Enable Thermal Health check of the chassis";
       uses apply-advanced;
       container fet-failure-check {
         presence "enable fet-failure-check";
         uses apply-advanced;
         leaf action-onfail {
           description "Set the action when Oring FET detected";
           default "none";
           type enumeration {
             enum "none" {
               description "No action when Oring FET detected";
             }
             enum "auto-shutdown" {
               description "Shutdown when Oring FET detected";
             }
           }
         }
       }
     }
     container mode {
       description "Set FRU mode";
       uses apply-advanced;
       container standalone {
         presence "enable standalone";
         description "Bringup FRU in standalone mode1";
         uses apply-advanced;
         list fpc {
           key name;
           leaf name {
             description "FPC slot number";
             type string {
               length "1 .. 4";
             }
           }
           uses apply-advanced;
           container loopback {
             description "Loopback Configuration for Mode & Type";
             uses apply-advanced;
             leaf wan {
               default "serdes";
               type enumeration {
                 enum "serdes" {
                   description "Serdes type loopback";
                 }
                 enum "retimer" {
                   description "Retimer type loopback";
                 }
               }
             }
             leaf fabric {
               default "serdes";
               type enumeration {
                 enum "serdes" {
                   description "Serdes type loopback";
                 }
                 enum "retimer" {
                   description "Retimer type loopback";
                 }
               }
             }
           }
         }
         list fabric-card {
           key name;
           ordered-by user;
           description "Fabric Card Loopback setting";
           uses chassis_fabric_card_type;
         }
       }
       choice power-mode {
         case case_1 {
           leaf power-optimized {
             description "Set power mode to power-optimized";
             type empty;
           }
         }
       }
     }
     leaf local-station-mac {
       description "Local station mac address configuration";
       type jt:mac-unicast;
     }
     container system-domains {
       presence "enable system-domains";
       description "Root and protected system domain configuration";
       uses apply-advanced;
       leaf root-domain-id {
         description "Root domain identifier";
         type union {
           type string {
             pattern "<.*>|$.*";
           }
           type uint32 {
             range "1 .. 3";
           }
         }
       }
       list protected-system-domains {
         key name;
         description "Protected system domain configuration";
         uses juniper-protected-system-domain;
       }
       container traceoptions {
         description "Protected system domain traceoptions";
         uses juniper-protected-system-domain-traceoptions;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping chassis-pw-type {
     uses apply-advanced;
     leaf device-count {
       description "Number of pseudo-wire ps devices";
       type union {
         type string {
           pattern "<.*>|$.*";
         }
         type uint32 {
           range "1 .. 18000";
         }
       }
     }
   }
   grouping chassis_agg_dev_type {
     uses apply-advanced;
     leaf ae-20 {
       description "Run AE over Container nexthops Infrastructure";
       status deprecated;
       type empty;
     }
     container ethernet {
       description "Aggregated device options for Ethernet";
       uses chassisd_agg_enet_type;
     }
     container sonet {
       description "Aggregated device options for SONET";
       uses chassisd_agg_pos_type;
     }
     leaf maximum-links {
       description "Maximum links limit for aggregated devices (16, 32, or 64)";
       type union {
         type int32;
         type string {
           pattern "<.*>|$.*";
         }
       }
     }
   }
   grouping chassis_alarm_port_op_type {
     uses apply-advanced;
     container input {
       description "Input alarm port";
       uses apply-advanced;
       list port {
         key name;
         ordered-by user;
         description "Input Port";
         leaf name {
           description "Alarm port ID";
           type union {
             type string {
               pattern "<.*>|$.*";
             }
             type uint32 {
               range "1 .. 3";
             }
           }
         }
         uses apply-advanced;
         leaf active {
           description "Active signal of alarm IO input port";
           type enumeration {
             enum "low" {
               description "Active signal of alarm IO port to low(default)";
             }
             enum "high" {
               description "Active signal of alarm IO port to high";
             }
           }
         }
         leaf admin-state {
           description "Administrative state of alarm IO input port";
           type enumeration {
             enum "disabled" {
               description "Administrative state of alarm IO port to disable(default)";
             }
             enum "enabled" {
               description "Administrative state of alarm IO port to enabled";
             }
           }
         }
         container description {
           description "Alarm description of alarm IO input port";
           uses apply-advanced;
           leaf descr {
             description "Description to be used for alarm IO output port";
             type string;
           }
         }
         leaf severity {
           description "Set alarm severity of alarm IO input port";
           type enumeration {
             enum "critical" {
               description "Alarm severity of alarm IO input port to ciritical(default)";
             }
             enum "major" {
               description "Alarm severity of alarm IO input port to major";
             }
             enum "minor" {
               description "Alarm severity of alarm IO input port to minor";
             }
             enum "warning" {
               description "Alarm severity of alarm IO input port to warning";
             }
           }
         }
       }
     }
     container output {
       description "Output alarm port";
       uses apply-advanced;
       list port {
         key name;
         ordered-by user;
         description "Output port";
         leaf name {
           description "Alarm IO output port ID";
           type union {
             type string {
               pattern "<.*>|$.*";
             }
             type uint32 {
               range 1;
             }
           }
         }
         uses apply-advanced;
         leaf admin-state {
           description "Administrative state of alarm IO output port";
           type enumeration {
             enum "disabled" {
               description "Administrative state of alarm IO port to disable(default)";
             }
             enum "enabled" {
               description "Administrative state of alarm IO port to enabled";
             }
           }
         }
         container description {
           description "Alarm description of alarm IO output port";
           uses apply-advanced;
           leaf descr {
             description "Description to be used for alarm IO output port";
             type string;
           }
         }
       }
     }
   }
   grouping chassis_alarm_type {
     uses apply-advanced;
     container management-ethernet {
       description "Management Ethernet alarms";
       uses chassis_alarm_ethernet_type;
     }
     container otn-odu {
       description "OTN ODU alarms";
       uses chassis_alarm_otn_odu_type;
     }
     container otn-otu {
       description "OTN OTU alarms";
       uses chassis_alarm_otn_otu_type;
     }
     container sonet {
       description "SONET alarms";
       uses chassis_alarm_sonet_type;
     }
     container t3 {
       description "DS3 alarms";
       uses chassis_alarm_ds3_type;
     }
     container ds1 {
       description "DS1 alarms";
       uses chassis_alarm_ds1_type;
     }
     container ethernet {
       description "Ethernet alarms";
       uses chassis_alarm_ethernet_type;
     }
     container integrated-services {
       description "Integrated services alarms";
       uses chassis_alarm_integrated_services_type;
     }
     container services {
       description "Services PIC alarms";
       uses chassis_alarm_services_type;
     }
     container serial {
       description "Serial alarms";
       uses chassis_alarm_serial_type;
     }
     container fibre-channel {
       description "Fibre Channel alarms";
       uses chassis_alarm_fibre-channel_type;
     }
     container fru-absence {
       description "FRU module absence";
       uses apply-advanced;
       container ignore {
         description "Ignore the power supply module absence alarm";
         uses apply-advanced;
         list fpc {
           key name;
           ordered-by user;
           description "FPC Slot Number";
           uses chassis_fpc_type_slot;
         }
       }
     }
   }
   grouping chassis_alarm_ds1_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ds3_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf exz {
       description "Excessive zeros";
       type enumeration {
         enum "red" {
           description "Assert red system alarm";
         }
         enum "yellow" {
           description "Assert yellow system alarm";
         }
         enum "ignore" {
           description "Do not assert any alarm signals";
         }
       }
     }
     leaf ferf {
       description "Far-end failure";
       type enumeration {
         enum "red" {
           description "Assert red system alarm";
         }
         enum "yellow" {
           description "Assert yellow system alarm";
         }
         enum "ignore" {
           description "Do not assert any alarm signals";
         }
       }
     }
     leaf idle {
       description "Idle alarm";
       type enumeration {
         enum "red" {
           description "Assert red system alarm";
         }
         enum "yellow" {
           description "Assert yellow system alarm";
         }
         enum "ignore" {
           description "Do not assert any alarm signals";
         }
       }
     }
     leaf lcv {
       description "Line code violation";
       type enumeration {
         enum "red" {
           description "Assert red system alarm";
         }
         enum "yellow" {
           description "Assert yellow system alarm";
         }
         enum "ignore" {
           description "Do not assert any alarm signals";
         }
       }
     }
     leaf lof {
       description "Loss of frame";
       type enumeration {
         enum "red" {
           description "Assert red system alarm";
         }
         enum "yellow" {
           description "Assert yellow system alarm";
         }
         enum "ignore" {
           description "Do not assert any alarm signals";
         }
       }
     }
     leaf los {
       description "Loss of signal";
       type enumeration {
         enum "red" {
           description "Assert red system alarm";
         }
         enum "yellow" {
           description "Assert yellow system alarm";
         }
         enum "ignore" {
           description "Do not assert any alarm signals";
         }
       }
     }
     leaf pll {
       description "Phase-locked loop out of lock";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ethernet_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_fibre-channel_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_integrated_services_type {
     uses apply-advanced;
     leaf failure {
       description "Integrated Services failure";
       type enumeration {
         enum "red" {
           description "Assert red system alarm";
         }
         enum "yellow" {
           description "Assert yellow system alarm";
         }
         enum "ignore" {
           description "Do not assert any alarm signals";
         }
       }
     }
   }
   grouping chassis_alarm_otn_odu_type {
     uses apply-advanced;
     leaf odu-bdi {
       description "ODU backward-defect-indicator, ODU-BDI failure";
       type enumeration {
         enum "red" {
           description "Assert red system alarm";
         }
         enum "yellow" {
           description "Assert yellow system alarm";
         }
         enum "ignore" {
           description "Do not assert any alarm signals";
         }
       }
     }
     leaf odu-ttim {
       description "ODU trail-trace-identifier-mismatch, ODU-TTIM failure";
       type enumeration {
         enum "red" {
           description "Assert red system alarm";
         }
         enum "yellow" {
           description "Assert yellow system alarm";
         }
         enum "ignore" {
           description "Do not assert any alarm signals";
         }
       }
     }
     leaf odu-ptim {
       description "ODU payload-type-mismatch, ODU-PTIM failure";
       type enumeration {
         enum "red" {
           description "Assert red system alarm";
         }
         enum "yellow" {
           description "Assert yellow system alarm";
         }
         enum "ignore" {
           description "Do not assert any alarm signals";
         }
       }
     }
   }
   grouping chassis_alarm_otn_otu_type {
     uses apply-advanced;
     leaf oc-los {
       description "Loss of signal, LOS failure";
       type enumeration {
         enum "red" {
           description "Assert red system alarm";
         }
         enum "yellow" {
           description "Assert yellow system alarm";
         }
         enum "ignore" {
           description "Do not assert any alarm signals";
         }
       }
     }
     leaf oc-lof {
       description "Loss of framing, LOF failure";
       type enumeration {
         enum "red" {
           description "Assert red system alarm";
         }
         enum "yellow" {
           description "Assert yellow system alarm";
         }
         enum "ignore" {
           description "Do not assert any alarm signals";
         }
       }
     }
     leaf oc-lom {
       description "Loss of multiframe, LOM failure";
       type enumeration {
         enum "red" {
           description "Assert red system alarm";
         }
         enum "yellow" {
           description "Assert yellow system alarm";
         }
         enum "ignore" {
           description "Do not assert any alarm signals";
         }
       }
     }
     leaf wavelength-lock {
       description "Wavelength lock alarm";
       type enumeration {
         enum "red" {
           description "Assert red system alarm";
         }
         enum "yellow" {
           description "Assert yellow system alarm";
         }
         enum "ignore" {
           description "Do not assert any alarm signals";
         }
       }
     }
     leaf otu-bdi {
       description "OTU backward-defect-indicator, OTU-BDI failure";
       type enumeration {
         enum "red" {
           description "Assert red system alarm";
         }
         enum "yellow" {
           description "Assert yellow system alarm";
         }
         enum "ignore" {
           description "Do not assert any alarm signals";
         }
       }
     }
     leaf otu-iae {
       description "OTU incoming-alignment-error, OTU-IAE failure";
       type enumeration {
         enum "red" {
           description "Assert red system alarm";
         }
         enum "yellow" {
           description "Assert yellow system alarm";
         }
         enum "ignore" {
           description "Do not assert any alarm signals";
         }
       }
     }
     leaf otu-ttim {
       description "OTU trail-trace-identifier-mismatch, OTU-TTIM failure";
       type enumeration {
         enum "red" {
           description "Assert red system alarm";
         }
         enum "yellow" {
           description "Assert yellow system alarm";
         }
         enum "ignore" {
           description "Do not assert any alarm signals";
         }
       }
     }
     leaf otu-fec-excessive-errs {
       description "OTU fec-excessive-errors, OTU-FEC_EXE failure";
       type enumeration {
         enum "red" {
           description "Assert red system alarm";
         }
         enum "yellow" {
           description "Assert yellow system alarm";
         }
         enum "ignore" {
           description "Do not assert any alarm signals";
         }
       }
     }
   }
   grouping chassis_alarm_serial_type {
     uses apply-advanced;
     leaf loss-of-rx-clock {
       description "RX clock absent";
       type enumeration {
         enum "red" {
           description "Assert red system alarm";
         }
         enum "yellow" {
           description "Assert yellow system alarm";
         }
         enum "ignore" {
           description "Do not assert any alarm signals";
         }
       }
     }
     leaf loss-of-tx-clock {
       description "TX clock absent";
       type enumeration {
         enum "red" {
           description "Assert red system alarm";
         }
         enum "yellow" {
           description "Assert yellow system alarm";
         }
         enum "ignore" {
           description "Do not assert any alarm signals";
         }
       }
     }
     leaf dcd-absent {
       description "DCD signal absent";
       type enumeration {
         enum "red" {
           description "Assert red system alarm";
         }
         enum "yellow" {
           description "Assert yellow system alarm";
         }
         enum "ignore" {
           description "Do not assert any alarm signals";
         }
       }
     }
     leaf cts-absent {
       description "CTS signal absent";
       type enumeration {
         enum "red" {
           description "Assert red system alarm";
         }
         enum "yellow" {
           description "Assert yellow system alarm";
         }
         enum "ignore" {
           description "Do not assert any alarm signals";
         }
       }
     }
     leaf dsr-absent {
       description "DSR signal absent";
       type enumeration {
         enum "red" {
           description "Assert red system alarm";
         }
         enum "yellow" {
           description "Assert yellow system alarm";
         }
         enum "ignore" {
           description "Do not assert any alarm signals";
         }
       }
     }
     leaf tm-absent {
       description "TM signal absent";
       type enumeration {
         enum "red" {
           description "Assert red system alarm";
         }
         enum "yellow" {
           description "Assert yellow system alarm";
         }
         enum "ignore" {
           description "Do not assert any alarm signals";
         }
       }
     }
   }
   grouping chassis_alarm_services_type {
     uses apply-advanced;
     leaf pic-reset {
       description "Services PIC reset";
       type enumeration {
         enum "red" {
           description "Assert red system alarm";
         }
         enum "yellow" {
           description "Assert yellow system alarm";
         }
         enum "ignore" {
           description "Do not assert any alarm signals";
         }
       }
     }
     leaf pic-hold-reset {
       description "Services PIC held in reset";
       type enumeration {
         enum "red" {
           description "Assert red system alarm";
         }
         enum "yellow" {
           description "Assert yellow system alarm";
         }
         enum "ignore" {
           description "Do not assert any alarm signals";
         }
       }
     }
     leaf linkdown {
       description "Services PIC linkdown";
       type enumeration {
         enum "red" {
           description "Assert red system alarm";
         }
         enum "yellow" {
           description "Assert yellow system alarm";
         }
         enum "ignore" {
           description "Do not assert any alarm signals";
         }
       }
     }
     leaf rx-errors {
       description "Services PIC excessive rx errors";
       type enumeration {
         enum "red" {
           description "Assert red system alarm";
         }
         enum "yellow" {
           description "Assert yellow system alarm";
         }
         enum "ignore" {
           description "Do not assert any alarm signals";
         }
       }
     }
     leaf tx-errors {
       description "Services PIC excessive tx errors";
       type enumeration {
         enum "red" {
           description "Assert red system alarm";
         }
         enum "yellow" {
           description "Assert yellow system alarm";
         }
         enum "ignore" {
           description "Do not assert any alarm signals";
         }
       }
     }
     leaf sw-down {
       description "Services PIC software problem";
       type enumeration {
         enum "red" {
           description "Assert red system alarm";
         }
         enum "yellow" {
           description "Assert yellow system alarm";
         }
         enum "ignore" {
           description "Do not assert any alarm signals";
         }
       }
     }
     leaf hw-down {
       description "Services PIC hardware problem";
       type enumeration {
         enum "red" {
           description "Assert red system alarm";
         }
         enum "yellow" {
           description "Assert yellow system alarm";
         }
         enum "ignore" {
           description "Do not assert any alarm signals";
         }
       }
     }
   }
   grouping chassis_alarm_sonet_type {
     uses apply-advanced;
     leaf lol {
       description "Loss of light";
       type enumeration {
         enum "red" {
           description "Assert red system alarm";
         }
         enum "yellow" {
           description "Assert yellow system alarm";
         }
         enum "ignore" {
           description "Do not assert any alarm signals";
         }
       }
     }
     leaf pll {
       description "Phase locked loop out of lock";
       type enumeration {
         enum "red" {
           description "Assert red system alarm";
         }
         enum "yellow" {
           description "Assert yellow system alarm";
         }
         enum "ignore" {
           description "Do not assert any alarm signals";
         }
       }
     }
     leaf lof {
       description "Loss of framing, LOF failure";
       type enumeration {
         enum "red" {
           description "Assert red system alarm";
         }
         enum "yellow" {
           description "Assert yellow system alarm";
         }
         enum "ignore" {
           description "Do not assert any alarm signals";
         }
       }
     }
     leaf los {
       description "Loss of signal, LOS failure";
       type enumeration {
         enum "red" {
           description "Assert red system alarm";
         }
         enum "yellow" {
           description "Assert yellow system alarm";
         }
         enum "ignore" {
           description "Do not assert any alarm signals";
         }
       }
     }
     leaf ais-l {
       description "Line alarm indication signal, AIS-L failure";
       type enumeration {
         enum "red" {
           description "Assert red system alarm";
         }
         enum "yellow" {
           description "Assert yellow system alarm";
         }
         enum "ignore" {
           description "Do not assert any alarm signals";
         }
       }
     }
     leaf ais-p {
       description "Path alarm indication signal, AIS-P failure";
       type enumeration {
         enum "red" {
           description "Assert red system alarm";
         }
         enum "yellow" {
           description "Assert yellow system alarm";
         }
         enum "ignore" {
           description "Do not assert any alarm signals";
         }
       }
     }
     leaf lop-p {
       description "Loss of pointer, LOP-P failure";
       type enumeration {
         enum "red" {
           description "Assert red system alarm";
         }
         enum "yellow" {
           description "Assert yellow system alarm";
         }
         enum "ignore" {
           description "Do not assert any alarm signals";
         }
       }
     }
     leaf ber-sd {
       description "Signal Degrade (SD), bit error rate > 1E-6";
       type enumeration {
         enum "red" {
           description "Assert red system alarm";
         }
         enum "yellow" {
           description "Assert yellow system alarm";
         }
         enum "ignore" {
           description "Do not assert any alarm signals";
         }
       }
     }
     leaf ber-sf {
       description "Signal Fail (SF), bit error rate > 1E-3";
       type enumeration {
         enum "red" {
           description "Assert red system alarm";
         }
         enum "yellow" {
           description "Assert yellow system alarm";
         }
         enum "ignore" {
           description "Do not assert any alarm signals";
         }
       }
     }
     leaf rfi-l {
       description "Line remote failure indication, RFI-L, line FERF";
       type enumeration {
         enum "red" {
           description "Assert red system alarm";
         }
         enum "yellow" {
           description "Assert yellow system alarm";
         }
         enum "ignore" {
           description "Do not assert any alarm signals";
         }
       }
     }
     leaf rfi-p {
       description "Path remote failure indication, RFI-P, STS path yellow";
       type enumeration {
         enum "red" {
           description "Assert red system alarm";
         }
         enum "yellow" {
           description "Assert yellow system alarm";
         }
         enum "ignore" {
           description "Do not assert any alarm signals";
         }
       }
     }
     leaf uneq-p {
       description "STS Path (C2) unequipped, UNEQ-P failure";
       type enumeration {
         enum "red" {
           description "Assert red system alarm";
         }
         enum "yellow" {
           description "Assert yellow system alarm";
         }
         enum "ignore" {
           description "Do not assert any alarm signals";
         }
       }
     }
     leaf locd {
       description "Loss of cell delineation (ATM only)";
       type enumeration {
         enum "red" {
           description "Assert red system alarm";
         }
         enum "yellow" {
           description "Assert yellow system alarm";
         }
         enum "ignore" {
           description "Do not assert any alarm signals";
         }
       }
     }
     leaf plm-p {
       description "STS payload label (C2) mismatch, PLM-P failure";
       type enumeration {
         enum "red" {
           description "Assert red system alarm";
         }
         enum "yellow" {
           description "Assert yellow system alarm";
         }
         enum "ignore" {
           description "Do not assert any alarm signals";
         }
       }
     }
   }
   grouping chassis_cb_type {
     leaf name {
       description "CB slot number";
       type union {
         type string {
           pattern "<.*>|$.*";
         }
         type uint32;
       }
     }
     uses apply-advanced;
     container temperature-threshold {
       description "CB temperature thresholds";
       uses chassis-temperature-threshold-type;
     }
     list temperature-sensor {
       key name;
       description "CB temperature sensor";
       uses chassis-temperature-sensor-type;
     }
   }
   grouping chassis-temperature-sensor-type {
     leaf name {
       description "Temperature sensor name";
       type string;
     }
     uses apply-advanced;
     container temperature-threshold {
       description "Temperature thresholds";
       uses chassis-temperature-threshold-type;
     }
   }
   grouping chassis-temperature-threshold-type {
     description "Chassis temperature thresholds";
     uses apply-advanced;
     leaf fans-to-normal-speed {
       description "Threshold at which fans return to normal speed";
       units "degrees C";
       type union {
         type uint32;
         type string {
           pattern "<.*>|$.*";
         }
       }
     }
     leaf fans-on-intermediate-speed {
       description "Threshold at which fans run intermediate speed";
       units "degrees C";
       type union {
         type uint32;
         type string {
           pattern "<.*>|$.*";
         }
       }
     }
     leaf fans-on-full-speed {
       description "Threshold at which fans run full speed";
       units "degrees C";
       type union {
         type uint32;
         type string {
           pattern "<.*>|$.*";
         }
       }
     }
     leaf fans-on-full-speed-if-failed-fan {
       description "Threshold at which fans run full speed when bad fan present";
       units "degrees C";
       type union {
         type uint32;
         type string {
           pattern "<.*>|$.*";
         }
       }
     }
     leaf yellow-alarm {
       description "Threshold at which yellow alarm is set";
       units "degrees C";
       type union {
         type uint32;
         type string {
           pattern "<.*>|$.*";
         }
       }
     }
     leaf yellow-alarm-if-failed-fan {
       description "Threshold at which yellow alarm is set when bad fan present";
       units "degrees C";
       type union {
         type uint32;
         type string {
           pattern "<.*>|$.*";
         }
       }
     }
     leaf red-alarm {
       description "Threshold at which red alarm is set";
       units "degrees C";
       type union {
         type uint32;
         type string {
           pattern "<.*>|$.*";
         }
       }
     }
     leaf red-alarm-if-failed-fan {
       description "Threshold at which red alarm is set when bad fan present";
       units "degrees C";
       type union {
         type uint32;
         type string {
           pattern "<.*>|$.*";
         }
       }
     }
     leaf fire-shutdown {
       description "Threshold at which router will be shutdown within 10 seconds";
       units "degrees C";
       type union {
         type uint32;
         type string {
           pattern "<.*>|$.*";
         }
       }
     }
   }
   grouping chassis_fabric_card_type {
     leaf name {
       description "Fabric Card slot number";
       type string {
         length "1 .. 5";
       }
     }
     uses apply-advanced;
     container loopback {
       description "Loopback Configuration for Mode & Type";
       uses apply-advanced;
       leaf serdes {
         description "Fabric Card serdes setting";
         type empty;
       }
       leaf retimer {
         description "Fabric card retimer setting";
         type empty;
       }
     }
   }
   grouping chassis_fabric_type {
     uses apply-advanced;
     leaf upgrade-mode {
       description "Enable online switch fabric upgrade";
       type enumeration {
         enum "default" {
           description "Fabric upgrade";
         }
         enum "t4000" {
           description "T4000 Fabric upgrade";
         }
         enum "3d-fabric" {
           description "TXP-3D Fabric upgrade";
         }
       }
     }
     container event {
       description "Fabric events";
       uses apply-advanced;
       container link-failure {
         presence "enable link-failure";
         description "Fabric link failure";
         uses apply-advanced;
         container action {
           presence "enable action";
           description "Fabric action to be taken";
           uses apply-advanced;
         }
       }
       container reachability-fault {
         presence "enable reachability-fault";
         description "Fabric reachability fault detection";
         uses apply-advanced;
         container degraded {
           presence "enable degraded";
           description "Degraded fabric configuration";
           uses apply-advanced;
           container error-threshold {
             presence "enable error-threshold";
             description "Fabric error threshold for degraded case";
             uses apply-advanced;
             container degradation {
               presence "enable degradation";
               description "Degradation attributes";
               uses apply-advanced;
               leaf percentage {
                 description "The percentage degradation on which action is taken";
                 type union {
                   type string {
                     pattern "<.*>|$.*";
                   }
                   type uint32 {
                     range "1 .. 99";
                   }
                 }
               }
             }
           }
         }
         container actions {
           description "Reachability fault actions";
           uses apply-advanced;
           container recovery-failure {
             description "Recovery failure action to be taken for FHP";
             uses apply-advanced;
           }
         }
       }
     }
     container oam {
       description "Fabric OAM configuration";
       uses apply-advanced;
       leaf detection-disable {
         description "Disable fabric OAM";
         type empty;
       }
       leaf runtime-disable {
         description "Disable runtime fabric OAM";
         type empty;
       }
     }
     container degraded {
       presence "enable degraded";
       description "Degraded fabric configuration";
       uses apply-advanced;
       leaf action-fpc-restart-disable {
         description "Limit degraded fabric actions to Plane restart only";
         type empty;
       }
       leaf degraded-fpc-bad-plane-threshold {
         description "No of bad planes to declare a FPC degraded";
         default "4";
         type union {
           type string {
             pattern "<.*>|$.*";
           }
           type uint32 {
             range "4 .. 18";
           }
         }
       }
       leaf degraded-fabric-detection-enable {
         description "Enable degraded FPC detection";
         type empty;
       }
     }
     container redundancy-mode {
       description "Fabric redundancy mode";
       uses apply-advanced;
       choice mode {
         case case_1 {
           leaf redundant {
             description "Fabric is configured in redundant mode";
             type empty;
           }
         }
         case case_2 {
           leaf increased-bandwidth {
             description "Fabric is configured in increased bandwidth mode";
             type empty;
           }
         }
       }
     }
   }
   grouping chassis_feb_type {
     uses apply-advanced;
     container sanity-poll {
       description "FPC register sanity poll";
       uses apply-advanced;
       leaf retry-count {
         description "Number of retries before reporting error";
         default "10";
         type union {
           type string {
             pattern "<.*>|$.*";
           }
           type uint32 {
             range "1 .. 30";
           }
         }
       }
       container on-error {
         description "Actions to be taken if inconsistencies are detected";
         uses apply-advanced;
         leaf raise-alarm {
           description "Raise emergency alarm";
           type empty;
         }
         leaf power {
           description "Power cycle or power off FPC";
           type enumeration {
             enum "cycle" {
               description "Write coredump and reboot FPC";
             }
             enum "off" {
               description "Power down FPC indefinitely";
             }
           }
         }
         leaf write-coredump {
           description "Write coredump and continue";
           type empty;
         }
       }
     }
     list slot {
       key name;
       ordered-by user;
       leaf name {
         description "FEB slot number";
         type union {
           type string {
             pattern "<.*>|$.*";
           }
           type uint32;
         }
       }
       uses apply-advanced;
       container sanity-poll {
         description "FPC register sanity poll";
         uses apply-advanced;
         leaf retry-count {
           description "Number of retries before reporting error";
           default "10";
           type union {
             type string {
               pattern "<.*>|$.*";
             }
             type uint32 {
               range "1 .. 30";
             }
           }
         }
         container on-error {
           description "Actions to be taken if inconsistencies are detected";
           uses apply-advanced;
           leaf raise-alarm {
             description "Raise emergency alarm";
             type empty;
           }
           leaf power {
             description "Power cycle or power off FPC";
             type enumeration {
               enum "cycle" {
                 description "Write coredump and reboot FPC";
               }
               enum "off" {
                 description "Power down FPC indefinitely";
               }
             }
           }
           leaf write-coredump {
             description "Write coredump and continue";
             type empty;
           }
         }
       }
       leaf power {
         description "Power FEBs on or off";
         type enumeration {
           enum "off" {
             description "Do not provide power to FEBs";
           }
           enum "on" {
             description "Provide power to FEBs";
           }
         }
       }
       choice mode {
       }
       leaf port-mirror-instance {
         description "Associate a port mirroring instance with the FEB";
         type string {
           length "1 .. 64";
         }
       }
       leaf sampling-instance {
         description "Associate a sampling instance with the FEB";
         type string {
           length "1 .. 64";
         }
       }
       leaf ucode-imem-remap {
         description "Remap the PIC microcode to IMEM on FEB";
         type empty;
       }
       container inline-services {
         uses apply-advanced;
         leaf report-zero-oif-gw-on-discard {
           description "Jflow reports value zero in OIF and GW when traffic is not forwarded";
           type empty;
         }
         leaf flex-flow-sizing {
           description "No fixed size allocation of flow tables for proto families";
           type empty;
         }
         leaf use-extended-flow-memory {
           description "Use extended memory for flow records";
           type empty;
         }
         container flow-table-size {
           uses apply-advanced;
           leaf ipv4-flow-table-size {
             description "IPv4 flow table size in units of 256k";
             type union {
               type string {
                 pattern "<.*>|$.*";
               }
               type uint32 {
                 range "1 .. 245";
               }
             }
           }
           leaf ipv6-flow-table-size {
             description "IPv6 flow table size in units of 256k";
             type union {
               type string {
                 pattern "<.*>|$.*";
               }
               type uint32 {
                 range "1 .. 245";
               }
             }
           }
           leaf vpls-flow-table-size {
             description "VPLS flow table size in units of 256k";
             type union {
               type string {
                 pattern "<.*>|$.*";
               }
               type uint32 {
                 range "1 .. 245";
               }
             }
           }
           leaf bridge-flow-table-size {
             description "BRIDGE flow table size in units of 256k";
             type union {
               type string {
                 pattern "<.*>|$.*";
               }
               type uint32 {
                 range "1 .. 245";
               }
             }
           }
           leaf ipv6-extended-attrib {
             description "Enable extended flow attribute";
             type empty;
           }
           leaf mpls-flow-table-size {
             description "MPLS flow table size in units of 256k";
             type union {
               type string {
                 pattern "<.*>|$.*";
               }
               type uint32 {
                 range "1 .. 245";
               }
             }
           }
         }
       }
       container inline-video-monitoring {
         uses apply-advanced;
         leaf maximum-flows-count {
           description "Maximum number of inline video monitoring flows per PFE instance";
           type union {
             type string {
               pattern "<.*>|$.*";
             }
             type uint32 {
               range "16 .. 8192";
             }
           }
         }
       }
       container openflow {
         description "Openflow configuration";
         uses apply-advanced;
         leaf access-list-partition {
           description "Space reserved for openflow access-list rules";
           units "percents";
           type union {
             type string {
               pattern "<.*>|$.*";
             }
             type uint32 {
               range "0 .. 100";
             }
           }
         }
       }
     }
   }
   grouping chassis_fpc_error_type {
     description "Chassis Fpc Error level";
     uses apply-advanced;
     container fatal {
       description "FPC Fatal errors (default threshold = 1)";
       uses chassis_fpc_error_level_major_fatal;
     }
     container major {
       description "FPC Major Level errors (default threshold = 1)";
       uses chassis_fpc_error_level_major_fatal;
     }
     container minor {
       description "FPC Minor Level errors (default threshold = 10)";
       uses chassis_fpc_error_level_minor;
     }
     list override-cmerror {
       key name;
       ordered-by user;
       description "Error configuration override";
       max-elements 100;
       uses chassis_fru_cmerror_override_type;
     }
     container reset-pfe {
       description "FPC config reset-pfe options";
       presence "enable reset-pfe";
       uses chassis_fpc_error_config_reset_pfe_opt;
     }
     container scope {
       description "Error scope";
       uses chassis_fpc_scope_type;
     }
   }
   grouping chassis_fpc_error_config_reset_pfe_opt {
     uses apply-advanced;
     leaf retry-limit {
       description "Reset pfe retry limit";
       type union {
         type string {
           pattern "<.*>|$.*";
         }
         type uint32 {
           range "0 .. 3";
         }
       }
     }
     leaf pause-period {
       description "Reset pfe pause period in minutes";
       type union {
         type string {
           pattern "<.*>|$.*";
         }
         type uint32 {
           range "0 .. 10000000";
         }
       }
     }
     leaf pfe-disable-period {
       description "Reset pfe disable period in minutes";
       type union {
         type string {
           pattern "<.*>|$.*";
         }
         type uint32 {
           range "1 .. 10000000";
         }
       }
     }
   }
   grouping chassis_fpc_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         type enumeration {
           enum "reset" {
             description "Reset FPC";
           }
           enum "offline" {
             description "Offline FPC";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise FPC trap";
           }
         }
       }
       uses apply-advanced;
     }
   }
   grouping chassis_fpc_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         type enumeration {
           enum "reset" {
             description "Reset FPC";
           }
           enum "offline" {
             description "Offline FPC";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise FPC trap";
           }
         }
       }
       uses apply-advanced;
     }
   }
   grouping chassis_fpc_scope_type {
     description "Chassis Fpc Error Scope";
     uses apply-advanced;
     container board {
       description "Board level scope";
       uses chassis_fpc_scope_category;
     }
     container pfe {
       description "Forwarding engine scope ";
       uses chassis_fpc_scope_category;
     }
   }
   grouping chassis_fpc_scope_category {
     description "Chassis Fpc Error Category";
     uses apply-advanced;
     container category {
       description "FPC error category";
       uses chassis_fpc_scope_category_type;
     }
   }
   grouping chassis_fpc_scope_category_type {
     description "Chassis Fpc Category level";
     uses apply-advanced;
     container functional {
       description "FPC functional category";
       uses chassis_fpc_scope_category_error_type;
     }
     container memory {
       description "FPC memory category";
       uses chassis_fpc_scope_category_error_type;
     }
     container io {
       description "FPC input-output category";
       uses chassis_fpc_scope_category_error_type;
     }
     container storage {
       description "FPC storage category";
       uses chassis_fpc_scope_category_error_type;
     }
     container switch {
       description "FPC switch category";
       uses chassis_fpc_scope_category_error_type;
     }
     container processing {
       description "FPC processing category";
       uses chassis_fpc_scope_category_error_type;
     }
   }
   grouping chassis_fpc_scope_category_error_type {
     description "Chassis Fpc Error level";
     uses apply-advanced;
     container fatal {
       description "FPC Fatal errors (default threshold = 1)";
       uses chassis_fpc_error_level_type;
     }
     container major {
       description "FPC Major Level errors (default threshold = 1)";
       uses chassis_fpc_error_level_type;
     }
     container minor {
       description "FPC Minor Level errors (default threshold = 10)";
       uses chassis_fpc_error_level_type;
     }
   }
   grouping chassis_fpc_error_level_type {
     uses apply-advanced;
     leaf threshold {
       description "Error count at which to take the action (0 - valid for minor only)";
       type union {
         type string {
           pattern "<.*>|$.*";
         }
         type uint32 {
           range "0 .. 4294967295";
         }
       }
     }
     list action {
       key name;
       ordered-by user;
       description "Configure the action for this level";
       leaf name {
         type enumeration {
           enum "reset" {
             description "Reset FPC";
           }
           enum "offline" {
             description "Offline FPC";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise trap";
           }
         }
       }
       uses apply-advanced;
     }
   }
   grouping chassis_fpc_type {
     leaf name {
       description "FPC slot number";
       type union {
         type string {
           pattern "<.*>|$.*";
         }
         type uint32;
       }
     }
     uses apply-advanced;
     container auto-speed-detection {
       description "Disables auto-speed detection";
       uses apply-advanced;
       choice auto-speed-detections {
         case case_1 {
           leaf disable {
             description "Disables automatic speed detection";
             type empty;
           }
         }
       }
     }
     container linkscan-per-fpc {
       presence "enable linkscan-per-fpc";
       description "Configure linkscan per FPC";
       uses apply-advanced;
       leaf fpc-linkscan-interval {
         description " setting linkscan interval of FPC in microsecond";
         type union {
           type string {
             pattern "<.*>|$.*";
           }
           type uint32 {
             range "10000 .. 500000";
           }
         }
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               type empty;
             }
             leaf unicast-in-lpm {
               description "Install unicast host entries in LPM table";
               type empty;
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:32K, needs reboot for VC; restarts PFE if standalone";
           }
         }
         case case_8 {
           container vxlan-gbp-l2-profile {
             presence "enable vxlan-gbp-l2-profile";
             description "MAC: 64K L3-host: 32K LPM: 16K EM:16K, needs reboot for VC; restarts PFE if standalone";
           }
         }
         case case_9 {
           container vxlan-gbp-l3-profile {
             presence "enable vxlan-gbp-l3-profile";
             description "MAC: 32K L3-host: 64K LPM: 16K EM:16K, needs reboot for VC; restarts PFE if standalone";
           }
         }
         case case_10 {
           container em-hw-profile {
             presence "enable em-hw-profile";
             description "MAC: 48K L3-host: 48K LPM: 16K EM:32K, needs reboot for VC; restarts PFE if standalone";
           }
         }
         case case_11 {
           container default-profile {
             presence "enable default-profile";
             description "MAC: 64K L3-host: 32K LPM: 24K IFP: 12K, needs reboot for VC; restarts PFE if standalone";
           }
         }
         case case_12 {
           container ifp-profile {
             presence "enable ifp-profile";
             description "MAC: 64K L3-host: 32K LPM: 12K IFP: 18K, needs reboot for VC; restarts PFE if standalone";
           }
         }
         case case_13 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     list pic {
       key name;
       description "Physical Interface Card number";
       uses chassis_pic_type;
     }
     leaf power {
       description "Power FPCs on or off";
       type enumeration {
         enum "off" {
           description "Do not provide power to FPCs";
         }
         enum "on" {
           description "Provide power to FPCs";
         }
       }
     }
     container traffic-manager {
       description "Configure traffic-manager attributes";
       uses apply-advanced;
       leaf buffer-monitor-enable {
         description "Enable port buffer monitoring";
         type empty;
       }
       container queue-threshold {
         description "Set queue thresholds";
         uses apply-advanced;
         container fabric-queue {
           description "Set fabric queue thresholds";
           uses apply-advanced;
           list priority {
             key name;
             ordered-by user;
             description "Queue priority";
             leaf name {
               description "Priority level";
               type enumeration {
                 enum "low" {
                   description "Low fabric priority";
                 }
                 enum "high" {
                   description "High fabric priority";
                 }
               }
             }
             uses apply-advanced;
             leaf threshold {
               description "Threshold percentage to be set";
               type union {
                 type string {
                   pattern "<.*>|$.*";
                 }
                 type uint32 {
                   range "1 .. 100";
                 }
               }
             }
           }
         }
         container wan-queue {
           description "Set wan queue thresholds";
           uses apply-advanced;
           list priority {
             key name;
             ordered-by user;
             description "Queue Priority";
             leaf name {
               description "Priority level";
               type enumeration {
                 enum "low" {
                   description "Low wan priority";
                 }
                 enum "medium-low" {
                   description "Medium low wan priority";
                 }
                 enum "medium-high" {
                   description "Medium high wan priority";
                 }
                 enum "high" {
                   description "High wan priority";
                 }
               }
             }
             uses apply-advanced;
             leaf threshold {
               description "Threshold percentage to be set";
               type union {
                 type string {
                   pattern "<.*>|$.*";
                 }
                 type uint32 {
                   range "1 .. 100";
                 }
               }
             }
           }
         }
       }
       choice enhanced-priority-mode-choice {
         leaf enhanced-priority-mode {
           description "Enable enhanced priority mode";
           type empty;
         }
         leaf no-enhanced-priority-mode {
           description "Don't enable enhanced priority mode";
           type empty;
         }
       }
       leaf packet-timestamp {
         description "Configure collecting CoS last packet enqueued timestamp";
         default "disable";
         type enumeration {
           enum "enable" {
             description "Enables collecting CoS last packet enqueued timestamp";
           }
           enum "disable" {
             description "Disables collecting CoS last packet enqueued timestamp";
           }
         }
       }
     }
     leaf max-power {
       description "Max power to be consumed by MPC";
       type union {
         type uint32;
         type string {
           pattern "<.*>|$.*";
         }
       }
     }
     leaf power-budget-priority {
       description "FPC priority number";
       type union {
         type string {
           pattern "<.*>|$.*";
         }
         type uint32;
       }
     }
     choice mode {
       case case_1 {
         leaf disable-power {
           description "Do not provide power to the card";
           status deprecated;
           type empty;
         }
       }
       case case_2 {
         leaf allow-sram-parity-errors {
           description "Do not power cycle FPC when SRAM parity errors occur";
           type empty;
         }
       }
     }
     choice riot-mode {
       case case_1 {
       }
       case case_2 {
       }
     }
     leaf cfp-to-et {
       description "Enable ET interface and remove CFP client";
       type empty;
     }
     container lossless-flow-control {
       presence "enable lossless-flow-control";
       description "Lossless buffer config for Ethernet Mac pause";
       uses apply-advanced;
       choice enable_choice {
         case case_1 {
           leaf lossless-flow-control-enable {
             description "Enable Lossless buffer config for Ethernet Mac pause";
             type empty;
           }
         }
         case case_2 {
           leaf no-lossless-flow-control-enable {
             description "Disable Lossless buffer config for Ethernet Mac pause";
             type empty;
           }
         }
       }
     }
     leaf offline {
       description "Keep FPC offline";
       type empty;
     }
     leaf license-mode {
       description "Configure license mode for PTX FPC3 and later cards";
       type enumeration {
         enum "r" {
           description "Set card to R mode";
         }
         enum "ir" {
           description "Set card to IR mode";
         }
         enum "lsr" {
           description "Set card to LSR mode";
         }
         enum "ip" {
           description "Set card to full IP mode";
         }
       }
     }
     list port-mirror-instance {
       key name;
       ordered-by user;
       max-elements 2;
       leaf name {
         description "Associate a port mirroring instance with the FPC";
         type string {
           length "1 .. 64";
         }
       }
       uses apply-advanced;
     }
     list sampling-instance {
       key name;
       ordered-by user;
       max-elements 1;
       leaf name {
         description "Associate a sampling instance with the FPC";
         type string {
           length "1 .. 64";
         }
       }
       uses apply-advanced;
     }
     container inline-services {
       uses apply-advanced;
       leaf report-zero-oif-gw-on-discard {
         description "Jflow reports value zero in OIF and GW when traffic is not forwarded";
         type empty;
       }
       leaf flex-flow-sizing {
         description "No fixed size allocation of flow tables for proto families";
         type empty;
       }
       leaf use-extended-flow-memory {
         description "Use extended memory for flow records";
         type empty;
       }
       container flow-table-size {
         uses apply-advanced;
         leaf ipv4-flow-table-size {
           description "IPv4 flow table size in units of 256k";
           type union {
             type string {
               pattern "<.*>|$.*";
             }
             type uint32 {
               range "1 .. 245";
             }
           }
         }
         leaf ipv6-flow-table-size {
           description "IPv6 flow table size in units of 256k";
           type union {
             type string {
               pattern "<.*>|$.*";
             }
             type uint32 {
               range "1 .. 245";
             }
           }
         }
         leaf vpls-flow-table-size {
           description "VPLS flow table size in units of 256k";
           status deprecated;
           type union {
             type string {
               pattern "<.*>|$.*";
             }
             type uint32 {
               range "1 .. 245";
             }
           }
         }
         leaf bridge-flow-table-size {
           description "BRIDGE flow table size in units of 256k";
           type union {
             type string {
               pattern "<.*>|$.*";
             }
             type uint32 {
               range "1 .. 245";
             }
           }
         }
         leaf ipv6-extended-attrib {
           description "Enable extended flow attribute";
           type empty;
         }
         leaf mpls-flow-table-size {
           description "MPLS flow table size in units of 256k";
           type union {
             type string {
               pattern "<.*>|$.*";
             }
             type uint32 {
               range "1 .. 245";
             }
           }
         }
       }
     }
     container inline-video-monitoring {
       uses apply-advanced;
       leaf maximum-flows-count {
         description "Maximum number of inline video monitoring flows per PFE instance.";
         status deprecated;
         type union {
           type string {
             pattern "<.*>|$.*";
           }
           type uint32 {
             range "16 .. 8192";
           }
         }
       }
       leaf flow-table-size {
         description "Size of flow table size per PFE instance";
         type union {
           type string {
             pattern "<.*>|$.*";
           }
           type uint32 {
             range "16 .. 8192";
           }
         }
       }
     }
     container slamon-services {
       description "SLA monitoring services";
       uses apply-advanced;
     }
     list pfe {
       key name;
       description "Packet forwarding engine parameters";
       uses chassis_pfe_type;
     }
     leaf service-package {
       description "Service package to be loaded on FPC";
       default "bundle-rfc2544";
       type enumeration {
         enum "bundle-rfc2544" {
           description "Service Package for RFC2544";
         }
         enum "bundle-nat-ipsec" {
           description "Service Package for NAT and IPSEC";
         }
         enum "bundle-ptp-enterprise-profile" {
           description "Service Package for PTP Enterprise Profile";
         }
       }
     }
     container error {
       description "Error level configuration for FPC";
       uses chassis_fpc_error_type;
     }
     list ether-type {
       key name;
       ordered-by user;
       description "Set Ethernet type on FPC";
       leaf name {
         description "TCAM slot";
         type union {
           type string {
             pattern "<.*>|$.*";
           }
           type uint8 {
             range "6 .. 27";
           }
         }
       }
       uses apply-advanced;
       leaf etype {
         description "Ether type";
         type string;
       }
     }
     container openflow {
       description "Openflow configuration";
       uses apply-advanced;
       leaf access-list-partition {
         description "Space reserved for openflow access-list rules";
         units "percents";
         type union {
           type string {
             pattern "<.*>|$.*";
           }
           type uint32 {
             range "0 .. 100";
           }
         }
       }
       leaf buffer-partition {
         description "Buffer space reserved for openflow traffic";
         units "percents";
         type union {
           type string {
             pattern "<.*>|$.*";
           }
           type uint32 {
             range "0 .. 100";
           }
         }
       }
     }
   }
   grouping chassis_fpc_type_slot {
     leaf name {
       description "FPC slot number";
       type string;
     }
     uses apply-advanced;
     list pem {
       key name;
       ordered-by user;
       description "Power Supply Module slot";
       uses chassis_pem_type_slot;
     }
   }
   grouping chassis_fru_cmerror_override_type {
     description "Chassis Fpc Error override";
     leaf name {
       description "Error identifier";
       type string {
         length "1 .. 255";
       }
     }
     uses apply-advanced;
     leaf state {
       description "State";
       type enumeration {
         enum "disable" {
           description "Disable error";
         }
       }
     }
     leaf severity {
       description "Severity";
       type enumeration {
         enum "minor" {
           description "Minor Severity";
         }
         enum "major" {
           description "Major Severity";
         }
         enum "fatal" {
           description "Fatal Severity";
         }
       }
     }
     container pfe {
       presence "enable pfe";
       description "Apply to these pfe";
       uses apply-advanced;
       leaf all {
         description "Apply to all pfe";
         type empty;
       }
     }
   }
   grouping chassis_pem_type {
     uses apply-advanced;
     leaf minimum {
       description "Minimum number of power supplies required for normal operation";
       type union {
         type string {
           pattern "<.*>|$.*";
         }
         type uint32;
       }
     }
     leaf input-current {
       description "Input current (Amps) in each feed ";
       default "60";
       type enumeration {
         enum "40" {
           description "40 Amps in each Feed";
         }
         enum "60" {
           description "60 Amps in each Feed";
         }
       }
     }
     container redundancy {
       description "PEM Source/Feed Redundancy configuration";
       uses apply-advanced;
       leaf source-redundancy {
         description "Toggle Source Redundancy for PEM";
         type empty;
       }
       container feed-redundancy {
         description "Toggle Feed Redundancy for a PEM slot";
         uses apply-advanced;
         list slot {
           key name;
           description "PEM Slot Number";
           leaf name {
             description "Select PEM slot";
             type union {
               type string {
                 pattern "<.*>|$.*";
               }
               type uint32;
             }
           }
           uses apply-advanced;
         }
       }
     }
   }
   grouping chassis_pem_type_slot {
     leaf name {
       description "PEM slot number";
       type string;
     }
     uses apply-advanced;
   }
   grouping chassis_pfe_type {
     description "PFE(Packet forwarding engine)";
     leaf name {
       description "PFE(Packet forwarding engine) identifier";
       type union {
         type string {
           pattern "<.*>|$.*";
         }
         type uint32;
       }
     }
     uses apply-advanced;
     container forwarding-packages {
       description "Associated forwarding package configuration";
       uses apply-advanced;
       container mobility {
         description "Mobility related PFE configuration";
         uses apply-advanced;
         choice package-type {
           case case_1 {
             leaf user-plane {
               description "User plane function";
               type empty;
             }
           }
         }
       }
     }
     leaf power {
       description "Power PFEs on or off";
       type enumeration {
         enum "off" {
           description "Power off PFE";
         }
         enum "on" {
           description "Power on PFE";
         }
       }
     }
     leaf node {
       description "PFE(Packet forwarding engine) global identifier";
       type union {
         type string {
           pattern "<.*>|$.*";
         }
         type uint64 {
           range "1 .. 18446744073709551615";
         }
       }
     }
     leaf tunnel-services {
       description "Tunnel services configuration";
       type empty;
     }
   }
   grouping chassis_pic_type {
     leaf name {
       description "PIC slot number";
       type union {
         type string {
           pattern "<.*>|$.*";
         }
         type uint32;
       }
     }
     uses apply-advanced;
     leaf alternate-speed-set {
       description "PIC run time mode configuration";
       type enumeration {
         enum "6x100g-1x400g" {
           description "6x100G + 400G mode";
         }
       }
     }
     leaf pic-mode {
       description "PIC mode configuration";
       type enumeration {
         enum "1G" {
           description "1GE mode";
         }
         enum "10G" {
           description "10GE mode";
         }
         enum "25G" {
           description "25GE mode";
         }
         enum "40G" {
           description "40GE mode";
         }
         enum "50G" {
           description "50GE mode";
         }
         enum "100G" {
           description "100GE mode";
         }
         enum "400G" {
           description "400GE mode";
         }
       }
     }
     container tunnel-services {
       presence "enable tunnel-services";
       description "Tunnel services configuration";
       uses apply-advanced;
       leaf bandwidth {
         description "Amount of bandwidth reserved for tunnel service";
         type string;
       }
       leaf tunnel-only {
         description "Support only tunnel traffic";
         type empty;
       }
       container priority {
         presence "enable priority";
         description "Specify bandwidths with priorities";
         uses apply-advanced;
         container high {
           presence "enable high";
           description "High Priority";
           uses apply-advanced;
           leaf bandwidth {
             description "Amount of bandwidth reserved for tunnel service";
             type string;
           }
         }
         container medium {
           presence "enable medium";
           description "Medium Priority";
           uses apply-advanced;
           leaf bandwidth {
             description "Amount of bandwidth reserved for tunnel service";
             type string;
           }
         }
         container low {
           presence "enable low";
           description "Low Priority";
           uses apply-advanced;
           leaf bandwidth {
             description "Amount of bandwidth reserved for tunnel service";
             type string;
           }
         }
       }
       list tunnel-port {
         key name;
         ordered-by user;
         description "Tunnel port number";
         leaf name {
           description "Port number";
           type union {
             type string {
               pattern "<.*>|$.*";
             }
             type uint32;
           }
         }
         uses apply-advanced;
         leaf bandwidth {
           description "Amount of bandwidth reserved for tunnel service";
           type string;
         }
       }
     }
     choice adaptive-or-monitoring {
       case case_1 {
       }
       case case_2 {
         container monitoring-services {
           description "Monitoring services configuration";
           uses apply-advanced;
           leaf application {
             description "Application mode";
             type enumeration {
               enum "dynamic-flow-capture" {
                 description "Dynamic flow capture mode";
               }
               enum "flow-collector" {
                 description "Flow collector mode";
               }
               enum "monitor" {
                 description "Monitor mode";
               }
             }
           }
         }
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
         enum "lan" {
           description "LAN mode";
         }
       }
     }
     container recovered-clock {
       description "Select recovered clock for this port";
       uses apply-advanced;
       leaf port {
         description "Port Number";
         type union {
           type string {
             pattern "<.*>|$.*";
           }
           type uint32 {
             range "0 .. 47";
           }
         }
       }
       leaf channel {
         description "Channel Number";
         type union {
           type string {
             pattern "<.*>|$.*";
           }
           type uint32 {
             range "0 .. 3";
           }
         }
       }
     }
     leaf vtmapping {
       description "Virtual tunnel mapping mode";
       type enumeration {
         enum "klm" {
           description "KLM mode";
         }
         enum "itu-t" {
           description "ITU-T mode";
         }
       }
     }
     leaf no-concatenate {
       description "Do not concatenate channels";
       type empty;
     }
     leaf no-multi-rate {
       description "Disable multi-rate mode";
       type empty;
     }
     leaf speed {
       description "Port speed";
       type enumeration {
         enum "1G" {
           description "1GE-Gigabit Ethernet";
         }
       }
     }
     leaf aggregate-ports {
       description "Aggregate multiple ports on a PIC as a single port";
       type empty;
     }
     leaf number-of-ports {
       description "Number of physical ports to enable on PIC";
       type union {
         type string {
           pattern "<.*>|$.*";
         }
         type uint32;
       }
     }
     leaf power {
       description "Power off PIC";
       type enumeration {
         enum "off" {
           description "Do not provide power to PIC";
         }
       }
     }
     leaf pic-type {
       description "OID of PIC type to be configured";
       type string {
       }
     }
     container aggregated-devices {
       description "Aggregated devices configuration";
       uses apply-advanced;
       container ima {
         description "Aggregated device options for Inverse Multiplexing for ATM";
         uses apply-advanced;
         leaf device-count {
           description "Number of IMA groups";
           type union {
             type string {
               pattern "<.*>|$.*";
             }
             type uint32 {
               range "1 .. 42";
             }
           }
         }
       }
     }
     leaf sparse-dlcis {
       description "Run in sparse data-link connection identifier mode";
       type empty;
     }
     container q-pic-large-buffer {
       presence "enable q-pic-large-buffer";
       description "Run in large delay buffer mode";
       uses apply-advanced;
       choice buffer-type {
         case case_1 {
           leaf small-scale {
             description "Supports less number of interfaces";
             type empty;
           }
         }
         case case_2 {
           leaf large-scale {
             description "Supports large number of interfaces";
             type empty;
           }
         }
       }
     }
     container red-buffer-occupancy {
       description "Computation type for RED buffer occupancy";
       uses apply-advanced;
       container weighted-averaged {
         presence "enable weighted-averaged";
         description "Weighted-average computation";
         uses apply-advanced;
         leaf instant-usage-weight-exponent {
           description "Weight for instant buffer usage (negative exponent of 2)";
           type union {
             type uint8;
             type string {
               pattern "<.*>|$.*";
             }
           }
         }
       }
     }
     container traffic-manager {
       description "Configure traffic manager attributes";
       uses apply-advanced;
       leaf ingress-shaping-overhead {
         description "Number of CoS shaping overhead bytes in ingress";
         units "bytes";
         type union {
           type string {
             pattern "<.*>|$.*";
           }
           type int32 {
             range "-62 .. 192";
           }
         }
       }
       leaf egress-shaping-overhead {
         description "Number of CoS shaping overhead bytes in egress";
         units "bytes";
         type union {
           type string {
             pattern "<.*>|$.*";
           }
           type int32 {
             range "-62 .. 192";
           }
         }
       }
       leaf mode {
         description "Configure traffic manager mode";
         type enumeration {
           enum "egress-only" {
             description "Egress traffic manager enabled, ingress traffic manager disabled";
           }
           enum "session-shaping" {
             description "Enable egress session shaping";
           }
           enum "ingress-and-egress" {
             description "Enable the ingress and egress traffic managers";
           }
         }
       }
     }
     container idle-cell-format {
       description "ATM idle cell configuration";
       uses apply-advanced;
       leaf itu-t {
         description "ITU-T idle cell header format";
         type empty;
       }
       leaf payload-pattern {
         description "Payload pattern byte (0x00-0xff)";
         type string;
       }
     }
     container atm-l2circuit-mode {
       description "Enable ATM Layer 2 circuit transport mode";
       uses apply-advanced;
       choice mode_choice {
         case case_1 {
           leaf aal5 {
             description "ATM Layer 2 circuit AAL5 mode";
             type empty;
           }
         }
         case case_2 {
           leaf cell {
             description "ATM Layer 2 circuit cell mode";
             type empty;
           }
         }
         case case_3 {
           container trunk {
             presence "enable trunk";
             description "Set ATM Layer 2 circuit trunk mode";
             uses apply-advanced;
             choice trunk-mode {
               case case_1 {
                 container uni {
                   presence "enable uni";
                   description "ATM Layer 2 circuit user-to-network interface trunk mode";
                   uses apply-advanced;
                 }
               }
               case case_2 {
                 container nni {
                   presence "enable nni";
                   description "ATM Layer 2 circuit network-to-network interface trunk mode";
                   uses apply-advanced;
                 }
               }
             }
           }
         }
       }
     }
     leaf atm-cell-relay-accumulation {
       description "Enable ATM cell-relay accumulation mode";
       type empty;
     }
     leaf mlfr-uni-nni-bundles {
       description "Number of multilink Frame Relay UNI NNI (FRF.16) bundles to allocate on PIC";
       type union {
         type string {
           pattern "<.*>|$.*";
         }
         type uint32 {
           range "1 .. 255";
         }
       }
     }
     leaf mlfr-uni-nni-bundles-inline {
       description "Number of inline multilink frame relay UNI NNI bundles";
       type union {
         type string {
           pattern "<.*>|$.*";
         }
         type uint32 {
           range "1 .. 255";
         }
       }
     }
     container ct3 {
       description "CT3 NxDS0 PIC configuration";
       uses apply-advanced;
       list port {
         key name;
         description "CT3 port";
         uses ct3_port_type;
       }
     }
     container ce1 {
       description "CE1 NxDS0 PIC configuration";
       uses apply-advanced;
       list e1 {
         key name;
         description "E1 link";
         uses ce1_channel_type;
       }
     }
     container shdsl {
       description "SHDSL chassis configuration";
       uses apply-advanced;
       leaf pic-mode {
         description "PIC mode";
         default "2-port-atm";
         type enumeration {
           enum "1-port-atm" {
             description "Single port ATM, 8 wire mode";
           }
           enum "2-port-atm" {
             description "Two port ATM, 4 wire mode";
           }
           enum "4-port-atm" {
             description "Four port ATM, 2 wire mode";
           }
           enum "efm" {
             description "Single port EFM, 2 wire mode";
           }
         }
       }
     }
     list port-mirror-instance {
       key name;
       ordered-by user;
       max-elements 2;
       leaf name {
         description "Associate a port mirroring instance with the PIC";
         type string {
           length "1 .. 64";
         }
       }
       uses apply-advanced;
     }
     list port {
       key name;
       description "Port number";
       uses chassis_pic_port_framing;
     }
     list port-range {
       key "port-range-low port-range-high";
       ordered-by user;
       description "Physical ports to channelize";
       leaf port-range-low {
         description "Port range low number";
         type union {
           type string {
             pattern "<.*>|$.*";
           }
           type uint32;
         }
       }
       leaf port-range-high {
         description "Port range high number";
         type union {
           type string {
             pattern "<.*>|$.*";
           }
           type uint32;
         }
       }
       uses apply-advanced;
       leaf short-reach-mode {
         description "Short reach mode (For ports 0..47)";
         type enumeration {
           enum "disable" {
             description "Disable";
           }
           enum "enable" {
             description "Enable";
           }
         }
       }
       leaf channel-speed {
         description "Port channel speed";
         type enumeration {
           enum "10g" {
             description "Set the port speed to 10G. This will restart PFE";
           }
           enum "25g" {
             description "Set the port speed to 25G.";
           }
           enum "50g" {
             description "Set the port speed to 50G.";
           }
           enum "disable-auto-speed-detection" {
             description "Disables automatic speed detection";
           }
         }
       }
     }
     container fibre-channel {
       description "Fibre channel configuration option";
       uses chassis_fibre_channel_type;
     }
     container xe {
       description "Ports configurable in 10G mode";
       uses apply-advanced;
       list port {
         key port-number;
         ordered-by user;
         description "Attribute port";
         leaf port-number {
           description "Port number";
           type union {
             type string {
               pattern "<.*>|$.*";
             }
             type uint32;
           }
         }
         uses apply-advanced;
       }
       list port-range {
         key "port-range-low port-range-high";
         ordered-by user;
         description "Attribute port range";
         leaf port-range-low {
           description "Port range low number";
           type union {
             type string {
               pattern "<.*>|$.*";
             }
             type uint32;
           }
         }
         leaf port-range-high {
           description "Port range high number";
           type union {
             type string {
               pattern "<.*>|$.*";
             }
             type uint32;
           }
         }
         uses apply-advanced;
       }
     }
     container xle {
       description "Ports configurable in 40G mode ";
       uses apply-advanced;
       list port {
         key port-number;
         ordered-by user;
         description "Attribute port";
         leaf port-number {
           description "Port number";
           type union {
             type string {
               pattern "<.*>|$.*";
             }
             type uint32;
           }
         }
         uses apply-advanced;
       }
       list port-range {
         key "port-range-low port-range-high";
         ordered-by user;
         description "Attribute port range";
         leaf port-range-low {
           description "Port range low number";
           type union {
             type string {
               pattern "<.*>|$.*";
             }
             type uint32;
           }
         }
         leaf port-range-high {
           description "Port range high number";
           type union {
             type string {
               pattern "<.*>|$.*";
             }
             type uint32;
           }
         }
         uses apply-advanced;
       }
     }
     container fte {
       description "Ports configurable in 40G HIGIG mode";
       uses apply-advanced;
       list port {
         key port-number;
         ordered-by user;
         description "Attribute port";
         leaf port-number {
           description "Port number";
           type union {
             type string {
               pattern "<.*>|$.*";
             }
             type uint32;
           }
         }
         uses apply-advanced;
       }
       list port-range {
         key "port-range-low port-range-high";
         ordered-by user;
         description "Attribute port range";
         leaf port-range-low {
           description "Port range low number";
           type union {
             type string {
               pattern "<.*>|$.*";
             }
             type uint32;
           }
         }
         leaf port-range-high {
           description "Port range high number";
           type union {
             type string {
               pattern "<.*>|$.*";
             }
             type uint32;
           }
         }
         uses apply-advanced;
       }
     }
     leaf account-layer2-overhead {
       description "Account Layer2 overhead in egress and ingress IFD/IFL stats";
       type empty;
     }
     leaf subscriber-aware-services {
       description "Enable subscriber aware services";
       type empty;
     }
     leaf ptp-mode {
       description "Set hardware to run PTP BC applications.";
       type empty;
     }
   }
   grouping ce1_channel_type {
     leaf name {
       description "E1 link number";
       type union {
         type string {
           pattern "<.*>|$.*";
         }
         type uint32 {
           range "0 .. 9";
         }
       }
     }
     uses apply-advanced;
     list channel-group {
       key name;
       description "Define channel group";
       leaf name {
         description "Channel group number";
         type union {
           type string {
             pattern "<.*>|$.*";
           }
           type uint32 {
             range "0 .. 23";
           }
         }
       }
       leaf timeslots {
         description "DS0 timeslots (1..31); for example, 1-3,4,9,22-24 (no spaces)";
         type string;
       }
     }
   }
   grouping chassis_fibre_channel_type {
     description "Fibre channel configuration option";
     uses apply-advanced;
     list port {
       key name;
       ordered-by user;
       description "Fibre channel port";
       leaf name {
         description "Port number for fibre channel mode";
         type union {
           type string {
             pattern "<.*>|$.*";
           }
           type uint32 {
             range "0 .. 47";
           }
         }
       }
       uses apply-advanced;
     }
     list port-range {
       key "port-range-low port-range-high";
       ordered-by user;
       description "Fibre channel port range";
       leaf port-range-low {
         description "Port range low number";
         type union {
           type string {
             pattern "<.*>|$.*";
           }
           type uint32 {
             range "0 .. 47";
           }
         }
       }
       leaf port-range-high {
         description "Port range high number";
         type union {
           type string {
             pattern "<.*>|$.*";
           }
           type uint32 {
             range "0 .. 47";
           }
         }
       }
       uses apply-advanced;
     }
   }
   grouping chassis_pic_port_framing {
     leaf name {
       description "Port number";
       type union {
         type string {
           pattern "<.*>|$.*";
         }
         type uint32;
       }
     }
     uses apply-advanced;
     leaf short-reach-mode {
       description "Short reach mode (For ports 0...47)";
       type enumeration {
         enum "disable" {
           description "Disable";
         }
         enum "enable" {
           description "Enable";
         }
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
       }
     }
     leaf number-of-sub-ports {
       description "Number of subports per physical port";
       type union {
         type string {
           pattern "<.*>|$.*";
         }
         type uint32;
       }
     }
     leaf unused {
       description "Keep the port unused.";
       type empty;
     }
     leaf speed {
       description "Port speed";
       type enumeration {
         enum "oc3-stm1" {
           description "OC3 or STM1";
         }
         enum "oc12-stm4" {
           description "OC12 or STM4";
         }
         enum "oc48-stm16" {
           description "OC48 or STM16";
         }
         enum "1G" {
           description "1GE-Gigabit Ethernet";
         }
         enum "10g" {
           description "Sets the interface mode to 10Gbps";
         }
         enum "25g" {
           description "Sets the interface mode to 25Gbps";
         }
         enum "40g" {
           description "Sets the interface mode to 40Gbps";
         }
         enum "100g" {
           description "Sets the interface mode to 100Gbps";
         }
         enum "50g" {
           description "Sets the interface mode to 50Gbps";
         }
         enum "200g" {
           description "Sets the interface mode to 200 Gbps";
         }
         enum "400g" {
           description "Sets the interface mode to 400Gbps";
         }
       }
     }
     leaf channel-speed {
       description "Port channel speed";
       type enumeration {
         enum "10g" {
           description "Set the port speed to 10G. This will restart PFE on some platforms.";
         }
         enum "25g" {
           description "Set the port speed to 25G.";
         }
         enum "50g" {
           description "Set the port speed to 50G.";
         }
         enum "disable-auto-speed-detection" {
           description "Disables automatic speed detection";
         }
       }
     }
     container forwarding-mode {
       description "PIC packet distribution mode - Brooklyn interop mode";
       uses apply-advanced;
       leaf sa-multicast {
         description "SA multicast mode - interop with 100G Brooklyn PIC";
         type empty;
       }
     }
     leaf no-mcast-replication {
       description "No multicast replication";
       type empty;
     }
     leaf no-temperature-monitoring {
       description "Disable empolicy";
       type empty;
     }
   }
   grouping chassis_redundancy_type {
     uses apply-advanced;
     list routing-engine {
       key name;
       description "Redundancy options for Routing Engines";
       uses chassis_rdd_re_type;
     }
     container failover {
       description "Failover to other Routing Engine";
       presence "enable failover";
       uses chassis_rdd_failover_type;
     }
     leaf keepalive-time {
       description "Time before Routing Engine failover";
       units "seconds";
       type union {
         type string {
           pattern "<.*>|$.*";
         }
         type uint32 {
           range "2 .. 10000";
         }
       }
     }
     container graceful-switchover {
       description "Enable graceful switchover on supported hardware";
       presence "enable graceful-switchover";
       uses chassis_non_stop_forwarding_type;
     }
   }
   grouping chassis_non_stop_forwarding_type {
     uses apply-advanced;
     container traceoptions {
       description "Graceful switchover trace options";
       status deprecated;
       uses apply-advanced;
       list flag {
         key name;
         ordered-by user;
         description "Tracing parameters";
         leaf name {
           type enumeration {
             enum "update" {
               description "Trace state updates";
             }
             enum "all" {
               description "Trace everything";
             }
           }
         }
       }
     }
   }
   grouping chassis_rdd_failover_type {
     uses apply-advanced;
     container category {
       description "Failover category";
       presence "enable category";
       uses chassis_rdd_fail_cat_type;
     }
     leaf on-loss-of-keepalives {
       description "Failover on loss of keepalives";
       type empty;
     }
     leaf on-re-to-fpc-stale {
       description "Failover on loss of communication between the re and fpc";
       type empty;
     }
     leaf on-disk-failure {
       description "Failover on disk failure";
       type empty;
     }
     leaf not-on-disk-underperform {
       description "Prevent gstatd from initiating failovers in response to slow disks";
       type empty;
     }
     leaf disk-read-threshold {
       description "Read threshold (ms) on disk underperform monitoring";
       type union {
         type string {
           pattern "<.*>|$.*";
         }
         type uint32 {
           range "1000 .. 10000";
         }
       }
     }
     leaf disk-write-threshold {
       description "Write threshold (ms) on disk underperform monitoring";
       type union {
         type string {
           pattern "<.*>|$.*";
         }
         type uint32 {
           range "1000 .. 10000";
         }
       }
     }
     leaf on-loss-of-vm-host-connection {
       description "Failover on loss of vm host connection";
       type empty;
     }
   }
   grouping chassis_rdd_fail_cat_type {
     uses apply-advanced;
     container component-failure {
       description "Failover due to component failure";
       presence "enable component-failure";
       uses chassis_rdd_fail_cat_sev_type;
     }
     container software-failure {
       description "Failover due to software failure";
       presence "enable software-failure";
       uses chassis_rdd_fail_cat_sev_type;
     }
     container power-failure {
       description "Failover due to power failure";
       presence "enable power-failure";
       uses chassis_rdd_fail_cat_sev_type;
     }
     container clock-failure {
       description "Failover due to clock failure";
       presence "enable clock-failure";
       uses chassis_rdd_fail_cat_sev_type;
     }
     container link-failure {
       description "Failover due to link failure";
       presence "enable link-failure";
       uses chassis_rdd_fail_cat_sev_type;
     }
     container degraded-health {
       description "Failover due to degraded health";
       presence "enable degraded-health";
       uses chassis_rdd_fail_cat_sev_type;
     }
   }
   grouping chassis_rdd_fail_cat_sev_type {
     uses apply-advanced;
     container critical {
       description "Critical severity";
       presence "enable critical";
       uses chassis_rdd_fail_cat_sev_act_type;
     }
     container important {
       description "Important severity";
       presence "enable important";
       uses chassis_rdd_fail_cat_sev_act_type;
     }
   }
   grouping chassis_rdd_fail_cat_sev_act_type {
     uses apply-advanced;
     leaf disable {
       description "Disable action";
       type empty;
     }
   }
   grouping chassis_rdd_re_type {
     leaf name {
       description "Routing Engine slot number";
       type union {
         type string {
           pattern "<.*>|$.*";
         }
         type uint32 {
           range "0 .. 1";
         }
       }
     }
     choice priority {
       case case_1 {
         leaf master {
           description "Master Routing Engine";
           type empty;
         }
       }
       case case_2 {
         leaf backup {
           description "Backup Routing Engine";
           type empty;
         }
       }
       case case_3 {
         leaf disabled {
           description "Routing Engine disabled";
           type empty;
         }
       }
     }
   }
   grouping chassis_routing_engine_type {
     uses apply-advanced;
     container on-disk-failure {
       description "Action to take when Routing Engine disk fails";
       uses chassis_re_on_disk_failure;
     }
     container disk {
       description "Action to take for Routing Engine disk";
       uses apply-advanced;
       leaf write-threshold-rate {
         description "Write threshold rate";
         default "4";
         units "MBPS";
         type union {
           type string {
             pattern "<.*>|$.*";
           }
           type uint32 {
             range "1 .. 20";
           }
         }
       }
       leaf write-threshold-duration {
         description "Write threshold duration";
         default "1000";
         units "seconds";
         type union {
           type string {
             pattern "<.*>|$.*";
           }
           type uint32 {
             range "300 .. 2592000";
           }
         }
       }
       leaf smart-check {
         description "Enable smart check command to disk";
         type empty;
       }
       list ssd-series {
         key name;
         ordered-by user;
         description "Specify the ssd vendor series";
         leaf name {
           description "SSD series name";
           type string {
             length "1 .. 40";
           }
         }
         uses apply-advanced;
         list id {
           key name;
           ordered-by user;
           description "Attribute ids to monitor of this series type";
           max-elements 30;
           leaf name {
             description "SSD smart attribute id";
             type union {
               type string {
                 pattern "<.*>|$.*";
               }
               type uint32 {
                 range "1 .. 255";
               }
             }
           }
           uses apply-advanced;
           leaf id-threshold {
             description "SSD smart attribute threshold";
             type union {
               type string {
                 pattern "<.*>|$.*";
               }
               type uint32 {
                 range "1 .. 4294967295";
               }
             }
           }
           leaf id-value {
             description "SSD attribute value";
             type enumeration {
               enum "raw" {
                 description "Raw value to be used for this smart id";
               }
               enum "norm" {
                 description "Normalised value to be used for this smart id";
               }
             }
           }
           leaf id-flag {
             description "SSD attribute flag";
             type enumeration {
               enum "low" {
                 description "Check if value is less than smart threshold";
               }
               enum "high" {
                 description "Check if value is greater than smart threshold";
               }
             }
           }
         }
       }
     }
   }
   grouping chassis_re_on_disk_failure {
     choice reboot_or_halt {
       case case_1 {
         leaf reboot {
           description "Reboot on disk failure";
           status deprecated;
           type empty;
         }
       }
       case case_2 {
         leaf disk-failure-action {
           type enumeration {
             enum "reboot" {
               description "Reboot on disk failure";
             }
             enum "halt" {
               description "Halt on disk failure";
             }
           }
         }
       }
     }
   }
   grouping chassis_sib_type {
     uses apply-advanced;
     list slot {
       key name;
       description "SIB slot number";
       leaf name {
         description "SIB slot number";
         type union {
           type string {
             pattern "<.*>|$.*";
           }
           type uint32;
         }
       }
       uses apply-advanced;
       container error {
         description "Error level configuration for SIB";
         uses chassis_sib_error_type;
       }
       leaf power {
         description "Power SIBs on or off";
         type enumeration {
           enum "off" {
             description "Do not provide power to SIBs";
           }
           enum "on" {
             description "Provide power to SIBs";
           }
         }
       }
     }
     container power-off {
       description "Power off the SIB slot";
       uses apply-advanced;
       list slot {
         key name;
         ordered-by user;
         description "SIB slot number to be powered off";
         leaf name {
           description "SIB slot number to be offlined";
           type union {
             type string {
               pattern "<.*>|$.*";
             }
             type uint32;
           }
         }
         uses apply-advanced;
       }
     }
   }
   grouping chassis_sib_error_type {
     description "Chassis SIB Error level";
     uses apply-advanced;
     container fatal {
       description "SIB Fatal errors (default threshold = 1)";
       uses chassis_sib_error_level_major_fatal;
     }
     container major {
       description "SIB Major Level errors (default threshold = 1)";
       uses chassis_sib_error_level_major_fatal;
     }
     container minor {
       description "SIB Minor Level errors (default threshold = 10)";
       uses chassis_sib_error_level_minor;
     }
     container scope {
       description "Error scope";
       uses chassis_sib_scope_type;
     }
   }
   grouping chassis_sib_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         type enumeration {
           enum "reset" {
             description "Reset SIB";
           }
           enum "offline" {
             description "Offline SIB";
           }
           enum "alarm" {
             description "Raise SIB alarm";
           }
           enum "get-state" {
             description "Retreive SIB state for debugging";
           }
           enum "log" {
             description "Log occurence to system log file";
           }
           enum "trap" {
             description "Raise SIB trap";
           }
         }
       }
       uses apply-advanced;
     }
   }
   grouping chassis_sib_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         type enumeration {
           enum "reset" {
             description "Reset SIB";
           }
           enum "offline" {
             description "Offline SIB";
           }
           enum "alarm" {
             description "Raise SIB alarm";
           }
           enum "get-state" {
             description "Retreive SIB state for debugging";
           }
           enum "log" {
             description "Log occurence to system log file";
           }
           enum "trap" {
             description "Raise SIB trap";
           }
         }
       }
       uses apply-advanced;
     }
   }
   grouping chassis_sib_scope_type {
     description "Chassis SIB Error Scope";
     uses apply-advanced;
     container board {
       description "Board level scope";
       uses chassis_sib_scope_category;
     }
     container switch {
       description "SIB scope ";
       uses chassis_sib_scope_category;
     }
   }
   grouping chassis_sib_scope_category {
     description "Chassis SIB Error Category";
     uses apply-advanced;
     container category {
       description "SIB error category";
       uses chassis_sib_scope_category_type;
     }
   }
   grouping chassis_sib_scope_category_type {
     description "Chassis SIB Category level";
     uses apply-advanced;
     container functional {
       description "SIB functional category";
       uses chassis_sib_scope_category_error_type;
     }
     container memory {
       description "SIB memory category";
       uses chassis_sib_scope_category_error_type;
     }
     container io {
       description "SIB input-output category";
       uses chassis_sib_scope_category_error_type;
     }
     container storage {
       description "SIB storage category";
       uses chassis_sib_scope_category_error_type;
     }
     container switch {
       description "SIB switch category";
       uses chassis_sib_scope_category_error_type;
     }
     container processing {
       description "SIB processing category";
       uses chassis_sib_scope_category_error_type;
     }
   }
   grouping chassis_sib_scope_category_error_type {
     description "Chassis SIB Error level";
     uses apply-advanced;
     container fatal {
       description "SIB Fatal errors (default threshold = 1)";
       uses chassis_sib_error_level_type;
     }
     container major {
       description "SIB Major Level errors (default threshold = 1)";
       uses chassis_sib_error_level_type;
     }
     container minor {
       description "SIB Minor Level errors (default threshold = 10)";
       uses chassis_sib_error_level_type;
     }
   }
   grouping chassis_sib_error_level_type {
     uses apply-advanced;
     leaf threshold {
       description "Error count at which to take the action (0 - valid for minor only)";
       type union {
         type string {
           pattern "<.*>|$.*";
         }
         type uint32 {
           range "0 .. 1024";
         }
       }
     }
     list action {
       key name;
       ordered-by user;
       description "Configure the action for this level";
       leaf name {
         type enumeration {
           enum "reset" {
             description "Reset device";
           }
           enum "offline" {
             description "Offline device";
           }
           enum "alarm" {
             description "Raise chassis alarm";
           }
           enum "get-state" {
             description "Retreive device state for debugging";
           }
           enum "log" {
             description "Log occurence to system log file";
           }
           enum "trap" {
             description "Raise trap";
           }
         }
       }
       uses apply-advanced;
     }
   }
   grouping chassisd-redundancy-group-type {
     uses apply-advanced;
     container interface-type {
       uses apply-advanced;
       container redundant-logical-tunnel {
         description "Redundant logical tunnel interface group";
         uses apply-advanced;
         leaf device-count {
           description "Number of devices";
           type union {
             type string {
               pattern "<.*>|$.*";
             }
             type uint32 {
               range "1 .. 255";
             }
           }
         }
       }
       container redundant-virtual-tunnel {
         description "Redundant virtual tunnel interface group";
         uses apply-advanced;
         leaf device-count {
           description "Number of devices";
           type union {
             type string {
               pattern "<.*>|$.*";
             }
             type uint32 {
               range "1 .. 16";
             }
           }
         }
       }
     }
   }
   grouping chassisd_agg_container_type {
     uses apply-advanced;
     leaf device-count {
       description "Number of container devices";
       type union {
         type string {
           pattern "<.*>|$.*";
         }
         type uint32 {
           range "1 .. 128";
         }
       }
     }
   }
   grouping chassisd_agg_enet_type {
     uses apply-advanced;
     leaf device-count {
       description "Number of aggregated Ethernet devices";
       type union {
         type string {
           pattern "<.*>|$.*";
         }
         type uint32;
       }
     }
     container lacp {
       description "Global Link Aggregation Control Protocol configuration";
       uses apply-advanced;
       leaf system-priority {
         description "Priority of the system (0 ... 65535)";
         type string;
       }
       container link-protection {
         presence "enable link-protection";
         uses apply-advanced;
         leaf non-revertive {
           description "Don't revert links when better priority link comes up";
           type empty;
         }
       }
     }
   }
   grouping chassisd_agg_pos_type {
     uses apply-advanced;
     leaf device-count {
       description "Number of aggregated SONET devices";
       type union {
         type string {
           pattern "<.*>|$.*";
         }
         type uint32 {
           range "1 .. 64";
         }
       }
     }
   }
   grouping ct3_port_type {
     leaf name {
       description "CT3  L2NG_PRODUCTSport number";
       type union {
         type string {
           pattern "<.*>|$.*";
         }
         type int32 {
           range "0 .. 1";
         }
       }
     }
     uses apply-advanced;
     list t1 {
       key name;
       description "T1 link";
       uses ct3_channel_type;
     }
   }
   grouping ct3_channel_type {
     leaf name {
       description "T1 link number";
       type union {
         type string {
           pattern "<.*>|$.*";
         }
         type int32 {
           range "0 .. 27";
         }
       }
     }
     uses apply-advanced;
     list channel-group {
       key name;
       description "Define channel group";
       leaf name {
         description "Channel group number";
         type union {
           type string {
             pattern "<.*>|$.*";
           }
           type uint32 {
             range "0 .. 7";
           }
         }
       }
       leaf timeslots {
         description "DS0 timeslots (1..24); for example, 1-3,4,9,22-24 (no spaces)";
         type string;
       }
     }
   }
   grouping juniper-protected-system-domain {
     description "Protected system domain configuration";
     leaf name {
       description "Name of protected system domain (psd[1-31], ex. psd2)";
       type string {
       }
     }
     uses apply-advanced;
     leaf description {
       description "Description of protected system domain";
       type string;
     }
     list lcc {
       key name;
       leaf name {
         description "Specific LCC";
         type union {
           type string {
             pattern "<.*>|$.*";
           }
           type uint32;
         }
       }
       uses apply-advanced;
       leaf-list fpcs {
         description "FPC associated with protected system domain";
         type union {
           type string {
             pattern "<.*>|$.*";
           }
           type uint32;
         }
       }
     }
     leaf control-system-id {
       description "Control system identifier";
       type union {
         type string {
           pattern "<.*>|$.*";
         }
         type uint32 {
           range "1 .. 4";
         }
       }
     }
     leaf-list control-slot-numbers {
       ordered-by user;
       description "Slots associated with protected system domain";
       type union {
         type string {
           pattern "<.*>|$.*";
         }
         type uint32 {
           range "1 .. 12";
         }
       }
       max-elements 2;
     }
     leaf control-plane-bandwidth-percent {
       description "Percentage of control plane bandwidth";
       units "percent";
       type union {
         type string {
           pattern "<.*>|$.*";
         }
         type uint32 {
           range "0 .. 100";
         }
       }
     }
   }
   grouping juniper-protected-system-domain-traceoptions {
     description "Protected system domain traceoptions";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "rtsock" {
             description "Trace rtsock messages";
           }
           enum "ipc" {
             description "Trace IPC messages";
           }
           enum "init" {
             description "Trace intialization messages";
           }
           enum "psd" {
             description "Trace psd messages";
           }
           enum "all" {
             description "Trace everything";
           }
         }
       }
     }
   }
   grouping macro-data-type {
     leaf name {
       description "Keyword part of the keyword-value pair";
       type string;
     }
     leaf value {
       description "Value part of the keyword-value pair";
       type string;
     }
   }
   grouping redundancy-group-type {
     description "Redundancy-group provisioning";
     leaf name {
       description "Redundancy-group name";
       type string {
         length "2 .. 64";
       }
     }
     uses apply-advanced;
     leaf redundancy-group-id {
       description "Redundancy Group ID";
       type union {
         type string {
           pattern "<.*>|$.*";
         }
         type uint32 {
           range "1 .. 255";
         }
       }
     }
     container protocol {
       description "Redundancy-group Protocol";
       uses apply-advanced;
       container evpn {
         description "EVPN Redundancy Group";
         uses apply-advanced;
         leaf-list peer-ip {
           ordered-by user;
           description "Peer chassis IPs for EVPN Cluster";
           type jt:ipv4addr;
         }
         leaf local-ip {
           description "Local chassis IP for EVPN Cluster";
           type jt:ipv4addr;
         }
         leaf routing-instance {
           description "Name of routing instance for EVPN Cluster";
           type string;
         }
       }
     }
     list peer-chassis-id {
       key name;
       ordered-by user;
       description "Peer Chassis ID";
       leaf name {
         description "Peer chassis identifier";
         type union {
           type string {
             pattern "<.*>|$.*";
           }
           type uint32 {
             range "1 .. 4";
           }
         }
       }
       uses apply-advanced;
       leaf no-auto-vlan-provisioning {
         description "Disable auto VLAN provisioning on inter-chassis-link";
         type empty;
       }
       leaf inter-chassis-link {
         description "ICL interface name";
         type union {
           type jt:interface-device;
           type string {
             pattern "<.*>|$.*";
           }
         }
       }
       leaf no-auto-iccp-provisioning {
         description "Disable auto ICCP provisioning";
         type empty;
       }
       leaf session-establishment-hold-time {
         description "Time within which connection must succeed with this peer";
         units "seconds";
         type union {
           type string {
             pattern "<.*>|$.*";
           }
           type uint32 {
             range "45 .. 600";
           }
         }
       }
       container liveness-detection {
         presence "enable liveness-detection";
         description "Bidirectional Forwarding Detection options for the peer";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 9000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
       }
       leaf authentication-key {
         description "MD5 authentication key";
         type string {
           length "1 .. 126";
         }
       }
       container traceoptions {
         description "Trace options for ICCP";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Trace flag information";
           leaf name {
             type enumeration {
               enum "error" {
                 description "Trace all errors";
               }
               enum "event" {
                 description "Trace all events";
               }
               enum "packet" {
                 description "Trace all packets";
               }
               enum "pipe" {
                 description "Trace pipe messages";
               }
               enum "pipe-detail" {
                 description "Trace pipe messages in detail";
               }
               enum "all" {
                 description "Trace everything";
               }
             }
           }
         }
       }
     }
     leaf-list satellite {
       ordered-by user;
       description "Satellite slot-id or range or all";
       type string {
         length "1 .. 100";
       }
     }
     leaf system-mac-address {
       description "System MAC address";
       type jt:mac-unicast;
     }
     list cluster {
       key name;
       description "Cluster member of redundancy-group";
       leaf name {
         description "Cluster name";
         type string;
       }
       uses apply-advanced;
     }
   }
   grouping satellite-bridge-filter {
     leaf name {
       description "Filter name";
       type string {
       }
     }
     uses apply-advanced;
     list term {
       key name;
       ordered-by user;
       description "Define a firewall term";
       leaf name {
         description "Term name";
         type string {
         }
       }
       uses apply-advanced;
       container from {
         description "Define match criteria";
         uses apply-advanced;
         list source-mac-address {
           key name;
           ordered-by user;
           description "Match MAC source address";
           uses firewall_mac_addr_object;
         }
         list destination-mac-address {
           key name;
           ordered-by user;
           description "Match MAC destination address";
           uses firewall_mac_addr_object;
         }
         list ip-source-address {
           key name;
           ordered-by user;
           description "Match IP source address";
           uses firewall_addr_object;
         }
         list ip-destination-address {
           key name;
           ordered-by user;
           description "Match IP destination address";
           uses firewall_addr_object;
         }
         choice ip-protocol_choice {
           case case_1 {
             leaf-list ip-protocol {
               ordered-by user;
               type string;
             }
           }
           case case_2 {
             leaf-list ip-protocol-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
       }
       container then {
         description "Action to take if the 'from' condition is matched";
         uses apply-advanced;
         choice designation {
           case case_1 {
             leaf accept {
               description "Accept the packet";
               type empty;
             }
           }
           case case_2 {
             leaf discard {
               description "Discard the packets";
               type empty;
             }
           }
         }
         leaf next-hop-group {
           description "Use specified next-hop group";
           type string;
         }
       }
     }
   }
   grouping firewall_addr_object {
     leaf name {
       description "Prefix to match";
       type jt:ipv4prefix;
     }
     leaf except {
       description "Match address not in this prefix";
       type empty;
     }
   }
   grouping firewall_mac_addr_object {
     leaf name {
       description "MAC address to match";
       type jt:mac-addr-prefix;
     }
     leaf except {
       description "Match MAC address not in this range";
       type empty;
     }
   }
   grouping upgrade-group-type {
     description "Upgrade group";
     leaf name {
       description "Upgrade group name";
       type string {
         length "2 .. 64";
       }
     }
     uses apply-advanced;
     leaf-list satellite {
       ordered-by user;
       description "Satellite slot-id or range or all";
       type string {
         length "1 .. 100";
       }
     }
   }
 }
