/*
 * Copyright (c) 2024 Juniper Networks, Inc.
 * All rights reserved.
 */
 module junos-qfx-rpc-diameter {
   namespace "http://yang.juniper.net/junos-qfx/rpc/diameter";

   prefix diameter;

   import junos-common-types {
     prefix jt;
     revision-date 2023-01-01;
   }

   organization "Juniper Networks, Inc.";

   contact "yang-support@juniper.net";

   description "Junos RPC YANG module for diameter command(s)";

   revision 2023-01-01 {
     description "Junos: 23.4R2.13";
   }

   rpc get-diameter-information {
     description "Show diameter information";
     input {
       leaf verbosity_level {
         default "summary";
         type enumeration {
           enum "summary" {
             description "Display summary output(default)";
           }
           enum "brief" {
             description "Display brief output";
           }
           enum "detail" {
             description "Display detailed output";
           }
         }
       }
     }
   }
   rpc get-diameter-function-information {
     description "Show diameter function information";
     input {
       leaf verbosity_level {
         default "summary";
         type enumeration {
           enum "summary" {
             description "Display summary output(default)";
           }
           enum "brief" {
             description "Display brief output";
           }
           enum "detail" {
             description "Display detailed output";
           }
         }
       }
       leaf func-name {
         description "Function name";
         type enumeration {
           enum "jsrc" {
             description "Function to use SRC application";
           }
           enum "charging-gw" {
             description "Function to use CHARGING application";
           }
           enum "gx-plus" {
             description "Function to use GX-PLUS application";
           }
           enum "sd-3gpp" {
             description "Function to use SD-3GPP application";
           }
           enum "nasreq" {
             description "Function to use NASREQ application";
           }
           enum "pcrf" {
             description "Function to use PCRF(GX) application";
           }
           enum "ocs" {
             description "Function to use OCS(GY) application";
           }
           enum "s6a" {
             description "Function to use S6A application";
           }
         }
       }
     }
   }
   rpc get-diameter-function-statistics {
     description "Show diameter function statistics";
     input {
       leaf verbosity_level {
         default "summary";
         type enumeration {
           enum "summary" {
             description "Display summary output(default)";
           }
           enum "brief" {
             description "Display brief output";
           }
           enum "detail" {
             description "Display detailed output";
           }
         }
       }
       leaf function-statistics-name {
         description "Function name";
         type enumeration {
           enum "jsrc" {
             description "Function to use SRC application";
           }
           enum "charging-gw" {
             description "Function to use CHARGING application";
           }
           enum "gx-plus" {
             description "Function to use GX-PLUS application";
           }
           enum "sd-3gpp" {
             description "Function to use SD-3GPP application";
           }
           enum "nasreq" {
             description "Function to use NASREQ application";
           }
           enum "pcrf" {
             description "Function to use PCRF(GX) application";
           }
           enum "ocs" {
             description "Function to use OCS(GY) application";
           }
           enum "s6a" {
             description "Function to use S6A application";
           }
         }
       }
     }
   }
   rpc get-diameter-instance-information {
     description "Show diameter instance information";
     input {
       leaf verbosity_level {
         default "summary";
         type enumeration {
           enum "summary" {
             description "Display summary output(default)";
           }
           enum "brief" {
             description "Display brief output";
           }
           enum "detail" {
             description "Display detailed output";
           }
         }
       }
       leaf instance-name {
         description "Instance name";
         type string;
       }
     }
   }
   rpc get-diameter-network-element-information {
     description "Show diameter network-element information";
     input {
       leaf verbosity_level {
         default "summary";
         type enumeration {
           enum "summary" {
             description "Display summary output(default)";
           }
           enum "brief" {
             description "Display brief output";
           }
           enum "detail" {
             description "Display detailed output";
           }
         }
       }
       leaf network-element-name {
         description "Network-element name";
         type string;
       }
     }
   }
   rpc get-diameter-network-element-map-information {
     description "Show diameter network-element map to peers";
     input {
       leaf verbosity_level {
         default "summary";
         type enumeration {
           enum "summary" {
             description "Display summary output(default)";
           }
           enum "brief" {
             description "Display brief output";
           }
           enum "detail" {
             description "Display detailed output";
           }
         }
       }
       leaf network-element-map-name {
         description "Network-element name";
         type string;
       }
     }
   }
   rpc get-diameter-route-information {
     description "Show diameter route information";
     input {
       leaf verbosity_level {
         default "summary";
         type enumeration {
           enum "summary" {
             description "Display summary output(default)";
           }
           enum "brief" {
             description "Display brief output";
           }
           enum "detail" {
             description "Display detailed output";
           }
         }
       }
       leaf route-name {
         description "Route name";
         type string;
       }
     }
   }
   rpc get-diameter-peer-information {
     description "Show diameter peer information";
     input {
       leaf verbosity_level {
         default "summary";
         type enumeration {
           enum "summary" {
             description "Display summary output(default)";
           }
           enum "brief" {
             description "Display brief output";
           }
           enum "detail" {
             description "Display detailed output";
           }
         }
       }
       leaf peer-name {
         description "Peer name";
         type string;
       }
     }
   }
   rpc get-diameter-peer-map-information {
     description "Show diameter peer mapping to network-elements";
     input {
       leaf verbosity_level {
         default "summary";
         type enumeration {
           enum "summary" {
             description "Display summary output(default)";
           }
           enum "brief" {
             description "Display brief output";
           }
           enum "detail" {
             description "Display detailed output";
           }
         }
       }
       leaf peer-map-name {
         description "Peer name";
         type string;
       }
     }
   }
   rpc get-diameter-peer-statistics {
     description "Show diameter peer statistics";
     input {
       leaf verbosity_level {
         default "summary";
         type enumeration {
           enum "summary" {
             description "Display summary output(default)";
           }
           enum "brief" {
             description "Display brief output";
           }
           enum "detail" {
             description "Display detailed output";
           }
         }
       }
       leaf peer-statistics-name {
         description "Peer name";
         type string;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
 }
