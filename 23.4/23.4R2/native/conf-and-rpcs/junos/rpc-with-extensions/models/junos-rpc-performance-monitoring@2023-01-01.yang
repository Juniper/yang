/*
 * Copyright (c) 2024 Juniper Networks, Inc.
 * All rights reserved.
 */
 module junos-rpc-performance-monitoring {
   namespace "http://yang.juniper.net/junos/rpc/performance-monitoring";

   prefix performance-monitoring;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for performance-monitoring command(s)";

   revision 2023-01-01 {
     description "Junos: 23.4R2.13";
   }

   rpc get-pm-mpls-lsp-information {
     junos:command "show performance-monitoring mpls lsp";
     input {
       leaf level {
         junos:cli-feature "nokeyword";
         default "brief";
         type enumeration {
           enum "brief" {
             description "Display brief output (default)";
           }
           enum "detail" {
             description "Display detailed output";
           }
           enum "extensive" {
             description "Display extensive output";
           }
         }
       }
       leaf regex {
         description "Regular expression for LSP names to match";
         type string;
       }
     }
     output {
       container pm-information {
         uses pm-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping pm-information-block {
     leaf total-number-of-sessions {
       type int32;
       description "Number of Total performance monitoring sessions";
     }
     leaf up-number-of-sessions {
       type int32;
       description "Number of Up performance monitoring sessions";
     }
     leaf down-number-of-sessions {
       type int32;
       description "Number of Down performance monitoring sessions";
     }
     container performance-monitor-mpls-lsp-information {
       leaf performance-monitor-lsp-name {
         type string;
         description "Name of MPLS LSP";
       }
       leaf performance-monitor-session-state {
         type string;
         description "State of PM session";
       }
       container loss-measurement-information {
         leaf duration {
           type string;
           description "Time since loss measurement data is being collected";
         }
         leaf pm-traffic-class {
           type string;
           description "Traffic class of the loss measurement session";
         }
         leaf queries-sent {
           type uint32;
           description "Number of loss measurement queries sent";
         }
         leaf responses-received {
           type uint32;
           description "Number of loss measurement responses received";
         }
         leaf responses-errored {
           type uint32;
           description "Number of error loss measurement responses";
         }
         leaf queries-timedout {
           type uint32;
           description "Number of queries time out";
         }
         container forward-loss-measurement-information {
           leaf average-packet-loss {
             type uint64;
             description "Average packet loss over time";
           }
           leaf average-packet-throughput {
             type string;
             description "Average packet throughput over time";
           }
           leaf average-octet-loss {
             type uint64;
             description "Average octet loss over time";
           }
           leaf average-octet-throughput {
             type string;
             description "Average octet throughput over time";
           }
           container packet-loss-information {
             description "Packet loss measurement samples";
             leaf packet-loss {
               type uint64;
               description "Packet loss measurement value";
             }
           }
           container packet-throughput-information {
             description "Packet throughput measurement samples";
             leaf packet-throughput {
               type string;
               description "Packet throughput measurement value";
             }
           }
           container octet-loss-information {
             description "Octet loss measurement samples";
             leaf octet-loss {
               type uint64;
               description "Octet loss measurement value";
             }
           }
           container octet-throughput-information {
             description "Octet throughput measurement samples";
             leaf octet-throughput {
               type string;
               description "Octet througput measurement value";
             }
           }
         }
         container reverse-loss-measurement-information {
           leaf average-packet-loss {
             type uint64;
             description "Average packet loss over time";
           }
           leaf average-packet-throughput {
             type string;
             description "Average packet throughput over time";
           }
           leaf average-octet-loss {
             type uint64;
             description "Average octet loss over time";
           }
           leaf average-octet-throughput {
             type string;
             description "Average octet throughput over time";
           }
           container packet-loss-information {
             description "Packet loss measurement samples";
             leaf packet-loss {
               type uint64;
               description "Packet loss measurement value";
             }
           }
           container packet-throughput-information {
             description "Packet throughput measurement samples";
             leaf packet-throughput {
               type string;
               description "Packet throughput measurement value";
             }
           }
           container octet-loss-information {
             description "Octet loss measurement samples";
             leaf octet-loss {
               type uint64;
               description "Octet loss measurement value";
             }
           }
           container octet-throughput-information {
             description "Octet throughput measurement samples";
             leaf octet-throughput {
               type string;
               description "Octet througput measurement value";
             }
           }
         }
       }
       container delay-measurement-information {
         leaf duration {
           type string;
           description "Time since loss measurement data is being collected";
         }
         leaf pm-traffic-class {
           type string;
           description "Traffic class of the loss measurement session";
         }
         leaf queries-sent {
           type uint32;
           description "Number of loss measurement queries sent";
         }
         leaf responses-received {
           type uint32;
           description "Number of loss measurement responses received";
         }
         leaf responses-errored {
           type uint32;
           description "Number of error loss measurement responses";
         }
         leaf queries-timedout {
           type uint32;
           description "Number of queries time out";
         }
         leaf best-two-way-channel-delay {
           type string;
           description "Best two way channel delay";
         }
         leaf worst-two-way-channel-delay {
           type string;
           description "Worst two way channel delay";
         }
         leaf best-round-trip-time {
           type string;
           description "Best round trip time";
         }
         leaf worst-round-trip-time {
           type string;
           description "Worst round trip time";
         }
         leaf average-absolute-forward-delay-variation {
           type string;
           description "Average absolute forward inter packet delay variation";
         }
         leaf average-absolute-reverse-delay-variation {
           type string;
           description "Average absolute reverse inter packet delay variation";
         }
         container two-way-channel-delay-information {
           description "Two-way delay";
           leaf two-way-channel-delay {
             type string;
             description "Two way channel delay";
           }
         }
         container two-way-round-trip-time-information {
           description "Two-way round-trip time";
           leaf two-way-round-trip-time {
             type string;
             description "Two way round trip time";
           }
         }
       }
     }
   }
 }
