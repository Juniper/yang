/*
 * Copyright (c) 2024 Juniper Networks, Inc.
 * All rights reserved.
 */
 module junos-ex-rpc-link-management {
   namespace "http://yang.juniper.net/junos-ex/rpc/link-management";

   prefix link-management;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for link-management command(s)";

   revision 2023-01-01 {
     description "Junos: 23.4R2.13";
   }

   rpc get-lm-information {
     description "Show link management information";
     junos:command "show link-management";
     output {
       container lm-information {
         uses lm-information-block;
       }
     }
   }
   rpc get-lm-peer-information {
     description "Show peer information";
     junos:command "show link-management peer";
     input {
       leaf peer-name {
         description "Name of peer";
         type string;
       }
     }
     output {
       container lm-peer-root-information {
         uses lm-peer-root-information-block;
       }
     }
   }
   rpc get-lm-te-link-information {
     description "Show traffic engineering links information";
     junos:command "show link-management te-link";
     input {
       leaf verbosity_level {
         junos:cli-feature "nokeyword";
         default "brief";
         type enumeration {
           enum "brief" {
             description "Display brief output (default)";
           }
           enum "detail" {
             description "Display detailed output";
           }
         }
       }
       leaf link-name {
         description "Name of traffic engineering link";
         type string;
       }
     }
     output {
       container lm-te-link-root-information {
         uses lm-te-link-root-information-block;
       }
     }
   }
   rpc get-lm-statistics-information {
     description "Show link management statistics";
     junos:command "show link-management statistics";
     output {
       container lm-statistics-information {
         uses lm-statistics-information-block;
       }
     }
   }
   rpc get-lm-peer-statistics {
     description "Show link management statistics for a peer";
     junos:command "show link-management statistics peer";
     input {
       leaf peer-name {
         description "Name of peer";
         type string;
       }
     }
     output {
       container lm-statistics-information {
         uses lm-statistics-information-block;
       }
     }
   }
   rpc get-lm-routing-information {
     description "Show link management information for routing";
     junos:command "show link-management routing";
     output {
       container lm-information {
         uses lm-information-block;
       }
     }
   }
   rpc get-lm-routing-peer-information {
     description "Show peer information";
     junos:command "show link-management routing peer";
     input {
       leaf peer-name {
         description "Name of peer";
         type string;
       }
     }
     output {
       container lm-peer-root-information {
         uses lm-peer-root-information-block;
       }
     }
   }
   rpc get-lm-routing-te-link-information {
     description "Show traffic engineering links information";
     junos:command "show link-management routing te-link";
     input {
       leaf verbosity_level {
         junos:cli-feature "nokeyword";
         default "brief";
         type enumeration {
           enum "brief" {
             description "Display brief output (default)";
           }
           enum "detail" {
             description "Display detailed output";
           }
         }
       }
       leaf link-name {
         description "Name of traffic engineering link";
         type string;
       }
     }
     output {
       container lm-te-link-root-information {
         uses lm-te-link-root-information-block;
       }
     }
   }
   rpc get-lm-routing-resource-information {
     description "Show resource information";
     junos:command "show link-management routing resource";
     input {
       leaf resource-name {
         description "Name of resource";
         type string;
       }
     }
     output {
       container lm-resource-root-information {
         uses lm-resource-root-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping lm-information-block {
     container lm-peer-root-information {
       list lm-peer-information {
         leaf lm-peer-name {
           type string;
           description "Name of object";
         }
         leaf lm-sys-id {
           type int32;
           description "System identifier of object";
         }
         leaf lm-state {
           type string;
           description "State of object";
         }
         leaf lm-peer-control-address {
           type jt:ipaddr;
           description "Peer control address";
         }
         leaf lm-peer-hello-interval {
           type int32;
           description "LMP hello interval";
         }
         leaf lm-peer-hello-dead-interval {
           type int32;
           description "LMP hello dead-interval";
         }
         leaf lm-source {
           type string;
           description "Source of information";
         }
         leaf lm-peer-received-message-id {
           type int32;
           description "LMP last per-peer received message ID";
         }
         leaf lm-peer-sent-message-id {
           type int32;
           description "LMP last per-peer sent message ID";
         }
         container lm-peer-control-channels {
           description "Link management control channels";
           list lm-control-channel-info {
             description "Link management control channel information";
             leaf lm-control-channel {
               type string;
               description "Peer control channel name";
             }
             leaf lm-control-channel-state {
               type string;
               description "Peer control channel state";
             }
           }
         }
         container lm-peer-lmp-control-channels {
           description "Link management control channels";
           list lm-peer-lmp-control-channel-information {
             description "Link management control channel information";
             leaf lm-lmp-control-channel-local-id {
               type int32;
               description "Peer control channel local ID";
             }
             leaf lm-lmp-control-channel-remote-id {
               type int32;
               description "Peer control channel remote ID";
             }
             leaf lm-lmp-control-channel-state {
               type string;
               description "Peer control channel state";
             }
             leaf lm-lmp-control-channel-tx-seq-num {
               type int32;
               description "LMP transmit sequence number";
             }
             leaf lm-lmp-control-channel-rcv-seq-num {
               type int32;
               description "LMP receive sequence number";
             }
             leaf lm-lmp-control-channel-received-message-id {
               type int32;
               description "LMP last per-control-channel received message ID";
             }
             leaf lm-lmp-control-channel-sent-message-id {
               type int32;
               description "LMP last per-control-channel sent message ID";
             }
             container lm-lmp-control-channel-flags {
               description "Peer control channel flags";
               leaf cc-restarting {
                 type empty;
               }
             }
           }
         }
         container lm-peer-te-links {
           description "Link management peer TE links";
           list lm-peer-te-link-information {
             description "Link management peer TE link information";
             leaf lm-peer-te-link {
               type string;
               description "TE link name contained in peer";
             }
           }
         }
       }
     }
     container lm-te-link-root-information {
       list lm-te-link-information {
         leaf lm-te-link-name {
           type string;
           description "Name of object";
         }
         leaf lm-state {
           type string;
           description "State of object";
         }
         leaf lm-te-link-flags {
           type string;
           description "Flags for object";
         }
         leaf lm-local-id {
           type int32;
           description "Local identifier of object";
         }
         leaf lm-remote-id {
           type int32;
           description "Remote identifier of object";
         }
         leaf lm-local-address {
           type string;
           description "Local address of object";
         }
         leaf lm-remote-address {
           type string;
           description "Remote address of object";
         }
         leaf lm-encoding {
           type string;
           description "TE-Link encoding type";
         }
         leaf lm-switching {
           type string;
           description "TE-Link switching capability";
         }
         leaf lm-min-bandwidth {
           type string;
           description "Minimum reservable bandwidth per allocation";
         }
         leaf lm-max-bandwidth {
           type string;
           description "Maximum reservable bandwidth per allocation";
         }
         leaf lm-total-bandwidth {
           type string;
           description "Total bandwidth available on this TE link";
         }
         leaf lm-avail-bandwidth {
           type string;
           description "Unallocated bandwidth on this TE link";
         }
         container lm-te-link-local-flags {
           leaf lm-te-link-nack-sent-flag {
             type empty;
           }
         }
         container lm-te-link-resources {
           list lm-te-link-resource {
             leaf lm-resource-name {
               type string;
               description "Resource name";
             }
             leaf lm-resource-state {
               type string;
             }
             leaf lm-resource-local-id {
               type int32;
               description "Resource local identifier";
             }
             leaf lm-resource-remote-id {
               type int32;
               description "Resource remote identifier";
             }
             leaf lm-resource-bandwidth {
               type string;
               description "Total bandwidth of resource";
             }
             leaf lm-resource-in-use {
               type string;
               description "Resource allocation status";
             }
             leaf lm-resource-lsp-name {
               type string;
               description "Name of LSP using resource";
             }
             leaf lm-resource-local-addr {
               type jt:ipaddr;
               description "Resource local address";
             }
             leaf lm-resource-remote-addr {
               type jt:ipaddr;
               description "Resource remote address";
             }
             leaf lm-resource-type {
               type string;
               description "Resource type";
             }
             leaf lm-sys-id {
               type int32;
               description "System identifier of object";
             }
             leaf lm-resource-flags {
               type string;
               description "Resource flags";
             }
             leaf lm-resource-avail-bandwidth {
               type string;
               description "Unallocated bandwidth on resource";
             }
             leaf lm-resource-traffic-params {
               type string;
               description "Traffic parameters of resource";
             }
             leaf lm-resource-max-allocations {
               type int32;
               description "Maximum number of allocations";
             }
             leaf lm-resource-num-allocations {
               type int32;
               description "Current number of allocations";
             }
             leaf lm-resource-unique-allocations {
               type int32;
               description "Current number of unique allocations";
             }
             list lm-resource-allocation-context {
               leaf lm-allocated-lsp-name {
                 type string;
               }
               leaf lm-local-label {
                 type int32;
               }
               leaf lm-remote-label {
                 type int32;
               }
               leaf lm-allocated-bandwidth {
                 type string;
               }
               leaf lm-bandwidth-shared {
                 type int32;
               }
               leaf lm-label-shared {
                 type empty;
               }
             }
           }
         }
       }
     }
     container lm-resource-root-information {
       leaf lm-source {
         type string;
         description "Source of information";
       }
       list lm-resource {
         leaf lm-resource-name {
           type string;
           description "Resource name";
         }
         leaf lm-resource-type {
           type string;
           description "Resource type";
         }
         leaf lm-resource-state {
           type string;
         }
         leaf lm-sys-id {
           type int32;
           description "System identifier of object";
         }
         leaf lm-resource-max-allocations {
           type int32;
           description "Maximum number of allocations";
         }
         leaf lm-resource-bandwidth {
           type string;
           description "Total bandwidth of resource";
         }
         leaf lm-resource-traffic-params {
           type string;
           description "Traffic parameters of resource";
         }
       }
     }
   }
   grouping lm-peer-root-information-block {
     list lm-peer-information {
       leaf lm-peer-name {
         type string;
         description "Name of object";
       }
       leaf lm-sys-id {
         type int32;
         description "System identifier of object";
       }
       leaf lm-state {
         type string;
         description "State of object";
       }
       leaf lm-peer-control-address {
         type jt:ipaddr;
         description "Peer control address";
       }
       leaf lm-peer-hello-interval {
         type int32;
         description "LMP hello interval";
       }
       leaf lm-peer-hello-dead-interval {
         type int32;
         description "LMP hello dead-interval";
       }
       leaf lm-source {
         type string;
         description "Source of information";
       }
       leaf lm-peer-received-message-id {
         type int32;
         description "LMP last per-peer received message ID";
       }
       leaf lm-peer-sent-message-id {
         type int32;
         description "LMP last per-peer sent message ID";
       }
       container lm-peer-control-channels {
         description "Link management control channels";
         list lm-control-channel-info {
           description "Link management control channel information";
           leaf lm-control-channel {
             type string;
             description "Peer control channel name";
           }
           leaf lm-control-channel-state {
             type string;
             description "Peer control channel state";
           }
         }
       }
       container lm-peer-lmp-control-channels {
         description "Link management control channels";
         list lm-peer-lmp-control-channel-information {
           description "Link management control channel information";
           leaf lm-lmp-control-channel-local-id {
             type int32;
             description "Peer control channel local ID";
           }
           leaf lm-lmp-control-channel-remote-id {
             type int32;
             description "Peer control channel remote ID";
           }
           leaf lm-lmp-control-channel-state {
             type string;
             description "Peer control channel state";
           }
           leaf lm-lmp-control-channel-tx-seq-num {
             type int32;
             description "LMP transmit sequence number";
           }
           leaf lm-lmp-control-channel-rcv-seq-num {
             type int32;
             description "LMP receive sequence number";
           }
           leaf lm-lmp-control-channel-received-message-id {
             type int32;
             description "LMP last per-control-channel received message ID";
           }
           leaf lm-lmp-control-channel-sent-message-id {
             type int32;
             description "LMP last per-control-channel sent message ID";
           }
           container lm-lmp-control-channel-flags {
             description "Peer control channel flags";
             leaf cc-restarting {
               type empty;
             }
           }
         }
       }
       container lm-peer-te-links {
         description "Link management peer TE links";
         list lm-peer-te-link-information {
           description "Link management peer TE link information";
           leaf lm-peer-te-link {
             type string;
             description "TE link name contained in peer";
           }
         }
       }
     }
   }
   grouping lm-te-link-root-information-block {
     list lm-te-link-information {
       leaf lm-te-link-name {
         type string;
         description "Name of object";
       }
       leaf lm-state {
         type string;
         description "State of object";
       }
       leaf lm-te-link-flags {
         type string;
         description "Flags for object";
       }
       leaf lm-local-id {
         type int32;
         description "Local identifier of object";
       }
       leaf lm-remote-id {
         type int32;
         description "Remote identifier of object";
       }
       leaf lm-local-address {
         type string;
         description "Local address of object";
       }
       leaf lm-remote-address {
         type string;
         description "Remote address of object";
       }
       leaf lm-encoding {
         type string;
         description "TE-Link encoding type";
       }
       leaf lm-switching {
         type string;
         description "TE-Link switching capability";
       }
       leaf lm-min-bandwidth {
         type string;
         description "Minimum reservable bandwidth per allocation";
       }
       leaf lm-max-bandwidth {
         type string;
         description "Maximum reservable bandwidth per allocation";
       }
       leaf lm-total-bandwidth {
         type string;
         description "Total bandwidth available on this TE link";
       }
       leaf lm-avail-bandwidth {
         type string;
         description "Unallocated bandwidth on this TE link";
       }
       container lm-te-link-local-flags {
         leaf lm-te-link-nack-sent-flag {
           type empty;
         }
       }
       container lm-te-link-resources {
         list lm-te-link-resource {
           leaf lm-resource-name {
             type string;
             description "Resource name";
           }
           leaf lm-resource-state {
             type string;
           }
           leaf lm-resource-local-id {
             type int32;
             description "Resource local identifier";
           }
           leaf lm-resource-remote-id {
             type int32;
             description "Resource remote identifier";
           }
           leaf lm-resource-bandwidth {
             type string;
             description "Total bandwidth of resource";
           }
           leaf lm-resource-in-use {
             type string;
             description "Resource allocation status";
           }
           leaf lm-resource-lsp-name {
             type string;
             description "Name of LSP using resource";
           }
           leaf lm-resource-local-addr {
             type jt:ipaddr;
             description "Resource local address";
           }
           leaf lm-resource-remote-addr {
             type jt:ipaddr;
             description "Resource remote address";
           }
           leaf lm-resource-type {
             type string;
             description "Resource type";
           }
           leaf lm-sys-id {
             type int32;
             description "System identifier of object";
           }
           leaf lm-resource-flags {
             type string;
             description "Resource flags";
           }
           leaf lm-resource-avail-bandwidth {
             type string;
             description "Unallocated bandwidth on resource";
           }
           leaf lm-resource-traffic-params {
             type string;
             description "Traffic parameters of resource";
           }
           leaf lm-resource-max-allocations {
             type int32;
             description "Maximum number of allocations";
           }
           leaf lm-resource-num-allocations {
             type int32;
             description "Current number of allocations";
           }
           leaf lm-resource-unique-allocations {
             type int32;
             description "Current number of unique allocations";
           }
           list lm-resource-allocation-context {
             leaf lm-allocated-lsp-name {
               type string;
             }
             leaf lm-local-label {
               type int32;
             }
             leaf lm-remote-label {
               type int32;
             }
             leaf lm-allocated-bandwidth {
               type string;
             }
             leaf lm-bandwidth-shared {
               type int32;
             }
             leaf lm-label-shared {
               type empty;
             }
           }
         }
       }
     }
   }
   grouping lm-statistics-information-block {
     list lm-peer-statistics {
       leaf lm-peer-name {
         type string;
         description "Name of object";
       }
       container lm-input-statistics {
         description "Input statistics";
         leaf lm-small-packets {
           type int32;
           description "Number of packets too small to process";
         }
         leaf lm-bad-version {
           type int32;
           description "Number of packets with unsupported protocol version";
         }
         leaf lm-no-peer {
           type int32;
           description "Number of messages received for unknown peer";
         }
         leaf lm-wrong-state {
           type int32;
           description "Number of messages received for control channel in wrong state";
         }
         leaf lm-stale-ack {
           type int32;
           description "Number of acknowledgments received for unknown messages";
         }
         leaf lm-stale-nack {
           type int32;
           description "Number of negative acknowledgments received for unknown messages";
         }
         leaf lm-no-cc {
           type int32;
           description "Number of messages received for unknown control channel";
         }
         list lm-received-packets {
           description "Number of packets received";
           leaf lm-packet-type {
             type string;
             description "Type of packet";
           }
           leaf lm-packet-count {
             type int32;
             description "Number of packets";
           }
         }
         list lm-received-bad-packets {
           description "Number of bad packets received";
           leaf lm-packet-type {
             type string;
             description "Type of packet";
           }
           leaf lm-packet-count {
             type int32;
             description "Number of packets";
           }
         }
         list lm-received-misordered-packets {
           description "Number of out-of-order packets received";
           leaf lm-packet-type {
             type string;
             description "Type of packet";
           }
           leaf lm-packet-count {
             type int32;
             description "Number of packets";
           }
         }
       }
       container lm-output-statistics {
         description "Output statistics";
         list lm-sent-packets {
           description "Number of packets sent";
           leaf lm-packet-type {
             type string;
             description "Type of packet";
           }
           leaf lm-packet-count {
             type int32;
             description "Number of packets";
           }
         }
         list lm-retransmit-packets {
           description "Number of packets retransmitted";
           leaf lm-packet-type {
             type string;
             description "Type of packet";
           }
           leaf lm-packet-count {
             type int32;
             description "Number of packets";
           }
         }
         list lm-tossed-packets {
           description "Number of messages which failed retransmission";
           leaf lm-packet-type {
             type string;
             description "Type of packet";
           }
           leaf lm-packet-count {
             type int32;
             description "Number of packets";
           }
         }
       }
     }
   }
   grouping lm-resource-root-information-block {
     leaf lm-source {
       type string;
       description "Source of information";
     }
     list lm-resource {
       leaf lm-resource-name {
         type string;
         description "Resource name";
       }
       leaf lm-resource-type {
         type string;
         description "Resource type";
       }
       leaf lm-resource-state {
         type string;
       }
       leaf lm-sys-id {
         type int32;
         description "System identifier of object";
       }
       leaf lm-resource-max-allocations {
         type int32;
         description "Maximum number of allocations";
       }
       leaf lm-resource-bandwidth {
         type string;
         description "Total bandwidth of resource";
       }
       leaf lm-resource-traffic-params {
         type string;
         description "Traffic parameters of resource";
       }
     }
   }
 }
