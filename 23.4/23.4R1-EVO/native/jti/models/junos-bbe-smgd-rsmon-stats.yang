module junos-bbe-smgd-rsmon-stats {
  yang-version 1;
  namespace "http://juniper.net/yang/bbe-smgd_rsmon_stats_tree";
  prefix junos-bbe-smgd-rsmon-stats;

  organization
    "Juniper Networks Inc.";
  contact
    "Juniper Networks, Inc.

     1133 Innovation Way
     Sunnyvale, CA

     +1 888 314-5822

     E-mail: yang-support@juniper.net";
  description
    "Top level grouping for rsmon stats";

  revision 2017-01-01 {
    description
      "Initial revision";
  }

  grouping smd-rsmon-fpc-rtt-thresholds {
    description
      "Counts of FPC Round-Trip-Time (RTT) threshold crossing events - above(exceeded) and below(nominal)";
    leaf delay-round-trip-exceeded {
      type uint32;
      description
        "Count of RTT threshold exceeded crossing events";
    }
    leaf delay-round-trip-nominal {
      type uint32;
      description
        "Count of RTT threshold nominal crossing events";
    }
  }

  grouping bbe-smgd-rsmon-stats-top {
    description
      "Top level grouping for rsmon stats";
    container junos {
      description
        "Container for JunOS";
      config false;
      container system {
        description
          "Container for system";
        container subscriber-management {
          description
            "Container for subscriber management";
          container infra {
            description
              "Container for infra";
            container resource-monitor {
              description
                "Container for resource monitor";
              container rsmon-infra {
                description
                  "Container for rsmon infra";
                container fpcs {
                  description
                    "Container for FPCs";
                  list fpc {
                    description
                      "List of FPC";
                    key "slot";
                    leaf slot {
                      description
                        "Slot";
                      type uint32;
                    }
                    uses smd-rsmon-fpc-rtt-thresholds;
                  }
                }
              }
            }
          }
        }
      }
    }
  }

  uses bbe-smgd-rsmon-stats-top;
}
