module junos-state-gnmi {
  yang-version 1.1;
  namespace "http://yang.juniper.net/junos/state/gnmi";
  prefix js-gnmi;

  import ietf-inet-types {
    prefix inet;
  }

  import junos-base-extensions {
    prefix junos-base;
  }

  import junos-state {
    prefix js;
  }

  import junos-state-system {
    prefix js-sys;
  }

  import junos-state-system-services {
    prefix js-sys-svc;
  }

  import junos-state-system-http {
    prefix js-http;
  }

  import junos-state-grpc {
    prefix js-grpc;
  }

  organization
    "Juniper Networks, Inc.";

  contact
    "Juniper Networks, Inc.

    1133 Innovation Way
    Sunnyvale, CA

    +1 888 314-5822

    E-mail: yang-support@juniper.net";

  description
    "This module contains state data of gNMI Server.

    Copyright (c) 2023 Juniper Networks, Inc.
    All rights reserved.";

  revision 2023-07-20 {
    description
      "Initial revision";
    reference "0.1.0";
  }

  junos-base:version "0.1.0";

  typedef gnmi-mode-type {
    type enumeration {
      enum stream {
        value 0;
        description
          "Export data in stream in long-lived connection";
      }
      enum once {
        value 1;
        description
          "Export data once and stop subscription";
      }
      enum poll {
        value 2;
        description
          "Values sent in response to a poll request";
      }
    }
  }

  typedef gnmi-submode-type {
    type enumeration {
      enum target-defined {
        value 0;
        description
          "Router decides mode for requested path";
      }
      enum on-change {
        value 1;
        description
          "Router exports data only when requested resource's value
           changes";
      }
      enum sample {
        value 2;
        description
          "Router exports data according to the interval requested";
      }
    }
  }

  typedef gnmi-encoding-type {
    type enumeration {
      enum json {
        value 0;
        description
          "JSON encoded text";
      }
      enum bytes {
        value 1;
        description
          "Arbitrarily encoded bytes";
      }
      enum proto {
        value 2;
        description
          "Encoded according to Protobuf's scalar data types";
      }
      enum ascii {
        value 3;
        description
          "ASCII text of an out-of-band agreed format";
      }
      enum json-ietf {
        value  4;
        description
          "JSON encoded text as per RFC7951";
      }
    }
  }

  grouping gnmi-top {
    description
      "Top-level grouping for gnmi service";

    container gnmi {
      description
        "Container for gNMI telemetry subscriptions and their
         statistics";

      container subscriptions {
        description
          "Container holding list of subscriptions";

        list subscription {
          key "client-address client-port";
          description
            "List of telemetry subscriptions";

          leaf client-address {
            type inet:ip-address;
            description
              "Client's address from where connection is established";
          }

          leaf client-port {
            type inet:port-number;
            description
              "Client's TCP port on which connection is established";
          }

          leaf mode {
            type gnmi-mode-type;
            description
              "Mode of subscription";
          }

          leaf encoding {
            type gnmi-encoding-type;
            description
              "Format of data exported exported";
          }

          container paths {
            description
              "Container holding list of requested paths of
               subscription";

            list path {
              key name;
              description
                "List of requested data-tree paths";

              leaf name {
                type string;
                description
                  "Data tree path in xpath format";
              }

              leaf subscription-mode {
                type gnmi-submode-type;
                description
                  "Per path subscription mode requested";
              }

              leaf sample-interval {
                type uint64;
                units "milliseconds";
                description
                  "Data export interval between samples in
                   milliseconds";
              }

              container counters {
              }
            }
          }
        }
      }
    }
  }

  augment "/js:state/js-sys:system/js-sys-svc:services/js-http:http" +
          "/js-http:servers/js-http:server/js-grpc:grpc" {
      description
        "Add gNMI servers to gRPC services";

      uses gnmi-top;
    }
}
