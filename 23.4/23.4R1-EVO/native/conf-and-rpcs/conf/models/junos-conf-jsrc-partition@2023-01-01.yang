/*
 * Copyright (c) 2023 Juniper Networks, Inc.
 * All rights reserved.
 */
 module junos-conf-jsrc-partition {
   namespace "http://yang.juniper.net/junos/conf/jsrc-partition";

   prefix jc-jsrc-partition;

   import junos-common-types {
     prefix jt;
     revision-date 2023-01-01;
   }

   import junos-conf-root {
     prefix jc;
     revision-date 2023-01-01;
   }

   organization "Juniper Networks, Inc.";

   contact "yang-support@juniper.net";

   description "Junos jsrc-partition configuration module";

   revision 2023-01-01 {
     description "Junos: 23.4R1.10-EVO";
   }

   augment /jc:configuration {
     uses jsrc-partition-group;
   }
   augment /jc:configuration/jc:groups {
     uses jsrc-partition-group;
   }
   grouping jsrc-partition-group {
     container jsrc-partition {
       description "JSRC partition configuration";
       leaf jsrc-partition-name {
         description "JSRC partition name";
         type string {
           length "1 .. 63";
         }
       }
     }
   }
 }
