module junos-interface-types {
  yang-version 1.1;
  namespace "http://yang.juniper.net/junos/interface/types";
  prefix junos-intft;

  import junos-base-extensions {
    prefix junos-base;
  }

  import junos-state {
    prefix js;
  }

  import junos-state-interfaces {
    prefix js-if;
  }

  organization
    "Juniper Networks, Inc.";

  contact
    "Juniper Networks, Inc.

     1133 Innovation Way
     Sunnyvale, CA 94089

     +1 888 314-5822

     E-mail: yang-support@juniper.net";

  description
    "This module contains a collection of JUNOS interface types.

     Copyright (c) 2025 Juniper Networks, Inc.
     All rights reserved.";

  revision 2025-01-09 {
    description
      "Addition of FEC related identities";
    reference "0.3.0";
  }

  revision 2024-03-05 {
    description
      "Addition of interface-name typedef";
    reference "0.2.0";
  }

  revision 2024-01-04 {
    description
      "Initial revision";
    reference "0.1.0";
  }

  junos-base:version "0.2.0";

  typedef base-state-interface-ref {
    type leafref {
      path "/js:state/js-if:interfaces/js-if:interface/js-if:name";
    }
    description
      "Reusable type for by-name reference to a base interface. This
       type may be used in cases where ability to reference a
       subinterface is not required.";
  }

  typedef interface-name {
    type string;
    description
      "An interface name in any JUNOS style convention.  This name can
       either represent PFE interfaces (eg. et-0/0/0, et-0/0/0:0),
       subinterfaces (eg. et-0/0/0.0, et-0/0/0:0.0), logical/virtual
       interfaces (eg. ae0, ae0.0, fti0.100, esi.100, vtep.32768,
       irb.100) or underlying kernel network devices (eg. eth0, jtd0,
       mgmt_junos).

       While there are no modeling restrictions on this string, it is
       still implied to be a reference to an actual interface on the
       system that is represented under the interfaces subtree.";

  }
  identity fec-mode {
    description
      "Base identity from which interface FEC modes are derived.";
  }

  identity none {
    base fec-mode;
    description
      "FEC is disabled on the interface";
  }

  identity fec91 {
    base fec-mode;
    description
      "This is used for channels with NRZ modulation. This FEC is
       designed to comply with IEEE 802.3, Clause 91.";
  }

  identity fec74 {
    base fec-mode;
    description
      "This is used for channels with NRZ modulation and speeds less
       than 100G. This FEC is designed to comply with the IEEE
       802.3,Clause 74.";
  }

  identity fec94 {
    base fec-mode;
    description
      "FEC mode for 100GBASE-KP4";
  }
  identity fec119 {
    base fec-mode;
    description
      "This FEC mode (KP4) is default FEC mode on 400-Gigabit Ethernet
       and 200-Gigabit Ethernet interfaces";
  }

  identity fec134 {
    base fec-mode;
    description
      "This FEC mode is default FEC mode for 50G PAM4";
  }

  identity fec91-rs544 {
    base fec-mode;
    description
      "This FEC mode (FEC91-KR4) is default FEC mode for 100G optic with
       PAM4 signal";
  }

  identity feckp4 {
    base fec-mode;
    description
      "FEC mode for 400G PAM4 signal";
  }

  identity fec161 {
    base fec-mode;
    description
      "This FEC mode is used for DAC interfaces with 106.25G SERDES";
  }

  identity fec-auto {
    base fec-mode;
    description
      "This FEC mode is auto detected based on the interface speed or
       optic";
  }

  identity fec-etc {
    base fec-mode;
    description
      "This FEC mode is used for 1X800G interface";
  }
}
