/*
 * Copyright (c) 2025 Juniper Networks, Inc.
 * All rights reserved.
 */
 module junos-nfx-rpc-extension-service {
   namespace "http://yang.juniper.net/junos-nfx/rpc/extension-service";

   prefix extension-service;

   import junos-common-types {
     prefix jt;
     revision-date 2025-01-01;
   }

   organization "Juniper Networks, Inc.";

   contact "yang-support@juniper.net";

   description "Junos RPC YANG module for extension-service command(s)";

   revision 2025-01-01 {
     description "Junos: 25.2R1.9";
   }

   rpc get-request-response-server-information {
     description "Request-response server information";
     output {
       container request-response-server-information {
         uses request-response-server-information-block;
       }
     }
   }
   rpc get-request-response-client-information {
     description "Request-response client information";
     input {
       leaf verbosity_level {
         default "brief";
         type enumeration {
           enum "brief" {
             description "Display brief output (default)";
           }
           enum "detail" {
             description "Display detailed output";
           }
         }
       }
       leaf client-id {
         description "Client identifier";
         type string;
       }
     }
     output {
       container request-response-client-information {
         uses request-response-client-information-block;
       }
     }
   }
   rpc jet-application-status {
     description "Status of JET application";
     input {
       leaf application-name {
         description "Application name";
         type string;
         mandatory true;
       }
     }
     output {
       choice output_c {
         case output-tag {
           leaf output {
             type string;
           }
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping request-response-server-information-block {
     container grpc-server-information {
       description "Request-response gRPC server information";
       leaf grpc-max-connections {
         type int32;
         description "Max gRPC connections";
       }
       leaf grpc-skip-authentication {
         type int32;
         description "GRPC skip-authentication";
       }
       list grpc-server {
         leaf grpc-server-address {
           type string;
           description "GRPC server address";
         }
         leaf grpc-server-port {
           type string;
           description "GRPC server port";
         }
         leaf grpc-server-status {
           type string;
           description "GRPC server status";
         }
         leaf grpc-server-type {
           type string;
           description "GRPC server type";
         }
       }
     }
     container thrift-server-information {
       description "Request-response thrift server information";
       leaf thrift-max-connections {
         type int32;
         description "Max thrift connections";
       }
       leaf thrift-skip-authentication {
         type int32;
         description "Thrift skip-authentication";
       }
       container thrift-server {
         leaf thrift-server-address {
           type string;
           description "Thrift server address";
         }
         leaf thrift-server-port {
           type string;
           description "Thrift server port";
         }
         leaf thrift-server-status {
           type string;
           description "Thrift server status";
         }
         leaf thrift-server-type {
           type string;
           description "Thrift server type";
         }
       }
     }
   }
   grouping request-response-client-information-block {
     list request-response-client {
       leaf client-id {
         type string;
         description "Client ID";
       }
       leaf socket-address {
         type string;
         description "Socket Address";
       }
       leaf client-type {
         type string;
         description "Client Type";
       }
       leaf client-login-time {
         type string;
         description "Client Login Time (UTC)";
       }
       leaf channel-count {
         type int32;
         description "Channel Count";
       }
       container grpc-channel-information {
         list grpc-channel {
           leaf target {
             type string;
             description "Channel target";
           }
           leaf status {
             type string;
             description "Channel status";
           }
           leaf user {
             type string;
             description "User name";
           }
         }
       }
     }
   }
 }
