/*
 * Copyright (c) 2025 Juniper Networks, Inc.
 * All rights reserved.
 */
 module junos-nfx-rpc-policer {
   namespace "http://yang.juniper.net/junos-nfx/rpc/policer";

   prefix policer;

   import junos-common-types {
     prefix jt;
     revision-date 2025-01-01;
   }

   organization "Juniper Networks, Inc.";

   contact "yang-support@juniper.net";

   description "Junos RPC YANG module for policer command(s)";

   revision 2025-01-01 {
     description "Junos: 25.2R1.9";
   }

   rpc get-policer-information {
     description "Show interface policer counters and information";
     input {
       leaf policer {
         description "Policer name";
         type string;
       }
       choice daemon-select {
         case logical-system {
           leaf logical-system {
             description "Name of logical system, or 'all'";
             type string {
             }
           }
         }
       }
       leaf detail {
         description "Show filter statistics with enhanced policer statistics";
         type empty;
       }
     }
     output {
       container firewall-information {
         uses firewall-information-block;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping firewall-information-block {
     list filter-information {
       description "Details of a firewall filter";
       leaf filter-name {
         type string;
         description "Name of filter";
       }
       leaf user-plane-name {
         type string;
         description "Name of the User Plane";
       }
       container error-status {
         leaf status {
           type string;
           description "Error status of the filter";
         }
       }
       list bind-error-status {
         leaf-list bind-name {
           type string;
           description "Error status of the filter bind point";
         }
       }
       list counter {
         description "Counter information";
         leaf counter-name {
           type string;
           description "Counter name";
         }
         leaf byte-count {
           type uint64;
           description "Bytes counted";
         }
         leaf packet-count {
           type uint64;
           description "Packets counted";
         }
       }
       list policer {
         description "Policer information";
         leaf policer-name {
           type string;
           description "Name of this policer";
         }
         leaf byte-count {
           type uint64;
           description "Bytes counted";
         }
         leaf packet-count {
           type uint64;
           description "Packets counted";
         }
       }
       list enchanced-hierarchical-policer {
         description "Hierarchical Policer information";
         leaf policer-name {
           type string;
           description "Name of this policer";
         }
         leaf byte-count-high {
           type uint64;
           description "Bytes counted";
         }
         leaf packet-count-high {
           type uint64;
           description "Packets counted";
         }
         leaf byte-count-medium-high {
           type uint64;
           description "Bytes counted";
         }
         leaf packet-count-medium-high {
           type uint64;
           description "Packets counted";
         }
         leaf byte-count-medium-low {
           type uint64;
           description "Bytes counted";
         }
         leaf packet-count-medium-low {
           type uint64;
           description "Packets counted";
         }
         leaf byte-count-low {
           type uint64;
           description "Bytes counted";
         }
         leaf packet-count-low {
           type uint64;
           description "Packets counted";
         }
         leaf packet-count {
           type uint64;
           description "Packets counted";
         }
         leaf byte-count {
           type uint64;
           description "Bytes counted";
         }
       }
       list filter-version {
         description "Filter version information";
         leaf filter-name {
           type string;
           description "Name of filter";
         }
         leaf version {
           type uint32;
           description "Filter version";
         }
       }
     }
     list user-plane-filter-information {
       description "Details of a user-plane firewall filter";
       leaf filter-name {
         type string;
         description "Name of filter";
       }
       leaf user-plane-name {
         type string;
         description "Name of the User Plane";
       }
       list counter {
         description "Counter information";
         leaf counter-name {
           type string;
           description "Counter name";
         }
         leaf byte-count {
           type uint64;
           description "Bytes counted";
         }
         leaf packet-count {
           type uint64;
           description "Packets counted";
         }
       }
       list filter-version {
         description "Filter version information";
         leaf filter-name {
           type string;
           description "Name of filter";
         }
         leaf version {
           type uint32;
           description "Filter version";
         }
       }
     }
     list subscribers-filter-information {
       description "Details of subscribers firewall filter";
       leaf filter-name {
         type string;
         description "Name of filter";
       }
       leaf user-plane-name {
         type string;
         description "Name of the User Plane";
       }
       list counter {
         description "Counter information";
         leaf counter-name {
           type string;
           description "Counter name";
         }
         leaf byte-count {
           type uint64;
           description "Bytes counted";
         }
         leaf packet-count {
           type uint64;
           description "Packets counted";
         }
       }
       list filter-version {
         description "Filter version information";
         leaf filter-name {
           type string;
           description "Name of filter";
         }
         leaf version {
           type uint32;
           description "Filter version";
         }
       }
     }
   }
 }
