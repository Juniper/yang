/*
 * Copyright (c) 2025 Juniper Networks, Inc.
 * All rights reserved.
 */
 module junos-qfx-conf-virtual-chassis {
   namespace "http://yang.juniper.net/junos-qfx/conf/virtual-chassis";

   prefix jc-virtual-chassis;

   import junos-common-ddl-extensions {
     prefix junos;
     revision-date 2025-01-01;
   }

   import junos-common-types {
     prefix jt;
     revision-date 2025-01-01;
   }

   import junos-qfx-conf-root {
     prefix jc;
     revision-date 2025-01-01;
   }

   organization "Juniper Networks, Inc.";

   contact "yang-support@juniper.net";

   description "Junos virtual-chassis configuration module";

   revision 2025-01-01 {
     description "Junos: 25.2R1.9";
   }

   augment /jc:configuration {
     uses virtual-chassis-group;
   }
   augment /jc:configuration/jc:groups {
     uses virtual-chassis-group;
   }
   grouping virtual-chassis-group {
     container virtual-chassis {
       junos:must "(!(\"forwarding-options hyper-mode\"))";
       junos:must-message "To configure virtual-chassis, 'forwarding-options hyper-mode' should not be configured";
       description "Virtual chassis configuration";
       uses apply-advanced;
       container auto-sw-update {
         presence "enable auto-sw-update";
         description "Auto software update";
         uses apply-advanced;
         leaf package-name {
           description "URL or pathname of software package";
           type string {
             junos:posix-pattern "![*]";
             junos:pattern-message "Package name cannot contain \'*\'.  Use TAB for filename completion";
           }
         }
         container ex-4300 {
           presence "enable ex-4300";
           description "URL or pathname of EX-43xx software package";
           uses apply-advanced;
           leaf package-name {
             description "URL or pathname of software package";
             type string {
               junos:posix-pattern "![*]";
               junos:pattern-message "Package name cannot contain \'*\'.  Use TAB for filename completion";
             }
           }
         }
         container ex-4600 {
           presence "enable ex-4600";
           description "URL or pathname of EX-46xx software package";
           uses apply-advanced;
           leaf package-name {
             description "URL or pathname of software package";
             type string {
               junos:posix-pattern "![*]";
               junos:pattern-message "Package name cannot contain \'*\'.  Use TAB for filename completion";
             }
           }
         }
         container qfx-3 {
           presence "enable qfx-3";
           description "URL or pathname of qfx-3 software package";
           uses apply-advanced;
           leaf package-name {
             description "URL or pathname of software package";
             type string {
               junos:posix-pattern "![*]";
               junos:pattern-message "Package name cannot contain \'*\'.  Use TAB for filename completion";
             }
           }
         }
         container qfx-5 {
           presence "enable qfx-5";
           description "URL or pathname of qfx-5 software package";
           uses apply-advanced;
           leaf package-name {
             description "URL or pathname of software package";
             type string {
               junos:posix-pattern "![*]";
               junos:pattern-message "Package name cannot contain \'*\'.  Use TAB for filename completion";
             }
           }
         }
       }
       choice provisioning {
         case case_1 {
           leaf preprovisioned {
             description "Only accept preprovisioned members";
             type empty;
           }
         }
         case case_2 {
           leaf auto-provisioned {
             description "Add and configure new line-card members automatically";
             type empty;
           }
         }
       }
       leaf id {
         description "Virtual chassis identifier, of type ISO system-id";
         type jt:isosysid;
       }
       container graceful-restart {
         junos:cli-feature "oneliner-plus";
         description "Configure graceful restart attributes";
         uses apply-advanced;
         choice enable-disable {
           case case_1 {
             leaf disable {
               description "Disable graceful restart";
               type empty;
             }
           }
         }
       }
       leaf no-split-detection {
         description "Disable split detection. This command is recommended to only be enabled in a 2 member setup";
         junos:must "(!(\"virtual-chassis heartbeat-address\"))";
         junos:must-message "no-split-detection is not allowed when heartbeat-address is configured";
         type empty;
       }
       container traceoptions {
         description "Trace options for virtual chassis";
         uses juniper-virtual-chassis-traceoptions;
       }
       list member {
         key name;
         ordered-by user;
         description "Member of virtual chassis configuration";
         leaf name {
           description "Member identifier";
           junos:cli-feature "nokeyword";
           type union {
             type string {
               pattern "<.*>|$.*";
             }
             type int32;
           }
         }
         uses apply-advanced;
         leaf mastership-priority {
           description "Member's mastership priority";
           type union {
             type string {
               pattern "<.*>|$.*";
             }
             type int32 {
               range "0 .. 255";
             }
           }
         }
         leaf fabric-tree-root {
           description "Member's participation as root of multicast distribution tree";
           type empty;
         }
         leaf role {
           description "Member's role";
           default "line-card";
           type enumeration {
             enum "routing-engine" {
               description "Member to assume role of routing engine";
             }
             enum "line-card" {
               description "Member to assume role of line card";
             }
           }
         }
         leaf serial-number {
           description "Member's serial number";
           type string {
             length "1 .. 12";
           }
         }
         leaf no-management-vlan {
           description "Disable management VLAN";
           type empty;
         }
         leaf location {
           description "Member's location";
           type string {
             length "1 .. 254";
           }
         }
       }
       container aliases {
         description "Aliases for serial numbers";
         uses apply-advanced;
         list serial-number {
           key name;
           ordered-by user;
           description "Set alias for a serial number";
           leaf name {
             description "Member's serial number";
             junos:cli-feature "nokeyword";
             type string {
               length "1 .. 12";
             }
           }
           uses apply-advanced;
           leaf alias-name {
             description "Provide an alias name for this serial-number";
             type string {
               length "1 .. 12";
             }
           }
         }
       }
       container mac-persistence-timer {
         description "How long to retain MAC address when member leaves virtual chassis";
         uses apply-advanced;
         leaf timer {
           description "MAC persistence time";
           junos:cli-feature "nokeyword";
           default "60";
           units "minutes";
           type union {
             type string {
               pattern "<.*>|$.*";
             }
             type uint32 {
               range "1 .. 60";
             }
           }
         }
         leaf disable {
           description "Disable MAC persistence timer";
           type empty;
         }
       }
       container fast-failover {
         description "Fast failover mechanism";
         uses apply-advanced;
         leaf ge {
           description "Fast failover on GE VC uplink ports (ring has to be formed)";
           type empty;
         }
         leaf xe {
           description "Fast failover on XE VC uplink ports (ring has to be formed)";
           type empty;
         }
         leaf et {
           description "Fast failover on ET VC uplink ports (ring has to be formed)";
           type empty;
         }
         container vcp {
           description "Fast failover on VCP ports";
           uses apply-advanced;
           leaf disable {
             description "Disable";
             type empty;
           }
         }
       }
       choice auto_conversion_choice {
         case case_1 {
           leaf no-auto-conversion {
             description "Disable automatic VC port conversion";
             type empty;
           }
         }
         case case_2 {
         }
       }
       leaf vcp-no-hold-time {
         description "Set no hold time for vcp interfaces";
         type empty;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       junos:cli-feature "nokeyword";
       type string;
     }
     list data {
       key name;
       uses macro-data-type;
       junos:cli-feature "nokeyword";
       junos:cli-feature "homogeneous";
       junos:cli-feature "oneliner";
     }
   }
   grouping juniper-virtual-chassis-traceoptions {
     description "Global tracing options for virtual chassis";
     uses apply-advanced;
     container file {
       description "Trace file options";
       junos:cli-feature "oneliner";
       uses vchassis_trace_file_type;
     }
     list flag {
       key name;
       ordered-by user;
       junos:cli-feature "oneliner";
       description "Tracing parameters";
       leaf name {
         junos:cli-feature "nokeyword";
         type enumeration {
           enum "parse" {
             description "Trace configuration parsing";
           }
           enum "hello" {
             description "Trace virtual chassis hello packets";
           }
           enum "psn" {
             description "Trace partial sequence number (PSN) packets";
           }
           enum "csn" {
             description "Trace complete sequence number (CSN) packets";
           }
           enum "lsp" {
             description "Trace virtual link-state packets";
           }
           enum "normal" {
             description "Trace normal events";
           }
           enum "task" {
             description "Trace virtual chassis task processing";
           }
           enum "krt" {
             description "Trace virtual chassis kernel events";
           }
           enum "spf" {
             description "Trace virtual chassis SPF events";
           }
           enum "me" {
             description "Trace virtual chassis master election events";
           }
           enum "packets" {
             description "Trace virtual chassis packets";
           }
           enum "lsp-generation" {
             description "Trace virtual chassis LSP generation";
           }
           enum "error" {
             description "Trace virtual chassis errors";
           }
           enum "route" {
             description "Trace virtual chassis routing information";
           }
           enum "state" {
             description "Trace virtual chassis state transitions";
           }
           enum "auto-configuration" {
             description "Trace virtual chassis ports auto configuration";
           }
           enum "graceful-restart" {
             description "Trace graceful restart events";
           }
           enum "dcp-infra" {
             description "Trace dcp infrastructure configuration";
           }
           enum "dcp-dev-state" {
             description "Trace dcp infrastructure configuration";
           }
           enum "heartbeat" {
             description "Trace virtual chassis heartbeat packets";
           }
           enum "all" {
             description "Trace everything";
           }
         }
       }
       leaf send {
         description "Trace transmitted packets";
         type empty;
       }
       leaf receive {
         description "Trace received packets";
         type empty;
       }
       leaf detail {
         description "Trace detailed information";
         type empty;
       }
       leaf disable {
         description "Disable this trace flag";
         type empty;
       }
     }
   }
   grouping macro-data-type {
     junos:cli-feature "nokeyword";
     junos:cli-feature "homogeneous";
     junos:cli-feature "oneliner";
     leaf name {
       description "Keyword part of the keyword-value pair";
       junos:cli-feature "nokeyword";
       type string;
     }
     leaf value {
       description "Value part of the keyword-value pair";
       junos:cli-feature "nokeyword";
       type string;
     }
   }
   grouping vchassis_trace_file_type {
     junos:cli-feature "oneliner";
     leaf filename {
       description "Name of file in which to write trace information";
       junos:cli-feature "nokeyword";
       type string {
         length "1 .. 1024";
         junos:posix-pattern "![/ %]";
         junos:pattern-message "Must not contain \'/\', % or a space";
       }
     }
     leaf replace {
       description "Replace trace file rather than appending to it";
       type empty;
     }
     leaf size {
       description "Maximum trace file size";
       type string;
     }
     leaf files {
       description "Maximum number of trace files";
       default "10";
       type union {
         type string {
           pattern "<.*>|$.*";
         }
         type uint32 {
           range "2 .. 1000";
         }
       }
     }
     leaf no-stamp {
       description "Do not timestamp trace file";
       type empty;
     }
     choice world-readable-choice {
       leaf world-readable {
         description "Allow any user to read the log file";
         type empty;
       }
       leaf no-world-readable {
         description "Don't allow any user to read the log file";
         type empty;
       }
     }
   }
 }
