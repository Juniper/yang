/*
 * Copyright (c) 2025 Juniper Networks, Inc.
 * All rights reserved.
 */
 module junos-ex-conf-system {
   namespace "http://yang.juniper.net/junos-ex/conf/system";

   prefix jc-system;

   import junos-common-types {
     prefix jt;
     revision-date 2025-01-01;
   }

   import junos-ex-conf-root {
     prefix jc;
     revision-date 2025-01-01;
   }

   organization "Juniper Networks, Inc.";

   contact "yang-support@juniper.net";

   description "Junos system configuration module";

   revision 2025-01-01 {
     description "Junos: 25.2R1.9";
   }

   augment /jc:configuration {
     uses system-group;
   }
   augment /jc:configuration/jc:groups {
     uses system-group;
   }
   grouping system-group {
     container system {
       description "System parameters";
       uses juniper-system;
     }
   }
   grouping juniper-system {
     uses apply-advanced;
     leaf host-name {
       description "Hostname for this router";
       type string {
         length "1 .. 255";
       }
     }
     container root-authentication {
       description "Authentication information for the root login";
       uses authentication-object;
     }
     container commit {
       description "Configuration commit management";
       uses apply-advanced;
       container commit-synchronize-server {
         description "Commit synchronize server configuration";
         uses apply-advanced;
         container traceoptions {
           description "Traceoptions for commit synchronize server";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf microsecond-stamp {
               description "Timestamp with microsecond granularity";
               type empty;
             }
           }
           list flag {
             key name;
             description "Tracing parameters";
             leaf name {
               type enumeration {
                 enum "ephemeral-commit" {
                   description "Trace ephemeral database commit synchronize requests";
                 }
                 enum "operational-command" {
                   description "Trace operational command requests";
                 }
                 enum "debug" {
                   description "Trace debug level information";
                 }
                 enum "all" {
                   description "Trace all information";
                 }
               }
             }
           }
         }
       }
       choice persist-groups-choice {
         case case_1 {
           leaf persist-groups-inheritance {
             description "Build configuration groups inheritance path";
             type empty;
           }
         }
         case case_2 {
           leaf no-persist-groups-inheritance {
             description "Don't build configuration groups inheritance path";
             type empty;
           }
         }
       }
       leaf ignore-xpath-failure {
         description "Ignore xpath failures during commit";
         status deprecated;
         type empty;
       }
       container server {
         description "Commit server (batch commit)";
         uses apply-advanced;
         leaf maximum-aggregate-pool {
           description "Maximum number of transactions to aggregate";
           type union {
             type string {
               pattern "<.*>|$.*";
             }
             type uint32 {
               range "1 .. 4294967295";
             }
           }
         }
         leaf maximum-entries {
           description "Maximum number of transactions allowed in queue";
           type union {
             type uint32;
             type string {
               pattern "<.*>|$.*";
             }
           }
         }
         leaf commit-interval {
           description "Number of seconds between commits";
           type union {
             type uint32;
             type string {
               pattern "<.*>|$.*";
             }
           }
         }
         leaf retry-attempts {
           description "Retry attempts for commit failure due to db lock error";
           default "5";
           type union {
             type uint32;
             type string {
               pattern "<.*>|$.*";
             }
           }
         }
         leaf retry-interval {
           description "Retry interval in seconds for commit failure";
           default "20";
           type union {
             type uint32;
             type string {
               pattern "<.*>|$.*";
             }
           }
         }
         leaf days-to-keep-error-logs {
           description "Number of day to keep error log entries";
           type union {
             type string {
               pattern "<.*>|$.*";
             }
             type uint32 {
               range "1 .. 366";
             }
           }
         }
         leaf redirect-completion-status {
           description "Redirect Async commit status to server configured here";
           type string;
         }
         list commit-schedule-profile {
           key name;
           ordered-by user;
           description "Scheduling profile for asynchronous low priority commits";
           leaf name {
             description "Schedule name for low priority commits";
             type string {
               length "1 .. 64";
             }
           }
           uses apply-advanced;
           leaf start-time {
             description "Time when the schedule starts processing low priority jobs (hh:mm)";
             type string {
             }
           }
           leaf end-time {
             description "Time when the schedule stops processing low priority jobs (hh:mm)";
             type string {
             }
           }
           leaf interruptible {
             description "Allow the low priority jobs to be interrupted during the schedule";
             type empty;
           }
           leaf load-average {
             description "Max load average of system at which schedule starts (last 1 min)";
             type jt:unsigned-float;
           }
         }
         container traceoptions {
           description "Trace options for commit server";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf microsecond-stamp {
               description "Timestamp with microsecond granularity";
               type empty;
             }
           }
           list flag {
             key name;
             description "Tracing parameters";
             leaf name {
               type enumeration {
                 enum "all" {
                   description "Trace all operations";
                 }
                 enum "commit-server" {
                   description "Trace commit server";
                 }
                 enum "batch" {
                   description "Trace file batching";
                 }
                 enum "configuration" {
                   description "Reading of configuration";
                 }
               }
             }
           }
         }
       }
       leaf fast-synchronize {
         description "Parallelized commit synchronizing multiple routing-engines";
         type empty;
       }
       leaf synchronize {
         description "Synchronize commit on both Routing Engines by default";
         type empty;
       }
       leaf delta-export {
         description "Export only delta configuration during commit";
         type empty;
       }
       leaf force-commit-log {
         description "Enforce log/message for each commit";
         type empty;
       }
       leaf config-sync-with-scp {
         description "Use SCP protocol to sync configuration to members in a virtual chassis";
         type empty;
       }
       container notification {
         presence "enable notification";
         description "Notify applications upon commit complete";
         uses apply-advanced;
       }
       leaf no-synchronize {
         description "Don't synchronize commit on both Routing Engines";
         type empty;
       }
       leaf peers-synchronize {
         description "Synchronize commit on remote peers by default";
         type empty;
       }
       list peers {
         key name;
         ordered-by user;
         description "Commit peers-synchronize details";
         max-elements 3;
         uses peers-type;
       }
     }
     container configuration-database {
       description "Configuration database parameters";
       uses apply-advanced;
       container ephemeral {
         presence "enable ephemeral";
         description "Configure ephemeral database";
         uses apply-advanced;
         list instance {
           key name;
           ordered-by user;
           description "Configure ephemeral instances";
           max-elements 8;
           leaf name {
             description "Name of ephemeral instance";
             type string {
               length "1 .. 32";
             }
           }
           uses apply-advanced;
           leaf cyclic-version {
             description "Reclaim database space in this version relative to current database version";
             default "10";
             type union {
               type string {
                 pattern "<.*>|$.*";
               }
               type uint32 {
                 range "0 .. 4294967295";
               }
             }
           }
           container resize {
             presence "enable resize";
             description "Resize configuration database";
             uses apply-advanced;
             leaf database-size-on-disk {
               description "Minimum configuration database size on disk";
               default "450";
               units "Megabytes";
               type union {
                 type string {
                   pattern "<.*>|$.*";
                 }
                 type uint32 {
                   range "1 .. 1024";
                 }
               }
             }
             leaf database-size-diff {
               description "Minimum difference between database size and actual usage";
               default "100";
               units "Megabytes";
               type union {
                 type string {
                   pattern "<.*>|$.*";
                 }
                 type uint32 {
                   range "1 .. 1024";
                 }
               }
             }
           }
         }
         leaf commit-synchronize-model {
           description "Select commit synchronize model for ephemeral";
           default "asynchronous";
           type enumeration {
             enum "asynchronous" {
               description "Commit synchronize on backup happens asynchronously";
             }
             enum "synchronous" {
               description "Commit synchronize on backup happens synchronously";
             }
           }
         }
         leaf ignore-ephemeral-default {
           description "Ignore ephemeral default database";
           type empty;
         }
         leaf delete-ephemeral-default {
           description "Delete ephemeral default database";
           type empty;
         }
         leaf cyclic-version-for-ephemeral-default {
           description "Reclaim database space in this version relative to current database version";
           default "10";
           type union {
             type string {
               pattern "<.*>|$.*";
             }
             type uint32 {
               range "0 .. 4294967295";
             }
           }
         }
         container resize-ephemeral-default {
           presence "enable resize-ephemeral-default";
           description "Resize configuration database";
           uses apply-advanced;
           leaf database-size-on-disk {
             description "Minimum configuration database size on disk";
             default "450";
             units "Megabytes";
             type union {
               type string {
                 pattern "<.*>|$.*";
               }
               type uint32 {
                 range "1 .. 1024";
               }
             }
           }
           leaf database-size-diff {
             description "Minimum difference between database size and actual usage";
             default "100";
             units "Megabytes";
             type union {
               type string {
                 pattern "<.*>|$.*";
               }
               type uint32 {
                 range "1 .. 1024";
               }
             }
           }
         }
         leaf allow-commit-synchronize-with-gres {
           description "Allow ephemeral commit synchronize with GRES";
           type empty;
         }
       }
       container virtual-memory-mapping {
         description "Virtual memory mapping configuration";
         uses apply-advanced;
         list process {
           key name;
           ordered-by user;
           description "Per process configuration";
           leaf name {
             description "Name of the process";
             type string;
           }
           uses apply-advanced;
           leaf fixed-size {
             description "Fixed memory mapped size in kilobytes";
             units "kilobytes";
             type union {
               type string {
                 pattern "<.*>|$.*";
               }
               type uint32 {
                 range "512 .. 696320";
               }
             }
           }
           leaf page-pooling-size {
             description "Page pooling memory mapped size in kilobytes";
             units "kilobytes";
             type union {
               type string {
                 pattern "<.*>|$.*";
               }
               type uint32 {
                 range "512 .. 696320";
               }
             }
           }
           leaf page-leak-debug {
             description "Page leak detection";
             type empty;
           }
         }
         container process-set {
           description "Set of processes using page pool";
           uses apply-advanced;
           container subscriber-management {
             presence "enable subscriber-management";
             description "Subscriber management processes will use page pooling";
             uses apply-advanced;
             leaf fixed-size {
               description "Fixed memory mapped size";
               units "kilobytes";
               type union {
                 type string {
                   pattern "<.*>|$.*";
                 }
                 type uint32 {
                   range "512 .. 696320";
                 }
               }
             }
             leaf page-pooling-size {
               description "Page pooling memory mapped size";
               units "kilobytes";
               type union {
                 type string {
                   pattern "<.*>|$.*";
                 }
                 type uint32 {
                   range "512 .. 696320";
                 }
               }
             }
           }
         }
       }
       leaf extend-size {
         description "Extend configuration database upto 2.2G";
         type empty;
       }
       container resize {
         presence "enable resize";
         description "Resize configuration database";
         uses apply-advanced;
         leaf database-size-on-disk {
           description "Minimum configuration database size on disk";
           default "450";
           units "Megabytes";
           type union {
             type string {
               pattern "<.*>|$.*";
             }
             type uint32 {
               range "1 .. 1024";
             }
           }
         }
         leaf database-size-diff {
           description "Minimum difference between database size and actual usage";
           default "100";
           units "Megabytes";
           type union {
             type string {
               pattern "<.*>|$.*";
             }
             type uint32 {
               range "1 .. 1024";
             }
           }
         }
       }
     }
     container scripts {
       description "Scripting mechanisms";
       uses scripts_type;
     }
     container login {
       description "Names, login classes, and passwords for users";
       uses apply-advanced;
       container retry-options {
         description "Configure password retry options";
         uses apply-advanced;
         leaf tries-before-disconnect {
           description "Number of times user is allowed to try password";
           default "3";
           type union {
             type string {
               pattern "<.*>|$.*";
             }
             type uint32 {
               range "2 .. 10";
             }
           }
         }
         leaf backoff-threshold {
           description "Number of password failures before delay is introduced";
           default "2";
           type union {
             type string {
               pattern "<.*>|$.*";
             }
             type uint32 {
               range "1 .. 3";
             }
           }
         }
         leaf backoff-factor {
           description "Delay factor after 'backoff-threshold' password failures";
           default "5";
           type union {
             type string {
               pattern "<.*>|$.*";
             }
             type uint32 {
               range "5 .. 10";
             }
           }
         }
         leaf minimum-time {
           description "Minimum total connection time if all attempts fail";
           default "20";
           type union {
             type string {
               pattern "<.*>|$.*";
             }
             type uint32 {
               range "20 .. 60";
             }
           }
         }
         leaf maximum-time {
           description "Maximum time the connection will remain for user to enter username and password";
           default "120";
           type union {
             type string {
               pattern "<.*>|$.*";
             }
             type uint32 {
               range "20 .. 300";
             }
           }
         }
         leaf lockout-period {
           description "Amount of time user account is locked after 'tries-before-disconnect' failures";
           units "minutes";
           type union {
             type string {
               pattern "<.*>|$.*";
             }
             type uint32 {
               range "1 .. 43200";
             }
           }
         }
       }
       leaf idle-timeout {
         description "Maximum idle time before logout";
         units "minutes";
         type union {
           type string {
             pattern "<.*>|$.*";
           }
           type uint32 {
             range "1 .. 60";
           }
         }
       }
       list class {
         key name;
         description "Login class";
         uses login-class-object;
       }
       list user {
         key name;
         description "Username";
         uses login-user-object;
       }
       container password {
         description "Password configuration";
         uses apply-advanced;
         leaf minimum-character-changes {
           description "Minimum number of character changes between old and new passwords";
           type union {
             type string {
               pattern "<.*>|$.*";
             }
             type int32 {
               range "4 .. 15";
             }
           }
         }
         leaf minimum-reuse {
           description "Minimum number of old passwords which should not be same as the new password";
           type union {
             type string {
               pattern "<.*>|$.*";
             }
             type int32 {
               range "1 .. 20";
             }
           }
         }
         leaf maximum-lifetime {
           description "Maximum password lifetime in days";
           type union {
             type string {
               pattern "<.*>|$.*";
             }
             type int32 {
               range "30 .. 365";
             }
           }
         }
         leaf minimum-lifetime {
           description "Minimum password lifetime in days";
           type union {
             type string {
               pattern "<.*>|$.*";
             }
             type int32 {
               range "1 .. 30";
             }
           }
         }
         leaf minimum-length {
           description "Minimum password length for all users";
           type union {
             type string {
               pattern "<.*>|$.*";
             }
             type int32 {
               range "6 .. 20";
             }
           }
         }
         leaf maximum-length {
           description "Maximum password length for all users";
           type union {
             type string {
               pattern "<.*>|$.*";
             }
             type int32 {
               range "20 .. 128";
             }
           }
         }
         leaf change-type {
           description "Password change type";
           type enumeration {
             enum "character-sets" {
               description "Count number of character type";
             }
             enum "set-transitions" {
               description "Count changes in character type";
             }
           }
         }
         leaf minimum-changes {
           description "Minimum number of changes in password";
           type union {
             type int32;
             type string {
               pattern "<.*>|$.*";
             }
           }
         }
         leaf minimum-numerics {
           description "Minimum number of numeric class characters in password";
           type union {
             type string {
               pattern "<.*>|$.*";
             }
             type int32 {
               range "1 .. 128";
             }
           }
         }
         leaf minimum-upper-cases {
           description "Minimum number of upper-case class characters in password";
           type union {
             type string {
               pattern "<.*>|$.*";
             }
             type int32 {
               range "1 .. 128";
             }
           }
         }
         leaf minimum-lower-cases {
           description "Minimum number of lower-case class characters in password";
           type union {
             type string {
               pattern "<.*>|$.*";
             }
             type int32 {
               range "1 .. 128";
             }
           }
         }
         leaf minimum-punctuations {
           description "Minimum number of punctuation class characters in password";
           type union {
             type string {
               pattern "<.*>|$.*";
             }
             type int32 {
               range "1 .. 128";
             }
           }
         }
         leaf format {
           description "Encryption method to use for password";
           type enumeration {
             enum "sha256" {
               description "Secure Hash Algorithm 256 ($5$)";
             }
             enum "sha512" {
               description "Secure Hash Algorithm 512 ($6$)";
             }
             enum "md5" {
               description "Message Digest 5";
             }
             enum "des" {
               description "Digital Encryption Standard";
             }
           }
         }
       }
       container deny-sources {
         description "Sources from which logins are denied";
         uses apply-advanced;
         leaf-list address {
           ordered-by user;
           description "IPv4/IPv6 addresses, prefix length optional, or hostnames";
           type jt:ipprefix-optional;
         }
       }
       leaf announcement {
         description "System announcement message (displayed after login)";
         type string {
           length "1 .. 2048";
         }
       }
       leaf message {
         description "System login message";
         type string {
           length "1 .. 2048";
         }
       }
     }
     container export-format {
       description "Setting the properties related to exporting the data";
       uses apply-advanced;
       container json {
         description "Set the type of JSON format";
         uses apply-advanced;
         choice json-type {
           case case_1 {
             leaf verbose {
               description "All the objects will be emitted as JSON arrays";
               type empty;
             }
           }
           case case_2 {
             leaf ietf {
               description "JSON format will be emitted as per IETF RFC 7951";
               type empty;
             }
           }
         }
       }
       container state-data {
         description "Setting the properties with respect to state data";
         status deprecated;
         uses apply-advanced;
         container json {
           description "Set the type of JSON format for state data rendering";
           uses apply-advanced;
           choice json-type {
             case case_1 {
               leaf compact {
                 description "Display JSON in compact format";
                 type empty;
               }
             }
           }
         }
       }
     }
     container configuration {
       description "Set the configuration processing related parameters";
       uses apply-advanced;
       container input {
         description "Set the input configuration processing related parameters";
         uses apply-advanced;
         container format {
           description "Specify the format";
           uses apply-advanced;
           container json {
             description "JSON format related parameters";
             uses apply-advanced;
             leaf reorder-list-keys {
               description "Reorder list keys as per JUNOS style";
               type empty;
             }
           }
         }
       }
     }
     leaf max-cli-sessions {
       description "Maximum number of cli sessions";
       type union {
         type string {
           pattern "<.*>|$.*";
         }
         type uint32 {
           range "1 .. 1024";
         }
       }
     }
     container services {
       presence "enable services";
       description "System services";
       uses apply-advanced;
       container netconf {
         description "Allow NETCONF connections";
         uses apply-advanced;
         container yang-modules {
           description "Tweak settings for YANG modules served on this device";
           uses apply-advanced;
           leaf emit-family-ns-and-module-name {
             description "Emit family specific namespace and module name in Yang modules";
             type empty;
           }
           leaf device-specific {
             description "Serve YANG modules specific to this device";
             type empty;
           }
           leaf emit-extensions {
             description "Enable serving of Junos YANG extension modules";
             type empty;
           }
           leaf rpc-output-verbose {
             description "Emit verbose rpc output";
             status deprecated;
             type empty;
           }
           leaf emit-anyxml-in-rpc-output {
             description "Emit anyxml stanza in RPC output/response block";
             type empty;
           }
         }
         container ssh {
           presence "enable ssh";
           description "Allow NETCONF over SSH";
           uses apply-advanced;
           leaf connection-limit {
             description "Limit number of simultaneous connections";
             default "75";
             units "connections";
             type union {
               type string {
                 pattern "<.*>|$.*";
               }
               type uint32 {
                 range "1 .. 250";
               }
             }
           }
           leaf rate-limit {
             description "Limit incoming connection rate";
             default "150";
             units "connections per minute";
             type union {
               type string {
                 pattern "<.*>|$.*";
               }
               type uint32 {
                 range "1 .. 250";
               }
             }
           }
           leaf client-alive-count-max {
             description "Threshold of missing client-alive responses that triggers a disconnect";
             default "3";
             type union {
               type string {
                 pattern "<.*>|$.*";
               }
               type uint32 {
                 range "0 .. 255";
               }
             }
           }
           leaf client-alive-interval {
             description "Frequency of client-alive requests";
             default "0";
             units "seconds";
             type union {
               type string {
                 pattern "<.*>|$.*";
               }
               type uint32 {
                 range "0 .. 65535";
               }
             }
           }
           leaf port {
             description "Service port number";
             default "830";
             type union {
               type string {
                 pattern "<.*>|$.*";
               }
               type int32 {
                 range "1 .. 65535";
               }
             }
           }
         }
         container tls {
           description "Allow NETCONF over TLS";
           uses apply-advanced;
           leaf local-certificate {
             description "Local Certificate ID";
             type string {
             }
           }
           list client-identity {
             key name;
             ordered-by user;
             description "Individual TLS/NETCONF client information";
             leaf name {
               description "Client ID";
               type string {
                 length "1 .. 31";
               }
             }
             uses apply-advanced;
             leaf fingerprint {
               description "Client certificate fingerprint in x509c2n:tls-fingerprint format";
               type string {
               }
             }
             leaf map-type {
               description "Map Type";
               type enumeration {
                 enum "specified" {
                   description "Use the specified username as NETCONF username";
                 }
                 enum "san-dirname-cn" {
                   description "Use the common name (CN) field of SAN DirName as NETCONF username";
                 }
               }
             }
             leaf username {
               description "NETCONF username if the map-type is specified";
               type string {
               }
             }
           }
           container default-client-identity {
             description "Default TLS/NETCONF client information";
             uses apply-advanced;
             leaf map-type {
               description "Map Type";
               type enumeration {
                 enum "specified" {
                   description "Use the specified username as NETCONF username";
                 }
                 enum "san-dirname-cn" {
                   description "Use the common name (CN) field of SAN DirName as NETCONF username";
                 }
               }
             }
             leaf username {
               description "NETCONF username if the map-type is specified";
               type string {
               }
             }
           }
           container traceoptions {
             description "NETCONF over TLS trace options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               default "error";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "general" {
                     description "Log the tls-proxyd infra related messages";
                   }
                   enum "pki" {
                     description "Log the PKI related messages";
                   }
                   enum "plugin" {
                     description "Log the plugin messages";
                   }
                   enum "app" {
                     description "Log the application data in plain text";
                   }
                   enum "all" {
                     description "Log the entire communication";
                   }
                 }
               }
             }
           }
         }
         container unified {
           description "Schema options for unified netconf";
           uses apply-advanced;
           leaf unhide {
             description "Unhide unified netconf get from CLI";
             type empty;
           }
         }
         container hello-message {
           description "Configuration for NETCONF 'hello' message";
           uses apply-advanced;
           container yang-module-capabilities {
             description "Advertise YANG module capabilities of the device";
             uses apply-advanced;
             leaf advertise-native-yang-modules {
               description "Advertise Junos native YANG modules";
               type empty;
             }
             leaf advertise-custom-yang-modules {
               description "Advertise custom YANG modules installed on the device";
               type empty;
             }
             leaf advertise-standard-yang-modules {
               description "Advertise standard YANG modules supported by the device";
               type empty;
             }
           }
         }
         container netconf-monitoring {
           description "NETCONF monitoring feature (RFC 6022) related configuration";
           uses apply-advanced;
           container netconf-state-schemas {
             description "Configuration to retrieve the schemas supported by the NETCONF server";
             uses apply-advanced;
             leaf retrieve-custom-yang-modules {
               description "Retrieve the custom YANG modules installed on the device";
               type empty;
             }
             leaf retrieve-standard-yang-modules {
               description "Retrieve the standard YANG modules supported by the device";
               type empty;
             }
           }
         }
         leaf rfc-compliant {
           description "Make the NETCONF sessions compliant to RFC 4741";
           type empty;
         }
         leaf yang-compliant {
           description "Make the NETCONF sessions compliant to yang schemas";
           type empty;
         }
         leaf flatten-commit-results {
           description "Suppress the 'commit-results' XML subtree in 'commit' rpc response";
           type empty;
         }
         container traceoptions {
           description "NETCONF trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "all" {
                   description "Log the entire communication";
                 }
                 enum "incoming" {
                   description "Log all incoming data";
                 }
                 enum "outgoing" {
                   description "Log all outgoing data";
                 }
                 enum "debug" {
                   description "Log debug level information";
                 }
               }
             }
           }
           leaf on-demand {
             description "Enable on-demand tracing";
             type empty;
           }
         }
         container notification {
           presence "enable notification";
           description "Enable Netconf notification service";
           uses apply-advanced;
           leaf interleave {
             description "Enable interleaving";
             type empty;
           }
         }
         container version-1.1 {
           presence "enable version-1.1";
           description "Make the NETCONF sessions compliant to RFC 6242";
         }
       }
       container netproxy {
         presence "enable netproxy";
         description "Netproxy configuration";
       }
       container ssh {
         presence "enable ssh";
         description "Allow ssh access";
         uses apply-advanced;
         leaf-list authentication-order {
           ordered-by user;
           type enumeration {
             enum "radius" {
               description "Remote Authentication Dial-In User Service";
             }
             enum "tacplus" {
               description "TACACS+ authentication services";
             }
             enum "password" {
               description "Traditional password authentication";
             }
           }
         }
         container cert-based-auth {
           description "Certificates for user authentication";
           uses apply-advanced;
           list trusted-user-ca-keys {
             key name;
             ordered-by user;
             description "Trusted User CA Keys";
             leaf name {
               description "SSH public key for validating user certificates";
               type string {
                 length "1 .. 4096";
               }
             }
             uses apply-advanced;
           }
           leaf host-certificate {
             description "SSH host certificate";
             type string {
               length "1 .. 8000";
             }
           }
         }
         leaf host-certificate-file {
           description "File containing the host certificate";
           type string;
         }
         leaf trusted-user-ca-key-file {
           description "File containing public keys for validating user certificates";
           type string;
         }
         leaf-list authorized-principals {
           ordered-by user;
           description "List of authorized principals";
           type string;
         }
         leaf authorized-principals-file {
           description "File containing list of authorized principals";
           type string;
         }
         leaf authorized-principals-command {
           description "Command to generate AuthorizedPrincipals file";
           type string;
         }
         leaf root-login {
           description "Configure root access via ssh";
           type enumeration {
             enum "allow" {
               description "Allow root access via ssh";
             }
             enum "deny" {
               description "Do not allow root access via ssh";
             }
             enum "deny-password" {
               description "Allow for non-password-based authentication methods only";
             }
           }
         }
         leaf no-challenge-response {
           description "Disables ssh challenge-response based authentication methods";
           type empty;
         }
         leaf no-password-authentication {
           description "Disables ssh password based authentication methods";
           type empty;
         }
         leaf no-passwords {
           description "Disables ssh password and challenge-response based authentication";
           type empty;
         }
         leaf no-public-keys {
           description "Disables ssh public key based authentication";
           type empty;
         }
         leaf allow-tcp-forwarding {
           description "Allow forwarding TCP connections via SSH";
           type empty;
         }
         leaf-list protocol-version {
           ordered-by user;
           description "Specify ssh protocol versions supported";
           type enumeration {
             enum "v2" {
               description "Version 2 ssh protocol";
             }
           }
         }
         leaf max-sessions-per-connection {
           description "Maximum number of sessions per single SSH connection";
           type union {
             type string {
               pattern "<.*>|$.*";
             }
             type int32 {
               range "1 .. 65535";
             }
           }
         }
         leaf max-pre-authentication-packets {
           description "Maximum number of pre-authentication SSH packets per single SSH connection";
           type union {
             type string {
               pattern "<.*>|$.*";
             }
             type int32 {
               range "20 .. 2147483647";
             }
           }
         }
         leaf sftp-server {
           description "Globally enable incoming SFTP connections";
           type empty;
         }
         leaf-list ciphers {
           ordered-by user;
           description "Specify the ciphers allowed for protocol version 2";
           type enumeration {
             enum "3des-cbc" {
               description "Triple DES in CBC mode";
             }
             enum "aes128-cbc" {
               description "128-bit AES with Cipher Block Chaining";
             }
             enum "aes192-cbc" {
               description "192-bit AES with Cipher Block Chaining";
             }
             enum "aes256-cbc" {
               description "256-bit AES with Cipher Block Chaining";
             }
             enum "aes128-ctr" {
               description "128-bit AES with Counter Mode";
             }
             enum "aes192-ctr" {
               description "192-bit AES with Counter Mode";
             }
             enum "aes256-ctr" {
               description "256-bit AES with Counter Mode";
             }
             enum "aes128-gcm@openssh.com" {
               description "128-bit AES with Galois/Counter Mode";
             }
             enum "aes256-gcm@openssh.com" {
               description "256-bit AES with Galois/Counter Mode";
             }
             enum "chacha20-poly1305@openssh.com" {
               description "ChaCha20 stream cipher and Poly1305 MAC";
             }
           }
         }
         leaf-list ca-signature-algorithms {
           ordered-by user;
           description "Specifies algorithms allowed for signing of certificates by certificate authorities (CAs)";
           type enumeration {
             enum "ssh-ed25519" {
               description "Use ed25519 algorithm to sign certificates";
             }
             enum "ecdsa-sha2-nistp256" {
               description "Use ecdsa-sha2-nistp256 algorithm to sign certificates";
             }
             enum "ecdsa-sha2-nistp384" {
               description "Use ecdsa-sha2-nistp384 algorithm to sign certificates";
             }
             enum "ecdsa-sha2-nistp521" {
               description "Use ecdsa-sha2-nistp521 algorithm to sign certificates";
             }
             enum "rsa-sha2-256" {
               description "Use rsa-sha2-256 algorithm to sign certificates";
             }
             enum "rsa-sha2-512" {
               description "Use rsa-sha2-512 algorithm to sign certificates";
             }
           }
         }
         leaf-list macs {
           ordered-by user;
           description "Message Authentication Code algorithms allowed (SSHv2)";
           type enumeration {
             enum "hmac-md5" {
               description "Hash-based MAC using Message-Digest 5 (MD5)";
             }
             enum "hmac-md5-etm@openssh.com" {
               description "Hash-based Encrypt-then-MAC using Message-Digest 5 (MD5)";
             }
             enum "hmac-sha1" {
               description "Hash-based MAC using Secure Hash Algorithm (SHA1)";
             }
             enum "hmac-sha1-etm@openssh.com" {
               description "Hash-based Encrypt-then-MAC using Secure Hash Algorithm (SHA1)";
             }
             enum "umac-64@openssh.com" {
               description "UMAC-64 algorithm specified in RFC4418";
             }
             enum "umac-128@openssh.com" {
               description "UMAC-128 algorithm specified in RFC4418";
             }
             enum "umac-64-etm@openssh.com" {
               description "Encrypt-then-MAC using UMAC-64 algorithm specified in RFC4418";
             }
             enum "umac-128-etm@openssh.com" {
               description "Encrypt-then-MAC using UMAC-128 algorithm specified in RFC4418";
             }
             enum "hmac-sha2-256" {
               description "Hash-based MAC using Secure Hash Algorithm (SHA2)";
             }
             enum "hmac-sha2-256-etm@openssh.com" {
               description "Hash-based Encrypt-then-Mac using Secure Hash Algorithm (SHA2)";
             }
             enum "hmac-sha2-512" {
               description "Hash-based MAC using Secure Hash Algorithm (SHA2)";
             }
             enum "hmac-sha2-512-etm@openssh.com" {
               description "Hash-based Encrypt-then-Mac using Secure Hash Algorithm (SHA2)";
             }
             enum "hmac-sha1-96" {
               description "96-bits of Hash-based MAC using SHA1";
             }
             enum "hmac-sha1-96-etm@openssh.com" {
               description "96-bits of Hash-based Encrypt-then-MAC using SHA1";
             }
             enum "hmac-md5-96" {
               description "96-bits of Hash-based MAC using MD5";
             }
             enum "hmac-md5-96-etm@openssh.com" {
               description "96-bits of Hash-based Encrypt-then-MAC using MD5";
             }
           }
         }
         leaf-list key-exchange {
           ordered-by user;
           description "Specify ssh key-exchange for Diffie-Hellman keys";
           type enumeration {
             enum "curve25519-sha256" {
               description "The EC Diffie-Hellman on Curve25519 with SHA2-256 hash";
             }
             enum "ecdh-sha2-nistp256" {
               description "The EC Diffie-Hellman on nistp256 with SHA2-256";
             }
             enum "ecdh-sha2-nistp384" {
               description "The EC Diffie-Hellman on nistp384 with SHA2-384";
             }
             enum "ecdh-sha2-nistp521" {
               description "The EC Diffie-Hellman on nistp521 with SHA2-512";
             }
             enum "group-exchange-sha2" {
               description "The RFC 4419 group exchange with SHA2-256 hash";
             }
             enum "group-exchange-sha1" {
               description "The RFC 4419 group exchange with SHA1 hash";
             }
             enum "dh-group14-sha1" {
               description "The RFC 4253 mandated group14 with SHA1 hash";
             }
             enum "dh-group1-sha1" {
               description "The RFC 4253 mandated group1 with SHA1 hash";
             }
             enum "dh-group16-sha512" {
               description "The RFC 8268 group16 with SHA512 hash";
             }
             enum "dh-group18-sha512" {
               description "The RFC 8268 group18 with SHA512 hash";
             }
           }
         }
         leaf client-alive-count-max {
           description "Threshold of missing client-alive responses that triggers a disconnect";
           default "3";
           type union {
             type string {
               pattern "<.*>|$.*";
             }
             type uint32 {
               range "0 .. 255";
             }
           }
         }
         leaf client-alive-interval {
           description "Frequency of client-alive requests";
           default "0";
           units "seconds";
           type union {
             type string {
               pattern "<.*>|$.*";
             }
             type uint32 {
               range "0 .. 65535";
             }
           }
         }
         container hostkey-algorithm-list {
           presence "enable hostkey-algorithm-list";
           description "Specify permissible SSH host-key algorithms";
           uses apply-advanced;
           leaf rsa {
             description "Allow use of RSA SHA1 based host-key";
             status deprecated;
             type empty;
           }
           leaf rsa-sha2-256 {
             description "Allow use of RSA SHA2-256 based host-key";
             type empty;
           }
           leaf rsa-sha2-512 {
             description "Allow use of RSA SHA2-512 based host-key";
             type empty;
           }
           leaf ecdsa-sha2-nistp256 {
             description "Allow use of ECDSA host-key with NIST P-256 curve";
             type empty;
           }
           leaf ecdsa-sha2-nistp384 {
             description "Allow use of ECDSA host-key with NIST P-384 curve";
             type empty;
           }
           leaf ecdsa-sha2-nistp521 {
             description "Allow use of ECDSA host-key with NIST P-521 curve";
             type empty;
           }
           leaf ed25519 {
             description "Allow use of EdDSA host-key with curve25519";
             type empty;
           }
         }
         leaf fingerprint-hash {
           description "Configure hash algorithm used when displaying key fingerprints";
           type enumeration {
             enum "sha2-256" {
               description "Enable use of SHA2-256";
             }
             enum "md5" {
               description "Enable use of MD5";
             }
           }
         }
         leaf authorized-keys-command {
           description "Specifies a command string to be used to look up the user's public keys";
           type string {
             length "1 .. 1024";
           }
         }
         leaf authorized-keys-command-user {
           description "Specifies the user under whose account the authorized-keys-command is run";
           type string {
             length "1 .. 256";
           }
         }
         container rekey {
           description "Limits before session keys are renegotiated";
           uses apply-advanced;
           leaf data-limit {
             description "Data limit before renegotiating session keys";
             units "bytes";
             type string;
           }
           leaf time-limit {
             description "Time limit before renegotiating session keys";
             units "minutes";
             type union {
               type string {
                 pattern "<.*>|$.*";
               }
               type uint32 {
                 range "1 .. 1440";
               }
             }
           }
         }
         leaf port {
           description "Port number to accept incoming connections";
           default "22";
           type union {
             type string {
               pattern "<.*>|$.*";
             }
             type uint32 {
               range "1 .. 65535";
             }
           }
         }
         leaf log-key-changes {
           description "Log changes to authorized keys to syslog";
           type empty;
         }
         leaf connection-limit {
           description "Limit number of simultaneous connections";
           default "75";
           units "connections";
           type union {
             type string {
               pattern "<.*>|$.*";
             }
             type uint32 {
               range "1 .. 250";
             }
           }
         }
         leaf rate-limit {
           description "Limit incoming connection rate";
           default "150";
           units "connections per minute";
           type union {
             type string {
               pattern "<.*>|$.*";
             }
             type uint32 {
               range "1 .. 250";
             }
           }
         }
       }
       container finger {
         presence "enable finger";
         description "Allow finger requests from remote systems";
         uses apply-advanced;
         leaf connection-limit {
           description "Limit number of simultaneous connections";
           default "75";
           units "connections";
           type union {
             type string {
               pattern "<.*>|$.*";
             }
             type uint32 {
               range "1 .. 250";
             }
           }
         }
         leaf rate-limit {
           description "Limit incoming connection rate";
           default "150";
           units "connections per minute";
           type union {
             type string {
               pattern "<.*>|$.*";
             }
             type uint32 {
               range "1 .. 250";
             }
           }
         }
       }
       container ftp {
         presence "enable ftp";
         description "Allow FTP file transfers";
         uses apply-advanced;
         leaf connection-limit {
           description "Limit number of simultaneous connections";
           default "75";
           units "connections";
           type union {
             type string {
               pattern "<.*>|$.*";
             }
             type uint32 {
               range "1 .. 250";
             }
           }
         }
         leaf rate-limit {
           description "Limit incoming connection rate";
           default "150";
           units "connections per minute";
           type union {
             type string {
               pattern "<.*>|$.*";
             }
             type uint32 {
               range "1 .. 250";
             }
           }
         }
         leaf-list authentication-order {
           ordered-by user;
           type enumeration {
             enum "radius" {
               description "Remote Authentication Dial-In User Service";
             }
             enum "tacplus" {
               description "TACACS+ authentication services";
             }
             enum "password" {
               description "Traditional password authentication";
             }
           }
         }
         leaf enable-anonymous-login {
           description "To enable anonymous login";
           type empty;
         }
       }
       container telnet {
         presence "enable telnet";
         description "Allow telnet login";
         uses apply-advanced;
         leaf connection-limit {
           description "Limit number of simultaneous connections";
           default "75";
           units "connections";
           type union {
             type string {
               pattern "<.*>|$.*";
             }
             type uint32 {
               range "1 .. 250";
             }
           }
         }
         leaf rate-limit {
           description "Limit incoming connection rate";
           default "150";
           units "connections per minute";
           type union {
             type string {
               pattern "<.*>|$.*";
             }
             type uint32 {
               range "1 .. 250";
             }
           }
         }
         leaf-list authentication-order {
           ordered-by user;
           type enumeration {
             enum "radius" {
               description "Remote Authentication Dial-In User Service";
             }
             enum "tacplus" {
               description "TACACS+ authentication services";
             }
             enum "password" {
               description "Traditional password authentication";
             }
           }
         }
       }
       container xnm-clear-text {
         presence "enable xnm-clear-text";
         description "Allow clear text-based JUNOScript connections";
         uses apply-advanced;
         leaf connection-limit {
           description "Limit number of simultaneous connections";
           default "75";
           units "connections";
           type union {
             type string {
               pattern "<.*>|$.*";
             }
             type uint32 {
               range "1 .. 250";
             }
           }
         }
         leaf rate-limit {
           description "Limit incoming connection rate";
           default "150";
           units "connections per minute";
           type union {
             type string {
               pattern "<.*>|$.*";
             }
             type uint32 {
               range "1 .. 250";
             }
           }
         }
       }
       container xnm-ssl {
         presence "enable xnm-ssl";
         description "Allow SSL-based JUNOScript connections";
         uses apply-advanced;
         leaf local-certificate {
           description "Name of local X.509 certificate to use";
           type string;
         }
         choice ssl-renegotiation-choice {
           leaf ssl-renegotiation {
             description "Allow SSL renegotiation";
             type empty;
           }
           leaf no-ssl-renegotiation {
             description "Don't allow SSL renegotiation";
             type empty;
           }
         }
         leaf connection-limit {
           description "Limit number of simultaneous connections";
           default "75";
           units "connections";
           type union {
             type string {
               pattern "<.*>|$.*";
             }
             type uint32 {
               range "1 .. 250";
             }
           }
         }
         leaf rate-limit {
           description "Limit incoming connection rate";
           default "150";
           units "connections per minute";
           type union {
             type string {
               pattern "<.*>|$.*";
             }
             type uint32 {
               range "1 .. 250";
             }
           }
         }
       }
       container jeb {
         presence "enable jeb";
         description "Configure the Juniper Juniper Entropy Beacon service";
         uses apply-advanced;
         leaf port {
           description "JEB Service port";
           default "57005";
           type union {
             type string {
               pattern "<.*>|$.*";
             }
             type uint32 {
               range "1025 .. 65535";
             }
           }
         }
         leaf rbg {
           description "Random Bit Generator";
           type enumeration {
             enum "default-rng" {
               description "Default CSPRNG";
             }
             enum "hmac-drbg" {
               description "HMAC DRBG, NIST SP800-90A";
             }
             enum "jrbc" {
               description "Juniper Random Bit Conditioner";
             }
           }
         }
         leaf max-seed-size {
           description "Maximum allowed size for a requested seed";
           default "4096";
           type union {
             type string {
               pattern "<.*>|$.*";
             }
             type uint32 {
               range "1 .. 65536";
             }
           }
         }
         container tls {
           presence "enable tls";
           description "Configure TLS Attributes for JEB Service";
           uses apply-advanced;
           leaf cert-bundle {
             description "Certificate Bundle File";
             type string;
           }
           leaf certificate {
             description "TLS Server Certificate";
             type string;
           }
           leaf key {
             description "Private Key File";
             type string;
           }
         }
       }
       container extension-service {
         description "Enable JUNOS extension services";
         uses apply-advanced;
         container request-response {
           description "Allow request-response API execution";
           uses apply-advanced;
           container grpc {
             description "Grpc server configuration";
             uses apply-advanced;
             choice request-response-type {
               case case_1 {
                 container ssl {
                   description "SSL based API connection settings";
                   uses apply-advanced;
                   leaf address {
                     description "Address to listen for incoming connections";
                     default "::";
                     type jt:ipaddr;
                   }
                   leaf port {
                     description "Port number to accept incoming connections";
                     default "32767";
                     type union {
                       type string {
                         pattern "<.*>|$.*";
                       }
                       type uint32 {
                         range "1 .. 65535";
                       }
                     }
                   }
                   leaf-list local-certificate {
                     ordered-by user;
                     description "Name of local X.509 certificate to use";
                     type string;
                   }
                   container mutual-authentication {
                     description "Enable TLS mutual authentication";
                     uses apply-advanced;
                     leaf certificate-authority {
                       description "Certificate authority profile";
                       type string {
                       }
                     }
                     leaf client-certificate-request {
                       description "Specify requirements for client certificate";
                       default "require-certificate-and-verify";
                       type enumeration {
                         enum "no-certificate" {
                           description "Client certificate is not requested";
                         }
                         enum "request-certificate" {
                           description "Request certificate from client, do not verify";
                         }
                         enum "request-certificate-and-verify" {
                           description "Request certificate from client, verify if provided";
                         }
                         enum "require-certificate" {
                           description "Client certificate is mandatory, do not verify";
                         }
                         enum "require-certificate-and-verify" {
                           description "Client certificate is mandatory, certificate is verified";
                         }
                       }
                     }
                   }
                   leaf hot-reloading {
                     description "Enable certificate reload without terminating existing gRPC sessions";
                     type empty;
                   }
                   leaf use-pki {
                     description "Use local-certificate loaded via pki hierarchy";
                     type empty;
                   }
                 }
               }
             }
             leaf max-connections {
               description "Maximum number of connections";
               default "5";
               type union {
                 type string {
                   pattern "<.*>|$.*";
                 }
                 type uint32 {
                   range "1 .. 30";
                 }
               }
             }
             leaf routing-instance {
               description "Routing instance for grpc";
               type string {
               }
             }
             leaf grpc-keep-alive {
               description "GRPC keep alive duration in seconds";
               default "300";
               units "seconds";
               type union {
                 type string {
                   pattern "<.*>|$.*";
                 }
                 type uint32 {
                   range "0 .. 4294967295";
                 }
               }
             }
           }
         }
         container notification {
           presence "enable notification";
           description "Enable Notification Services";
           uses apply-advanced;
           leaf port {
             description "Port number to accept incoming connections";
             default "1883";
             type union {
               type string {
                 pattern "<.*>|$.*";
               }
               type uint32 {
                 range "1 .. 65535";
               }
             }
           }
           leaf max-connections {
             description "Maximum number of connections";
             default "20";
             type union {
               type string {
                 pattern "<.*>|$.*";
               }
               type uint32 {
                 range "1 .. 20";
               }
             }
           }
           leaf broker-socket-send-buffer-size {
             description "Socket send buffer size for the broker to publish the messages";
             default "65536";
             type union {
               type uint32;
               type string {
                 pattern "<.*>|$.*";
               }
             }
           }
           container allow-clients {
             description "Client IPs from which notifications are allowed";
             uses apply-advanced;
             leaf-list address {
               ordered-by user;
               description "IPv4/IPv6 addresses, prefix length optional, or hostnames";
               type jt:ipprefix-optional;
             }
           }
         }
         container traceoptions {
           description "Trace options for JSD";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "10";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           container level {
             description "Trace verbosity level";
             choice level-name {
               case case_1 {
                 leaf error {
                   description "Only trace error events";
                   type empty;
                 }
               }
             }
           }
           list flag {
             key name;
             ordered-by user;
             description "Tracing parameters";
             leaf name {
               type enumeration {
                 enum "timer" {
                   description "Trace internal timer events";
                 }
                 enum "timeouts" {
                   description "Trace timeouts ";
                 }
                 enum "routing-socket" {
                   description "Trace routing socket calls";
                 }
                 enum "general" {
                   description "Trace general events";
                 }
                 enum "config" {
                   description "Trace config events";
                 }
                 enum "grpc" {
                   description "Trace grpc related events";
                 }
                 enum "libgrpc-debug" {
                   description "Trace all lib grpc related events";
                 }
                 enum "libgrpc-errors" {
                   description "Trace lib grpc errors";
                 }
                 enum "libgrpc-info" {
                   description "Trace lib grpc info and errors";
                 }
                 enum "notification" {
                   description "Trace notification events";
                 }
                 enum "all" {
                   description "Trace everything";
                 }
               }
             }
           }
         }
       }
       container tftp-server {
         presence "enable tftp-server";
         description "Enable TFTP file transfers";
         uses apply-advanced;
         leaf connection-limit {
           description "Limit number of simultaneous connections";
           default "75";
           units "connections";
           type union {
             type string {
               pattern "<.*>|$.*";
             }
             type uint32 {
               range "1 .. 250";
             }
           }
         }
         leaf rate-limit {
           description "Limit incoming connection rate";
           default "150";
           units "connections per minute";
           type union {
             type string {
               pattern "<.*>|$.*";
             }
             type uint32 {
               range "1 .. 250";
             }
           }
         }
       }
       leaf dtcp-only {
         description "Allow subscriber DTCP based lawful intercept only";
         type empty;
       }
       container http {
         description "HTTP service";
         uses apply-advanced;
         container servers {
           presence "enable servers";
           description "Container for GRPC servers configuration";
           uses apply-advanced;
           list server {
             key name;
             ordered-by user;
             description "GRPC server";
             max-elements 5;
             leaf name {
               description "Name of the GRPC server";
               type string;
             }
             uses apply-advanced;
             leaf-list listen-address {
               ordered-by user;
               description "Address on which server is listening for gRPC connection";
               type jt:ipaddr;
             }
             leaf port {
               description "Port on which server is listening for gRPC connection";
               type union {
                 type string {
                   pattern "<.*>|$.*";
                 }
                 type uint32 {
                   range "1 .. 65535";
                 }
               }
             }
             leaf routing-instance {
               description "Routing instance for server";
               type string {
               }
             }
             leaf-list grpc {
               ordered-by user;
               description "Services supported by gRPC server";
               type enumeration {
                 enum "all-grpc" {
                   description "All GRPC services";
                 }
                 enum "gnmi" {
                   description "GNMI services";
                 }
                 enum "gnoi" {
                   description "GNOI services";
                 }
                 enum "gribi" {
                   description "GRIBI services";
                 }
                 enum "p4" {
                   description "P4 services";
                 }
                 enum "enrollz-attestz" {
                   description "Enrollz and Attestz services";
                 }
               }
             }
             leaf max-connections {
               description "Maximum number of connections";
               default "5";
               type union {
                 type string {
                   pattern "<.*>|$.*";
                 }
                 type uint32 {
                   range "1 .. 30";
                 }
               }
             }
             choice security-type {
               case case_1 {
                 container tls {
                   presence "enable tls";
                   description "TLS configuration";
                   uses apply-advanced;
                   leaf local-certificate {
                     description "Name of local X.509 certificate to use";
                     type string;
                   }
                   container mutual-authentication {
                     presence "enable mutual-authentication";
                     description "Enable TLS mutual authentication";
                     uses apply-advanced;
                     leaf certificate-authority {
                       description "Certificate authority profile";
                       type string {
                       }
                     }
                     leaf authentication-type {
                       description "Specify requirements for client certificate";
                       default "request-and-require-cert-and-verify";
                       type enumeration {
                         enum "dont-request-cert" {
                           description "Client certificate is not requested";
                         }
                         enum "request-cert-but-dont-verify" {
                           description "Request certificate from client, do not verify";
                         }
                         enum "request-cert-and-verify" {
                           description "Request certificate from client, verify if provided";
                         }
                         enum "request-and-require-cert-but-dont-verify" {
                           description "Client certificate is mandatory, do not verify";
                         }
                         enum "request-and-require-cert-and-verify" {
                           description "Client certificate is mandatory, certificate is verified";
                         }
                       }
                     }
                   }
                 }
               }
             }
           }
         }
       }
       container grpc-tunnel {
         description "GRPC tunnel configuration for outbound TCP over gRPC";
         uses apply-advanced;
         container servers {
           description "GRPC tunnel servers configuration";
           uses apply-advanced;
           leaf retry-interval {
             description "Retry interval for unreachable targets";
             default "30";
             units "seconds";
             type union {
               type string {
                 pattern "<.*>|$.*";
               }
               type uint32 {
                 range "10 .. 300";
               }
             }
           }
           list server {
             key name;
             ordered-by user;
             description "List of tunnel servers to be dialled";
             max-elements 10;
             leaf name {
               description "Name of the tunnel server";
               type string {
                 length "1 .. 31";
               }
             }
             uses apply-advanced;
             leaf address {
               description "IP address or hostname of the tunnel server";
               type jt:hostname;
             }
             leaf port {
               description "Port number where gRPC tunnel server is listening";
               type union {
                 type string {
                   pattern "<.*>|$.*";
                 }
                 type uint32 {
                   range "1 .. 65535";
                 }
               }
             }
             leaf-list targets {
               ordered-by user;
               description "Targets to be registered with the tunnel server";
               type enumeration {
                 enum "ssh" {
                   description "Configure SSH to be registered";
                 }
                 enum "netconf-ssh" {
                   description "Configure NETCONF over SSH to be registered";
                 }
                 enum "gnmi-gnoi" {
                   description "Configure gNMI and gNOI to be registered";
                 }
               }
             }
             leaf routing-instance {
               description "Routing instance to be used for tunnel server dial-out";
               type string {
               }
             }
             leaf source-address {
               description "Source address to be used for tunnel server dial-out";
               type jt:ipaddr;
             }
             container credentials {
               description "Credentials to use for gRPC connection";
               uses apply-advanced;
               choice credential-type {
                 case case_1 {
                   container tls {
                     presence "enable tls";
                     description "Configure secure TLS credentials";
                     uses apply-advanced;
                     leaf certificate-id {
                       description "Local certificate ID to be used for gRPC tunnel target";
                       type string {
                       }
                     }
                     leaf-list ca-profiles {
                       ordered-by user;
                       description "List of CA profiles to be used to verify tunnel server";
                       type string;
                     }
                   }
                 }
               }
             }
           }
         }
         container target-string-option {
           description "Option to configure target string for this device";
           uses apply-advanced;
           leaf-list pattern {
             ordered-by user;
             description "Ordered list to build customised target string";
             type enumeration {
               enum "hostname" {
                 description "Hostname of this device";
               }
               enum "vendor" {
                 description "Vendor name";
               }
               enum "model" {
                 description "Hardware model";
               }
               enum "version" {
                 description "Software version";
               }
               enum "custom" {
                 description "Custom string to be used as target string";
               }
             }
           }
           leaf custom-string {
             description "Custom string to be used when 'custom' option is chosen";
             type string {
               length "1 .. 31";
             }
           }
           leaf delimiter {
             description "Delimiter to separate the options under pattern";
             type string {
               length "1 .. 3";
             }
           }
         }
         container traceoptions {
           description "GRPC tunnel trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           list flag {
             key name;
             ordered-by user;
             description "Tracing parameters";
             leaf name {
               type enumeration {
                 enum "general" {
                   description "Log general messages";
                 }
                 enum "grpc-events" {
                   description "Log grpc events with tunnel server";
                 }
                 enum "timer" {
                   description "Log timer events";
                 }
                 enum "config" {
                   description "Log configuration messages";
                 }
                 enum "all" {
                   description "Log all the messages";
                 }
               }
             }
           }
         }
       }
       container inband-ztp {
         presence "enable inband-ztp";
         description "Enable in-band ZTP";
         uses apply-advanced;
         leaf management-vlan-id {
           description "Management vlan id";
           type union {
             type string {
               pattern "<.*>|$.*";
             }
             type uint32 {
               range "1 .. 4094";
             }
           }
         }
         container traceoptions {
           description "Inband ztp trace options";
           uses apply-advanced;
           leaf file {
             description "Log file name";
             type string;
           }
           leaf level {
             description "Inband-ztp log level";
             type enumeration {
               enum "nolog" {
                 description "Disable inband-ztp log";
               }
               enum "debug" {
                 description "Debug level";
               }
               enum "info" {
                 description "Info level";
               }
               enum "warning" {
                 description "Warning level";
               }
               enum "error" {
                 description "Error level";
               }
               enum "critical" {
                 description "Critical level";
               }
             }
           }
         }
         leaf-list name-server {
           ordered-by user;
           description "DNS name server address";
           type jt:ipaddr;
         }
       }
       container rest {
         description "Allow RPC execution over HTTP(S) connection";
         uses apply-advanced;
         container http {
           presence "enable http";
           description "Unencrypted HTTP connection settings";
           uses apply-advanced;
           leaf port {
             description "Port number to accept HTTP connections";
             default "3000";
             type union {
               type string {
                 pattern "<.*>|$.*";
               }
               type uint32 {
                 range "1024 .. 65535";
               }
             }
           }
           leaf-list addresses {
             ordered-by user;
             description "List of addresses to listen for incoming connections";
             type jt:ipaddr;
           }
         }
         container https {
           description "Encrypted HTTPS connections";
           uses apply-advanced;
           leaf port {
             description "Port number to accept HTTPS connections";
             default "3443";
             type union {
               type string {
                 pattern "<.*>|$.*";
               }
               type uint32 {
                 range "1024 .. 65535";
               }
             }
           }
           leaf-list addresses {
             ordered-by user;
             description "List of addresses to listen for incoming connections";
             type jt:ipaddr;
           }
           leaf server-certificate {
             description "Local certificate identifier";
             type string {
             }
           }
           leaf ca-chain {
             description "Certificate authority chain profile";
             type string {
             }
           }
           leaf-list cipher-list {
             ordered-by user;
             description "List of allowed cipher suites in order of preference";
             type enumeration {
               enum "rsa-with-rc4-128-md5" {
                 description "RSA, 128bit rc4, md5 hash";
               }
               enum "rsa-with-rc4-128-sha" {
                 description "RSA, 128bit rc4, sha hash";
               }
               enum "rsa-with-3des-ede-cbc-sha" {
                 description "RSA, 3des ede/cbc, sha hash";
               }
               enum "dhe-rsa-with-3des-ede-cbc-sha" {
                 description "DHE/rsa, 3es/ede cbc, sha hash";
               }
               enum "rsa-with-aes-128-cbc-sha" {
                 description "RSA, 128 bit aes/cbc, sha hash";
               }
               enum "dhe-rsa-with-aes-128-cbc-sha" {
                 description "DHE/rsa, 128 bit aes/cbc, sha hash";
               }
               enum "rsa-with-aes-256-cbc-sha" {
                 description "RSA, 256 bit aes/cbc, sha hash";
               }
               enum "dhe-rsa-with-aes-256-cbc-sha" {
                 description "DHE/rsa, 256 bit aes/cbc, sha hash";
               }
               enum "ecdhe-rsa-with-rc4-128-sha" {
                 description "ECDHE/rsa, 128 bit rc4, sha hash";
               }
               enum "ecdhe-rsa-with-3des-ede-cbc-sha" {
                 description "ECDHE/rsa, 128bit 3des ede/cbc sha hash";
               }
               enum "ecdhe-rsa-with-aes-128-cbc-sha" {
                 description "ECDHE/rsa, 128 bit aes/cbc, sha hash";
               }
               enum "ecdhe-rsa-with-aes-256-cbc-sha" {
                 description "ECDHE/rsa, 256 bit aes/cbc, sha hash";
               }
               enum "rsa-with-aes-128-cbc-sha256" {
                 description "RSA, 128 bit aes/cbc, sha256 hash ";
               }
               enum "rsa-with-aes-256-cbc-sha256" {
                 description "RSA, 256 bit aes/cbc, sha256 hash";
               }
               enum "dhe-rsa-with-aes-128-cbc-sha256" {
                 description "DHE/rsa, 128 bit aes/cbc, sha256 hash";
               }
               enum "dhe-rsa-with-aes-256-cbc-sha256" {
                 description "DHE/rsa, 256 bit aes/cbc, sha256 hash";
               }
               enum "rsa-with-aes-128-gcm-sha256" {
                 description "RSA, 128 bit aes/gcm, sha256 hash";
               }
               enum "rsa-with-aes-256-gcm-sha384" {
                 description "RSA, 256 bit aes/gcm, sha384 hash";
               }
               enum "dhe-rsa-with-aes-128-gcm-sha256" {
                 description "DHE/rsa, 128 bit aes/gcm, sha256 hash";
               }
               enum "dhe-rsa-with-aes-256-gcm-sha384" {
                 description "DHE/rsa, 256 bit aes/gcm, sha384 hash";
               }
               enum "ecdhe-rsa-with-aes-128-cbc-sha256" {
                 description "ECDHE/rsa, 128 bit aes/cbc, sha256 hash";
               }
               enum "ecdhe-rsa-with-aes-256-cbc-sha384" {
                 description "ECDHE/rsa, 256 bit aes/cbc, sha384 hash";
               }
               enum "ecdhe-rsa-with-aes-128-gcm-sha256" {
                 description "ECDHE/rsa, 128 bit aes/gcm, sha256 hash";
               }
               enum "ecdhe-rsa-with-aes-256-gcm-sha384" {
                 description "ECDHE/rsa, 256 bit aes/gcm, sha384 hash";
               }
               enum "tls-aes-128-gcm-sha256" {
                 description "128 bit aes/gcm, sha256 hash";
               }
               enum "tls-aes-256-gcm-sha384" {
                 description "256 bit aes/gcm, sha384 hash";
               }
             }
           }
           container mutual-authentication {
             description "Enable TLS mutual authentication";
             uses apply-advanced;
             leaf certificate-authority {
               description "Certificate authority profile";
               type string {
               }
             }
           }
         }
         container https-5g {
           description "Encrypted HTTPS connections";
           uses apply-advanced;
           leaf port {
             description "Port number to accept HTTPS connections";
             default "3443";
             type union {
               type string {
                 pattern "<.*>|$.*";
               }
               type uint32 {
                 range "1024 .. 65535";
               }
             }
           }
           leaf-list addresses {
             ordered-by user;
             description "List of addresses to listen for incoming connections";
             type jt:ipv4addr;
           }
           leaf server-certificate {
             description "Local certificate identifier";
             type string {
             }
           }
           container mutual-authentication {
             description "Enable TLS mutual authentication";
             uses apply-advanced;
             leaf certificate-authority {
               description "Certificate authority profile";
               type string {
               }
             }
           }
         }
         container control {
           description "Control of the rest-api process";
           uses apply-advanced;
           leaf-list allowed-sources {
             ordered-by user;
             description "List of allowed source IP addresses";
             type jt:ipv4addr;
           }
           leaf connection-limit {
             description "Maximum number of simultaneous connections";
             type union {
               type string {
                 pattern "<.*>|$.*";
               }
               type int32;
             }
           }
         }
         container traceoptions {
           description "Trace options for rest-api service";
           uses apply-advanced;
           leaf flag {
             description "Area to enable tracing";
             type enumeration {
               enum "lighttpd" {
                 description "Enable tracing for lighttpd";
               }
               enum "juise" {
                 description "Enable tracing for JUISE";
               }
               enum "all" {
                 description "Enable all traces";
               }
             }
           }
         }
         leaf enable-explorer {
           description "Enable REST API explorer tool";
           type empty;
         }
         leaf routing-instance {
           description "Routing instance";
           type string {
           }
         }
       }
       container dhcp-local-server {
         description "Dynamic Host Configuration Protocol server configuration";
         uses jdhcp-local-server-type;
       }
       container database-replication {
         description "Database replication configuration";
         uses bdbrepd-type;
       }
       container web-management {
         description "Web management configuration";
         uses apply-advanced;
         container traceoptions {
           description "Web management trace options";
           uses httpd_traceoptions_type;
         }
         leaf management-url {
           description "URL path for web management access";
           type string;
         }
         container https {
           presence "enable https";
           description "Encrypted HTTPS connections";
           uses apply-advanced;
           leaf port {
             description "TCP port for incoming HTTPS connections";
             default "443";
             type union {
               type string {
                 pattern "<.*>|$.*";
               }
               type uint16 {
                 range "1 .. 65535";
               }
             }
           }
           choice certificate-choice {
             case case_1 {
               leaf local-certificate {
                 description "X.509 certificate to use (from configuration)";
                 type string;
               }
             }
             case case_2 {
               leaf pki-local-certificate {
                 description "X.509 certificate to use (from PKI local store)";
                 type string {
                 }
               }
             }
             case case_3 {
               leaf system-generated-certificate {
                 description "X.509 certificate generated automatically by system";
                 type empty;
               }
             }
           }
           leaf-list interface {
             ordered-by user;
             description "Interfaces that accept HTTPS access";
             type union {
               type jt:interface-name;
               type string {
                 pattern "<.*>|$.*";
               }
             }
           }
           list virtual-domain {
             key name;
             ordered-by user;
             description "Domain to certificate mapping";
             leaf name {
               description "FQDN i.e. host.domain.com (subjectAltName)";
               type string {
                 length "1 .. 250";
               }
             }
             uses apply-advanced;
             leaf pki-local-certificate {
               description "X.509 certificate to use (from PKI local store)";
               type string {
                 length "1 .. 32";
               }
             }
             container mtls {
               description "Mutual-Authentication parameters";
               uses apply-advanced;
               leaf port {
                 description "HTTPS-mTLS listening port";
                 type union {
                   type string {
                     pattern "<.*>|$.*";
                   }
                   type int32 {
                     range "1024 .. 65535";
                   }
                 }
               }
               leaf ca-profile {
                 description "CA profiles for validating client-certificate";
                 type string {
                 }
               }
               list firewall-authentication-profile {
                 key name;
                 description "Firewall-authentication profiles";
                 max-elements 10;
                 leaf name {
                   type string;
                 }
                 uses apply-advanced;
               }
             }
           }
         }
         container control {
           description "Control of the web management process";
           uses apply-advanced;
           leaf max-threads {
             description "Maximum simultaneous threads to handle requests";
             default "5";
             type union {
               type string {
                 pattern "<.*>|$.*";
               }
               type uint32 {
                 range "0 .. 16";
               }
             }
           }
         }
         container session {
           description "Session parameters";
           uses apply-advanced;
           leaf idle-timeout {
             description "Default timeout of web-management sessions";
             default "30";
             units "minutes";
             type union {
               type string {
                 pattern "<.*>|$.*";
               }
               type uint32 {
                 range "1 .. 1440";
               }
             }
           }
           leaf session-limit {
             description "Maximum number of web-management sessions to allow";
             type union {
               type string {
                 pattern "<.*>|$.*";
               }
               type uint32 {
                 range "1 .. 1024";
               }
             }
           }
         }
       }
       container static-subscribers {
         description "Static Subscriber Client configuration";
         uses jsscd-static-subscribers-type;
       }
       container subscriber-management {
         description "Subscriber management configuration";
         uses smid-type;
       }
       container resource-monitor {
         description "Resource monitor configuration";
         uses resource-monitor-type;
       }
       container dhcp {
         description "Configure DHCP server";
         uses apply-advanced;
         leaf maximum-lease-time {
           description "Maximum lease time advertised to clients";
           units "seconds";
           type string;
         }
         leaf default-lease-time {
           description "Default lease time advertised to clients";
           units "seconds";
           type string;
         }
         leaf domain-name {
           description "Domain name advertised to clients";
           type string {
             length "1 .. 254";
           }
         }
         list name-server {
           key name;
           ordered-by user;
           description "Domain name servers available to the client";
           leaf name {
             description "DNS server's IPv4 address";
             type jt:ipv4addr;
           }
           uses apply-advanced;
         }
         list domain-search {
           key name;
           ordered-by user;
           description "Domain search list used to resolve hostnames";
           leaf name {
             description "DNS search suffix";
             type string;
           }
           uses apply-advanced;
         }
         list wins-server {
           key name;
           ordered-by user;
           description "NetBIOS name servers";
           leaf name {
             description "WINS server's IPv4 address";
             type jt:ipv4addr;
           }
           uses apply-advanced;
         }
         list router {
           key name;
           ordered-by user;
           description "Routers advertised to clients";
           leaf name {
             description "Router's IPv4 address";
             type jt:ipv4addr;
           }
           uses apply-advanced;
         }
         leaf boot-file {
           description "Boot filename advertised to clients";
           type string;
         }
         leaf boot-server {
           description "Boot server advertised to clients";
           type string {
           }
         }
         leaf next-server {
           description "Next server that clients need to contact";
           type jt:ipv4addr;
         }
         leaf server-identifier {
           description "DHCP server identifier advertised to clients";
           type jt:ipv4addr;
         }
         list option {
           key name;
           ordered-by user;
           description "DHCP option";
           leaf name {
             description "DHCP option identifier code";
             type union {
               type string {
                 pattern "<.*>|$.*";
               }
               type uint32 {
                 range "1 .. 255";
               }
             }
           }
           choice option-type-choice {
             case case_1 {
               leaf flag {
                 description "Boolean flag value";
                 type enumeration {
                   enum "true" {
                     description "True value";
                   }
                   enum "false" {
                     description "False value";
                   }
                   enum "on" {
                     description "On value";
                   }
                   enum "off" {
                     description "Off value";
                   }
                 }
               }
             }
             case case_2 {
               leaf byte {
                 description "Unsigned 8-bit value";
                 type union {
                   type uint8;
                   type string {
                     pattern "<.*>|$.*";
                   }
                 }
               }
             }
             case case_3 {
               leaf short {
                 description "Signed 16-bit numeric value";
                 type union {
                   type int16;
                   type string {
                     pattern "<.*>|$.*";
                   }
                 }
               }
             }
             case case_4 {
               leaf unsigned-short {
                 description "Unsigned 16-bit numeric value";
                 type union {
                   type uint16;
                   type string {
                     pattern "<.*>|$.*";
                   }
                 }
               }
             }
             case case_5 {
               leaf integer {
                 description "Signed 32-bit numeric value";
                 type union {
                   type int32;
                   type string {
                     pattern "<.*>|$.*";
                   }
                 }
               }
             }
             case case_6 {
               leaf unsigned-integer {
                 description "Unsigned 32-bit numeric value";
                 type union {
                   type uint32;
                   type string {
                     pattern "<.*>|$.*";
                   }
                 }
               }
             }
             case case_7 {
               leaf string {
                 description "Character string value";
                 type string {
                   length "1 .. 254";
                 }
               }
             }
             case case_8 {
               leaf ip-address {
                 description "IP address value";
                 type jt:ipv4addr;
               }
             }
             case case_9 {
               container array {
                 presence "enable array";
                 description "Array of values";
                 uses apply-advanced;
                 choice option-type-array-choice {
                   case case_1 {
                     leaf-list flag {
                       ordered-by user;
                       description "Array of boolean flag values";
                       type enumeration {
                         enum "true" {
                           description "True value";
                         }
                         enum "false" {
                           description "False value";
                         }
                         enum "on" {
                           description "On value";
                         }
                         enum "off" {
                           description "Off value";
                         }
                       }
                     }
                   }
                   case case_2 {
                     leaf-list byte {
                       ordered-by user;
                       description "Array of unsigned 8-bit values";
                       type union {
                         type uint8;
                         type string {
                           pattern "<.*>|$.*";
                         }
                       }
                     }
                   }
                   case case_3 {
                     leaf-list short {
                       ordered-by user;
                       description "Array of signed 16-bit numeric values";
                       type union {
                         type int16;
                         type string {
                           pattern "<.*>|$.*";
                         }
                       }
                     }
                   }
                   case case_4 {
                     leaf-list unsigned-short {
                       ordered-by user;
                       description "Array of 16-bit numeric values";
                       type union {
                         type uint16;
                         type string {
                           pattern "<.*>|$.*";
                         }
                       }
                     }
                   }
                   case case_5 {
                     leaf-list integer {
                       ordered-by user;
                       description "Array of signed 32-bit numeric values";
                       type union {
                         type int32;
                         type string {
                           pattern "<.*>|$.*";
                         }
                       }
                     }
                   }
                   case case_6 {
                     leaf-list unsigned-integer {
                       ordered-by user;
                       description "Array of unsigned 32-bit numeric values";
                       type union {
                         type uint32;
                         type string {
                           pattern "<.*>|$.*";
                         }
                       }
                     }
                   }
                   case case_7 {
                     leaf-list string {
                       ordered-by user;
                       description "Array of character string values";
                       type string {
                         length "1 .. 254";
                       }
                     }
                   }
                   case case_8 {
                     leaf-list ip-address {
                       ordered-by user;
                       description "Array of IP address values";
                       type jt:ipv4addr;
                     }
                   }
                 }
               }
             }
             case case_10 {
               leaf byte-stream {
                 description "Stream of unsigned 8-bit values within quotes";
                 type string;
               }
             }
           }
         }
         container sip-server {
           description "SIP servers to clients";
           uses apply-advanced;
           list name {
             key name;
             ordered-by user;
             description "Names of SIP servers";
             leaf name {
               description "SIP server name";
               type string;
             }
             uses apply-advanced;
           }
           list address {
             key name;
             ordered-by user;
             description "IP addresses of SIP servers";
             leaf name {
               description "SIP server's IPv4 address";
               type jt:ipv4addr;
             }
             uses apply-advanced;
           }
         }
         container traceoptions {
           description "DHCP server trace options";
           uses dhcp-traceoptions-type;
         }
         list pool {
           key name;
           ordered-by user;
           description "DHCP address pool";
           leaf name {
             description "Logical subnet address/netmask";
             type jt:ipprefix;
           }
           uses apply-advanced;
           container address-range {
             presence "enable address-range";
             description "Range of addresses to choose from";
             leaf low {
               description "Lowest address in the range";
               type jt:ipv4addr;
             }
             leaf high {
               description "Highest address in the range";
               type jt:ipv4addr;
             }
           }
           list exclude-address {
             key name;
             ordered-by user;
             description "Address to exclude from pool";
             leaf name {
               description "IPv4 address";
               type jt:ipv4addr;
             }
             uses apply-advanced;
           }
           leaf maximum-lease-time {
             description "Maximum lease time advertised to clients";
             units "seconds";
             type string;
           }
           leaf default-lease-time {
             description "Default lease time advertised to clients";
             units "seconds";
             type string;
           }
           leaf domain-name {
             description "Domain name advertised to clients";
             type string {
               length "1 .. 254";
             }
           }
           list name-server {
             key name;
             ordered-by user;
             description "Domain name servers available to the client";
             leaf name {
               description "DNS server's IPv4 address";
               type jt:ipv4addr;
             }
             uses apply-advanced;
           }
           list domain-search {
             key name;
             ordered-by user;
             description "Domain search list used to resolve hostnames";
             leaf name {
               description "DNS search suffix";
               type string;
             }
             uses apply-advanced;
           }
           list wins-server {
             key name;
             ordered-by user;
             description "NetBIOS name servers";
             leaf name {
               description "WINS server's IPv4 address";
               type jt:ipv4addr;
             }
             uses apply-advanced;
           }
           list router {
             key name;
             ordered-by user;
             description "Routers advertised to clients";
             leaf name {
               description "Router's IPv4 address";
               type jt:ipv4addr;
             }
             uses apply-advanced;
           }
           leaf boot-file {
             description "Boot filename advertised to clients";
             type string;
           }
           leaf boot-server {
             description "Boot server advertised to clients";
             type string {
             }
           }
           leaf next-server {
             description "Next server that clients need to contact";
             type jt:ipv4addr;
           }
           leaf server-identifier {
             description "DHCP server identifier advertised to clients";
             type jt:ipv4addr;
           }
           list option {
             key name;
             ordered-by user;
             description "DHCP option";
             leaf name {
               description "DHCP option identifier code";
               type union {
                 type string {
                   pattern "<.*>|$.*";
                 }
                 type uint32 {
                   range "1 .. 255";
                 }
               }
             }
             choice option-type-choice {
               case case_1 {
                 leaf flag {
                   description "Boolean flag value";
                   type enumeration {
                     enum "true" {
                       description "True value";
                     }
                     enum "false" {
                       description "False value";
                     }
                     enum "on" {
                       description "On value";
                     }
                     enum "off" {
                       description "Off value";
                     }
                   }
                 }
               }
               case case_2 {
                 leaf byte {
                   description "Unsigned 8-bit value";
                   type union {
                     type uint8;
                     type string {
                       pattern "<.*>|$.*";
                     }
                   }
                 }
               }
               case case_3 {
                 leaf short {
                   description "Signed 16-bit numeric value";
                   type union {
                     type int16;
                     type string {
                       pattern "<.*>|$.*";
                     }
                   }
                 }
               }
               case case_4 {
                 leaf unsigned-short {
                   description "Unsigned 16-bit numeric value";
                   type union {
                     type uint16;
                     type string {
                       pattern "<.*>|$.*";
                     }
                   }
                 }
               }
               case case_5 {
                 leaf integer {
                   description "Signed 32-bit numeric value";
                   type union {
                     type int32;
                     type string {
                       pattern "<.*>|$.*";
                     }
                   }
                 }
               }
               case case_6 {
                 leaf unsigned-integer {
                   description "Unsigned 32-bit numeric value";
                   type union {
                     type uint32;
                     type string {
                       pattern "<.*>|$.*";
                     }
                   }
                 }
               }
               case case_7 {
                 leaf string {
                   description "Character string value";
                   type string {
                     length "1 .. 254";
                   }
                 }
               }
               case case_8 {
                 leaf ip-address {
                   description "IP address value";
                   type jt:ipv4addr;
                 }
               }
               case case_9 {
                 container array {
                   presence "enable array";
                   description "Array of values";
                   uses apply-advanced;
                   choice option-type-array-choice {
                     case case_1 {
                       leaf-list flag {
                         ordered-by user;
                         description "Array of boolean flag values";
                         type enumeration {
                           enum "true" {
                             description "True value";
                           }
                           enum "false" {
                             description "False value";
                           }
                           enum "on" {
                             description "On value";
                           }
                           enum "off" {
                             description "Off value";
                           }
                         }
                       }
                     }
                     case case_2 {
                       leaf-list byte {
                         ordered-by user;
                         description "Array of unsigned 8-bit values";
                         type union {
                           type uint8;
                           type string {
                             pattern "<.*>|$.*";
                           }
                         }
                       }
                     }
                     case case_3 {
                       leaf-list short {
                         ordered-by user;
                         description "Array of signed 16-bit numeric values";
                         type union {
                           type int16;
                           type string {
                             pattern "<.*>|$.*";
                           }
                         }
                       }
                     }
                     case case_4 {
                       leaf-list unsigned-short {
                         ordered-by user;
                         description "Array of 16-bit numeric values";
                         type union {
                           type uint16;
                           type string {
                             pattern "<.*>|$.*";
                           }
                         }
                       }
                     }
                     case case_5 {
                       leaf-list integer {
                         ordered-by user;
                         description "Array of signed 32-bit numeric values";
                         type union {
                           type int32;
                           type string {
                             pattern "<.*>|$.*";
                           }
                         }
                       }
                     }
                     case case_6 {
                       leaf-list unsigned-integer {
                         ordered-by user;
                         description "Array of unsigned 32-bit numeric values";
                         type union {
                           type uint32;
                           type string {
                             pattern "<.*>|$.*";
                           }
                         }
                       }
                     }
                     case case_7 {
                       leaf-list string {
                         ordered-by user;
                         description "Array of character string values";
                         type string {
                           length "1 .. 254";
                         }
                       }
                     }
                     case case_8 {
                       leaf-list ip-address {
                         ordered-by user;
                         description "Array of IP address values";
                         type jt:ipv4addr;
                       }
                     }
                   }
                 }
               }
               case case_10 {
                 leaf byte-stream {
                   description "Stream of unsigned 8-bit values within quotes";
                   type string;
                 }
               }
             }
           }
           container sip-server {
             description "SIP servers to clients";
             uses apply-advanced;
             list name {
               key name;
               ordered-by user;
               description "Names of SIP servers";
               leaf name {
                 description "SIP server name";
                 type string;
               }
               uses apply-advanced;
             }
             list address {
               key name;
               ordered-by user;
               description "IP addresses of SIP servers";
               leaf name {
                 description "SIP server's IPv4 address";
                 type jt:ipv4addr;
               }
               uses apply-advanced;
             }
           }
         }
         list static-binding {
           key name;
           ordered-by user;
           description "DHCP client's hardware address";
           leaf name {
             description "Ethernet hardware address belonging to host";
             type jt:mac-addr;
           }
           uses apply-advanced;
           list fixed-address {
             key name;
             ordered-by user;
             description "Possible IP addresses to assign to host";
             leaf name {
               description "IPv4 address";
               type jt:ipaddr;
             }
             uses apply-advanced;
           }
           leaf host-name {
             description "Hostname for this client";
             type string {
             }
           }
           container client-identifier {
             description "Client identifier option";
             choice client-identifier-choice {
               case case_1 {
                 leaf ascii {
                   description "Client identifier as an ASCII string";
                   type string;
                 }
               }
               case case_2 {
                 leaf hexadecimal {
                   description "Client identifier as a hexadecimal string";
                   type string {
                   }
                 }
               }
             }
           }
           leaf domain-name {
             description "Domain name advertised to clients";
             type string {
               length "1 .. 254";
             }
           }
           list name-server {
             key name;
             ordered-by user;
             description "Domain name servers available to the client";
             leaf name {
               description "DNS server's IPv4 address";
               type jt:ipv4addr;
             }
             uses apply-advanced;
           }
           list domain-search {
             key name;
             ordered-by user;
             description "Domain search list used to resolve hostnames";
             leaf name {
               description "DNS search suffix";
               type string;
             }
             uses apply-advanced;
           }
           list wins-server {
             key name;
             ordered-by user;
             description "NetBIOS name servers";
             leaf name {
               description "WINS server's IPv4 address";
               type jt:ipv4addr;
             }
             uses apply-advanced;
           }
           list router {
             key name;
             ordered-by user;
             description "Routers advertised to clients";
             leaf name {
               description "Router's IPv4 address";
               type jt:ipv4addr;
             }
             uses apply-advanced;
           }
           leaf boot-file {
             description "Boot filename advertised to clients";
             type string;
           }
           leaf boot-server {
             description "Boot server advertised to clients";
             type string {
             }
           }
           leaf next-server {
             description "Next server that clients need to contact";
             type jt:ipv4addr;
           }
           leaf server-identifier {
             description "DHCP server identifier advertised to clients";
             type jt:ipv4addr;
           }
           list option {
             key name;
             ordered-by user;
             description "DHCP option";
             leaf name {
               description "DHCP option identifier code";
               type union {
                 type string {
                   pattern "<.*>|$.*";
                 }
                 type uint32 {
                   range "1 .. 255";
                 }
               }
             }
             choice option-type-choice {
               case case_1 {
                 leaf flag {
                   description "Boolean flag value";
                   type enumeration {
                     enum "true" {
                       description "True value";
                     }
                     enum "false" {
                       description "False value";
                     }
                     enum "on" {
                       description "On value";
                     }
                     enum "off" {
                       description "Off value";
                     }
                   }
                 }
               }
               case case_2 {
                 leaf byte {
                   description "Unsigned 8-bit value";
                   type union {
                     type uint8;
                     type string {
                       pattern "<.*>|$.*";
                     }
                   }
                 }
               }
               case case_3 {
                 leaf short {
                   description "Signed 16-bit numeric value";
                   type union {
                     type int16;
                     type string {
                       pattern "<.*>|$.*";
                     }
                   }
                 }
               }
               case case_4 {
                 leaf unsigned-short {
                   description "Unsigned 16-bit numeric value";
                   type union {
                     type uint16;
                     type string {
                       pattern "<.*>|$.*";
                     }
                   }
                 }
               }
               case case_5 {
                 leaf integer {
                   description "Signed 32-bit numeric value";
                   type union {
                     type int32;
                     type string {
                       pattern "<.*>|$.*";
                     }
                   }
                 }
               }
               case case_6 {
                 leaf unsigned-integer {
                   description "Unsigned 32-bit numeric value";
                   type union {
                     type uint32;
                     type string {
                       pattern "<.*>|$.*";
                     }
                   }
                 }
               }
               case case_7 {
                 leaf string {
                   description "Character string value";
                   type string {
                     length "1 .. 254";
                   }
                 }
               }
               case case_8 {
                 leaf ip-address {
                   description "IP address value";
                   type jt:ipv4addr;
                 }
               }
               case case_9 {
                 container array {
                   presence "enable array";
                   description "Array of values";
                   uses apply-advanced;
                   choice option-type-array-choice {
                     case case_1 {
                       leaf-list flag {
                         ordered-by user;
                         description "Array of boolean flag values";
                         type enumeration {
                           enum "true" {
                             description "True value";
                           }
                           enum "false" {
                             description "False value";
                           }
                           enum "on" {
                             description "On value";
                           }
                           enum "off" {
                             description "Off value";
                           }
                         }
                       }
                     }
                     case case_2 {
                       leaf-list byte {
                         ordered-by user;
                         description "Array of unsigned 8-bit values";
                         type union {
                           type uint8;
                           type string {
                             pattern "<.*>|$.*";
                           }
                         }
                       }
                     }
                     case case_3 {
                       leaf-list short {
                         ordered-by user;
                         description "Array of signed 16-bit numeric values";
                         type union {
                           type int16;
                           type string {
                             pattern "<.*>|$.*";
                           }
                         }
                       }
                     }
                     case case_4 {
                       leaf-list unsigned-short {
                         ordered-by user;
                         description "Array of 16-bit numeric values";
                         type union {
                           type uint16;
                           type string {
                             pattern "<.*>|$.*";
                           }
                         }
                       }
                     }
                     case case_5 {
                       leaf-list integer {
                         ordered-by user;
                         description "Array of signed 32-bit numeric values";
                         type union {
                           type int32;
                           type string {
                             pattern "<.*>|$.*";
                           }
                         }
                       }
                     }
                     case case_6 {
                       leaf-list unsigned-integer {
                         ordered-by user;
                         description "Array of unsigned 32-bit numeric values";
                         type union {
                           type uint32;
                           type string {
                             pattern "<.*>|$.*";
                           }
                         }
                       }
                     }
                     case case_7 {
                       leaf-list string {
                         ordered-by user;
                         description "Array of character string values";
                         type string {
                           length "1 .. 254";
                         }
                       }
                     }
                     case case_8 {
                       leaf-list ip-address {
                         ordered-by user;
                         description "Array of IP address values";
                         type jt:ipv4addr;
                       }
                     }
                   }
                 }
               }
               case case_10 {
                 leaf byte-stream {
                   description "Stream of unsigned 8-bit values within quotes";
                   type string;
                 }
               }
             }
           }
           container sip-server {
             description "SIP servers to clients";
             uses apply-advanced;
             list name {
               key name;
               ordered-by user;
               description "Names of SIP servers";
               leaf name {
                 description "SIP server name";
                 type string;
               }
               uses apply-advanced;
             }
             list address {
               key name;
               ordered-by user;
               description "IP addresses of SIP servers";
               leaf name {
                 description "SIP server's IPv4 address";
                 type jt:ipv4addr;
               }
               uses apply-advanced;
             }
           }
         }
       }
       container outbound-https {
         description "Initiate outbound HTTPS connection";
         uses apply-advanced;
         list client {
           key name;
           ordered-by user;
           description "Define a device initiated outbound https connection";
           leaf name {
             description "Client application identifier";
             type string;
           }
           uses apply-advanced;
           leaf device-id {
             description "Unique ID used by client to identify this device";
             type string;
           }
           leaf secret {
             description "Shared secret between client and this device";
             type jt:unreadable;
           }
           leaf waittime {
             description "Wait time to retry if none of the gRPC servers are available";
             type union {
               type uint32;
               type string {
                 pattern "<.*>|$.*";
               }
             }
           }
           leaf reconnect-strategy {
             description "Strategy used to reconnect to a gRPC server in the list";
             default "in-order";
             type enumeration {
               enum "sticky" {
                 description "Attempt to reconnect to the gRPC server last connected to";
               }
               enum "in-order" {
                 description "Attempt to reconnect to the first gRPC server configured";
               }
             }
           }
           list servers {
             key name;
             ordered-by user;
             description "Client application servers";
             leaf name {
               description "GRPC server IP or hostname";
               type string;
             }
             uses apply-advanced;
             leaf port {
               description "GRPC server port";
               type union {
                 type uint16;
                 type string {
                   pattern "<.*>|$.*";
                 }
               }
             }
             leaf trusted-cert {
               description "Certificate chain content without newlines";
               type string;
             }
           }
         }
       }
       container service-deployment {
         description "Configuration for Service Deployment (SDXD) management application";
         uses apply-advanced;
         leaf local-certificate {
           description "Name of local X.509 certificate to use";
           type string {
             length "1 .. 1024";
           }
         }
         leaf source-address {
           description "Local IPv4 address to be used as source address for traffic to SDX";
           type jt:ipv4addr;
         }
         list servers {
           key name;
           ordered-by user;
           description "Service deployment system configuration";
           max-elements 3;
           leaf name {
             description "IPv4 address of SDX server";
             type jt:ipv4addr;
           }
           uses apply-advanced;
           leaf port {
             description "TCP port of SDX server";
             type union {
               type uint16;
               type string {
                 pattern "<.*>|$.*";
               }
             }
           }
           leaf user {
             description "Username used by SDX when logging into the router";
             type string;
           }
           container security-options {
             description "Specify mechanism to secure the connection";
             uses apply-advanced;
             choice protocol {
               case case_1 {
                 leaf tls {
                   description "Use TLS for transport layer security";
                   type empty;
                 }
               }
               case case_2 {
                 leaf ssl3 {
                   description "Use SSLv3 for transport layer security";
                   type empty;
                 }
               }
             }
           }
         }
         container traceoptions {
           description "Service deployment daemon trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing options";
             leaf name {
               type enumeration {
                 enum "beep" {
                   description "Trace BEEP protocol events";
                 }
                 enum "profile" {
                   description "Trace BEEP profile events";
                 }
                 enum "application" {
                   description "Trace application events";
                 }
                 enum "io" {
                   description "Trace I/O activities";
                 }
                 enum "all" {
                   description "Trace everything";
                 }
               }
             }
           }
         }
       }
       container outbound-ssh {
         description "Initiate outbound SSH connection";
         uses apply-advanced;
         leaf routing-instance {
           description "Routing instance through which client is reachable";
           type string {
           }
         }
         container traceoptions {
           description "Outbound SSH trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "connectivity" {
                   description "Trace TCP connection handling";
                 }
                 enum "all" {
                   description "Trace everything";
                 }
               }
             }
           }
         }
         list client {
           key name;
           ordered-by user;
           description "Define a device initiated SSH connection";
           leaf name {
             description "Client application identifier";
             type string;
           }
           uses apply-advanced;
           leaf disable-ssh-security-settings {
             description "Disable ssh security parameter defined under [system services ssh]";
             status deprecated;
             type empty;
           }
           leaf device-id {
             description "Unique ID used by client to identify this device";
             type string;
           }
           leaf secret {
             description "Shared secret between client and this device";
             type jt:unreadable;
           }
           container keep-alive {
             presence "enable keep-alive";
             uses apply-advanced;
             leaf retry {
               description "Maximum number of connection attempts";
               default "3";
               type union {
                 type uint32;
                 type string {
                   pattern "<.*>|$.*";
                 }
               }
             }
             leaf timeout {
               description "Timeout value for conection attempts";
               default "15";
               type union {
                 type uint32;
                 type string {
                   pattern "<.*>|$.*";
                 }
               }
             }
           }
           leaf reconnect-strategy {
             description "Strategy used to reconnect to a server";
             default "in-order";
             type enumeration {
               enum "sticky" {
                 description "Attempt to reconnect to the server last connected to";
               }
               enum "in-order" {
                 description "Attempt to reconnect to the first server configured";
               }
             }
           }
           leaf services {
             description "The subsystem(s) that can be invoked";
             type enumeration {
               enum "netconf" {
                 description "Enable invoking NETCONF sub-system";
               }
             }
           }
           list servers {
             key name;
             ordered-by user;
             description "Client application servers";
             leaf name {
               description "Client address to connect to";
               type string;
             }
             uses apply-advanced;
             leaf port {
               description "Client port to connect to";
               type union {
                 type uint16;
                 type string {
                   pattern "<.*>|$.*";
                 }
               }
             }
             leaf retry {
               description "Maximum number of connection attempts";
               default "3";
               type union {
                 type uint32;
                 type string {
                   pattern "<.*>|$.*";
                 }
               }
             }
             leaf timeout {
               description "Timeout value for conection attempts";
               default "15";
               type union {
                 type uint32;
                 type string {
                   pattern "<.*>|$.*";
                 }
               }
             }
           }
           container proxy-server {
             description "Proxy server to reach the application server";
             uses apply-advanced;
             choice proxy-type {
               case case_1 {
                 leaf dhcp {
                   description "Read proxy server information from DHCP generated file";
                   type empty;
                 }
               }
               case case_2 {
                 container static {
                   description "Proxy server details";
                   uses apply-advanced;
                   leaf host {
                     description "Host name or address";
                     type string;
                   }
                   leaf port {
                     description "Port number";
                     default "8080";
                     type union {
                       type uint16;
                       type string {
                         pattern "<.*>|$.*";
                       }
                     }
                   }
                   container proxy-authorization {
                     description "Credentials for proxy authorization with basic authentication type";
                     uses apply-advanced;
                     leaf user {
                       description "User name";
                       type string {
                         length "1 .. 255";
                       }
                     }
                     leaf password {
                       description "Password";
                       type string {
                         length "1 .. 255";
                       }
                     }
                   }
                 }
               }
             }
           }
         }
       }
     }
     container schema {
       description "System schema";
       uses apply-advanced;
       container openconfig {
         description "Openconfig schema options";
         uses apply-advanced;
         leaf unhide {
           description "Unhide openconfig from CLI";
           type empty;
         }
       }
     }
     container autoinstallation {
       presence "enable autoinstallation";
       description "Autoinstallation configuration";
     }
     leaf dual-phase-bootup {
       description "Dual-phase-bootup option for using rescue.conf from next reboot";
       type empty;
     }
     leaf auto-snapshot {
       description "Enable auto-snapshot when boots from alternate slice";
       type empty;
     }
     leaf unattended-boot {
       description "Enable Unattended Boot mode";
       type empty;
     }
     leaf domain-name {
       description "Domain name for this router";
       type string {
         length "1 .. 255";
       }
     }
     leaf-list domain-search {
       ordered-by user;
       description "List of domain names to search";
       type string;
     }
     leaf no-hidden-commands {
       description "Deny hidden commands for all users except root";
       type empty;
     }
     container statistics-timeout {
       description "Statistics - Configurable Timeout";
       uses apply-advanced;
       leaf statistics-timeout-value {
         description "Statistics - Configurable Timeout value in milliseconds(1000 to 60000)";
         type union {
           type string {
             pattern "<.*>|$.*";
           }
           type int32 {
             range "1000 .. 60000";
           }
         }
       }
     }
     container icmp {
       presence "enable icmp";
       description " ICMP ";
       uses apply-advanced;
       leaf ttl-expired-source-address {
         description "IPv4 address for ttl-expiry";
         type jt:ipv4addr;
       }
     }
     container backup-router {
       description "IPv4 router to use while booting";
       leaf address {
         description "Address of router to use while booting";
         type jt:ipv4addr;
       }
       leaf-list destination {
         ordered-by user;
         description "Destination network reachable through the router";
         type jt:ipv4prefix;
       }
     }
     leaf time-zone {
       description "Time zone name or POSIX-compliant time zone string";
       default "UTC";
       units "<continent>/<major-city> or <time-zone>";
       type string {
       }
     }
     leaf use-imported-time-zones {
       description "Use locally generated time-zone database";
       type empty;
     }
     leaf regex-additive-logic {
       description "Set regex-additive-logic";
       type empty;
     }
     leaf switchover-on-routing-crash {
       description "On failure, switch mastership to other Routing Engine";
       type empty;
     }
     leaf default-address-selection {
       description "Use system address for locally originated traffic";
       type empty;
     }
     leaf ndcpp-compliant {
       description "Enable NDcPP compliance";
       type empty;
     }
     leaf nd-maxmcast-solicit {
       description "Set Maximum multicast solicit";
       type union {
         type int32;
         type string {
           pattern "<.*>|$.*";
         }
       }
     }
     leaf nd-maxucast-retry {
       description "Set Maximum unicast retry count";
       type union {
         type int32;
         type string {
           pattern "<.*>|$.*";
         }
       }
     }
     leaf nd-retransmit-timer {
       description "Set retransmit timer";
       type union {
         type int32;
         type string {
           pattern "<.*>|$.*";
         }
       }
     }
     leaf nd-system-cache-limit {
       description "Set max system cache size for IPv6 nexthops";
       type union {
         type string {
           pattern "<.*>|$.*";
         }
         type int32 {
           range "200 .. 2000000";
         }
       }
     }
     leaf arp-system-cache-limit {
       description "Set max system cache size for ARP nexthops";
       type union {
         type string {
           pattern "<.*>|$.*";
         }
         type int32 {
           range "200 .. 2600000";
         }
       }
     }
     leaf no-neighbor-learn {
       description "Disable neighbor address learning";
       type empty;
     }
     leaf no-multicast-echo {
       description "Disable ICMP echo on multicast addresses";
       type empty;
     }
     leaf extended-echo {
       description "Enable ICMP extended echo processing";
       type empty;
     }
     leaf no-redirects {
       description "Disable ICMP redirects";
       type empty;
     }
     leaf no-redirects-ipv6 {
       description "Disable IPV6 ICMP redirects";
       type empty;
     }
     leaf nd-override-preferred-src {
       description "Do not use preferred source address for unnumbered interface as the source of NA/NS";
       type empty;
     }
     leaf no-ping-record-route {
       description "Do not insert IP address in ping replies";
       type empty;
     }
     leaf no-ping-time-stamp {
       description "Do not insert time stamp in ping replies";
       type empty;
     }
     leaf dump-device {
       description "Device to record memory snapshots on operating system failure";
       type string;
     }
     container arp {
       description "ARP settings";
       uses apply-advanced;
       leaf aging-timer {
         description "Change the ARP aging time value";
         units "minutes";
         type union {
           type string {
             pattern "<.*>|$.*";
           }
           type int32 {
             range "1 .. 240";
           }
         }
       }
       container interfaces {
         description "Logical interface on which to specify ARP aging timer";
         uses apply-advanced;
         list arp-interface {
           key name;
           uses arp-interface-type;
         }
       }
       leaf passive-learning {
         description "ARP passive learning";
         type empty;
       }
       leaf purging {
         description "ARP purging when link goes down";
         type empty;
       }
       leaf gratuitous-arp-on-ifup {
         description "Gratuitous ARP announcement on interface up";
         type empty;
       }
       leaf gratuitous-arp-delay {
         description "Delay gratuitous ARP request";
         type union {
           type string {
             pattern "<.*>|$.*";
           }
           type uint32 {
             range "1 .. 4000000";
           }
         }
       }
       leaf non-subscriber-no-reply {
         description "Do not reply to ARP requests from non-subscribers";
         type empty;
       }
       leaf unicast-mode-on-expire {
         description "Send unicast ARP request on expiry timer";
         type empty;
       }
       leaf respond-out-of-subnet {
         description "Respond to out of subnet arp requests";
         type empty;
       }
       leaf arp-retries {
         description "Set maximum ARP retries";
         type union {
           type uint32;
           type string {
             pattern "<.*>|$.*";
           }
         }
       }
     }
     leaf-list personality-file-list-of-directories {
       ordered-by user;
       description "List of Optional directories for personality-tarball of device";
       type string;
     }
     leaf saved-core-files {
       description "Number of saved core files per executable";
       default "5";
       type union {
         type string {
           pattern "<.*>|$.*";
         }
         type uint32 {
           range "1 .. 10";
         }
       }
     }
     choice saved-core-context-choice {
       leaf saved-core-context {
         description "Save context information for core files";
         type empty;
       }
       leaf no-saved-core-context {
         description "Don't save context information for core files";
         type empty;
       }
     }
     container kernel-replication {
       presence "enable kernel-replication";
       description "Kernel replication";
       uses apply-advanced;
     }
     leaf mirror-flash-on-disk {
       description "Mirror contents of the flash drive onto hard drive";
       status deprecated;
       type empty;
     }
     container icmp-rate-limit {
       description "Rate-limiting parameters for ICMP messages";
       status deprecated;
       leaf packet-rate {
         description "ICMP rate-limiting packets earned per second";
         default "1000";
         type union {
           type uint32;
           type string {
             pattern "<.*>|$.*";
           }
         }
       }
       leaf bucket-size {
         description "ICMP rate-limiting maximum bucket size";
         default "5";
         units "seconds";
         type union {
           type uint32;
           type string {
             pattern "<.*>|$.*";
           }
         }
       }
     }
     leaf tcp-ack-rst-syn {
       description "Send ACKs for in-window RSTs and SYN packets on TCP connections";
       status deprecated;
       type empty;
     }
     leaf management-instance {
       description "Enable Management VRF Instance";
       type empty;
     }
     container demux-options {
       description "Tunable options for demux link local address generation";
       uses apply-advanced;
       leaf use-underlying-interface-mac {
         description "Use underlying interface MAC for link local address";
         type empty;
       }
     }
     container internet-options {
       description "Tunable options for Internet operation";
       uses apply-advanced;
       container icmpv4-rate-limit {
         description "Rate-limiting parameters for ICMPv4 messages";
         leaf packet-rate {
           description "ICMP rate-limiting packets earned per second";
           default "1000";
           type union {
             type uint32;
             type string {
               pattern "<.*>|$.*";
             }
           }
         }
         leaf bucket-size {
           description "ICMP rate-limiting maximum bucket size";
           default "5";
           units "seconds";
           type union {
             type uint32;
             type string {
               pattern "<.*>|$.*";
             }
           }
         }
       }
       container icmpv6-rate-limit {
         description "Rate-limiting parameters for ICMPv6 messages";
         leaf packet-rate {
           description "ICMPv6 rate-limiting packets earned per second";
           default "1000";
           type union {
             type uint32;
             type string {
               pattern "<.*>|$.*";
             }
           }
         }
         leaf bucket-size {
           description "ICMPv6 rate-limiting maximum bucket size";
           default "5";
           units "seconds";
           type union {
             type uint32;
             type string {
               pattern "<.*>|$.*";
             }
           }
         }
       }
       choice path-mtu-discovery-choice {
         leaf path-mtu-discovery {
           description "Enable Path MTU discovery on TCP connections";
           type empty;
         }
         leaf no-path-mtu-discovery {
           description "Don't enable Path MTU discovery on TCP connections";
           type empty;
         }
       }
       choice gre-path-mtu-discovery-choice {
         leaf gre-path-mtu-discovery {
           description "Enable path MTU discovery for GRE tunnels";
           type empty;
         }
         leaf no-gre-path-mtu-discovery {
           description "Don't enable path MTU discovery for GRE tunnels";
           type empty;
         }
       }
       choice ipip-path-mtu-discovery-choice {
         leaf ipip-path-mtu-discovery {
           description "Enable path MTU discovery for IP-IP tunnels";
           type empty;
         }
         leaf no-ipip-path-mtu-discovery {
           description "Don't enable path MTU discovery for IP-IP tunnels";
           type empty;
         }
       }
       container source-port {
         description "Source port selection parameters";
         uses apply-advanced;
         leaf upper-limit {
           description "Specify upper limit of source port selection range";
           type union {
             type string {
               pattern "<.*>|$.*";
             }
             type uint32 {
               range "5000 .. 65535";
             }
           }
         }
       }
       choice source-quench-choice {
         leaf source-quench {
           description "React to incoming ICMP Source Quench messages";
           type empty;
         }
         leaf no-source-quench {
           description "Don't react to incoming ICMP Source Quench messages";
           type empty;
         }
       }
       leaf tcp-drop-synfin-set {
         description "Drop TCP packets that have both SYN and FIN flags";
         type empty;
       }
       leaf no-tcp-rfc1323 {
         description "Disable RFC 1323 TCP extensions";
         type empty;
       }
       leaf no-tcp-rfc1323-paws {
         description "Disable RFC 1323 Protection Against Wrapped Sequence Number extension";
         type empty;
       }
       choice ipv6-path-mtu-discovery-choice {
         leaf ipv6-path-mtu-discovery {
           description "Enable IPv6 Path MTU discovery";
           type empty;
         }
         leaf no-ipv6-path-mtu-discovery {
           description "Don't enable IPv6 Path MTU discovery";
           type empty;
         }
       }
       leaf ipv6-path-mtu-discovery-timeout {
         description "IPv6 Path MTU Discovery timeout";
         default "10";
         units "minutes";
         type union {
           type string {
             pattern "<.*>|$.*";
           }
           type uint32 {
             range "5 .. 71582788";
           }
         }
       }
       leaf no-tcp-reset {
         description "Do not send RST TCP packet for packets sent to non-listening ports";
         type enumeration {
           enum "drop-tcp-with-syn-only" {
             description "Drop only those TCP Packets with SYN bit";
           }
           enum "drop-all-tcp" {
             description "Drop all TCP Packets";
           }
         }
       }
     }
     leaf-list authentication-order {
       ordered-by user;
       type enumeration {
         enum "radius" {
           description "Remote Authentication Dial-In User Service";
         }
         enum "tacplus" {
           description "TACACS+ authentication services";
         }
         enum "password" {
           description "Traditional password authentication";
         }
       }
     }
     container location {
       description "Location of the system, in various forms";
       uses location-type;
     }
     container ports {
       description "Craft interface RS-232 ports";
       uses apply-advanced;
       container console {
         description "Console port";
         uses tty_port_object;
       }
       container auxiliary {
         description "Auxiliary port";
         uses tty_port_object;
       }
     }
     container diag-port-authentication {
       description "Authentication for the diagnostic port";
       uses apply-advanced;
       leaf plain-text-password-value {
         description "Plain text password";
         type string;
       }
       leaf encrypted-password {
         description "Encrypted password string";
         type string {
           length "1 .. 128";
         }
       }
     }
     container pic-console-authentication {
       description "Authentication for the console port on PICs";
       uses apply-advanced;
       leaf plain-text-password-value {
         description "Plain text password";
         type string;
       }
       leaf encrypted-password {
         description "Encrypted password string";
         type string {
           length "1 .. 128";
         }
       }
     }
     container boot-loader-authentication {
       description "Authentication for the boot loader";
       uses apply-advanced;
       leaf plain-text-password-value {
         description "Plain text password";
         type string;
       }
       leaf encrypted-password {
         description "Encrypted password string";
         type string {
           length "1 .. 128";
         }
       }
     }
     list name-server {
       key name;
       ordered-by user;
       description "DNS name servers";
       uses nameserver-object;
     }
     container name-resolution {
       description "Configure hostname resolution behaviour";
       uses apply-advanced;
       container no-resolve-host-on-input {
         presence "enable no-resolve-host-on-input";
         description "Do not resolve hostnames at the time of input";
       }
     }
     list radius-server {
       key name;
       ordered-by user;
       description "RADIUS server configuration";
       uses radius-server-object;
     }
     container dynamic-profile-options {
       description "Dynamic profile options";
       uses dynamic-profile-option-object;
     }
     list tacplus-server {
       key name;
       ordered-by user;
       description "TACACS+ server configuration";
       uses tacplus-server-object;
     }
     container password-options {
       description "Local password options, password should be configured at [system authentication-order]";
       uses apply-advanced;
       leaf tacplus-authorization {
         description "TACACS+ authorization for locally authenticated users";
         type empty;
       }
     }
     container ldap-server {
       presence "enable ldap-server";
       description "LDAP server configuration";
       uses apply-advanced;
       leaf-list address {
         ordered-by user;
         description "LDAP authentication server address";
         type jt:hostname;
         max-elements 2;
       }
       leaf-list port {
         ordered-by user;
         description "LDAP authentication server port number";
         type union {
           type uint32;
           type string {
             pattern "<.*>|$.*";
           }
         }
         max-elements 2;
       }
       leaf base {
         description "LDAP base";
         type string;
       }
       leaf binddn {
         description "LDAP binddn";
         type string;
       }
       leaf bindpw {
         description "LDAP bindpw";
         type string;
       }
       leaf routing-instance {
         description "LDAP routing instance";
         type string {
         }
       }
       leaf ldaps-cert {
         description "LDAPS client certificate id";
         type string;
       }
     }
     container radius-options {
       description "RADIUS options";
       uses apply-advanced;
       leaf password-protocol {
         description "Specify password protocol used in RADIUS packets";
         type enumeration {
           enum "mschap-v2" {
             description "MSCHAP version 2";
           }
         }
       }
       leaf enhanced-accounting {
         description "Include authentication method, remote port and user-privileges in 'login' accounting";
         type empty;
       }
       container attributes {
         description "Configure RADIUS attributes";
         uses apply-advanced;
         leaf nas-ip-address {
           description "Value of NAS-IP-Address in outgoing RADIUS packets";
           type jt:ipaddr;
         }
         leaf nas-id {
           description "Value of NAS-ID in outgoing RADIUS packets";
           type string {
             length "3 .. 64";
           }
         }
       }
     }
     container tacplus-options {
       description "TACACS+ options";
       uses apply-advanced;
       leaf service-name {
         description "TACACS+ service name";
         type string;
       }
       leaf authorization-time-interval {
         description "TACACS+ authorization refresh time interval";
         units "minutes";
         type union {
           type string {
             pattern "<.*>|$.*";
           }
           type uint32 {
             range "15 .. 1440";
           }
         }
       }
       choice strict-authorization-choice {
         leaf strict-authorization {
           description "Deny login if authorization request fails";
           type empty;
         }
         leaf no-strict-authorization {
           description "Don't deny login if authorization request fails";
           type empty;
         }
       }
       choice cmd-attribute {
         case case_1 {
           leaf no-cmd-attribute-value {
             description "In start/stop requests, set 'cmd' attribute value to empty string";
             type empty;
           }
         }
         case case_2 {
           leaf exclude-cmd-attribute {
             description "In start/stop requests, do not include 'cmd' attribute";
             type empty;
           }
         }
       }
       leaf enhanced-accounting {
         description "Include authentication method, remote port and user-privileges in 'login' accounting";
         type empty;
       }
       leaf timestamp-and-timezone {
         description "In start/stop accounting packets, include 'start-time', 'stop-time' and 'timezone' attributes";
         type empty;
       }
     }
     container accounting {
       description "System accounting configuration";
       uses apply-advanced;
       leaf-list events {
         description "Events to be logged";
         type enumeration {
           enum "login" {
             description "Login session";
           }
           enum "change-log" {
             description "Configuration changes";
           }
           enum "interactive-commands" {
             description "Commands";
           }
         }
       }
       leaf enhanced-avs-max {
         description "No. of AV pairs each of which can store a max of 250 Bytes";
         default "7";
         type union {
           type string {
             pattern "<.*>|$.*";
           }
           type int32 {
             range "7 .. 15";
           }
         }
       }
       container traceoptions {
         description "Trace options for system accounting";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "all" {
                 description "Trace all operations";
               }
               enum "events" {
                 description "Trace accounting events and their processing";
               }
               enum "config" {
                 description "Trace configuration processing";
               }
               enum "radius" {
                 description "Trace RADIUS processing";
               }
               enum "tacplus" {
                 description "Trace TACPLUS processing";
               }
             }
           }
         }
       }
       container destination {
         description "Destination for system accounting records";
         uses apply-advanced;
         container radius {
           presence "enable radius";
           description "Configure RADIUS accounting";
           uses apply-advanced;
           list server {
             key name;
             ordered-by user;
             description "RADIUS accounting server configuration";
             uses radius-server-object;
           }
         }
         container tacplus {
           presence "enable tacplus";
           description "Send TACACS+ accounting records";
           uses apply-advanced;
           list server {
             key name;
             ordered-by user;
             description "TACACS+ server configuration";
             uses tacplus-server-object;
           }
         }
       }
     }
     leaf allow-v4mapped-packets {
       description "Allow processing for packets with V4 mapped address";
       type empty;
     }
     leaf allow-6pe-traceroute {
       description "Allow IPv4-mapped v6 address in tag icmp6 TTL expired packet";
       type empty;
     }
     leaf allow-l3vpn-traceroute-src-select {
       description "Select best src addr for icmp ttl expiry error in case l3vpn";
       type empty;
     }
     leaf allow-6vpe-traceroute-src-select {
       description "Select best src addr for icmp6 ttl expiry error in case 6vpe";
       type empty;
     }
     leaf allow-icmp4-extension {
       description "Allow icmp4 to add additional data structures in the extension";
       type empty;
     }
     leaf allow-icmp6-extension {
       description "Allow icmp6 to add additional data structures in the extension";
       type empty;
     }
     leaf donot-disable-ip6op-ondad {
       description "Do not disable IP operation on interface, if DAD fails on EUI-64 link local address ";
       type empty;
     }
     list static-host-mapping {
       key name;
       ordered-by user;
       description "Static hostname database mapping";
       leaf name {
         description "Fully qualified name of system";
         type string {
         }
       }
       uses apply-advanced;
       leaf-list inet {
         ordered-by user;
         description "IP address";
         type jt:ipv4addr;
       }
       leaf sysid {
         description "ISO/IS-IS system identifier";
         type jt:sysid;
       }
       leaf-list alias {
         ordered-by user;
         description "Hostname alias";
         type string;
       }
     }
     container syslog {
       description "System logging facility";
       uses apply-advanced;
       container archive {
         description "Archive file information";
         presence "enable archive";
         uses archive-object;
       }
       list user {
         key name;
         ordered-by user;
         description "Notify a user of the event";
         leaf name {
           description "Name of user to notify";
           type string {
           }
         }
         uses apply-advanced;
         list contents {
           key name;
           uses syslog-object;
         }
         leaf match {
           description "Regular expression for lines to be logged";
           type jt:regular-expression;
         }
         leaf allow-duplicates {
           description "Do not suppress the repeated message";
           type empty;
         }
         leaf-list match-strings {
           ordered-by user;
           description "Matching string(s) for lines to be logged";
           type string;
           max-elements 50;
         }
       }
       list host {
         key name;
         ordered-by user;
         description "Host to be notified";
         leaf name {
           description "Name of host to notify";
           type string;
         }
         uses apply-advanced;
         list contents {
           key name;
           uses syslog-object;
         }
         leaf match {
           description "Regular expression for lines to be logged";
           type jt:regular-expression;
         }
         leaf allow-duplicates {
           description "Do not suppress the repeated message";
           type empty;
         }
         leaf port {
           description "Port number";
           type union {
             type uint16;
             type string {
               pattern "<.*>|$.*";
             }
           }
         }
         leaf facility-override {
           description "Alternate facility for logging to remote host";
           type enumeration {
             enum "authorization" {
               description "Authorization system";
             }
             enum "daemon" {
               description "Various system processes";
             }
             enum "ftp" {
               description "FTP process";
             }
             enum "kernel" {
               description "Kernel";
             }
             enum "user" {
               description "User processes";
             }
             enum "local0" {
               description "Local logging option number 0";
             }
             enum "local1" {
               description "Local logging option number 1";
             }
             enum "local2" {
               description "Local logging option number 2";
             }
             enum "local3" {
               description "Local logging option number 3";
             }
             enum "local4" {
               description "Local logging option number 4";
             }
             enum "local5" {
               description "Local logging option number 5";
             }
             enum "local6" {
               description "Local logging option number 6";
             }
             enum "local7" {
               description "Local logging option number 7";
             }
           }
         }
         leaf log-prefix {
           description "Prefix for all logging to this host";
           type string {
           }
         }
         leaf source-address {
           description "Use specified address as source address";
           type jt:ipaddr;
         }
         leaf routing-instance {
           description "Routing instance";
           type string {
           }
         }
         leaf explicit-priority {
           description "Include priority and facility in messages";
           type empty;
         }
         leaf exclude-hostname {
           description "Exclude hostname field in messages";
           type empty;
         }
         leaf transport {
           description "Transport type";
           default "udp";
           type enumeration {
             enum "tcp" {
               description "TCP as transport for syslog";
             }
             enum "udp" {
               description "UDP as transport for syslog";
             }
             enum "tls" {
               description "TLS as transport for syslog";
             }
           }
         }
         container tlsdetails {
           presence "enable tlsdetails";
           description "TLS for TCP";
           uses apply-advanced;
           leaf local-certificate {
             description "Local Certificate ID";
             type string {
             }
           }
           container mutual-authentication {
             description "Enable TLS mutual authentication";
             uses apply-advanced;
             leaf certificate-authority {
               description "Certificate authority profile";
               type string {
               }
             }
           }
           list trusted-ca-group {
             key name;
             ordered-by user;
             description "Trusted Certificate Authority group configuration";
             leaf name {
               description "Name of the trusted CA group";
               type string {
                 length "1 .. 63";
               }
             }
             uses apply-advanced;
             leaf-list ca-profiles {
               ordered-by user;
               description "Name of the CA profiles (maximum 20)";
               type string {
                 length "1 .. 63";
               }
               max-elements 20;
             }
           }
         }
         leaf-list match-strings {
           ordered-by user;
           description "Matching string(s) for lines to be logged";
           type string;
           max-elements 50;
         }
         container structured-data {
           presence "enable structured-data";
           description "Log system message in structured format";
           uses apply-advanced;
           choice format {
             case case_1 {
               leaf brief {
                 description "Omit English-language text from end of logged message";
                 type empty;
               }
             }
           }
         }
       }
       leaf allow-duplicates {
         description "Do not suppress the repeated message for all targets";
         type empty;
       }
       list file {
         key name;
         description "File in which to log data";
         leaf name {
           description "Name of file in which to log data";
           type string {
             length "1 .. 1024";
           }
         }
         uses apply-advanced;
         list contents {
           key name;
           uses syslog-object;
         }
         leaf match {
           description "Regular expression for lines to be logged";
           type jt:regular-expression;
         }
         leaf allow-duplicates {
           description "Do not suppress the repeated message";
           type empty;
         }
         container archive {
           description "Archive file information";
           presence "enable archive";
           uses archive-object;
         }
         leaf explicit-priority {
           description "Include priority and facility in messages";
           type empty;
         }
         leaf-list match-strings {
           ordered-by user;
           description "Matching string(s) for lines to be logged";
           type string;
           max-elements 50;
         }
         container structured-data {
           presence "enable structured-data";
           description "Log system message in structured format";
           uses apply-advanced;
           choice format {
             case case_1 {
               leaf brief {
                 description "Omit English-language text from end of logged message";
                 type empty;
               }
             }
           }
         }
       }
       list console {
         key name;
         description "Console logging";
         leaf name {
           description "Facility type";
           type enumeration {
             enum "any" {
               description "All facilities";
             }
             enum "authorization" {
               description "Authorization system";
             }
             enum "daemon" {
               description "Various system processes";
             }
             enum "ftp" {
               description "FTP process";
             }
             enum "ntp" {
               description "NTP process";
             }
             enum "security" {
               description "Security related";
             }
             enum "kernel" {
               description "Kernel";
             }
             enum "user" {
               description "User processes";
             }
             enum "dfc" {
               description "Dynamic flow capture";
             }
             enum "external" {
               description "Local external applications";
             }
             enum "firewall" {
               description "Firewall filtering system";
             }
             enum "pfe" {
               description "Packet Forwarding Engine";
             }
             enum "conflict-log" {
               description "Configuration conflict log";
             }
             enum "change-log" {
               description "Configuration change log";
             }
             enum "interactive-commands" {
               description "Commands executed by the UI";
             }
             enum "application-status" {
               description "Application stop / start status";
             }
           }
         }
         choice level {
           case case_1 {
             leaf any {
               description "All levels";
               type empty;
             }
           }
           case case_2 {
             leaf emergency {
               description "Panic conditions";
               type empty;
             }
           }
           case case_3 {
             leaf alert {
               description "Conditions that should be corrected immediately";
               type empty;
             }
           }
           case case_4 {
             leaf critical {
               description "Critical conditions";
               type empty;
             }
           }
           case case_5 {
             leaf error {
               description "Error conditions";
               type empty;
             }
           }
           case case_6 {
             leaf warning {
               description "Warning messages";
               type empty;
             }
           }
           case case_7 {
             leaf notice {
               description "Conditions that should be handled specially";
               type empty;
             }
           }
           case case_8 {
             leaf info {
               description "Informational messages";
               type empty;
             }
           }
           case case_9 {
             leaf none {
               description "No messages";
               type empty;
             }
           }
         }
       }
       container time-format {
         presence "enable time-format";
         description "Additional information to include in system log timestamp";
         leaf year {
           description "Include year in timestamp";
           type empty;
         }
         leaf millisecond {
           description "Include milliseconds in timestamp";
           type empty;
         }
       }
       leaf source-address {
         description "Use specified address as source address";
         type jt:ipaddr;
       }
       leaf routing-instance {
         description "Routing instance";
         type string {
         }
       }
       leaf log-rotate-frequency {
         description "Rotate log frequency";
         default "15";
         units "minutes";
         type union {
           type string {
             pattern "<.*>|$.*";
           }
           type uint32 {
             range "1 .. 59";
           }
         }
       }
       container server {
         presence "enable server";
         description "Enable syslog server";
         uses apply-advanced;
         list routing-instances {
           key name;
           ordered-by user;
           description "Enable/disable syslog server in routing-instances";
           leaf name {
             description "Routing instance name";
             type string;
           }
           uses apply-advanced;
           container disable {
             presence "enable disable";
             description "Disable syslog server in this routing instance";
           }
         }
       }
       leaf alternate-format {
         description "Append node name with daemon name instead of hostname(default) in the log entries";
         type empty;
       }
       container grpc-replay {
         description "GRPC streaming";
         uses apply-advanced;
         list contents {
           key name;
           uses syslog-object;
         }
         leaf-list match-strings {
           ordered-by user;
           description "Matching string(s) for lines to be logged";
           type string;
           max-elements 50;
         }
         leaf last {
           description "Store last x minutes events";
           units "minutes";
           type union {
             type uint32;
             type string {
               pattern "<.*>|$.*";
             }
           }
         }
       }
       leaf shell {
         description "Enable syslogging of shell commands started by 'start shell'";
         type empty;
       }
     }
     container tracing {
       description "System wide option for remote tracing";
       container destination-override {
         description "Override tracing destination";
         container syslog {
           description "Send trace messages to remote syslog server";
           leaf host {
             description "IPv4 address of remote syslog server";
             type jt:ipv4addr;
           }
         }
       }
     }
     choice compress-configuration-files-choice {
       leaf compress-configuration-files {
         description "Compress the router configuration files";
         type empty;
       }
       leaf no-compress-configuration-files {
         description "Don't compress the router configuration files";
         type empty;
       }
     }
     leaf max-configurations-on-flash {
       description "Number of configuration files stored on flash";
       default "3";
       type union {
         type string {
           pattern "<.*>|$.*";
         }
         type uint32 {
           range "0 .. 49";
         }
       }
     }
     container archival {
       description "System archival management";
       uses apply-advanced;
       container configuration {
         description "Automatic configuration uploads to host(s)";
         uses apply-advanced;
         choice transfer-method {
           case case_1 {
             leaf transfer-interval {
               description "Frequency at which file transfer happens";
               units "minutes";
               type union {
                 type string {
                   pattern "<.*>|$.*";
                 }
                 type uint32 {
                   range "15 .. 2880";
                 }
               }
             }
           }
           case case_2 {
             leaf transfer-on-commit {
               description "Transfer after each commit";
               type empty;
             }
           }
         }
         leaf routing-instance {
           description "Routing instance through which server is reachable";
           type string {
           }
         }
         list archive-sites {
           key name;
           ordered-by user;
           description "List of archive destinations";
           leaf name {
             description "URLs to receive configuration files";
             type string;
           }
           leaf password {
             description "Password for login into the archive site";
             type jt:unreadable;
           }
         }
       }
     }
     container extensions {
       presence "enable extensions";
       description "Configuration for extensions to JUNOS";
       uses apply-advanced;
       list providers {
         key name;
         ordered-by user;
         leaf name {
           type string {
           }
         }
         uses apply-advanced;
         list license-type {
           key name;
           ordered-by user;
           leaf name {
             description "Type of the license";
             type string {
             }
           }
           leaf-list deployment-scope {
             ordered-by user;
             type string;
           }
         }
       }
       container extension-service {
         presence "enable extension-service";
         description "Enable JUNOS extension service";
         uses apply-advanced;
         container application {
           presence "enable application";
           description "JUNOS extension service application";
           uses apply-advanced;
           leaf refresh {
             description "Refresh all operation scripts from their source";
             type empty;
           }
           leaf refresh-from {
             description "Refresh all operation scripts from a given base URL";
             type string {
               length "1 .. 254";
             }
           }
           container start {
             description "Start JET applications with start-criteria check";
             uses apply-advanced;
             container start-options {
               description "Start options for JET applications";
               uses apply-advanced;
               leaf mem-factor {
                 description "Memory factor at which to start/stop";
                 type union {
                   type string {
                     pattern "<.*>|$.*";
                   }
                   type uint32 {
                     range "1 .. 100";
                   }
                 }
               }
             }
           }
           list file {
             key name;
             description "Configuration for each extension-service application";
             uses jet_scripts_file_type;
           }
           container traceoptions {
             description "Trace options for extension-service applications";
             uses script_traceoptions;
           }
           leaf max-datasize {
             description "Maximum data segment size for apps execution";
             units "bytes";
             type string;
           }
         }
       }
       container resource-limits {
         description "Process resource limits";
         uses apply-advanced;
         list process {
           key name;
           ordered-by user;
           leaf name {
             description "Process name";
             type string;
           }
           uses apply-advanced;
           container resources {
             description "Resource limits";
             presence "enable resources";
             uses resources-type;
           }
         }
         list package {
           key name;
           ordered-by user;
           leaf name {
             description "Package name";
             type string;
           }
           uses apply-advanced;
           container resources {
             description "Resource limits";
             presence "enable resources";
             uses resources-type;
           }
         }
       }
     }
     container license {
       description "License information for the router";
       uses license-object;
     }
     container proxy {
       description "Proxy information for the router";
       uses proxy-object;
     }
     container kernel-options {
       description "Kernel options: selectively enable few knobs";
       uses apply-advanced;
       leaf select-active-unilist-member {
         description "Select active unilist member for host path forwarding";
         status deprecated;
         type empty;
       }
     }
     container fips {
       description "FIPS configuration";
       uses apply-advanced;
       container chassis {
         description "FIPS chassis boundary configuration";
         uses apply-advanced;
         leaf level {
           description "FIPS chassis level configuration";
           type union {
             type string {
               pattern "<.*>|$.*";
             }
             type int32 {
               range "0 .. 2";
             }
           }
         }
       }
       leaf level {
         description "FIPS 140 level";
         type union {
           type string {
             pattern "<.*>|$.*";
           }
           type int32 {
             range "0 .. 2";
           }
         }
       }
       container self-test {
         description "Configure FIPS self-test execution";
         uses apply-advanced;
         leaf after-key-generation {
           description "FIPS self-test after cryptographic key generation";
           status deprecated;
           type enumeration {
             enum "enable" {
               description "Enable FIPS self-test after cryptographic key generation";
               status deprecated;
             }
             enum "disable" {
               description "Disable FIPS self-test after cryptographic key generation";
               status deprecated;
             }
           }
         }
         container periodic {
           description "Configure periodic FIPS self-test";
           uses apply-advanced;
           leaf start-time {
             description "Time when the periodic FIPS self-tests are to be executed (hh:mm)";
             type string {
             }
           }
           leaf day-of-month {
             description "Day of the month when FIPS self-tests are to be executed";
             type union {
               type string {
                 pattern "<.*>|$.*";
               }
               type int32 {
                 range "1 .. 31";
               }
             }
           }
           leaf month {
             description "The month when FIPS self-tests are to be executed";
             type union {
               type string {
                 pattern "<.*>|$.*";
               }
               type int32 {
                 range "1 .. 12";
               }
             }
           }
           leaf day-of-week {
             description "Day of the week when the FIPS self-tests are to be executed (where 1 - Monday, 7 - Sunday)";
             type union {
               type string {
                 pattern "<.*>|$.*";
               }
               type int32 {
                 range "1 .. 7";
               }
             }
           }
         }
       }
     }
     container rng {
       description "Configure system CSPRNG";
       uses apply-advanced;
       choice algorithm {
         case case_1 {
           leaf fortuna {
             description "Fortuna";
             type empty;
           }
         }
         case case_2 {
           leaf hmac-drbg {
             description "HMAC DRBG, NIST SP800-90A";
             type empty;
           }
         }
         case case_3 {
           leaf dyce {
             description "DYCE Randomizer";
             type empty;
           }
         }
       }
     }
     container health-monitor {
       presence "enable health-monitor";
       description "Kernel health monitoring system";
       uses apply-advanced;
       container ifstate-clients {
         presence "enable ifstate-clients";
         description "Configure health monitor for ifstate clients on ifstate consumption";
         uses apply-advanced;
         container peer-stuck {
           presence "enable peer-stuck";
           description "PFE/RE/Smart PIC peers ifstate consumption";
           uses apply-advanced;
           leaf threshold-level {
             description "Threshold level to categorize peers as stuck";
             default "medium";
             type enumeration {
               enum "low" {
                 description "Low - 180s";
               }
               enum "medium" {
                 description "Medium - 360s";
               }
               enum "high" {
                 description "High - 540s";
               }
             }
           }
           leaf action {
             description "Set an action on stuck peers";
             default "alarm";
             type enumeration {
               enum "alarm" {
                 description "An alarm will be raised";
               }
               enum "alarm-with-cores" {
                 description "Live cores(stuck peer and vmcore) along with Alarm";
               }
               enum "restart" {
                 description "The stuck peers will be restarted";
               }
             }
           }
         }
         container non-peer-stuck {
           presence "enable non-peer-stuck";
           description "Non-peer clients(daemons) on ifstate consumption";
           uses apply-advanced;
           leaf threshold-level {
             description "Threshold level to categorize non-peer ifstate clients as stuck";
             default "medium";
             type enumeration {
               enum "low" {
                 description "Low - 180s";
               }
               enum "medium" {
                 description "Medium - 360s(Default)";
               }
               enum "high" {
                 description "High - 540s";
               }
             }
           }
           leaf action {
             description "Set an action on stuck non-peer ifstate clients";
             default "alarm";
             type enumeration {
               enum "alarm" {
                 description "An alarm will be raised";
               }
               enum "alarm-with-cores" {
                 description "Live cores(stuck client and vmcore) along with Alarm";
               }
               enum "restart" {
                 description "The stuck non-peer ifstate clients will be restarted";
               }
             }
           }
         }
         container all-clients-stuck {
           presence "enable all-clients-stuck";
           description "All ifstate clients on ifstate consumption";
           uses apply-advanced;
           leaf threshold-level {
             description "Threshold level to categorize all ifsate clients as stuck";
             default "medium";
             type enumeration {
               enum "low" {
                 description "Low - 180s";
               }
               enum "medium" {
                 description "Medium - 360s(Default)";
               }
               enum "high" {
                 description "High - 540s";
               }
             }
           }
           leaf action {
             description "Set an action on all stuck ifstate clients";
             default "alarm";
             type enumeration {
               enum "alarm" {
                 description "An alarm will be raised";
               }
               enum "alarm-with-cores" {
                 description "Live cores(stuck ifstate client and vmcore) along with Alarm";
               }
               enum "restart" {
                 description "The stuck non-peer ifstate clients will be restarted";
               }
             }
           }
         }
       }
     }
     leaf netlink-async-mode {
       description "Enable async mode in nlsd";
       type empty;
     }
     container snapshot {
       description "System snapshot";
       uses apply-advanced;
       container recovery {
         description "System snapshot recovery management";
         uses apply-advanced;
         leaf on-upgrade {
           description "Update the recovery snapshot when the JUNOS release changes";
           type empty;
         }
         leaf configuration-only {
           description "Save configuration only, snapshot updated when out-of-date";
           type empty;
         }
         choice automatic-choice {
           leaf automatic {
             description "Automatically recover junos volume when necessary";
             type empty;
           }
           leaf no-automatic {
             description "Don't automatically recover junos volume when necessary";
             type empty;
           }
         }
         leaf-list configuration-preference {
           ordered-by user;
           description "Configuration to use when booting a snapshot from OAM";
           type enumeration {
             enum "config" {
               description "Use '/config/juniper.conf.gz' if available";
             }
             enum "snapshot" {
               description "Use configuration saved in snapshot";
             }
           }
         }
       }
       choice configuration-choice {
         leaf configuration {
           description "Save configuration in snapshot";
           type empty;
         }
         leaf no-configuration {
           description "Don't save configuration in snapshot";
           type empty;
         }
       }
     }
     container auto-configuration {
       presence "enable auto-configuration";
       description "System Autoconfiguration";
       status deprecated;
       uses apply-advanced;
       container traceoptions {
         description "Autoconfiguration trace options";
         status deprecated;
         uses autoconf_traceoptions_type;
       }
     }
     container processes {
       description "Process control";
       uses apply-advanced;
       container routing {
         description "Routing process";
         uses apply-advanced;
         choice enable-disable {
           case case_1 {
             leaf disable {
               description "Disable routing process";
               type empty;
             }
           }
         }
         leaf failover {
           description "How to handle failure of routing process";
           type enumeration {
             enum "other-routing-engine" {
               description "On failure, switch mastership to other Routing Engine";
             }
             enum "alternate-media" {
               description "On failure, reboot off alternate media";
             }
           }
         }
         choice mode {
           case case_1 {
             leaf force-32-bit {
               description "Always use 32-bit mode";
               type empty;
             }
           }
           case case_2 {
             leaf force-64-bit {
               description "Always use 64-bit mode";
               type empty;
             }
           }
           case case_3 {
             leaf auto-64-bit {
               description "Use 64-bit mode if RE memory is sufficient";
               type empty;
             }
           }
         }
         container bgp {
           description "BGP protocol control";
           uses apply-advanced;
           container rib-sharding {
             presence "enable rib-sharding";
             description "Enable BGP RIB sharding";
             uses apply-advanced;
             leaf number-of-shards {
               description "Set number of sharding threads";
               type union {
                 type string {
                   pattern "<.*>|$.*";
                 }
                 type uint32 {
                   range "1 .. 31";
                 }
               }
             }
           }
           container update-threading {
             presence "enable update-threading";
             description "Enable BGP update threading";
             uses apply-advanced;
             leaf number-of-threads {
               description "Set number of update threads";
               type union {
                 type string {
                   pattern "<.*>|$.*";
                 }
                 type uint32 {
                   range "1 .. 128";
                 }
               }
             }
             leaf group-split-size {
               description "Threshold value to assign a new update thread for group";
               type union {
                 type string {
                   pattern "<.*>|$.*";
                 }
                 type uint32 {
                   range "0 .. 2000";
                 }
               }
             }
           }
         }
       }
       container software-forwarding {
         description "Software forwarding process";
         choice enable-disable {
           case case_1 {
             leaf disable {
               description "Disable software forwarding process";
               type empty;
             }
           }
         }
       }
       container packet-forwarding-engine {
         description "Packet forwarding engine process";
         choice enable-disable {
           case case_1 {
             leaf disable {
               description "Disable packet forwarding engine process";
               type empty;
             }
           }
         }
       }
       container chassis-control {
         description "Chassis control process";
         choice enable-disable {
           case case_1 {
             leaf disable {
               description "Disable chassis control process";
               type empty;
             }
           }
         }
       }
       container service-pics {
         description "Service PICs process";
         choice enable-disable {
           case case_1 {
             leaf disable {
               description "Disable service PICs process";
               type empty;
             }
           }
         }
         leaf failover {
           description "How to handle failure of service PICs process";
           type enumeration {
             enum "other-routing-engine" {
               description "On failure, switch mastership to other Routing Engine";
             }
             enum "alternate-media" {
               description "On failure, reboot off alternate media";
             }
           }
         }
       }
       container ntp {
         description "Network time process";
         choice enable-disable {
           case case_1 {
             leaf disable {
               description "Disable network time process";
               type empty;
             }
           }
         }
         leaf failover {
           description "How to handle failure of network time process";
           type enumeration {
             enum "other-routing-engine" {
               description "On failure, switch mastership to other Routing Engine";
             }
             enum "alternate-media" {
               description "On failure, reboot off alternate media";
             }
           }
         }
       }
       container watchdog {
         description "Watchdog timer";
         choice enable-disable {
           case case_1 {
             leaf enable {
               description "Enable watchdog timer";
               type empty;
             }
           }
           case case_2 {
             leaf disable {
               description "Disable watchdog timer";
               type empty;
             }
           }
         }
         leaf timeout {
           description "Watchdog timer value";
           units "seconds";
           type union {
             type string {
               pattern "<.*>|$.*";
             }
             type uint32 {
               range "1 .. 3600";
             }
           }
         }
       }
       container process-monitor {
         description "Process health monitor process";
         uses apply-advanced;
         choice enable-disable {
           case case_1 {
             leaf disable {
               description "Disable Process health monitor process";
               type empty;
             }
           }
         }
         container traceoptions {
           description "Process health monitor trace options";
           uses pmond-traceoptions-type;
         }
       }
       container resource-cleanup {
         description "Resource cleanup process";
         uses apply-advanced;
         choice enable-disable {
           case case_1 {
             leaf disable {
               description "Disable Resource cleanup process";
               type empty;
             }
           }
         }
         container traceoptions {
           description "Resource cleanup process trace options";
           uses res-cleanupd-traceoptions-type;
         }
       }
       container routing-socket-proxy {
         description "Routing socket proxy process";
         choice enable-disable {
           case case_1 {
             leaf disable {
               description "Disable routing socket proxy process";
               type empty;
             }
           }
         }
         leaf failover {
           description "How to handle failure of routing socket proxy process";
           type enumeration {
             enum "other-routing-engine" {
               description "On failure, switch mastership to other Routing Engine";
             }
             enum "alternate-media" {
               description "On failure, reboot off alternate media";
             }
           }
         }
       }
       container web-management {
         description "Web management process";
         choice enable-disable {
           case case_1 {
             leaf disable {
               description "Disable web management process";
               type empty;
             }
           }
         }
         leaf failover {
           description "How to handle failure of web management process";
           type enumeration {
             enum "other-routing-engine" {
               description "On failure, switch mastership to other Routing Engine";
             }
             enum "alternate-media" {
               description "On failure, reboot off alternate media";
             }
           }
         }
       }
       container named-service {
         presence "enable named-service";
         description "DNS server process";
         uses apply-advanced;
         choice enable-disable {
           case case_1 {
             leaf disable {
               description "Disable dns server process";
               type empty;
             }
           }
         }
         leaf failover {
           description "How to handle failure of dns server process";
           type enumeration {
             enum "other-routing-engine" {
               description "On failure, switch mastership to other Routing Engine";
             }
             enum "alternate-media" {
               description "On failure, reboot off alternate media";
             }
           }
         }
       }
       container cfm {
         description "Ethernet OAM connectivity fault management process";
         choice enable-disable {
           case case_1 {
             leaf disable {
               description "Disable CFM process";
               type empty;
             }
           }
         }
       }
       container general-authentication-service {
         description "General authentication service process";
         uses apply-advanced;
         choice enable-disable {
           case case_1 {
             leaf disable {
               description "Disable general-authentication service process";
               type empty;
             }
           }
         }
         container traceoptions {
           description "General authentication service trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           container filter {
             presence "enable filter";
             description "Filter to control trace messages";
             uses apply-advanced;
           }
           list flag {
             key name;
             ordered-by user;
             description "Tracing parameters";
             leaf name {
               type enumeration {
                 enum "configuration" {
                   description "Trace configuration events";
                 }
                 enum "framework" {
                   description "Trace authentication framework events";
                 }
                 enum "radius" {
                   description "Trace radius authentication events";
                 }
                 enum "local-authentication" {
                   description "Trace local authentication events";
                 }
                 enum "ldap" {
                   description "Trace ldap authentication events";
                 }
                 enum "address-assignment" {
                   description "Trace address-assignment events";
                 }
                 enum "jsrc" {
                   description "Trace jsrc events";
                 }
                 enum "gx-plus" {
                   description "Trace gx-plus events";
                 }
                 enum "session-db" {
                   description "Trace session DB events";
                 }
                 enum "profile-db" {
                   description "Trace profile DB events";
                 }
                 enum "lib-stats" {
                   description "Trace lib stats events";
                 }
                 enum "user-access" {
                   description "Trace subscriber events";
                 }
                 enum "nasreq" {
                   description "Trace nasreq events";
                 }
                 enum "ocs-backup" {
                   description "Trace osc-backup events";
                 }
                 enum "s6a" {
                   description "Trace s6a events";
                 }
                 enum "nas-5g" {
                   description "Trace nas-5g events";
                 }
                 enum "saml" {
                   description "Trace saml events";
                 }
                 enum "all" {
                   description "Trace everything";
                 }
               }
             }
           }
         }
       }
       container dhcp-service {
         description "Dynamic Host Configuration Protocol general configuration";
         uses apply-advanced;
         choice enable-disable {
           case case_1 {
             leaf disable {
               description "Disable dhcp service process";
               type empty;
             }
           }
         }
         leaf failover {
           description "How to handle failure of dhcp service process";
           type enumeration {
             enum "other-routing-engine" {
               description "On failure, switch mastership to other Routing Engine";
             }
             enum "alternate-media" {
               description "On failure, reboot off alternate media";
             }
           }
         }
         container persistent-storage {
           description "DHCP persistent storage configuration parameters";
           uses apply-advanced;
           leaf file-name {
             description "File name";
             type string {
               length "1 .. 64";
             }
           }
           leaf backup-interval {
             description "Number of hours after which backup file will be created";
             type union {
               type string {
                 pattern "<.*>|$.*";
               }
               type uint32 {
                 range "1 .. 48";
               }
             }
           }
         }
         container traceoptions {
           description "Trace options for DHCP";
           uses jdhcp-traceoptions-level-type;
         }
         container interface-traceoptions {
           description "Interface trace options for DHCP";
           uses jdhcp-interface-traceoptions-level-type;
         }
         container log {
           description "Output the logs";
           uses apply-advanced;
           container session {
             description "Logs of sessions";
             uses apply-advanced;
             leaf client {
               description "Logs of the client";
               type empty;
             }
             leaf server {
               description "Logs of the server";
               type empty;
             }
             leaf relay {
               description "Logs of the relay";
               type empty;
             }
             leaf all {
               description "Logs of the cleint, server and relay";
               type empty;
             }
             container dhcpv6 {
               description "Logs of DHCPv6";
               uses apply-advanced;
               leaf client {
                 description "Logs of the client";
                 type empty;
               }
               leaf server {
                 description "Logs of the server";
                 type empty;
               }
               leaf relay {
                 description "Logs of the relay";
                 type empty;
               }
               leaf dynamic-server {
                 description "Logs of the dynamic-server";
                 type empty;
               }
               leaf all {
                 description "Logs of the cleint, server, relay and dynamic-server";
                 type empty;
               }
             }
           }
         }
         container dhcp-snooping-file {
           description "DHCP snooping persistence file, write-interval and timeout";
           uses apply-advanced;
           leaf location {
             description "Location of DHCP snooping entries file";
             type jt:filename;
           }
           leaf write-interval {
             description "Time interval for writing DHCP snooping entries";
             units "seconds";
             type union {
               type string {
                 pattern "<.*>|$.*";
               }
               type uint32 {
                 range "60 .. 86400";
               }
             }
           }
         }
         container dhcpv6-snooping-file {
           description "DHCPv6 snooping persistence file and write-interval timeout";
           uses apply-advanced;
           leaf location {
             description "Location of DHCPv6 snooping entries file";
             type jt:filename;
           }
           leaf write-interval {
             description "Time interval in seconds for writing DHCPv6 snooping entries";
             units "seconds";
             type union {
               type string {
                 pattern "<.*>|$.*";
               }
               type uint32 {
                 range "60 .. 86400";
               }
             }
           }
         }
         container ltv-syslog-interval {
           description "Lease time violation syslog interval";
           uses apply-advanced;
           leaf syslog-interval {
             description "Syslog interval in secs";
             units "seconds";
             type union {
               type string {
                 pattern "<.*>|$.*";
               }
               type uint32 {
                 range "600 .. 86400";
               }
             }
           }
         }
         leaf accept-max-tcp-connections {
           description "Max TCP connections served globally at a time";
           default "5";
           type union {
             type string {
               pattern "<.*>|$.*";
             }
             type uint32 {
               range "1 .. 100";
             }
           }
         }
         leaf request-max-tcp-connections {
           description "Max TCP connections requested globally at a time";
           default "3";
           type union {
             type string {
               pattern "<.*>|$.*";
             }
             type uint32 {
               range "1 .. 100";
             }
           }
         }
         leaf max-leasequery-reply-packet-retries {
           description "Max TCP connections requested globally at a time";
           default "5";
           type union {
             type string {
               pattern "<.*>|$.*";
             }
             type uint32 {
               range "0 .. 10000";
             }
           }
         }
         leaf leasequery-reply-packet-retry-timer {
           description "Max TCP connections requested globally at a time";
           default "10";
           type union {
             type string {
               pattern "<.*>|$.*";
             }
             type uint32 {
               range "0 .. 10000";
             }
           }
         }
         leaf max-leasequery-reply-packet-process {
           description "Max TCP connections requested globally at a time";
           default "100";
           type union {
             type string {
               pattern "<.*>|$.*";
             }
             type uint32 {
               range "0 .. 1000000";
             }
           }
         }
         leaf era-logging-disable {
           description "DHCP era logging disable";
           type empty;
         }
       }
       container diameter-service {
         description "Diameter process";
         uses apply-advanced;
         choice enable-disable {
           case case_1 {
             leaf disable {
               description "Disable diameter process";
               type empty;
             }
           }
         }
         container traceoptions {
           description "Diameter service trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           list flag {
             key name;
             ordered-by user;
             description "Aread to enabe debugging output";
             leaf name {
               type enumeration {
                 enum "framework" {
                   description "Trace Diameter framework";
                 }
                 enum "configuration" {
                   description "Trace configuration events";
                 }
                 enum "memory-management" {
                   description "Trace memory management events";
                 }
                 enum "daemon" {
                   description "Trace daemon level events";
                 }
                 enum "application" {
                   description "Trace Diameter application interface";
                 }
                 enum "node" {
                   description "Trace Diameter node events";
                 }
                 enum "diameter-instance" {
                   description "Trace Diameter instance events";
                 }
                 enum "dne" {
                   description "Trace Diameter DNE events";
                 }
                 enum "peer" {
                   description "Trace Diameter peer events";
                 }
                 enum "messages" {
                   description "Trace Diameter messages";
                 }
                 enum "all" {
                   description "Trace everything";
                 }
               }
             }
           }
         }
       }
       container sbc-configuration-process {
         description "SBC configuration process";
         uses apply-advanced;
         choice enable-disable {
           case case_1 {
             leaf disable {
               description "Disable SBC configuration process";
               type empty;
             }
           }
         }
         leaf failover {
           description "How to handle failure of SBC configuration process";
           type enumeration {
             enum "other-routing-engine" {
               description "On failure, switch mastership to other Routing Engine";
             }
             enum "alternate-media" {
               description "On failure, reboot off alternate media";
             }
           }
         }
         container traceoptions {
           description "SBC configuration process trace options";
           uses sbc_traceoptions;
         }
       }
       container sdk-service {
         description "SDK Service Daemon";
         uses apply-advanced;
         choice enable-disable {
           case case_1 {
             leaf disable {
               description "Disable SDK Service Daemon";
               type empty;
             }
           }
         }
         container traceoptions {
           description "SDK Service Daemon trace options";
           uses ssd-traceoptions-type;
         }
       }
       container aaad {
         description "AAAD process";
         uses apply-advanced;
         choice enable-disable {
           case case_1 {
             leaf disable {
               description "Disable AAAD process";
               type empty;
             }
           }
         }
         container traceoptions {
           description "AAA trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           list flag {
             key name;
             ordered-by user;
             description "Tracing parameters";
             leaf name {
               type enumeration {
                 enum "send" {
                   description "Trace transmitted packets";
                 }
                 enum "send-detail" {
                   description "Trace transmitted packets in detail";
                 }
                 enum "receive" {
                   description "Trace received packets";
                 }
                 enum "receive-detail" {
                   description "Trace received packets in detail";
                 }
                 enum "timeout" {
                   description "Trace timeout events";
                 }
                 enum "state" {
                   description "Trace DIAMTER peer state changes";
                 }
                 enum "all" {
                   description "Trace everything";
                 }
               }
             }
           }
           list peer {
             key name;
             ordered-by user;
             description "Trace packet sent to or received from the peer[s]";
             leaf name {
               description "Trace packet sent to or received from the peer";
               type string {
                 length "1 .. 31";
               }
             }
             uses apply-advanced;
           }
         }
       }
       container app-engine-management-service {
         description "App-engine Management Daemon";
         uses apply-advanced;
         choice enable-disable {
           case case_1 {
             leaf disable {
               description "Disable SDK Management Daemon";
               type empty;
             }
           }
         }
         container traceoptions {
           description "App-engine management daemon trace options";
           uses sdk-mgmtd-traceoptions-type;
         }
       }
       container send {
         description "Secure Neighbor Discovery Protocol process";
         choice enable-disable {
           case case_1 {
             leaf disable {
               description "Disable SEND process";
               type empty;
             }
           }
         }
       }
       container static-subscribers {
         description "Static subscribers process";
         uses apply-advanced;
         choice enable-disable {
           case case_1 {
             leaf disable {
               description "Disable static-subscribers process";
               type empty;
             }
           }
         }
       }
       container extensible-subscriber-services {
         description "Extensible Subscriber Services Manager Daemon";
         uses apply-advanced;
         choice enable-disable {
           case case_1 {
             leaf disable {
               description "Disable Extensible Subscriber Services Manager Daemon";
               type empty;
             }
           }
         }
       }
       list daemon-process {
         key name;
         ordered-by user;
         uses daemon-process;
       }
       container video-monitoring {
         description "Video Monitoring Process";
         choice enable-disable {
           case case_1 {
             leaf disable {
               description "Disable video monitoring process";
               type empty;
             }
           }
         }
         container traceoptions {
           description "Trace options for VMOND";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
       }
       container remote-device-management {
         description "Remote device management daemon";
         uses apply-advanced;
         choice enable-disable {
           case case_1 {
             leaf disable {
               description "Disable Remote Device Management Daemon";
               type empty;
             }
           }
         }
       }
     }
     container ntp {
       description "Network Time Protocol services";
       uses apply-advanced;
       leaf boot-server {
         description "Server to query during boot sequence";
         status deprecated;
         type jt:ipaddr;
       }
       container interval-range {
         description "Set the minpoll and maxpoll interval range";
         leaf value {
           description "The poll interval range";
           type union {
             type string {
               pattern "<.*>|$.*";
             }
             type int32 {
               range "0 .. 3";
             }
           }
         }
       }
       list authentication-key {
         key name;
         ordered-by user;
         description "Authentication key information";
         leaf name {
           description "Authentication key number";
           type union {
             type string {
               pattern "<.*>|$.*";
             }
             type uint32 {
               range "1 .. 65534";
             }
           }
         }
         leaf type {
           description "Authentication key type";
           type enumeration {
             enum "md5" {
               description "MD5 authentication key";
             }
             enum "des" {
               description "DES authentication key";
             }
             enum "sha1" {
               description "Secure Hash Algorithm 1";
             }
             enum "sha256" {
               description "Secure Hash Algorithm 2-256";
             }
           }
         }
         leaf value {
           description "Authentication key value";
           type jt:unreadable;
         }
       }
       list peer {
         key name;
         ordered-by user;
         description "Peer parameters";
         leaf name {
           description "Name or address of peer";
           type jt:ipaddr;
         }
         leaf key {
           description "Authentication key";
           type union {
             type string {
               pattern "<.*>|$.*";
             }
             type uint32 {
               range "1 .. 65534";
             }
           }
         }
         leaf version {
           description "NTP version to use";
           type union {
             type string {
               pattern "<.*>|$.*";
             }
             type uint32 {
               range "1 .. 4";
             }
           }
         }
         leaf prefer {
           description "Prefer this peer_serv";
           type empty;
         }
       }
       list server {
         key name;
         ordered-by user;
         description "Server parameters";
         leaf name {
           description "Name or address of server";
           type jt:hostname;
         }
         leaf key {
           description "Authentication key";
           type union {
             type string {
               pattern "<.*>|$.*";
             }
             type uint32 {
               range "1 .. 65534";
             }
           }
         }
         leaf version {
           description "NTP version to use";
           type union {
             type string {
               pattern "<.*>|$.*";
             }
             type uint32 {
               range "1 .. 4";
             }
           }
         }
         leaf prefer {
           description "Prefer this peer_serv";
           type empty;
         }
         leaf routing-instance {
           description "Routing instance through which server is reachable";
           type string {
           }
         }
         container nts {
           presence "enable nts";
           description "Enable NTS protocol for this server";
           container remote-identity {
             description "Remote identity of server for verification";
             choice remote-id-type {
               case case_1 {
                 container distinguished-name {
                   description "Use a distinguished name of server";
                   uses apply-advanced;
                   choice name-type {
                     case case_1 {
                       leaf container {
                         description "Specify the container string";
                         type string;
                       }
                     }
                     case case_2 {
                       leaf wildcard {
                         description "Specify the wildcard string";
                         type string;
                       }
                     }
                   }
                 }
               }
               case case_2 {
                 leaf hostname {
                   description "Use a fully-qualified domain name";
                   type string;
                 }
               }
             }
           }
         }
       }
       list broadcast {
         key name;
         ordered-by user;
         description "Broadcast parameters";
         leaf name {
           description "Broadcast or multicast address to use";
           type jt:ipaddr;
         }
         leaf routing-instance-name {
           description "Routing intance name in which interface has address in broadcast subnet";
           type string {
           }
         }
         leaf key {
           description "Authentication key";
           type union {
             type string {
               pattern "<.*>|$.*";
             }
             type uint32 {
               range "1 .. 65534";
             }
           }
         }
         leaf version {
           description "NTP version to use";
           type union {
             type string {
               pattern "<.*>|$.*";
             }
             type uint32 {
               range "1 .. 4";
             }
           }
         }
         leaf ttl {
           description "TTL value to transmit";
           type union {
             type string {
               pattern "<.*>|$.*";
             }
             type uint32 {
               range "1 .. 255";
             }
           }
         }
       }
       leaf broadcast-client {
         description "Listen to broadcast NTP";
         type empty;
       }
       container multicast-client {
         presence "enable multicast-client";
         description "Listen to multicast NTP";
         leaf address {
           description "Multicast address to listen to";
           type jt:ipaddr;
         }
       }
       leaf-list trusted-key {
         ordered-by user;
         description "List of trusted authentication keys";
         type union {
           type string {
             pattern "<.*>|$.*";
           }
           type uint32 {
             range "1 .. 65534";
           }
         }
       }
       list restrict {
         key name;
         ordered-by user;
         description "Restrict options";
         leaf name {
           description "Address of a host or network";
           type string;
         }
         leaf mask {
           description "Mask address of host or network";
           type string;
         }
         leaf noquery {
           description "Deny ntpq and ntpdc queries";
           type empty;
         }
       }
       container threshold {
         description "Set the maximum threshold(sec) allowed for NTP adjustment";
         leaf value {
           description "The maximum value(sec) allowed for NTP adjustment";
           type union {
             type string {
               pattern "<.*>|$.*";
             }
             type int32 {
               range "1 .. 600";
             }
           }
         }
         leaf action {
           description "Select actions for NTP abnormal adjustment";
           type enumeration {
             enum "accept" {
               description "Enable log mode for abnormal NTP adjustment";
             }
             enum "reject" {
               description "Enable reject mode for abnormal NTP adjustment";
             }
           }
         }
       }
       list source-address {
         key name;
         ordered-by user;
         description "Source-Address parameters";
         leaf name {
           description "Use specified address as source address";
           type jt:ipaddr;
         }
         leaf routing-instance {
           description "Routing instance name in which source address is defined";
           type string {
           }
         }
       }
       container nts {
         description "NTS Configuration";
         leaf local-certificate {
           description "Local Certificate ID for NTS-KE server";
           type string {
           }
         }
         container trusted-ca {
           description "Specify the trusted CA to use for verifying server certificate";
           choice ca {
             case case_1 {
               leaf trusted-ca-profile {
                 description "Name of the trusted CA profile to use";
                 type string;
               }
             }
             case case_2 {
               leaf trusted-ca-group {
                 description "Name of the trusted CA group to use";
                 type string;
               }
             }
           }
         }
       }
     }
     container monitor {
       description "Monitoring system for system and daemons";
       uses apply-advanced;
       container traceoptions {
         description "System monitoring daemon trace options";
         uses apply-advanced;
         leaf level {
           type enumeration {
             enum "error" {
               description "Trace error messages";
             }
             enum "warning" {
               description "Trace warning messages";
             }
             enum "debug" {
               description "Trace debug messages";
             }
             enum "info" {
               description "Trace info messages";
             }
             enum "critical" {
               description "Trace critical messages";
             }
             enum "all" {
               description "Trace all messages";
             }
           }
         }
         container file {
           description "Monitoring system for system and daemons";
           uses apply-advanced;
           leaf filename {
             description "Name of file in which to write trace information";
             type string {
               length "1 .. 1024";
             }
           }
           leaf size {
             description "Size of the each log file in MB(s)";
             type union {
               type string {
                 pattern "<.*>|$.*";
               }
               type uint32 {
                 range "1 .. 100";
               }
             }
           }
           leaf files {
             description "Number of log files";
             type union {
               type string {
                 pattern "<.*>|$.*";
               }
               type uint32 {
                 range "1 .. 10";
               }
             }
           }
         }
         list flag {
           key name;
           ordered-by user;
           description "Tracing parameters";
           leaf name {
             type enumeration {
               enum "infra" {
                 description "Trace jsysmond infrastructure events";
               }
               enum "alarm" {
                 description "Trace jsysmond alarm events";
               }
               enum "event" {
                 description "Trace jsysmond kevents";
               }
               enum "all" {
                 description "Trace everything in jsysmond";
               }
             }
           }
         }
       }
       container memory {
         description "Memory monitoring system";
         uses apply-advanced;
         container system {
           description "System level memory monitoring";
           uses apply-advanced;
           container frequency {
             description "Frequency of system monitoring";
             uses apply-advanced;
             choice frequency-choice {
               case case_1 {
                 leaf days {
                   description "In days";
                   type union {
                     type string {
                       pattern "<.*>|$.*";
                     }
                     type uint32 {
                       range "1 .. 65535";
                     }
                   }
                 }
               }
               case case_2 {
                 leaf hours {
                   description "In hours";
                   type union {
                     type string {
                       pattern "<.*>|$.*";
                     }
                     type uint32 {
                       range "1 .. 65535";
                     }
                   }
                 }
               }
               case case_3 {
                 leaf minutes {
                   description "In minutes";
                   type union {
                     type string {
                       pattern "<.*>|$.*";
                     }
                     type uint32 {
                       range "1 .. 65535";
                     }
                   }
                 }
               }
             }
           }
           container critical-event {
             description "Critical event - high attention";
             uses apply-advanced;
             container threshold {
               description "System threshold level for critical event";
               uses apply-advanced;
               leaf swap-usage {
                 description "Swap usage in percentage";
                 type union {
                   type string {
                     pattern "<.*>|$.*";
                   }
                   type uint32 {
                     range "1 .. 100";
                   }
                 }
               }
             }
             leaf-list actions {
               ordered-by user;
               description "Actions on a critical event";
               type enumeration {
                 enum "snmp-trap" {
                   description "Make SNMP-trap when critical event occurred";
                 }
                 enum "live-vmcore" {
                   description "Create a live-vmcore when critical event occurred";
                 }
                 enum "re-switchover" {
                   description "Attempt switchover when critical event occurred";
                 }
                 enum "re-restart" {
                   description "Restart the RE when critical event occurred";
                 }
               }
             }
           }
           container major-event {
             description "Major event - medium attention";
             uses apply-advanced;
             container threshold {
               description "System threshold level for major event";
               uses apply-advanced;
               leaf swap-usage {
                 description "Swap usage in percentage";
                 type union {
                   type string {
                     pattern "<.*>|$.*";
                   }
                   type uint32 {
                     range "1 .. 100";
                   }
                 }
               }
             }
             leaf-list actions {
               ordered-by user;
               description "Actions on a Major event";
               type enumeration {
                 enum "snmp-trap" {
                   description "Make SNMP-trap when major event occurred";
                 }
                 enum "live-vmcore" {
                   description "Create a live-vmcore when major event occurred";
                 }
               }
             }
           }
           container minor-event {
             description "Minor event - low attention";
             uses apply-advanced;
             container threshold {
               description "System threshold level for minor event";
               uses apply-advanced;
               leaf swap-usage {
                 description "Swap usage in percentage";
                 type union {
                   type string {
                     pattern "<.*>|$.*";
                   }
                   type uint32 {
                     range "1 .. 100";
                   }
                 }
               }
             }
             leaf-list actions {
               ordered-by user;
               description "Actions on a minor event";
               type enumeration {
                 enum "snmp-trap" {
                   description "Make SNMP-trap when minor event occurred";
                 }
               }
             }
           }
           leaf alarm {
             description "System-monitor alarm enable";
             type empty;
           }
         }
         container process {
           description "Process level memory monitoring";
           uses apply-advanced;
           container frequency {
             description "Frequency of process monitoring";
             uses apply-advanced;
             choice frequency-choice {
               case case_1 {
                 leaf days {
                   description "In days";
                   type union {
                     type string {
                       pattern "<.*>|$.*";
                     }
                     type uint32 {
                       range "1 .. 65535";
                     }
                   }
                 }
               }
               case case_2 {
                 leaf hours {
                   description "In hours";
                   type union {
                     type string {
                       pattern "<.*>|$.*";
                     }
                     type uint32 {
                       range "1 .. 65535";
                     }
                   }
                 }
               }
               case case_3 {
                 leaf minutes {
                   description "In minutes";
                   type union {
                     type string {
                       pattern "<.*>|$.*";
                     }
                     type uint32 {
                       range "1 .. 65535";
                     }
                   }
                 }
               }
             }
           }
           container critical-event {
             description "Critical event - high attention";
             uses apply-advanced;
             list threshold {
               key name;
               ordered-by user;
               description "Process threshold level for critical event";
               leaf name {
                 description "Process name to be monitored";
                 type string;
               }
               uses apply-advanced;
               leaf memory-limit {
                 description "Memory limit ";
                 units "MB";
                 type union {
                   type string {
                     pattern "<.*>|$.*";
                   }
                   type uint32 {
                     range "1 .. 65535";
                   }
                 }
               }
             }
             leaf-list actions {
               ordered-by user;
               description "Actions on a critical event";
               type enumeration {
                 enum "snmp-trap" {
                   description "Make SNMP-trap when critical event occurred";
                 }
                 enum "live-core" {
                   description "Create a live core(gcore) when critical event occured";
                 }
                 enum "terminate-process-force" {
                   description "Terminate the process when critical event occurred";
                 }
                 enum "terminate-process" {
                   description "Terminate the process with force when critical event occurred";
                 }
               }
             }
           }
           container major-event {
             description "Major event - medium attention";
             uses apply-advanced;
             list threshold {
               key name;
               ordered-by user;
               description "Process threshold level for major event";
               leaf name {
                 description "Process name to be monitored";
                 type string;
               }
               uses apply-advanced;
               leaf memory-limit {
                 description "Memory limit ";
                 units "MB";
                 type union {
                   type string {
                     pattern "<.*>|$.*";
                   }
                   type uint32 {
                     range "1 .. 65535";
                   }
                 }
               }
             }
             leaf-list actions {
               ordered-by user;
               description "Actions on a Major event";
               type enumeration {
                 enum "snmp-trap" {
                   description "Make SNMP-trap when major event occurred";
                 }
                 enum "live-core" {
                   description "Create a live core(gcore) when major event occured";
                 }
                 enum "terminate-process-force" {
                   description "Terminate the process when major event occurred";
                 }
                 enum "terminate-process" {
                   description "Terminate the process with force when major event occurred";
                 }
               }
             }
           }
           container minor-event {
             description "Minor event - low attention";
             uses apply-advanced;
             list threshold {
               key name;
               ordered-by user;
               description "Process threshold level for minor event";
               leaf name {
                 description "Process name to be monitored";
                 type string;
               }
               uses apply-advanced;
               leaf memory-limit {
                 description "Memory limit ";
                 units "MB";
                 type union {
                   type string {
                     pattern "<.*>|$.*";
                   }
                   type uint32 {
                     range "1 .. 65535";
                   }
                 }
               }
             }
             leaf-list actions {
               ordered-by user;
               description "Actions on a minor event";
               type enumeration {
                 enum "snmp-trap" {
                   description "Make SNMP-trap when minor event occurred";
                 }
               }
             }
           }
         }
       }
     }
     container node-health-monitor {
       description "Node Health Monitoring Configuration";
       uses apply-advanced;
       leaf refresh-interval {
         description "Node Health Monitoring Refresh Interval";
         default "120";
         units "seconds";
         type union {
           type string {
             pattern "<.*>|$.*";
           }
           type uint32 {
             range "60 .. 86400";
           }
         }
       }
     }
     container master-password {
       description "Master password for $8$ password-encryption";
       uses apply-advanced;
       leaf iteration-count {
         description "Define PBKDF2 iteration count";
         default "100";
         type union {
           type string {
             pattern "<.*>|$.*";
           }
           type uint32 {
             range "10 .. 10000";
           }
         }
       }
       leaf pseudorandom-function {
         description "Define PBKDF2 PRF";
         default "hmac-sha2-256";
         type enumeration {
           enum "hmac-sha2-256" {
             description "HMAC-SHA2-256 authentication algorithm";
           }
           enum "hmac-sha1" {
             description "HMAC-SHA1 authentication algorithm";
           }
           enum "hmac-sha2-512" {
             description "HMAC-SHA2-512 authentication algorithm";
           }
         }
       }
     }
     container pixel-tracing {
       description "Pixel tracing";
       uses apply-advanced;
       leaf level {
         description " Enable pixel log level";
         type enumeration {
           enum "info" {
             description "Important information";
           }
           enum "critical" {
             description "Critical information";
           }
           enum "debug" {
             description "Enable debug";
           }
           enum "any" {
             description "All levels";
           }
           enum "none" {
             description "No messages";
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping archive-object {
     uses apply-advanced;
     leaf size {
       description "Size of files to be archived";
       units "bytes";
       type string;
     }
     leaf files {
       description "Number of files to be archived";
       type string;
     }
     choice world-readable-choice {
       leaf world-readable {
         description "Allow any user to read the log file";
         type empty;
       }
       leaf no-world-readable {
         description "Don't allow any user to read the log file";
         type empty;
       }
     }
     choice binary-data-choice {
       leaf binary-data {
         description "Mark file as if it contains binary data";
         type empty;
       }
       leaf no-binary-data {
         description "Don't mark file as if it contains binary data";
         type empty;
       }
     }
     leaf transfer-interval {
       description "Frequency at which to transfer files to archive sites";
       units "minutes";
       type union {
         type string {
           pattern "<.*>|$.*";
         }
         type uint32 {
           range "5 .. 2880";
         }
       }
     }
     leaf start-time {
       description "Start time for file transmission (yyyy-mm-dd.hh:mm)";
       type jt:time;
     }
     list archive-sites {
       key name;
       ordered-by user;
       leaf name {
         description "Primary and failover URLs to receive archive files";
         type string;
       }
       leaf password {
         description "Password for login into the archive site";
         type jt:unreadable;
       }
       leaf routing-instance {
         description "Routing instance";
         type string {
         }
       }
     }
   }
   grouping arp-interface-type {
     description "Logical interface on which to configure ARP aging timer";
     leaf name {
       description "Interface name";
       type union {
         type jt:interface-name;
         type string {
           pattern "<.*>|$.*";
         }
       }
     }
     uses apply-advanced;
     leaf aging-timer {
       description "Change the ARP aging time value";
       units "minutes";
       type union {
         type string {
           pattern "<.*>|$.*";
         }
         type uint32 {
           range "1 .. 600000";
         }
       }
     }
   }
   grouping authentication-object {
     description "Authentication method";
     uses apply-advanced;
     leaf plain-text-password-value {
       description "Plain text password";
       type string;
     }
     leaf encrypted-password {
       description "Encrypted password string";
       type string {
         length "1 .. 128";
       }
     }
     leaf no-public-keys {
       description "Disables SSH public key based authentication";
       type empty;
     }
     list ssh-rsa {
       key name;
       ordered-by user;
       description "Secure shell (SSH) RSA public key string";
       leaf name {
         description "Secure shell (SSH) RSA public key string";
         type string {
         }
       }
       uses apply-advanced;
       leaf key-options {
         description "SSH key options";
         type string;
       }
       leaf from {
         description "Pattern-list of allowed hosts";
         type string {
         }
       }
     }
     list ssh-dsa {
       key name;
       ordered-by user;
       description "Secure shell (SSH) DSA public key string";
       status deprecated;
       leaf name {
         description "Secure shell (SSH) DSA public key string";
         type string {
         }
       }
       uses apply-advanced;
       leaf key-options {
         description "SSH key options";
         type string;
       }
       leaf from {
         description "Pattern-list of allowed hosts";
         type string {
         }
       }
     }
     list ssh-ecdsa {
       key name;
       ordered-by user;
       description "Secure shell (SSH) ECDSA public key string";
       leaf name {
         description "Secure shell (SSH) ECDSA public key string";
         type string {
         }
       }
       uses apply-advanced;
       leaf key-options {
         description "SSH key options";
         type string;
       }
       leaf from {
         description "Pattern-list of allowed hosts";
         type string {
         }
       }
     }
     list ssh-ed25519 {
       key name;
       ordered-by user;
       description "Secure shell (SSH) ED25519 public key string";
       leaf name {
         description "Secure shell (SSH) EC25519 public key string";
         type string {
         }
       }
       uses apply-advanced;
       leaf key-options {
         description "SSH key options";
         type string;
       }
       leaf from {
         description "Pattern-list of allowed hosts";
         type string {
         }
       }
     }
   }
   grouping autoconf_traceoptions_type {
     description "Trace options for autoconfiguration";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of autoconfiguration to enable debugging output";
       leaf name {
         type enumeration {
           enum "configuration" {
             description "Trace configuration";
           }
           enum "interfaces" {
             description "Trace interface database";
           }
           enum "io" {
             description "Trace interface database";
           }
           enum "rtsock" {
             description "Trace routing socket";
           }
           enum "ui" {
             description "Trace user interface";
           }
           enum "auth" {
             description "Trace VLAN authentication";
           }
           enum "all" {
             description "Trace all areas";
           }
         }
       }
     }
   }
   grouping bdbrepd-type {
     description "Database replication configuration";
     uses apply-advanced;
     container traceoptions {
       description "Database replication trace options";
       uses bdbrepd-traceoptions-type;
     }
   }
   grouping bdbrepd-traceoptions-type {
     description "Trace options for Database replication";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Database replication operations to include in debugging trace";
       leaf name {
         type enumeration {
           enum "database" {
             description "Database operations";
           }
           enum "mirror" {
             description "Mirror operations";
           }
           enum "replication" {
             description "Database replication operations";
           }
           enum "ui" {
             description "User Interface operations";
           }
           enum "general" {
             description "Miscellaneous operations";
           }
           enum "session-db" {
             description "Session database operations";
           }
           enum "server" {
             description "Server operations";
           }
           enum "all" {
             description "All operations";
           }
         }
       }
     }
   }
   grouping daemon-process {
     leaf name {
       type string;
     }
     choice enable-disable {
       case case_1 {
         leaf disable {
           description "Disable process";
           type empty;
         }
       }
     }
     leaf failover {
       description "How to handle failure of parameter";
       type enumeration {
         enum "other-routing-engine" {
           description "On failing, switch mastership to other routing engine";
         }
         enum "alternate-media" {
           description "On failing, reboot off alternate media";
         }
       }
     }
     leaf command {
       description "Path to binary for process";
       type string {
         length "1 .. 1024";
       }
     }
   }
   grouping dhcp-traceoptions-type {
     description "Trace options for DHCP server";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of DHCP server process to enable debugging output";
       leaf name {
         type enumeration {
           enum "binding" {
             description "Trace bindings code";
           }
           enum "config" {
             description "Trace configuration code";
           }
           enum "conflict" {
             description "Trace conflict detection code";
           }
           enum "event" {
             description "Trace event code";
           }
           enum "ifdb" {
             description "Trace interface database code";
           }
           enum "io" {
             description "Trace I/O code";
           }
           enum "lease" {
             description "Trace lease code";
           }
           enum "main" {
             description "Trace main loop code";
           }
           enum "misc" {
             description "Trace miscellaneous code";
           }
           enum "option" {
             description "Trace option code";
           }
           enum "packet" {
             description "Trace packet code";
           }
           enum "pool" {
             description "Trace pool code";
           }
           enum "protocol" {
             description "Trace protocol code";
           }
           enum "relay" {
             description "Trace relay code";
           }
           enum "rtsock" {
             description "Trace routing socket code";
           }
           enum "scope" {
             description "Trace scope code";
           }
           enum "signal" {
             description "Trace signal code";
           }
           enum "trace" {
             description "Trace tracing code";
           }
           enum "ui" {
             description "Trace user interface code";
           }
           enum "all" {
             description "Trace all areas of code";
           }
         }
       }
     }
   }
   grouping dynamic-profile-option-object {
     uses apply-advanced;
     leaf versioning {
       description "Enable dynamic profile versioning";
       type empty;
     }
   }
   grouping httpd_traceoptions_type {
     description "Trace options for Web management process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of HTTPD process to enable debugging output";
       leaf name {
         type enumeration {
           enum "configuration" {
             description "Trace configuration";
           }
           enum "mgd" {
             description "Trace MGD requests";
           }
           enum "webauth" {
             description "Trace webauth requests";
           }
           enum "init" {
             description "Trace daemon init process";
           }
           enum "all" {
             description "Trace all areas";
           }
         }
       }
     }
   }
   grouping jdhcp-interface-traceoptions-level-type {
     description "Interface trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Interface trace categories";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
         }
       }
     }
   }
   grouping jdhcp-local-server-type {
     uses apply-advanced;
     container traceoptions {
       description "DHCP local server trace options";
       status deprecated;
       uses jdhcp-traceoptions-type;
     }
     container interface-traceoptions {
       description "DHCP local server interface trace options";
       status deprecated;
       uses jdhcp-interface-traceoptions-type;
     }
     container dhcpv6 {
       description "DHCPv6 configuration";
       uses dhcpv6-local-server-type;
     }
     list pool-match-order {
       key name;
       ordered-by user;
       description "Define order of attribute matching for pool selection";
       leaf name {
         description "Match type";
         type enumeration {
           enum "external-authority" {
             description "External authority handles address selection";
           }
           enum "ip-address-first" {
             description "IP address used first to select a pool";
           }
           enum "option-82" {
             description "Option 82 used in matching of pool";
           }
           enum "option-82-strict" {
             description "Option 82 used in strict matching of pool";
           }
         }
       }
       uses apply-advanced;
     }
     leaf duplicate-clients-on-interface {
       description "Allow duplicate clients on different interfaces in a subnet";
       status deprecated;
       type empty;
     }
     container duplicate-clients-in-subnet {
       description "Allow duplicate clients in a subnet";
       uses jdhcp-duplicate-clients-in-subnet-type;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container authentication {
       description "DHCP authentication";
       uses authentication-type;
     }
     container liveness-detection {
       description "DHCP client liveness detection processing";
       uses dhcp-liveness-detection-type;
     }
     container reconfigure {
       description "DHCP reconfigure processing";
       presence "enable reconfigure";
       uses reconfigure-type;
     }
     container overrides {
       description "DHCP override processing";
       presence "enable overrides";
       uses override-local-server-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container route-suppression {
       description "Suppress access-internal and/or destination route addition";
       uses dhcp-route-suppression-type;
     }
     list group {
       key name;
       description "Define a DHCP local server group";
       uses dhcp-local-server-group;
     }
     list dual-stack-group {
       key name;
       description "Define a DHCP dual stack group";
       uses dhcp-local-server-dual-stack-group;
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject discover and renew";
               type empty;
             }
           }
           case case_2 {
             leaf override-lease {
               description "Override assigned lease time with threshold";
               type empty;
             }
           }
         }
       }
     }
     choice requested-ip-check {
       case case_1 {
         leaf requested-ip-network-match {
           description "Subnet to match server's address for active and giaddr for passive clients";
           default "8";
           type union {
             type string {
               pattern "<.*>|$.*";
             }
             type uint32 {
               range "0 .. 31";
             }
           }
         }
       }
       case case_2 {
         leaf requested-ip-interface-match {
           description "Use incoming-interface's subnet to check";
           type empty;
         }
       }
     }
     leaf no-snoop {
       description "Do not snoop DHCP packets";
       type empty;
     }
     container persistent-storage {
       description "Trigger to enable flat file storage";
       leaf automatic {
         description "Trigger automatically";
         type empty;
       }
     }
     container allow-leasequery {
       description "Allow DHCP leasequery";
       presence "enable allow-leasequery";
       uses server-leasequery-type;
     }
     container remote-id-mismatch {
       description "DHCP client remote-id mismatch";
       presence "enable remote-id-mismatch";
       uses dhcp-remote-id-mismatch-type;
     }
     container reauthenticate {
       presence "enable reauthenticate";
       description "DHCP client reauthenticate processing";
       uses apply-advanced;
       leaf lease-renewal {
         description "Reauthenticate on each renew, rebind, DISCOVER or SOLICIT";
         type empty;
       }
       leaf remote-id-mismatch {
         description "Reauthenticate on remote-id mismatch for renew, rebind and re-negotiation";
         type empty;
       }
       container actual-data-rate-change {
         description "Reauthenticate on data rate change";
         uses actual-data-rate-change-type;
       }
     }
     container allow-bulk-leasequery {
       description "Allow DHCP bulk leasequery";
       presence "enable allow-bulk-leasequery";
       uses server-bulk-leasequery-type;
     }
     container allow-active-leasequery {
       description "Allow DHCP active leasequery";
       presence "enable allow-active-leasequery";
       uses server-active-leasequery-type;
     }
     container active-leasequery {
       description "DHCPv4 active leasequery configuration";
       presence "enable active-leasequery";
       uses active-leasequery-v4-type;
     }
   }
   grouping active-leasequery-v4-type {
     description "Configure active leasequery";
     uses apply-advanced;
     leaf topology-discover {
       description "Topology discovery";
       type empty;
     }
     list peer-address {
       key name;
       description "Server ip address";
       leaf name {
         description "Peer ip address";
         type jt:ipaddr;
       }
       uses apply-advanced;
     }
     list exclude-interface {
       key name;
       ordered-by user;
       description "Exclude interface participating in active leasequery";
       leaf name {
         description "Interface name";
         type union {
           type jt:interface-name;
           type string {
             pattern "<.*>|$.*";
           }
         }
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
   }
   grouping actual-data-rate-change-type {
     description "Reauthenticate on data rate change processing";
     uses apply-advanced;
     container actual-data-rate-upstream {
       description "Actual data rate upstream";
       presence "enable actual-data-rate-upstream";
       uses actual-data-rate-type;
     }
     container actual-data-rate-downstream {
       description "Actual data rate downstream";
       presence "enable actual-data-rate-downstream";
       uses actual-data-rate-type;
     }
   }
   grouping actual-data-rate-type {
     description "Actual data rate type processing";
     uses apply-advanced;
     leaf threshold {
       description "Threshold in kbps";
       type union {
         type uint32;
         type string {
           pattern "<.*>|$.*";
         }
       }
     }
   }
   grouping authentication-type {
     description "DHCP authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container option-82 {
         presence "enable option-82";
         description "Include option 82";
         leaf circuit-id {
           description "Include option 82 circuit-id (sub option 1)";
           type empty;
         }
         leaf remote-id {
           description "Include option 82 remote-id (sub option 2)";
           type empty;
         }
       }
       leaf logical-system-name {
         description "Include logical system name";
         type empty;
       }
       leaf routing-instance-name {
         description "Include routing instance name";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       leaf option-60 {
         description "Include option 60";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcp-liveness-detection-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Address resolution options";
             uses dhcp-arp-nud-liveness-detection-type;
           }
         }
       }
     }
   }
   grouping dhcp-arp-nud-liveness-detection-type {
     description "Address Resolution detection options";
     uses apply-advanced;
     leaf transmit-interval {
       description "Transmit interval for address resolution";
       default "300";
       units "seconds";
       type union {
         type string {
           pattern "<.*>|$.*";
         }
         type uint32 {
           range "300 .. 1800";
         }
       }
     }
     leaf max-consecutive-retries {
       description "Retry attempts";
       default "3";
       type union {
         type string {
           pattern "<.*>|$.*";
         }
         type uint32 {
           range "3 .. 6";
         }
       }
     }
   }
   grouping dhcp-bfd-liveness-detection-type {
     description "Bidirectional Forwarding Detection (BFD) options";
     uses apply-advanced;
     leaf version {
       description "BFD protocol version number";
       default "automatic";
       type enumeration {
         enum "0" {
           description "BFD version 0 (deprecated)";
         }
         enum "1" {
           description "BFD version 1";
         }
         enum "automatic" {
           description "Choose BFD version automatically";
         }
       }
     }
     leaf minimum-interval {
       description "Minimum transmit and receive interval";
       units "milliseconds";
       type union {
         type string {
           pattern "<.*>|$.*";
         }
         type uint32 {
           range "30000 .. 255000";
         }
       }
     }
     leaf minimum-transmit-interval {
       description "Minimum transmit interval";
       status deprecated;
       units "milliseconds";
       type union {
         type string {
           pattern "<.*>|$.*";
         }
         type uint32 {
           range "30000 .. 255000";
         }
       }
     }
     leaf minimum-receive-interval {
       description "Minimum receive interval";
       units "milliseconds";
       type union {
         type string {
           pattern "<.*>|$.*";
         }
         type uint32 {
           range "30000 .. 255000";
         }
       }
     }
     leaf multiplier {
       description "Detection time multiplier";
       default "3";
       type union {
         type string {
           pattern "<.*>|$.*";
         }
         type uint32 {
           range "1 .. 255";
         }
       }
     }
     leaf inline-disable {
       description "Disable inline mode for this BFD session";
       type empty;
     }
     leaf pdu-size {
       description "BFD transport protocol payload size";
       default "24";
       type union {
         type string {
           pattern "<.*>|$.*";
         }
         type uint32 {
           range "24 .. 16000";
         }
       }
     }
     choice adaptation-choice {
       case case_1 {
         leaf no-adaptation {
           description "Disable adaptation";
           type empty;
         }
       }
     }
     container transmit-interval {
       description "Transmit-interval options";
       uses apply-advanced;
       leaf minimum-interval {
         description "Minimum transmit interval";
         units "milliseconds";
         type union {
           type string {
             pattern "<.*>|$.*";
           }
           type uint32 {
             range "30000 .. 255000";
           }
         }
       }
       leaf threshold {
         description "High transmit interval triggering a trap";
         units "milliseconds";
         type union {
           type uint32;
           type string {
             pattern "<.*>|$.*";
           }
         }
       }
     }
     container detection-time {
       description "Detection-time options";
       uses apply-advanced;
       leaf threshold {
         description "High detection-time triggering a trap";
         units "milliseconds";
         type union {
           type uint32;
           type string {
             pattern "<.*>|$.*";
           }
         }
       }
     }
     leaf session-mode {
       description "BFD single-hop or multihop session-mode";
       default "automatic";
       type enumeration {
         enum "automatic" {
           description "Choose session-mode automatically";
         }
         enum "single-hop" {
           description "Use single-hop";
         }
         enum "multihop" {
           description "Use multihop";
         }
       }
     }
     leaf holddown-interval {
       description "Time to hold the session-UP notification to the client";
       default "0";
       units "milliseconds";
       type union {
         type string {
           pattern "<.*>|$.*";
         }
         type uint32 {
           range "0 .. 255000";
         }
       }
     }
   }
   grouping dhcp-liveness-detection-failure-action-type {
     description "Liveness detection failure action options";
     uses apply-advanced;
     choice failure-action-type {
       case case_1 {
         leaf clear-binding {
           description "Clear the client binding";
           type empty;
         }
       }
       case case_2 {
         leaf clear-binding-if-interface-up {
           description "Clear the client binding only if the incoming interface is up";
           type empty;
         }
       }
       case case_3 {
         leaf log-only {
           description "Maintain the client binding and log the failure event";
           type empty;
         }
       }
     }
   }
   grouping dhcp-local-server-dual-stack-group {
     description "DHCP dual stack groups";
     leaf name {
       description "Dual stack group name";
       type string {
         length "1 .. 64";
       }
     }
     uses apply-advanced;
     container authentication {
       description "DHCP authentication";
       uses dual-stack-authentication-type;
     }
     leaf access-profile {
       description "Access profile to be used for jdhcpd";
       type string {
         length "1 .. 128";
       }
     }
     container dynamic-profile {
       description "Dynamic profile to use";
       uses dynamic-profile-type;
     }
     leaf service-profile {
       description "Dynamic profile to use for default service activation";
       type string {
         length "1 .. 128";
       }
     }
     leaf on-demand-address-allocation {
       description "Allocate addresses on demand";
       type empty;
     }
     container classification-key {
       description "Classification key for identifying dual stack household";
       uses classification-types;
     }
     leaf dual-stack-interface-client-limit {
       description "Limit the number of client allowed on an interface";
       type union {
         type string {
           pattern "<.*>|$.*";
         }
         type uint32 {
           range "1 .. 500000";
         }
       }
     }
     container protocol-master {
       description "Select family as protocol master";
       uses jdhcp-dual-stack-protocol-mstr-type;
     }
     container liveness-detection {
       description "DHCP client liveness detection processing";
       uses dhcp-liveness-detection-dualstack-type;
     }
     container reauthenticate {
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping classification-types {
     description "Different mechanisms to identify a single household";
     uses apply-advanced;
     leaf mac-address {
       description "MAC address of client";
       type empty;
     }
     leaf circuit-id {
       description "Circuit-id as key";
       type empty;
     }
     leaf remote-id {
       description "Remote-id as key";
       type empty;
     }
   }
   grouping dhcp-liveness-detection-dualstack-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container layer2-liveness-detection {
             description "Address resolution options";
             uses dhcp-arp-nud-liveness-detection-type;
           }
         }
       }
     }
   }
   grouping dhcp-local-server-group {
     description "DHCP groups";
     leaf name {
       description "Group name";
       type string {
         length "1 .. 64";
       }
     }
     uses apply-advanced;
     container authentication {
       description "DHCP authentication";
       uses authentication-type;
     }
     container liveness-detection {
       description "DHCP client liveness detection processing";
       uses dhcp-liveness-detection-type;
     }
     container reconfigure {
       description "DHCP reconfigure processing";
       presence "enable reconfigure";
       uses reconfigure-type;
     }
     container overrides {
       description "DHCP override processing";
       presence "enable overrides";
       uses override-local-server-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container route-suppression {
       description "Suppress access-internal and/or destination route addition";
       uses dhcp-route-suppression-type;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCP override processing";
         uses override-local-server-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interface tag configuration";
       leaf name {
         description "Interface tag name";
         type string {
           length "1 .. 64";
         }
       }
       uses apply-advanced;
       container overrides {
         description "DHCP override processing";
         uses override-local-server-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject discover and renew";
               type empty;
             }
           }
           case case_2 {
             leaf override-lease {
               description "Override assigned lease time with threshold";
               type empty;
             }
           }
         }
       }
     }
     container remote-id-mismatch {
       description "DHCP client remote-id mismatch";
       presence "enable remote-id-mismatch";
       uses dhcp-remote-id-mismatch-type;
     }
     container reauthenticate {
       presence "enable reauthenticate";
       description "DHCP client reauthenticate processing";
       uses apply-advanced;
       leaf lease-renewal {
         description "Reauthenticate on each renew, rebind, DISCOVER or SOLICIT";
         type empty;
       }
       leaf remote-id-mismatch {
         description "Reauthenticate on remote-id mismatch for renew, rebind and re-negotiation";
         type empty;
       }
       container actual-data-rate-change {
         description "Reauthenticate on data rate change";
         uses actual-data-rate-change-type;
       }
     }
   }
   grouping dhcp-remote-id-mismatch-type {
     description "DHCP client remote-id-mismatch processing";
     uses apply-advanced;
     leaf disconnect {
       description "Disconnect session on remote-id mismatch";
       type empty;
     }
   }
   grouping dhcp-route-suppression-type {
     uses apply-advanced;
     choice dhcp-route-suppression-choice {
       case case_1 {
         leaf access-internal {
           description "Suppress access-internal and destination route addition";
           type empty;
         }
       }
       case case_2 {
         leaf destination {
           description "Suppress destination route addition";
           type empty;
         }
       }
     }
   }
   grouping dhcpv6-local-server-type {
     uses apply-advanced;
     container authentication {
       description "DHCPv6 authentication";
       uses dhcpv6-authentication-type;
     }
     container liveness-detection {
       description "DHCPv6 client liveness detection processing";
       uses dhcpv6-liveness-detection-type;
     }
     container reconfigure {
       description "DHCPv6 reconfigure processing";
       presence "enable reconfigure";
       uses dhcpv6-reconfigure-type;
     }
     container dynamic-profile {
       description "Dynamic profile to use";
       uses dynamic-profile-type;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-local-server-type;
     }
     container route-suppression {
       description "Suppress access-internal and/or access route addition";
       uses dhcpv6-route-suppression-type;
     }
     list group {
       key name;
       description "Define a DHCPv6 local server group";
       uses dhcpv6-local-server-group;
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject solicit and renew";
               type empty;
             }
           }
           case case_2 {
             leaf override-lease {
               description "Override assigned lease time with threshold";
               type empty;
             }
           }
         }
       }
     }
     choice requested-ip-check {
       case case_1 {
         leaf requested-ip-network-match {
           description "Subnet to match server's address for active and link-address for passive clients";
           default "16";
           type union {
             type string {
               pattern "<.*>|$.*";
             }
             type uint32 {
               range "0 .. 127";
             }
           }
         }
       }
       case case_2 {
         leaf requested-ip-interface-match {
           description "Use incoming-interface's subnet to check";
           type empty;
         }
       }
     }
     leaf no-snoop {
       description "Do not snoop DHCPV6 packets";
       type empty;
     }
     container persistent-storage {
       description "Trigger to enable flat file storage";
       leaf automatic {
         description "Trigger automatically";
         type empty;
       }
     }
     container server-duid-type {
       description "Define the DUID type to be used as the Server ID. Type supported is DUID-LL";
       uses duid-type;
     }
     container remote-id-mismatch {
       description "DHCP client remote-id mismatch";
       presence "enable remote-id-mismatch";
       uses dhcp-remote-id-mismatch-type;
     }
     container reauthenticate {
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
     container allow-leasequery {
       description "Allow DHCPv6 leasequery";
       presence "enable allow-leasequery";
       uses server-leasequery-type;
     }
     container allow-bulk-leasequery {
       description "Allow DHCPv6 bulk leasequery";
       presence "enable allow-bulk-leasequery";
       uses server-bulk-leasequery-type;
     }
     container allow-active-leasequery {
       description "Allow DHCPv6 active leasequery";
       presence "enable allow-active-leasequery";
       uses server-active-leasequery-type;
     }
     container duplicate-clients {
       description "Allow duplicate clients";
       uses dhcpv6-duplicate-clients-type;
     }
     container active-leasequery {
       description "DHCPv6 active leasequery configuration";
       presence "enable active-leasequery";
       uses active-leasequery-v6-type;
     }
   }
   grouping active-leasequery-v6-type {
     description "Configure active leasequery";
     uses apply-advanced;
     leaf topology-discover {
       description "Topology discovery";
       type empty;
     }
     list exclude-interface {
       key name;
       ordered-by user;
       description "Exclude interface participating in active leasequery";
       leaf name {
         description "Interface name";
         type union {
           type jt:interface-name;
           type string {
             pattern "<.*>|$.*";
           }
         }
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
     list peer-address {
       key name;
       description "Peer ipv6 address";
       leaf name {
         description "Peer ipv6 address";
         type jt:ipv6addr;
       }
       uses apply-advanced;
     }
   }
   grouping dhcpv6-authentication-type {
     description "DHCPv6 authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       container relay-agent-remote-id {
         presence "enable relay-agent-remote-id";
         description "Include the relay agent remote ID";
         uses apply-advanced;
         choice relay-agent-remote-id-choice {
           case case_1 {
             leaf enterprise-id {
               description "Only use enterprise-id portion of option-37";
               status deprecated;
               type empty;
             }
           }
           case case_2 {
             leaf remote-id {
               description "Only use remote-id portion of option-37";
               status deprecated;
               type empty;
             }
           }
         }
       }
       leaf logical-system-name {
         description "Include logical system name";
         type empty;
       }
       leaf routing-instance-name {
         description "Include routing instance name";
         type empty;
       }
       leaf relay-agent-subscriber-id {
         description "Include the relay agent subscriber ID";
         type empty;
       }
       leaf relay-agent-interface-id {
         description "Include the relay agent interface ID";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcpv6-duplicate-clients-type {
     description "Allow duplicate clients";
     choice distinguish-with {
       case case_1 {
         leaf incoming-interface {
           description "Allow duplicate clients on different underlying interfaces";
           type empty;
         }
       }
     }
   }
   grouping dhcpv6-liveness-detection-type {
     description "DHCPv6 client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Neighbor discovery options";
             uses dhcp-arp-nud-liveness-detection-type;
           }
         }
       }
     }
   }
   grouping dhcpv6-local-server-group {
     description "DHCP groups";
     leaf name {
       description "Group name";
       type string {
         length "1 .. 64";
       }
     }
     uses apply-advanced;
     container authentication {
       description "DHCP authentication";
       uses dhcpv6-authentication-type;
     }
     container liveness-detection {
       description "DHCPv6 client liveness detection processing";
       uses dhcpv6-liveness-detection-type;
     }
     container reconfigure {
       description "DHCPv6 reconfigure processing";
       presence "enable reconfigure";
       uses dhcpv6-reconfigure-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       uses dhcpv6-override-local-server-type;
     }
     container route-suppression {
       description "Suppress access-internal and/or access route addition";
       uses dhcpv6-route-suppression-type;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCP override processing";
         uses dhcpv6-override-local-server-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interface tag configuration";
       leaf name {
         description "Interface tag name";
         type string {
           length "1 .. 64";
         }
       }
       uses apply-advanced;
       container overrides {
         description "DHCP override processing";
         uses dhcpv6-override-local-server-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject solicit and renew";
               type empty;
             }
           }
           case case_2 {
             leaf override-lease {
               description "Override assigned lease time with threshold";
               type empty;
             }
           }
         }
       }
     }
     container remote-id-mismatch {
       description "DHCP client remote-id mismatch";
       presence "enable remote-id-mismatch";
       uses dhcp-remote-id-mismatch-type;
     }
     container reauthenticate {
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
   }
   grouping dhcpv6-override-local-server-type {
     description "DHCP override processing";
     uses apply-advanced;
     leaf interface-client-limit {
       description "Limit the number of clients allowed on an interface";
       type union {
         type string {
           pattern "<.*>|$.*";
         }
         type uint32 {
           range "1 .. 500000";
         }
       }
     }
     leaf rapid-commit {
       description "Enable rapid commit processing";
       type empty;
     }
     container client-negotiation-match {
       description "Use secondary match criteria for SOLICIT PDU";
       choice match-with {
         case case_1 {
           leaf incoming-interface {
             description "Use incoming interface";
             type empty;
           }
         }
       }
     }
     container process-inform {
       presence "enable process-inform";
       description "Process INFORMATION request PDUs";
       uses apply-advanced;
       leaf pool {
         description "Pool name for family inet6";
         type string {
           length "1 .. 64";
         }
       }
     }
     container delay-advertise {
       description "Filter options for dhcp-server";
       presence "enable delay-advertise";
       uses dhcpv6-filter-option;
     }
     leaf delegated-pool {
       description "Delegated pool name for inet6";
       type string {
         length "1 .. 64";
       }
     }
     leaf multi-address-embedded-option-response {
       description "If the client requests multiple addresses place the options in each address";
       type empty;
     }
     leaf always-process-option-request-option {
       description "Always process option even after address allocation failure";
       type empty;
     }
     leaf delete-binding-on-renegotiation {
       description "Delete binding on renegotiation";
       type empty;
     }
     leaf top-level-status-code {
       description "A top level status code option rather than encapsulated in IA for NoAddrsAvail in Advertise PDUs";
       type empty;
     }
     leaf always-add-option-dns-server {
       description "Add option-23, DNS recursive name server in Advertise and Reply";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
     leaf protocol-attributes {
       description "DHCPv6 attributes to use as defined under access protocol-attributes";
       type string {
         length "1 .. 64";
       }
     }
     leaf dual-stack {
       description "Dual stack group to use";
       type string {
         length "1 .. 64";
       }
     }
   }
   grouping dhcpv6-filter-option {
     description "Generic DHCPv6 filter processing";
     uses apply-advanced;
     leaf delay-time {
       description "Time delay between solicit and advertise";
       default "3";
       units "seconds";
       type union {
         type string {
           pattern "<.*>|$.*";
         }
         type uint32 {
           range "1 .. 30";
         }
       }
     }
     container based-on {
       description "Option number";
       uses apply-advanced;
       container option-18 {
         presence "enable option-18";
         description "Option 18";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-37 {
         presence "enable option-37";
         description "Option 37";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-15 {
         presence "enable option-15";
         description "Option 15";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-16 {
         presence "enable option-16";
         description "Option 16";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
     }
   }
   grouping dhcpv6-reconfigure-type {
     description "DHCPv6 reconfigure processing";
     uses apply-advanced;
     leaf strict {
       description "Only allow packets containing Reconfigure Accept Option";
       type empty;
     }
     leaf clear-on-abort {
       description "Delete client on reconfiguration abort";
       type empty;
     }
     leaf defer-nack-on-abort {
       description "Defer client NACK on reconfiguration abort";
       type empty;
     }
     leaf attempts {
       description "Number of reconfigure attempts before aborting";
       type union {
         type string {
           pattern "<.*>|$.*";
         }
         type uint32 {
           range "1 .. 10";
         }
       }
     }
     leaf timeout {
       description "Initial timeout value for retry";
       type union {
         type string {
           pattern "<.*>|$.*";
         }
         type uint32 {
           range "1 .. 10";
         }
       }
     }
     leaf token {
       description "Reconfigure token";
       type string {
         length "1 .. 244";
       }
     }
     container trigger {
       description "DHCP reconfigure trigger";
       uses reconfigure-trigger-type;
     }
     leaf support-option-pd-exclude {
       description "Request prefix exclude option in reconfigure message";
       type empty;
     }
   }
   grouping dhcpv6-route-suppression-type {
     description "Suppress access-internal and/or access route addition";
     leaf access {
       description "Suppress access route addition";
       type empty;
     }
     leaf access-internal {
       description "Suppress access-internal route addition";
       type empty;
     }
   }
   grouping dual-stack-authentication-type {
     description "DHCP dual stack authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       leaf relay-agent-remote-id {
         description "Include the relay agent remote ID";
         type empty;
       }
       leaf logical-system-name {
         description "Include logical system name";
         type empty;
       }
       leaf routing-instance-name {
         description "Include routing instance name";
         type empty;
       }
       leaf relay-agent-interface-id {
         description "Include the relay agent interface ID";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf circuit-type {
         description "Include circuit type";
         type empty;
       }
       leaf vlan-tags {
         description "Include the vlan tag(s)";
         type empty;
       }
     }
   }
   grouping duid-type {
     uses apply-advanced;
     leaf duid_ll {
       description "Link Layer Address based DUID ";
       type empty;
     }
   }
   grouping dynamic-profile-type {
     description "Dynamic profile to use";
     uses apply-advanced;
     leaf dynamic-profile {
       description "Dynamic profile to use";
       type string {
         length "1 .. 80";
       }
     }
     choice dynamic-profile-type-choice {
       case case_1 {
         leaf use-primary {
           description "Dynamic profile to use on the primary interface";
           type string {
             length "1 .. 80";
           }
         }
       }
       case case_2 {
         container aggregate-clients {
           presence "enable aggregate-clients";
           description "Aggregate client profiles";
           uses apply-advanced;
           choice aggregate-type {
             case case_1 {
               leaf merge {
                 description "Merge the client dynamic profiles";
                 type empty;
               }
             }
             case case_2 {
               leaf replace {
                 description "Replace client dynamic profiles";
                 type empty;
               }
             }
           }
         }
       }
     }
   }
   grouping jdhcp-dual-stack-protocol-mstr-type {
     description "Select family as protocol master";
     choice addr-fam {
       case case_1 {
         leaf inet {
           description "INET family has protocol master behavior";
           type empty;
         }
       }
       case case_2 {
         leaf inet6 {
           description "INET6 family has protocol master behavior";
           type empty;
         }
       }
     }
   }
   grouping jdhcp-duplicate-clients-in-subnet-type {
     description "Allow duplicate clients in a subnet";
     choice distinguish-with {
       case case_1 {
         leaf incoming-interface {
           description "Allow duplicate clients on different interfaces in a subnet";
           type empty;
         }
       }
       case case_2 {
         leaf option-82 {
           description "Allow duplicate clients using different option-82 options in a subnet";
           type empty;
         }
       }
     }
   }
   grouping jdhcp-interface-traceoptions-type {
     description "Interface trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Interface trace categories";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
         }
       }
     }
   }
   grouping jdhcp-traceoptions-level-type {
     description "Trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "DHCP operations to include in debugging trace";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
           enum "database" {
             description "Database operations";
           }
           enum "persistent" {
             description "Persitent file operations";
           }
           enum "lockout-db" {
             description "Lockout database operations";
           }
           enum "interface" {
             description "Interface operations";
           }
           enum "rtsock" {
             description "Routing socket operations";
           }
           enum "flow-notify" {
             description "Flow notification operations";
           }
           enum "io" {
             description "I/O operations";
           }
           enum "ha" {
             description "High Availability-related operations";
           }
           enum "ui" {
             description "User Interface operations";
           }
           enum "general" {
             description "Miscellaneous operations";
           }
           enum "fwd" {
             description "Firewall process operations";
           }
           enum "rpd" {
             description "Routing Protocol process operations";
           }
           enum "auth" {
             description "Authentication operations";
           }
           enum "profile" {
             description "Profile operations";
           }
           enum "session-db" {
             description "Session database operations";
           }
           enum "performance" {
             description "Performance measurement operations";
           }
           enum "statistics" {
             description "Baseline statistics operations";
           }
           enum "dhcpv6-io" {
             description "I/O operations for dhcpv6";
           }
           enum "dhcpv6-rpd" {
             description "Routing Protocol process operations for dhcpv6";
           }
           enum "dhcpv6-session-db" {
             description "Session database operations for dhcpv6";
           }
           enum "dhcpv6-general" {
             description "Miscellaneous operations for dhcpv6";
           }
           enum "liveness-detection" {
             description "Liveness detection operations";
           }
           enum "security-persistence" {
             description "Liveness detection operations";
           }
           enum "mclag" {
             description "Multichassis LAG";
           }
           enum "ra-guard" {
             description "DHCP RA guard option for dhcpv6";
           }
           enum "era" {
             description "DHCP ERA logging option dhcp";
           }
           enum "telemetry" {
             description "Telemetry operation";
           }
         }
       }
     }
   }
   grouping jdhcp-traceoptions-type {
     description "Trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "DHCP operations to include in debugging trace";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
           enum "database" {
             description "Database operations";
           }
           enum "persistent" {
             description "Persitent file operations";
           }
           enum "lockout-db" {
             description "Lockout database operations";
           }
           enum "interface" {
             description "Interface operations";
           }
           enum "rtsock" {
             description "Routing socket operations";
           }
           enum "flow-notify" {
             description "Flow notification operations";
           }
           enum "io" {
             description "I/O operations";
           }
           enum "ha" {
             description "High Availability-related operations";
           }
           enum "ui" {
             description "User Interface operations";
           }
           enum "general" {
             description "Miscellaneous operations";
           }
           enum "fwd" {
             description "Firewall process operations";
           }
           enum "rpd" {
             description "Routing Protocol process operations";
           }
           enum "auth" {
             description "Authentication operations";
           }
           enum "profile" {
             description "Profile operations";
           }
           enum "session-db" {
             description "Session database operations";
           }
           enum "performance" {
             description "Performance measurement operations";
           }
           enum "statistics" {
             description "Baseline statistics operations";
           }
           enum "dhcpv6-io" {
             description "I/O operations for dhcpv6";
           }
           enum "dhcpv6-rpd" {
             description "Routing Protocol process operations for dhcpv6";
           }
           enum "dhcpv6-session-db" {
             description "Session database operations for dhcpv6";
           }
           enum "dhcpv6-general" {
             description "Miscellaneous operations for dhcpv6";
           }
           enum "liveness-detection" {
             description "Liveness detection operations";
           }
           enum "security-persistence" {
             description "Liveness detection operations";
           }
           enum "mclag" {
             description "Multichassis LAG";
           }
           enum "ra-guard" {
             description "DHCP RA guard option for dhcpv6";
           }
           enum "era" {
             description "DHCP ERA logging option dhcp";
           }
           enum "telemetry" {
             description "Telemetry operation";
           }
         }
       }
     }
   }
   grouping jet_scripts_file_type {
     leaf name {
       description "Local filename of the script file";
       type string {
         length "1 .. 254";
       }
     }
     uses apply-advanced;
     container checksum {
       description "Checksum of this script";
       uses apply-advanced;
       leaf sha-256 {
         description "SHA-256 checksum of this script";
         type string {
           length "1 .. 254";
         }
       }
     }
     leaf arguments {
       description "Command line arguments to JET application";
       type string;
     }
     leaf daemonize {
       description "Runs application as daemon";
       type empty;
     }
     leaf interpreter {
       description "Runs application using on-box <python|python3|bash>";
       type enumeration {
         enum "python" {
           description "Runs application using on-box python";
         }
         enum "python3" {
           description "Runs application using on-box python3";
         }
         enum "bash" {
           description "Runs application using on-box bash";
         }
       }
     }
     leaf respawn-on-normal-exit {
       description "Respawn application on normal exit";
       type empty;
     }
     leaf username {
       description "User under whose privileges extension service will execute";
       type string {
       }
     }
     leaf source {
       description "URL of source for this script";
       type string {
         length "1 .. 254";
       }
     }
     leaf cert-file {
       description "Specify the ca certificate file name";
       type string;
     }
     leaf routing-instance {
       description "Routing instance";
       type string {
       }
     }
     container traceoptions {
       description "Trace options per application";
       uses script_traceoptions;
     }
     container start {
       description "Start JET applications with start-criteria check";
       uses apply-advanced;
       container start-options {
         description "Start options for JET applications";
         uses apply-advanced;
         leaf mem-factor {
           description "Memory factor at which to start/stop";
           type union {
             type string {
               pattern "<.*>|$.*";
             }
             type uint32 {
               range "1 .. 100";
             }
           }
         }
       }
     }
     leaf refresh {
       description "Refresh all operation scripts from their source";
       type empty;
     }
     leaf refresh-from {
       description "Refresh all operation scripts from a given base URL";
       type string {
         length "1 .. 254";
       }
     }
   }
   grouping jsscd-static-subscribers-type {
     uses apply-advanced;
     container access-profile {
       description "Access profile reference";
       uses jsscd-access-profile-type;
     }
     container dynamic-profile {
       description "Dynamic profile reference";
       uses jsscd-dynamic-profile-type;
     }
     container service-profile {
       description "Dynamic profile to use for default service activation";
       uses jsscd-service-profile-type;
     }
     container authentication {
       description "Static Subscriber Client authentication";
       uses jsscd-authentication-type;
     }
     list group {
       key name;
       ordered-by user;
       description "Static Subscriber Client group configuration";
       uses jsscd-group-type;
     }
     leaf auto-login {
       description "Auto login the operator logged-out static subscribers";
       type empty;
     }
     leaf baseline-stats {
       description "Baseline the statistics for static subscribers";
       type empty;
     }
     list interface {
       key name;
       description "One or more interfaces";
       leaf name {
         description "Interface name";
         type union {
           type jt:interface-unit;
           type string {
             pattern "<.*>|$.*";
           }
         }
       }
       uses apply-advanced;
       container subscriber-ip-address {
         description "Assigned IP address to report externally";
         uses apply-advanced;
         leaf address {
           description "IPv4 address";
           type jt:ipv4addr;
         }
       }
       container subscriber-ipv6-address {
         description "Assigned IPv6 address to report externally";
         uses apply-advanced;
         leaf address {
           description "IPv6 Address or Prefix";
           type jt:ipv6prefix;
         }
       }
     }
   }
   grouping jsscd-access-profile-type {
     description "Access profile for static subscribers";
     uses apply-advanced;
     leaf access-profile-name {
       description "Profile name";
       type string;
     }
   }
   grouping jsscd-authentication-type {
     description "Static Subscriber Client authentication";
     uses apply-advanced;
     leaf password {
       description "Username password to use";
       type jt:unreadable;
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf interface {
         description "Include interface name";
         type empty;
       }
       leaf logical-system-name {
         description "Include logical system name";
         type empty;
       }
       leaf routing-instance-name {
         description "Include routing instance name";
         type empty;
       }
       leaf vlan-tags {
         description "Include vlan tag(s)";
         type empty;
       }
     }
   }
   grouping jsscd-dynamic-profile-type {
     description "Dynamic profile to use";
     uses apply-advanced;
     leaf dynamic-profile-name {
       description "Dynamic profile to use";
       type string {
         length "1 .. 80";
       }
     }
     container aggregate-clients {
       presence "enable aggregate-clients";
       description "Aggregate client profiles";
       uses apply-advanced;
       choice aggregate-type {
         case case_1 {
           leaf merge {
             description "Merge the client dynamic profiles";
             type empty;
           }
         }
         case case_2 {
           leaf replace {
             description "Replace client dynamic profiles";
             type empty;
           }
         }
       }
     }
   }
   grouping jsscd-group-type {
     leaf name {
       description "Group name";
       type string {
         length "1 .. 64";
       }
     }
     uses apply-advanced;
     container service-profile {
       description "Dynamic profile to use for default service activation";
       uses jsscd-service-profile-type;
     }
     container access-profile {
       description "Access profile reference";
       uses jsscd-access-profile-type;
     }
     container dynamic-profile {
       description "Dynamic profile reference";
       uses jsscd-dynamic-profile-type;
     }
     container authentication {
       description "Static Subscriber Client authentication";
       uses jsscd-authentication-type;
     }
     list interface {
       key name;
       description "One or more interfaces";
       leaf name {
         description "Interface name";
         type union {
           type jt:interface-unit;
           type string {
             pattern "<.*>|$.*";
           }
         }
       }
       uses apply-advanced;
       leaf upto {
         description "Interface up to";
         type union {
           type jt:interface-unit;
           type string {
             pattern "<.*>|$.*";
           }
         }
       }
       leaf exclude {
         description "Exclude this interface range";
         type empty;
       }
       list unit {
         key name;
         description "Logical interface";
         leaf name {
           description "Logical unit number";
           type union {
             type string {
               pattern "<.*>|$.*";
             }
             type uint32 {
               range "0 .. 1073741823";
             }
           }
         }
         uses apply-advanced;
         container demux-options {
           description "IP demux subscriber options";
           uses apply-advanced;
           container underlying-interface-tag {
             description "Tag name for matching GRE tunnel";
             uses apply-advanced;
             leaf tag-name {
               description "Interface tag name";
               type string {
                 length "1 .. 64";
               }
             }
           }
         }
         container family {
           description "Protocol family";
           container inet {
             presence "enable inet";
             description "IPv4 parameters";
             uses apply-advanced;
             container demux-source {
               description "Client source ipv4 address";
               uses apply-advanced;
               leaf address {
                 description "IPv4 address with prefix";
                 type jt:ipv4prefix;
               }
             }
           }
         }
       }
     }
     leaf auto-login {
       description "Auto login the operator logged-out static subscribers";
       type empty;
     }
   }
   grouping jsscd-service-profile-type {
     description "Service profile for static subscribers";
     uses apply-advanced;
     leaf service-profile-name {
       description "Service profile name";
       type string {
         length "1 .. 80";
       }
     }
   }
   grouping license-object {
     description "License configuration for this router";
     uses apply-advanced;
     container autoupdate {
       presence "enable autoupdate";
       description "Autoupdate license keys from license servers";
       uses apply-advanced;
       list url {
         key name;
         ordered-by user;
         description "URL of a license server";
         max-elements 10;
         leaf name {
           description "URL of a license server for license keys";
           type string;
         }
         leaf password {
           description "Password of URL for a license server";
           type jt:unreadable;
         }
       }
     }
     container log-frequency {
       description "Generate a syslog message for nagging";
       choice time_choice {
         case case_1 {
           leaf time-of-day {
             description "Time of day at which to log nag message (hh:mm)";
             type jt:time-of-day;
           }
         }
         case case_2 {
           leaf time-interval {
             description "Frequency for logging nag message (multiples of 60)";
             units "seconds";
             type union {
               type string {
                 pattern "<.*>|$.*";
               }
               type uint32 {
                 range "60 .. 86400";
               }
             }
           }
         }
       }
     }
     container renew {
       presence "enable renew";
       description "License renew lead time and checking interval";
       leaf before-expiration {
         description "License renew lead time before expiration in days";
         type union {
           type string {
             pattern "<.*>|$.*";
           }
           type uint32 {
             range "0 .. 60";
           }
         }
       }
       leaf interval {
         description "License checking interval in hours";
         type union {
           type string {
             pattern "<.*>|$.*";
           }
           type uint32 {
             range "1 .. 336";
           }
         }
       }
     }
     container traceoptions {
       description "Trace options for licenses";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "all" {
               description "Trace all operations";
             }
             enum "events" {
               description "Trace licensing events and their processing";
             }
             enum "config" {
               description "Trace license configuration processing";
             }
           }
         }
       }
     }
     container keys {
       presence "enable keys";
       description "License keys";
       uses apply-advanced;
       list key {
         key name;
         ordered-by user;
         description "License key";
         leaf name {
           description "License key";
           type string;
         }
         uses apply-advanced;
       }
     }
     leaf liblicense-trace {
       description "Traces for liblicense from next reboot";
       type empty;
     }
     choice mode-selection {
       case case_1 {
         leaf standalone-mode {
           description "Forcing the node to standalone licensing";
           type empty;
         }
       }
     }
   }
   grouping location-type {
     uses apply-advanced;
     leaf country-code {
       description "Two-letter country code";
       type string;
     }
     leaf postal-code {
       description "Zip code or postal code";
       type string;
     }
     leaf npa-nxx {
       description "First six digits of phone number (area code plus exchange)";
       type string;
     }
     leaf latitude {
       description "Latitude in degree format";
       type string;
     }
     leaf longitude {
       description "Longitude in degree format";
       type string;
     }
     leaf altitude {
       description "Feet above (or below) sea level";
       type union {
         type int32;
         type string {
           pattern "<.*>|$.*";
         }
       }
     }
     leaf lata {
       description "Local access transport area";
       type string;
     }
     leaf vcoord {
       description "Bellcore vertical coordinate";
       type string;
     }
     leaf hcoord {
       description "Bellcore horizontal coordinate";
       type string;
     }
     leaf building {
       description "Building name";
       type string;
     }
     leaf floor {
       description "Floor of the building";
       type union {
         type int32;
         type string {
           pattern "<.*>|$.*";
         }
       }
     }
     leaf rack {
       description "Rack number";
       type union {
         type uint32;
         type string {
           pattern "<.*>|$.*";
         }
       }
     }
     list lcc {
       key name;
       description "Line-card chassis location";
       leaf name {
         description "LCC number";
         type union {
           type string {
             pattern "<.*>|$.*";
           }
           type uint32 {
             range "0 .. 3";
           }
         }
       }
       uses apply-advanced;
       leaf floor {
         description "Floor of the building";
         type union {
           type int32;
           type string {
             pattern "<.*>|$.*";
           }
         }
       }
       leaf rack {
         description "Rack number";
         type union {
           type uint32;
           type string {
             pattern "<.*>|$.*";
           }
         }
       }
     }
   }
   grouping login-class-object {
     leaf name {
       description "Login class name";
       type string {
       }
     }
     uses apply-advanced;
     leaf-list allowed-days {
       ordered-by user;
       description "Day(s) of week when access is allowed.";
       type enumeration {
         enum "sunday" {
           description "Sunday";
         }
         enum "monday" {
           description "Monday";
         }
         enum "tuesday" {
           description "Tuesday";
         }
         enum "wednesday" {
           description "Wednesday";
         }
         enum "thursday" {
           description "Thursday";
         }
         enum "friday" {
           description "Friday";
         }
         enum "saturday" {
           description "Saturday";
         }
       }
     }
     leaf access-start {
       description "Start time for remote access (hh:mm)";
       type jt:time-of-day;
     }
     leaf access-end {
       description "End time for remote access (hh:mm)";
       type jt:time-of-day;
     }
     leaf idle-timeout {
       description "Maximum idle time before logout";
       units "minutes";
       type union {
         type uint32;
         type string {
           pattern "<.*>|$.*";
         }
       }
     }
     leaf logical-system {
       description "Logical system associated with login";
       type string;
     }
     leaf tenant {
       description "Tenant associated with this login";
       type string;
     }
     leaf login-alarms {
       description "Display system alarms when logging in";
       type empty;
     }
     leaf login-script {
       description "Execute this login-script when logging in";
       type string;
     }
     leaf login-tip {
       description "Display tip when logging in";
       type empty;
     }
     leaf no-scp-server {
       description "Disable incoming SCP connections";
       type empty;
     }
     leaf no-sftp-server {
       description "Disable incoming SFTP connections";
       type empty;
     }
     leaf-list permissions {
       ordered-by user;
       type string;
     }
     leaf allow-commands {
       description "Regular expression for commands to allow explicitly";
       type jt:regular-expression;
     }
     leaf deny-commands {
       description "Regular expression for commands to deny explicitly";
       type jt:regular-expression;
     }
     leaf allow-configuration {
       description "Regular expression for configure to allow explicitly";
       type jt:regular-expression;
     }
     leaf deny-configuration {
       description "Regular expression for configure to deny explicitly";
       type jt:regular-expression;
     }
     leaf-list allow-commands-regexps {
       ordered-by user;
       description "Object path regular expressions to allow commands";
       type string;
     }
     leaf-list deny-commands-regexps {
       ordered-by user;
       description "Object path regular expressions to deny commands";
       type string;
     }
     leaf-list allow-configuration-regexps {
       ordered-by user;
       description "Object path regular expressions to allow";
       type string;
     }
     leaf-list deny-configuration-regexps {
       ordered-by user;
       description "Object path regular expressions to deny";
       type string;
     }
     leaf allow-configuration-exact-match {
       description "Regular expression for configure to allow exact match explicitly";
       type jt:regular-expression;
     }
     leaf deny-configuration-exact-match {
       description "Regular expression for configure to deny exact match explicitly";
       type jt:regular-expression;
     }
     leaf-list allow-grpc-rpc-regexps {
       ordered-by user;
       description "Regular expressions of gRPC rpcs to be allowed";
       type string;
     }
     leaf-list deny-grpc-rpc-regexps {
       ordered-by user;
       description "Regular expressions of gRPC rpcs to be denied";
       type string;
     }
     leaf configuration-breadcrumbs {
       description "Enable breadcrumbs during display of configuration";
       type empty;
     }
     list confirm-commands {
       key name;
       ordered-by user;
       description "List of commands to be confirmed explicitly";
       leaf name {
         description "Regular expression for confirm commands";
         type jt:regular-expression;
       }
       uses apply-advanced;
       leaf message {
         description "Message to be displayed during confirmation";
         type string;
       }
     }
     choice hidden-commands {
       case case_1 {
         leaf allow-hidden-commands {
           description "Allow all hidden commands to be executed";
           type empty;
         }
       }
       case case_2 {
         container no-hidden-commands {
           description "Deny all hidden commands with exemptions";
           uses apply-advanced;
           list except {
             key name;
             ordered-by user;
             description "Specify the list of hidden command to be exempted";
             leaf name {
               description "Exempted hidden command(s)";
               type string;
             }
             uses apply-advanced;
           }
         }
       }
     }
     container cli {
       uses apply-advanced;
       leaf prompt {
         description "Cli prompt name for this class";
         type string {
           length "1 .. 255";
         }
       }
       container timestamp {
         presence "enable timestamp";
         description "Cli Timestamp for this class (default format is '%b %d %T')";
         uses apply-advanced;
         leaf format {
           description "Timestamp format (default is '%b %d %T')";
           default "%b %d %T";
           type string {
           }
         }
       }
     }
     leaf web-ui-hidden-menus {
       description "Hidden menus in web user interface";
       type string;
     }
     leaf web-ui-read-only-menus {
       description "Read only menus in web user interface";
       type string;
     }
     leaf security-role {
       description "Common Criteria security role";
       type enumeration {
         enum "audit-administrator" {
           description "Audit administrator";
         }
         enum "crypto-administrator" {
           description "Cryptographic administrator";
         }
         enum "ids-administrator" {
           description "IDS administrator";
         }
         enum "security-administrator" {
           description "Security administrator";
         }
       }
     }
   }
   grouping login-user-object {
     leaf name {
       description "User name (login)";
       type string {
       }
     }
     uses apply-advanced;
     leaf full-name {
       description "Full name";
       type string {
         length "1 .. 255";
       }
     }
     container cli {
       uses apply-advanced;
       leaf prompt {
         description "Cli prompt name for this user";
         type string {
           length "1 .. 255";
         }
       }
       container timestamp {
         presence "enable timestamp";
         description "Cli Timestamp for this class (default format is '%b %d %T')";
         uses apply-advanced;
         leaf format {
           description "Timestamp format (default is '%b %d %T')";
           default "%b %d %T";
           type string {
           }
         }
       }
       choice allow-syslog-output-choice {
         leaf allow-syslog-output {
           description "Enable monitor and syslog output";
           type empty;
         }
         leaf no-allow-syslog-output {
           description "Don't enable monitor and syslog output";
           type empty;
         }
       }
     }
     leaf uid {
       description "User identifier (uid)";
       type union {
         type string {
           pattern "<.*>|$.*";
         }
         type uint32 {
           range "100 .. 64000";
         }
       }
     }
     leaf class {
       description "Login class";
       type string {
       }
     }
     container authentication {
       description "Authentication method";
       uses authentication-object;
     }
     leaf-list authorized-principals {
       ordered-by user;
       description "List of authorized principals";
       type string;
     }
     leaf authorized-principals-file {
       description "File containing list of authorized principals";
       type string;
     }
   }
   grouping macro-data-type {
     leaf name {
       description "Keyword part of the keyword-value pair";
       type string;
     }
     leaf value {
       description "Value part of the keyword-value pair";
       type string;
     }
   }
   grouping nameserver-object {
     leaf name {
       description "DNS name server address";
       type jt:ipaddr;
     }
     leaf routing-instance {
       description "Routing instance through which server is reachable";
       type string {
       }
     }
   }
   grouping override-local-server-type {
     description "DHCP override processing";
     uses apply-advanced;
     leaf interface-client-limit {
       description "Limit the number of clients allowed on an interface";
       type union {
         type string {
           pattern "<.*>|$.*";
         }
         type uint32 {
           range "1 .. 500000";
         }
       }
     }
     leaf no-arp {
       description "Disable DHCP ARP table population";
       status deprecated;
       type empty;
     }
     leaf bootp-support {
       description "Allow processing of bootp requests";
       type empty;
     }
     container client-discover-match {
       presence "enable client-discover-match";
       description "Use secondary match criteria for DISCOVER PDU";
       choice match-with {
         case case_1 {
           leaf option60-and-option82 {
             description "Use option 60 and option 82";
             type empty;
           }
         }
         case case_2 {
           leaf incoming-interface {
             description "Use incoming interface";
             type empty;
           }
         }
       }
     }
     container delay-offer {
       description "Filter options for dhcp-server";
       uses dhcpv4-filter-option;
     }
     container process-inform {
       presence "enable process-inform";
       description "Process INFORM PDUs";
       uses apply-advanced;
       leaf pool {
         description "Pool name for family inet";
         type string {
           length "1 .. 64";
         }
       }
     }
     container include-option-82 {
       description "Include option-82 in reply packets";
       uses apply-advanced;
       leaf nak {
         description "Include option-82 in NAK";
         type empty;
       }
       leaf forcerenew {
         description "Include option-82 in FORCERENEW";
         type empty;
       }
     }
     leaf delete-binding-on-renegotiation {
       description "Delete binding on renegotiation";
       type empty;
     }
     leaf allow-no-end-option {
       description "Allow packets without end-of-option";
       type empty;
     }
     leaf asymmetric-lease-time {
       description "Use a reduced lease time for the client. In seconds";
       units "seconds";
       type union {
         type string {
           pattern "<.*>|$.*";
         }
         type uint32 {
           range "600 .. 86400";
         }
       }
     }
     leaf protocol-attributes {
       description "DHCPv4 attributes to use as defined under access protocol-attributes";
       type string {
         length "1 .. 64";
       }
     }
     leaf dual-stack {
       description "Dual stack group to use";
       type string {
         length "1 .. 64";
       }
     }
     leaf nak-unknown-rebind {
       description "Nak unknown rebind requests";
       type empty;
     }
     leaf nak-unknown-renew {
       description "Nak unknown renew requests";
       type empty;
     }
   }
   grouping dhcpv4-filter-option {
     description "Generic DHCPv4 filter processing";
     uses apply-advanced;
     leaf delay-time {
       description "Time delay between discover and offer";
       default "3";
       units "seconds";
       type union {
         type string {
           pattern "<.*>|$.*";
         }
         type uint32 {
           range "1 .. 30";
         }
       }
     }
     container based-on {
       description "Option number";
       uses apply-advanced;
       container option-82 {
         presence "enable option-82";
         description "Option 82";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-60 {
         presence "enable option-60";
         description "Option 60";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-77 {
         presence "enable option-77";
         description "Option 77";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
     }
   }
   grouping peers-type {
     description "Commit peers-synchronize type";
     leaf name {
       description "Remote peer hostname or ip-address";
       type string {
         length "1 .. 255";
       }
     }
     uses apply-advanced;
     leaf user {
       description "User name";
       type string;
     }
     leaf authentication {
       description "Authentication string";
       type jt:unreadable;
     }
     leaf routing-instance {
       description "Specific routing instance for connectivity to remote peer";
       type string {
       }
     }
   }
   grouping pmond-traceoptions-type {
     description "Trace options for process health monitor";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of process health monitor to enable debugging output";
       leaf name {
         type enumeration {
           enum "events" {
             description "Trace event conde";
           }
           enum "heartbeat" {
             description "Trace heartbeat code";
           }
           enum "process-tracking" {
             description "Trace process tracking code";
           }
           enum "ui" {
             description "Trace user interface code";
           }
           enum "all" {
             description "Trace all areas of code";
           }
         }
       }
     }
   }
   grouping proxy-object {
     description "License download proxy server.";
     uses apply-advanced;
     leaf server {
       description "URL or IP address of the proxy server host";
       type string {
         length "1 .. 256";
       }
     }
     leaf port {
       description "Proxy server port";
       default "3128";
       type union {
         type string {
           pattern "<.*>|$.*";
         }
         type uint16 {
           range "0 .. 65535";
         }
       }
     }
     leaf username {
       description "Username as configured in the proxy server";
       type string {
         length "1 .. 256";
       }
     }
     leaf password {
       description "Password as configured in the proxy server";
       type jt:unreadable;
     }
   }
   grouping radius-server-object {
     leaf name {
       description "RADIUS server address";
       type jt:hostname;
     }
     uses apply-advanced;
     leaf routing-instance {
       description "Routing instance";
       type string {
       }
     }
     leaf port {
       description "RADIUS server authentication port number";
       default "1812";
       type union {
         type string {
           pattern "<.*>|$.*";
         }
         type uint16 {
           range "1 .. 65535";
         }
       }
     }
     leaf preauthentication-port {
       description "RADIUS server preauthentication port number";
       type union {
         type string {
           pattern "<.*>|$.*";
         }
         type uint16 {
           range "1 .. 65535";
         }
       }
     }
     leaf accounting-port {
       description "RADIUS server accounting port number";
       default "1813";
       type union {
         type string {
           pattern "<.*>|$.*";
         }
         type uint16 {
           range "1 .. 65535";
         }
       }
     }
     leaf dynamic-request-port {
       description "RADIUS client dynamic request port number";
       default "3799";
       type union {
         type string {
           pattern "<.*>|$.*";
         }
         type uint16 {
           range "1 .. 65535";
         }
       }
     }
     leaf secret {
       description "Shared secret with the RADIUS server";
       type jt:unreadable;
     }
     leaf preauthentication-secret {
       description "Shared secret with the RADIUS server";
       type jt:unreadable;
     }
     leaf timeout {
       description "Request timeout period";
       default "3";
       units "seconds";
       type union {
         type string {
           pattern "<.*>|$.*";
         }
         type uint32 {
           range "1 .. 1000";
         }
       }
     }
     leaf retry {
       description "Retry attempts";
       default "3";
       type union {
         type string {
           pattern "<.*>|$.*";
         }
         type uint32 {
           range "1 .. 100";
         }
       }
     }
     leaf accounting-timeout {
       description "Accounting request timeout period";
       default "0";
       units "seconds";
       type union {
         type string {
           pattern "<.*>|$.*";
         }
         type uint32 {
           range "0 .. 1000";
         }
       }
     }
     leaf accounting-retry {
       description "Accounting retry attempts";
       default "0";
       type union {
         type string {
           pattern "<.*>|$.*";
         }
         type uint32 {
           range "0 .. 100";
         }
       }
     }
     leaf max-outstanding-requests {
       description "Maximum requests in flight to server";
       default "1000";
       type union {
         type string {
           pattern "<.*>|$.*";
         }
         type uint32 {
           range "0 .. 2000";
         }
       }
     }
     leaf no-message-authenticator {
       description "Don't require Message-Authenticator attribute in all access messages";
       type empty;
     }
     leaf message-authenticator {
       description "Require Message-Authenticator attribute in all access messages";
       type empty;
     }
     leaf source-address {
       description "Use specified address as source address";
       type jt:ipaddr;
     }
     container tls {
       description "Radius over TLS";
       uses apply-advanced;
       leaf-list trusted-ca-group {
         ordered-by user;
         description "Name of the trusted CA groups (maximum 20)";
         type string {
           length "1 .. 63";
         }
         max-elements 20;
       }
       container mutual-authentication {
         description "Enable TLS mutual authentication";
         uses apply-advanced;
         leaf certificate-id {
           description "Local Certificate ID";
           type string {
           }
         }
       }
     }
   }
   grouping reconfigure-trigger-type {
     description "DHCP reconfigure trigger";
     uses apply-advanced;
     leaf radius-disconnect {
       description "Trigger DHCP reconfigure by radius initiated disconnect";
       type empty;
     }
   }
   grouping reconfigure-type {
     description "DHCP reconfigure processing";
     uses apply-advanced;
     leaf clear-on-abort {
       description "Delete client on reconfiguration abort";
       type empty;
     }
     leaf defer-nack-on-abort {
       description "Defer client NACK on reconfiguration abort";
       type empty;
     }
     leaf attempts {
       description "Number of reconfigure attempts before aborting";
       type union {
         type string {
           pattern "<.*>|$.*";
         }
         type uint32 {
           range "1 .. 10";
         }
       }
     }
     leaf timeout {
       description "Initial timeout value for retry";
       type union {
         type string {
           pattern "<.*>|$.*";
         }
         type uint32 {
           range "1 .. 10";
         }
       }
     }
     leaf token {
       description "Reconfigure token";
       type string {
         length "1 .. 244";
       }
     }
     container trigger {
       description "DHCP reconfigure trigger";
       uses reconfigure-trigger-type;
     }
     leaf support-option-pd-exclude {
       description "Request prefix exclude option in reconfigure message";
       type empty;
     }
   }
   grouping res-cleanupd-traceoptions-type {
     description "Trace options for resource cleanup process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of resource cleanup process to enable debugging output";
       leaf name {
         type enumeration {
           enum "events" {
             description "Trace event code";
           }
           enum "gencfg" {
             description "Trace GENCFG blob cleanup code";
           }
           enum "module" {
             description "Trace module code";
           }
           enum "sysvsem" {
             description "Trace SYSV semaphore cleanup code";
           }
           enum "sysvshm" {
             description "Trace SYSV shared memory cleanup code";
           }
           enum "tracking" {
             description "Trace process tracking code";
           }
           enum "ui" {
             description "Trace user interface code";
           }
           enum "all" {
             description "Trace all areas of code";
           }
         }
       }
     }
   }
   grouping resource-monitor-type {
     description "Resource monitor configuration";
     uses apply-advanced;
     list resource-category {
       key name;
       ordered-by user;
       description "Resource category";
       leaf name {
         type enumeration {
           enum "jtree" {
             description "Category jtree";
           }
         }
       }
       uses apply-advanced;
       list resource-type {
         key name;
         ordered-by user;
         description "Resource type";
         leaf name {
           type enumeration {
             enum "free-pages" {
               description "Type free-pages";
             }
             enum "free-dwords" {
               description "Type free-dwords";
             }
             enum "contiguous-pages" {
               description " Type contiguous-pages";
             }
           }
         }
         uses apply-advanced;
         leaf low-watermark {
           description "Low watermark limit percentage";
           type union {
             type string {
               pattern "<.*>|$.*";
             }
             type uint32 {
               range "1 .. 100";
             }
           }
         }
         leaf high-watermark {
           description "High watermark limit percentage";
           type union {
             type string {
               pattern "<.*>|$.*";
             }
             type uint32 {
               range "1 .. 100";
             }
           }
         }
       }
     }
     container traceoptions {
       description "Resource monitor trace options";
       uses resource-monitor-traceoptions-type;
     }
     leaf no-throttle {
       description "Disable throttling of subscribers and services based on resource utilization";
       type empty;
     }
     leaf no-usage-update {
       description "Disable IFD usage update to CP";
       type empty;
     }
     leaf no-load-throttle {
       description "Disable throttling of subscribers and services based on PFE load";
       type empty;
     }
     leaf no-logging {
       description "Disable logging of warning or error messages resource levels exceeded";
       type empty;
     }
     leaf high-threshold {
       description "High threshold percentage for resource utilization";
       units "percentage";
       type union {
         type string {
           pattern "<.*>|$.*";
         }
         type uint32 {
           range "1 .. 99";
         }
       }
     }
     leaf high-cos-queue-threshold {
       description "High threshold percentage for cos queue utilization per scheduler";
       units "percentage";
       type union {
         type string {
           pattern "<.*>|$.*";
         }
         type uint32 {
           range "0 .. 90";
         }
       }
     }
     leaf free-heap-memory-watermark {
       description "Watermark percentage for ukern heap resource utilization";
       units "percentage";
       type union {
         type string {
           pattern "<.*>|$.*";
         }
         type uint32 {
           range "1 .. 99";
         }
       }
     }
     leaf free-nh-memory-watermark {
       description "Watermark percentage for NH resource utilization";
       units "percentage";
       type union {
         type string {
           pattern "<.*>|$.*";
         }
         type uint32 {
           range "1 .. 99";
         }
       }
     }
     leaf free-fw-memory-watermark {
       description "Watermark percentage for Filter / Firewall resource utilization";
       units "percentage";
       type union {
         type string {
           pattern "<.*>|$.*";
         }
         type uint32 {
           range "1 .. 99";
         }
       }
     }
     container subscribers-limit {
       description "Limit number of subscribers allowed to login";
       uses apply-advanced;
       list client-type {
         key name;
         ordered-by user;
         description "Subscriber client type";
         leaf name {
           type enumeration {
             enum "pppoe" {
               description "PPPoE client type";
             }
             enum "dhcp" {
               description "DHCP client type";
             }
             enum "l2tp" {
               description "L2TP client type";
             }
             enum "any" {
               description "Any client type";
             }
           }
         }
         uses apply-advanced;
         container chassis {
           description "Max subscriers allowed in chassis";
           uses apply-advanced;
           leaf limit {
             description "Number of subscribers allowed";
             type union {
               type string {
                 pattern "<.*>|$.*";
               }
               type uint32 {
                 range "1 .. 1000000";
               }
             }
           }
         }
         list fpc {
           key name;
           description "Limiting subscriber on fpc";
           uses rsmon_fpc_type;
         }
       }
     }
   }
   grouping resource-monitor-traceoptions-type {
     description "Trace options for Resource monitor ";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Resource monitor operations to include in debugging trace";
       leaf name {
         type enumeration {
           enum "all" {
             description "All operations";
           }
         }
       }
     }
   }
   grouping resources-type {
     uses apply-advanced;
     container cpu {
       uses apply-advanced;
       leaf priority {
         description "Highest priority (nice level) process can run at";
         type union {
           type int32;
           type string {
             pattern "<.*>|$.*";
           }
         }
       }
       leaf time {
         description "Maximum amount of CPU time that can be accumulated";
         type union {
           type uint64;
           type string {
             pattern "<.*>|$.*";
           }
         }
       }
     }
     container memory {
       uses apply-advanced;
       leaf data-size {
         description "Maximum size of the data segment";
         units "mbytes";
         type string;
       }
       leaf locked-in {
         description "Maximum bytes that can be locked into memory";
         units "mbytes";
         type string;
       }
       leaf resident-set-size {
         description "Maximum amount of private physical memory at any given moment";
         units "mbytes";
         type string;
       }
       leaf socket-buffers {
         description "Maximum amount of physical memory that may be dedicated to socket buffers";
         units "mbytes";
         type string;
       }
       leaf stack-size {
         description "Maximum size of the stack segment";
         units "mbytes";
         type string;
       }
     }
     container file {
       uses apply-advanced;
       leaf size {
         description "Maximum size of a file that can be created";
         units "mbytes";
         type string;
       }
       leaf open {
         description "Maximum number of simultaneous open files";
         type union {
           type uint64;
           type string {
             pattern "<.*>|$.*";
           }
         }
       }
       leaf core-size {
         description "Maximum size of a core file that can be created";
         units "mbytes";
         type string;
       }
     }
   }
   grouping rsmon_fpc_type {
     leaf name {
       description "FPC slot number";
       type union {
         type string {
           pattern "<.*>|$.*";
         }
         type uint32 {
           range "0 .. 512";
         }
       }
     }
     uses apply-advanced;
     list pic {
       key name;
       description "Limiting subscriber on fpc";
       uses rsmon_pic_type;
     }
     leaf limit {
       description "Number of subscribers allowed";
       type union {
         type string {
           pattern "<.*>|$.*";
         }
         type uint32 {
           range "1 .. 256000";
         }
       }
     }
     leaf oversubscription-limit {
       description "Number of oversubscription subscribers allowed";
       type union {
         type string {
           pattern "<.*>|$.*";
         }
         type uint32 {
           range "1 .. 256000";
         }
       }
     }
   }
   grouping rsmon_pic_type {
     leaf name {
       description "PIC slot number";
       type union {
         type string {
           pattern "<.*>|$.*";
         }
         type uint32 {
           range "0 .. 5";
         }
       }
     }
     uses apply-advanced;
     list port {
       key name;
       description "Limiting subscriber on port";
       uses rsmon_port_type;
     }
     leaf limit {
       description "Number of subscribers allowed";
       type union {
         type string {
           pattern "<.*>|$.*";
         }
         type uint32 {
           range "1 .. 256000";
         }
       }
     }
   }
   grouping rsmon_port_type {
     leaf name {
       description "Port number";
       type union {
         type string {
           pattern "<.*>|$.*";
         }
         type uint32 {
           range "0 .. 23";
         }
       }
     }
     uses apply-advanced;
     leaf limit {
       description "Number of subscribers allowed";
       type union {
         type string {
           pattern "<.*>|$.*";
         }
         type uint32 {
           range "1 .. 256000";
         }
       }
     }
   }
   grouping sbc_traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     container flag {
       presence "enable flag";
       description "Tracing parameters";
       uses apply-advanced;
       leaf configuration {
         description "Trace configuration events";
         default "error";
         type enumeration {
           enum "trace" {
             description "Trace functions entering and exiting";
           }
           enum "debug" {
             description "Trace code flow, branching, positive style guide check";
           }
           enum "info" {
             description "Summary logs for normal operations";
           }
           enum "warning" {
             description "Failure-recovery or Failure of an external entity";
           }
           enum "error" {
             description "Failure with short-term affect";
           }
         }
       }
       leaf ipc {
         description "Trace IPC events";
         default "error";
         type enumeration {
           enum "trace" {
             description "Trace functions entering and exiting";
           }
           enum "debug" {
             description "Trace code flow, branching, positive style guide check";
           }
           enum "info" {
             description "Summary logs for normal operations";
           }
           enum "warning" {
             description "Failure-recovery or Failure of an external entity";
           }
           enum "error" {
             description "Failure with short-term affect";
           }
         }
       }
       leaf device-monitor {
         description "Trace device monitor events";
         default "error";
         type enumeration {
           enum "trace" {
             description "Trace functions entering and exiting";
           }
           enum "debug" {
             description "Trace code flow, branching, positive style guide check";
           }
           enum "info" {
             description "Summary logs for normal operations";
           }
           enum "warning" {
             description "Failure-recovery or Failure of an external entity";
           }
           enum "error" {
             description "Failure with short-term affect";
           }
         }
       }
       leaf ui {
         description "Trace ui events";
         default "error";
         type enumeration {
           enum "trace" {
             description "Trace functions entering and exiting";
           }
           enum "debug" {
             description "Trace code flow, branching, positive style guide check";
           }
           enum "info" {
             description "Summary logs for normal operations";
           }
           enum "warning" {
             description "Failure-recovery or Failure of an external entity";
           }
           enum "error" {
             description "Failure with short-term affect";
           }
         }
       }
       leaf common {
         description "Trace common events";
         default "error";
         type enumeration {
           enum "trace" {
             description "Trace functions entering and exiting";
           }
           enum "debug" {
             description "Trace code flow, branching, positive style guide check";
           }
           enum "info" {
             description "Summary logs for normal operations";
           }
           enum "warning" {
             description "Failure-recovery or Failure of an external entity";
           }
           enum "error" {
             description "Failure with short-term affect";
           }
         }
       }
       leaf memory-pool {
         description "Trace memory-pool events";
         default "error";
         type enumeration {
           enum "trace" {
             description "Trace functions entering and exiting";
           }
           enum "debug" {
             description "Trace code flow, branching, positive style guide check";
           }
           enum "info" {
             description "Summary logs for normal operations";
           }
           enum "warning" {
             description "Failure-recovery or Failure of an external entity";
           }
           enum "error" {
             description "Failure with short-term affect";
           }
         }
       }
       leaf packet-capture {
         description "Trace packet capture events";
         default "error";
         type enumeration {
           enum "trace" {
             description "Trace functions entering and exiting";
           }
           enum "debug" {
             description "Trace code flow, branching, positive style guide check";
           }
           enum "info" {
             description "Summary logs for normal operations";
           }
           enum "warning" {
             description "Failure-recovery or Failure of an external entity";
           }
           enum "error" {
             description "Failure with short-term affect";
           }
         }
       }
       leaf all {
         description "Minimal trace level for all components";
         default "error";
         type enumeration {
           enum "trace" {
             description "Trace functions entering and exiting";
           }
           enum "debug" {
             description "Trace code flow, branching, positive style guide check";
           }
           enum "info" {
             description "Summary logs for normal operations";
           }
           enum "warning" {
             description "Failure-recovery or Failure of an external entity";
           }
           enum "error" {
             description "Failure with short-term affect";
           }
         }
       }
     }
   }
   grouping script_traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     list flag {
       key name;
       description "Tracing parameters";
       leaf name {
         type enumeration {
           enum "all" {
             description "Trace all operations";
           }
           enum "events" {
             description "Trace important events";
           }
           enum "input" {
             description "Trace script input data";
           }
           enum "offline" {
             description "Generate data for offline development";
           }
           enum "output" {
             description "Trace script output data";
           }
           enum "rpc" {
             description "Trace script RPCs";
           }
           enum "xslt" {
             description "Trace the XSLT library";
           }
         }
       }
     }
   }
   grouping scripts_type {
     uses apply-advanced;
     container commit {
       description "Commit-time scripting mechanism";
       uses apply-advanced;
       leaf allow-transients {
         description "Allow loading of transient configuration changes";
         type empty;
       }
       container traceoptions {
         description "Trace options for commit scripts";
         uses script_traceoptions;
       }
       leaf refresh {
         description "Refresh all operation scripts from their source";
         type empty;
       }
       leaf refresh-from {
         description "Refresh all operation scripts from a given base URL";
         type string {
           length "1 .. 254";
         }
       }
       leaf max-datasize {
         description "Maximum data segment size for scripts execution";
         units "bytes";
         type string;
       }
       leaf direct-access {
         description "Access the configuration directly from database";
         type empty;
       }
       container dampen {
         presence "enable dampen";
         description "Dampen execution of commit scripts";
         uses apply-advanced;
         container dampen-options {
           description "Dampen options for commit scripts";
           uses apply-advanced;
           leaf cpu-factor {
             description "CPU factor at which to pause";
             type union {
               type string {
                 pattern "<.*>|$.*";
               }
               type uint32 {
                 range "1 .. 100";
               }
             }
           }
           leaf line-interval {
             description "Line interval at which to pause";
             type union {
               type string {
                 pattern "<.*>|$.*";
               }
               type uint32 {
                 range "1 .. 4294967295";
               }
             }
           }
           leaf time-interval {
             description "Time to pause";
             units "microseconds";
             type union {
               type string {
                 pattern "<.*>|$.*";
               }
               type uint32 {
                 range "1 .. 4294967295";
               }
             }
           }
         }
       }
       list file {
         key name;
         ordered-by user;
         description "Commit script file";
         uses commit_scripts_file_type;
       }
     }
     container op {
       description "Operations scripting";
       uses apply-advanced;
       leaf refresh {
         description "Refresh all operation scripts from their source";
         type empty;
       }
       leaf refresh-from {
         description "Refresh all operation scripts from a given base URL";
         type string {
           length "1 .. 254";
         }
       }
       container traceoptions {
         description "Trace options for operation scripts";
         uses script_traceoptions;
       }
       list file {
         key name;
         description "Configuration for each operation script";
         uses op_scripts_file_type;
       }
       leaf no-allow-url {
         description "Do not allow the remote execution of op scripts";
         type empty;
       }
       leaf allow-url-for-python {
         description "Allow the remote execution of Python op scripts";
         type empty;
       }
       leaf max-datasize {
         description "Maximum data segment size for scripts execution";
         units "bytes";
         type string;
       }
       container dampen {
         presence "enable dampen";
         description "Dampen execution of op scripts";
         uses apply-advanced;
         container dampen-options {
           description "Dampen options for op scripts";
           uses apply-advanced;
           leaf cpu-factor {
             description "CPU factor at which to pause";
             type union {
               type string {
                 pattern "<.*>|$.*";
               }
               type uint32 {
                 range "1 .. 100";
               }
             }
           }
           leaf line-interval {
             description "Line interval at which to pause";
             type union {
               type string {
                 pattern "<.*>|$.*";
               }
               type uint32 {
                 range "1 .. 4294967295";
               }
             }
           }
           leaf time-interval {
             description "Time to pause";
             units "microseconds";
             type union {
               type string {
                 pattern "<.*>|$.*";
               }
               type uint32 {
                 range "1 .. 4294967295";
               }
             }
           }
         }
       }
       container start {
         description "Start op scripts with start-criteria check";
         uses apply-advanced;
         container start-options {
           description "Start options for op scripts";
           uses apply-advanced;
           leaf mem-factor {
             description "Memory factor at which to start/stop";
             type union {
               type string {
                 pattern "<.*>|$.*";
               }
               type uint32 {
                 range "1 .. 100";
               }
             }
           }
         }
       }
     }
     container translation {
       description "Translation scripts";
       uses apply-advanced;
       leaf max-datasize {
         description "Maximum data segment size for translation scripts execution";
         units "bytes";
         type string;
       }
     }
     container action {
       description "Action scripts";
       uses apply-advanced;
       leaf max-datasize {
         description "Maximum data segment size for action scripts execution";
         units "bytes";
         type string;
       }
     }
     leaf load-scripts-from-flash {
       description "Load scripts from flash";
       type empty;
     }
     leaf language {
       description "Allow/Disallow Python scripts on-box";
       type enumeration {
         enum "python" {
           description "Allow Python 2.x scripts on-box (Python2.x support will be deprecated in 21.1)";
         }
         enum "python3" {
           description "Allow Python 3.x scripts on-box";
         }
       }
     }
     leaf synchronize {
       description "Push all scripts to other RE on commit synchronize";
       type empty;
     }
     container snmp {
       description "Snmp scripts";
       uses apply-advanced;
       leaf refresh {
         description "Refresh all snmp scripts from their source";
         type empty;
       }
       leaf refresh-from {
         description "Refresh all snmp scripts from a given base URL";
         type string {
           length "1 .. 254";
         }
       }
       list file {
         key name;
         description "Configuration for each snmp script";
         uses snmp_scripts_file_type;
       }
       container traceoptions {
         description "Trace options for snmp scripts";
         uses script_traceoptions;
       }
       leaf max-datasize {
         description "Maximum data segment size for scripts execution";
         units "bytes";
         type string;
       }
       container start {
         description "Start snmp scripts with start-criteria check";
         uses apply-advanced;
         container start-options {
           description "Start options for snmp scripts";
           uses apply-advanced;
           leaf mem-factor {
             description "Memory factor at which to start/stop";
             type union {
               type string {
                 pattern "<.*>|$.*";
               }
               type uint32 {
                 range "1 .. 100";
               }
             }
           }
         }
       }
     }
   }
   grouping commit_scripts_file_type {
     leaf name {
       description "Local filename of the script file";
       type string {
         length "1 .. 254";
       }
     }
     uses apply-advanced;
     leaf allow-transients {
       description "Allow loading of transient configuration changes";
       type empty;
     }
     leaf optional {
       description "Allow commit to succeed if the script is missing";
       type empty;
     }
     leaf source {
       description "URL of source for this script";
       type string {
         length "1 .. 254";
       }
     }
     leaf cert-file {
       description "Specify the ca certificate file name";
       type string;
     }
     leaf routing-instance {
       description "Routing instance";
       type string {
       }
     }
     leaf refresh {
       description "Refresh all operation scripts from their source";
       type empty;
     }
     leaf refresh-from {
       description "Refresh all operation scripts from a given base URL";
       type string {
         length "1 .. 254";
       }
     }
     container checksum {
       description "Checksum of this script";
       uses apply-advanced;
       leaf sha-256 {
         description "SHA-256 checksum of this script";
         type string {
           length "1 .. 254";
         }
       }
     }
   }
   grouping op_scripts_file_type {
     leaf name {
       description "Local filename of the script file";
       type string {
         length "1 .. 254";
       }
     }
     uses apply-advanced;
     leaf command {
       description "Command alias for the script file";
       type string {
         length "1 .. 254";
       }
     }
     container dampen {
       presence "enable dampen";
       description "Dampen execution of the script";
       uses apply-advanced;
       container dampen-options {
         description "Dampen options for the script";
         uses apply-advanced;
         leaf cpu-factor {
           description "CPU factor at which to pause";
           type union {
             type string {
               pattern "<.*>|$.*";
             }
             type uint32 {
               range "1 .. 100";
             }
           }
         }
         leaf line-interval {
           description "Line interval at which to pause";
           type union {
             type string {
               pattern "<.*>|$.*";
             }
             type uint32 {
               range "1 .. 4294967295";
             }
           }
         }
         leaf time-interval {
           description "Time to pause";
           units "microseconds";
           type union {
             type string {
               pattern "<.*>|$.*";
             }
             type uint32 {
               range "1 .. 4294967295";
             }
           }
         }
       }
     }
     container start {
       description "Start op scripts with start-criteria check";
       uses apply-advanced;
       container start-options {
         description "Start options for the op script";
         uses apply-advanced;
         leaf mem-factor {
           description "Memory factor at which to start/stop";
           type union {
             type string {
               pattern "<.*>|$.*";
             }
             type uint32 {
               range "1 .. 100";
             }
           }
         }
       }
     }
     leaf description {
       description "Description of the script";
       type string {
         length "1 .. 254";
       }
     }
     leaf source {
       description "URL of source for this script";
       type string {
         length "1 .. 254";
       }
     }
     leaf cert-file {
       description "Specify the ca certificate file name";
       type string;
     }
     leaf routing-instance {
       description "Routing instance";
       type string {
       }
     }
     leaf allow-commands {
       description "Regular expression for commands to allow explicitly";
       type jt:regular-expression;
     }
     leaf refresh {
       description "Refresh all operation scripts from their source";
       type empty;
     }
     leaf refresh-from {
       description "Refresh all operation scripts from a given base URL";
       type string {
         length "1 .. 254";
       }
     }
     list arguments {
       key name;
       description "Command line argument to the script";
       leaf name {
         description "Name of the argument";
         type string {
           length "1 .. 254";
         }
       }
       uses apply-advanced;
       leaf description {
         description "Description of the argument";
         type string {
           length "1 .. 254";
         }
       }
     }
     container checksum {
       description "Checksum of this script";
       uses apply-advanced;
       leaf sha-256 {
         description "SHA-256 checksum of this script";
         type string {
           length "1 .. 254";
         }
       }
     }
   }
   grouping sdk-mgmtd-traceoptions-type {
     description "Trace options for App-engine management daemon";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of daemon to enable debugging output";
       leaf name {
         type enumeration {
           enum "service-infrastructure" {
             description "Trace service infrastructure code";
           }
           enum "routing-instance" {
             description "Trace routing instance functionality code";
           }
           enum "config-handling" {
             description "Trace configuration command handling functionality code";
           }
           enum "command-handling" {
             description "Trace operational command handling functionality code";
           }
           enum "cli-show-commands" {
             description "Trace show commands for JDAF message statistics";
           }
           enum "all" {
             description "Trace all areas of App-engine management";
           }
         }
       }
     }
   }
   grouping server-active-leasequery-type {
     description "Allow active leasequery";
     uses apply-advanced;
     leaf timeout {
       description "Read/write timeout in seconds";
       default "120";
       units "seconds";
       type union {
         type string {
           pattern "<.*>|$.*";
         }
         type uint32 {
           range "10 .. 3600";
         }
       }
     }
     leaf idle-timeout {
       description "Idle-timeout in seconds";
       default "60";
       units "seconds";
       type union {
         type string {
           pattern "<.*>|$.*";
         }
         type uint32 {
           range "10 .. 3600";
         }
       }
     }
   }
   grouping server-bulk-leasequery-type {
     description "Allow bulk leasequery";
     uses apply-advanced;
     leaf max-connections {
       description "Max TCP connections allowed at a time";
       default "3";
       type union {
         type string {
           pattern "<.*>|$.*";
         }
         type uint32 {
           range "1 .. 10";
         }
       }
     }
     leaf timeout {
       description "Timeout for blocked connection";
       default "120";
       units "seconds";
       type union {
         type string {
           pattern "<.*>|$.*";
         }
         type uint32 {
           range "1 .. 1000";
         }
       }
     }
     leaf max-empty-replies {
       description "Maximum number of empty replies for a connection";
       default "5";
       units "seconds";
       type union {
         type string {
           pattern "<.*>|$.*";
         }
         type uint32 {
           range "1 .. 100";
         }
       }
     }
     leaf restricted-requestor {
       description "Allow bulk leasequery only from restricted requestors";
       type empty;
     }
   }
   grouping server-leasequery-type {
     description "Allow leasequery";
     uses apply-advanced;
     leaf restricted-requestor {
       description "Allow leasequery only from restricted requestors";
       type empty;
     }
   }
   grouping server-v6-option-ascii-hex {
     uses apply-advanced;
     list ascii {
       key name;
       description "ASCII string";
       leaf name {
         description "ASCII string";
         type string {
           length "1 .. 256";
         }
       }
       uses apply-advanced;
     }
     list hexadecimal {
       key name;
       description "Hexadecimal string";
       leaf name {
         description "Hexadecimal string";
         type string {
           length "1 .. 512";
         }
       }
       uses apply-advanced;
     }
   }
   grouping smid-type {
     description "Subscriber management configuration";
     uses apply-advanced;
     container traceoptions {
       description "Subscriber management trace options";
       uses smid-traceoptions-type;
     }
     container maintain-subscriber {
       description "Options to maintain subscriber";
       uses smid-maintain-subscriber-type;
     }
     leaf gres-route-flush-delay {
       description "Delay flushing routes after RE switchover";
       type empty;
     }
     container enforce-strict-scale-limit-license {
       presence "enable enforce-strict-scale-limit-license";
       description "Options to enforce strict scale limit license";
     }
     container overrides {
       description "Subscriber management configuration";
       uses apply-advanced;
       leaf no-unsolicited-ra {
         description "Disable all unsolicited router advertisement packets";
         type empty;
       }
       leaf force-show-arp-resolve {
         description "Enable show arp resolve mode for subscribers";
         type empty;
       }
       container interfaces {
         presence "enable interfaces";
         uses apply-advanced;
         container family {
           presence "enable family";
           uses apply-advanced;
           container inet6 {
             presence "enable inet6";
             uses apply-advanced;
             leaf layer2-liveness-detection {
               description "Enabled ipv6-nud liveness detection";
               type empty;
             }
           }
           container inet {
             presence "enable inet";
             uses apply-advanced;
             leaf layer2-liveness-detection {
               description "Enabled arp-ping liveness detection";
               type empty;
             }
             leaf receive-gratuitous-arp {
               description "Enable receieve gratuitous arp packet processing";
               type empty;
             }
             leaf ipoe-dynamic-arp-enable {
               description "Enable IPOE dynamic ARP";
               type empty;
             }
           }
         }
       }
       container shmlog {
         description "Subscriber management shmlog configuration";
         uses apply-advanced;
         leaf disable {
           description "Disable shmlogs";
           type empty;
         }
         container filtering {
           description "Subscriber management shmlog filtering";
           uses apply-advanced;
           leaf enable {
             description "Enable shmlog filtering";
             type empty;
           }
         }
         container file {
           presence "enable file";
           leaf filename {
             description "Name of file in which to write trace information";
             type string {
               length "1 .. 1024";
             }
           }
           leaf size {
             description "Maximum file size";
             type string;
           }
           leaf files {
             description "Maximum number of  files";
             default "3";
             type union {
               type string {
                 pattern "<.*>|$.*";
               }
               type uint32 {
                 range "2 .. 1000";
               }
             }
           }
         }
         list log-name {
           key name;
           ordered-by user;
           description "The log name(s) to override";
           leaf name {
             type string;
           }
           uses apply-advanced;
           choice verbosity {
             case case_1 {
               leaf none {
                 description "Shmlog verbosity null";
                 type empty;
               }
             }
             case case_2 {
               leaf terse {
                 description "Shmlog verbosity terse";
                 type empty;
               }
             }
             case case_3 {
               leaf brief {
                 description "Shmlog verbosity brief";
                 type empty;
               }
             }
             case case_4 {
               leaf detail {
                 description "Shmlog verbosity detail";
                 type empty;
               }
             }
             case case_5 {
               leaf extensive {
                 description "Shmlog verbosity extensive";
                 type empty;
               }
             }
           }
           choice file-enable {
             case case_1 {
               leaf file-logging {
                 description "Enable file write for the log(s)";
                 type empty;
               }
             }
             case case_2 {
               leaf no-file-logging {
                 description "Disable file write for the log(s)";
                 type empty;
               }
             }
           }
         }
         list log-type {
           key name;
           ordered-by user;
           description "The log type to override";
           leaf name {
             type enumeration {
               enum "debug" {
                 description "The severity debug";
               }
               enum "info" {
                 description "The severity info";
               }
               enum "notice" {
                 description "The severity notice and more severe";
               }
             }
           }
           uses apply-advanced;
           choice verbosity {
             case case_1 {
               leaf none {
                 description "Shmlog verbosity null";
                 type empty;
               }
             }
             case case_2 {
               leaf terse {
                 description "Shmlog verbosity terse";
                 type empty;
               }
             }
             case case_3 {
               leaf brief {
                 description "Shmlog verbosity brief";
                 type empty;
               }
             }
             case case_4 {
               leaf detail {
                 description "Shmlog verbosity detail";
                 type empty;
               }
             }
             case case_5 {
               leaf extensive {
                 description "Shmlog verbosity extensive";
                 type empty;
               }
             }
           }
           choice file-enable {
             case case_1 {
               leaf file-logging {
                 description "Enable file write for the log(s)";
                 type empty;
               }
             }
             case case_2 {
               leaf no-file-logging {
                 description "Disable file write for the log(s)";
                 type empty;
               }
             }
           }
         }
       }
     }
     container enable {
       presence "enable enable";
       description "Enable subscriber management features";
       uses apply-advanced;
     }
     container mode {
       description "Configure the operational role of this system (control-plane or user-plane)";
       uses apply-advanced;
       choice modetype {
         case case_1 {
           container user-plane {
             presence "enable user-plane";
             description "User-plane mode (DBNG)";
             uses apply-advanced;
             leaf user-plane-name {
               description "User-plane name";
               type string {
                 length "1 .. 12";
               }
             }
             container transport {
               presence "enable transport";
               description "User plane transport address information";
               uses apply-advanced;
               choice familytype {
                 case case_1 {
                   leaf inet {
                     description "Use IPv4 addressing";
                     type jt:ipv4addr;
                   }
                 }
                 case case_2 {
                   leaf inet6 {
                     description "Use IPv6 addressing";
                     type jt:ipv6addr;
                   }
                 }
               }
               leaf routing-instance {
                 description "Routing-Instance Name";
                 type string {
                   length "1 .. 64";
                 }
               }
               leaf security-profile {
                 description "Security-profile name";
                 type string {
                   length "1 .. 127";
                 }
               }
             }
             list security-profiles {
               key name;
               ordered-by user;
               description "Security-profile configuration";
               max-elements 16;
               leaf name {
                 description "Security-profile name";
                 type string {
                   length "1 .. 127";
                 }
               }
               uses apply-advanced;
               leaf ca-cert-file-name {
                 description "Security CA cert file name";
                 type string {
                   length "1 .. 127";
                 }
               }
               leaf cert-file-name {
                 description "Security cert file name";
                 type string {
                   length "1 .. 127";
                 }
               }
               leaf key-file-name {
                 description "Security key file name";
                 type string {
                   length "1 .. 127";
                 }
               }
             }
             container pfcp {
               description "PFCP protocol configuration";
               uses apply-advanced;
               leaf message-interval {
                 description "The message retry interval in milliseconds";
                 default "3000";
                 units "milliseconds";
                 type union {
                   type string {
                     pattern "<.*>|$.*";
                   }
                   type uint16 {
                     range "100 .. 9000";
                   }
                 }
               }
               leaf message-retries {
                 description "The number of retransmission attempts";
                 default "5";
                 type union {
                   type string {
                     pattern "<.*>|$.*";
                   }
                   type int32 {
                     range "2 .. 10";
                   }
                 }
               }
               leaf heartbeat-interval {
                 description "The time interval between successive heartbeat requests";
                 default "1";
                 units "seconds";
                 type union {
                   type string {
                     pattern "<.*>|$.*";
                   }
                   type int32 {
                     range "1 .. 600";
                   }
                 }
               }
               leaf association-heartbeat-loss-count {
                 description "The association heartbeat loss count";
                 default "1200";
                 type union {
                   type string {
                     pattern "<.*>|$.*";
                   }
                   type uint32 {
                     range "100 .. 60000";
                   }
                 }
               }
               leaf resiliency-heartbeat-loss-count {
                 description "The resiliency heartbeat loss count";
                 default "20";
                 type union {
                   type string {
                     pattern "<.*>|$.*";
                   }
                   type uint16 {
                     range "1 .. 1200";
                   }
                 }
               }
               leaf restoration-heartbeat-count {
                 description "The restoration heartbeat count";
                 default "3";
                 type union {
                   type string {
                     pattern "<.*>|$.*";
                   }
                   type uint16 {
                     range "1 .. 120";
                   }
                 }
               }
             }
             container control-plane {
               presence "enable control-plane";
               description "Control-plane configuration";
               uses apply-advanced;
               leaf bng-controller-name {
                 description "BNG Controller name";
                 type string {
                   length "1 .. 64";
                 }
               }
               container transport {
                 presence "enable transport";
                 uses apply-advanced;
                 choice familyType {
                   case case_1 {
                     leaf inet {
                       description "The IPv4 address";
                       type jt:ipv4addr;
                     }
                   }
                   case case_2 {
                     leaf inet6 {
                       description "The IPv6 address";
                       type jt:ipv6addr;
                     }
                   }
                 }
                 leaf inet-tcp {
                   description "The IPv4 address on which to listen for tcp connections";
                   type jt:ipv4addr;
                 }
                 leaf port {
                   description "The port number";
                   default "8805";
                   type union {
                     type uint16;
                     type string {
                       pattern "<.*>|$.*";
                     }
                   }
                 }
               }
             }
             container selection-function {
               description "User-plane selection function";
               uses apply-advanced;
               list cluster {
                 key name;
                 ordered-by user;
                 description "Cluster for user-plane";
                 leaf name {
                   description "Cluster name";
                   type string;
                 }
                 uses apply-advanced;
               }
               list service-group {
                 key name;
                 ordered-by user;
                 description "Service-group supported by user-plane";
                 leaf name {
                   description "Service-group name";
                   type string;
                 }
                 uses apply-advanced;
               }
             }
             container capabilities {
               description "Local capabilities control";
               uses apply-advanced;
               container function-features {
                 description "Features to exclude from capabilities";
                 uses apply-advanced;
                 leaf exclude-lac {
                   description "Exclude L2TP access concentrator feature";
                   type empty;
                 }
                 leaf exclude-lns {
                   description "Exclude L2TP network server feature";
                   type empty;
                 }
                 leaf exclude-lcp-keepalive-offload {
                   description "Exclude PPP LCP echo feature";
                   type empty;
                 }
               }
             }
           }
         }
       }
     }
     container redundancy {
       description "Interface level redundancy configuration";
       uses apply-advanced;
       list interface {
         key name;
         description "One or more interfaces";
         leaf name {
           description "Interfaces participating in redundancy";
           type union {
             type jt:interface-name;
             type string {
               pattern "<.*>|$.*";
             }
           }
         }
         uses apply-advanced;
         leaf virtual-inet-address {
           description "Virtual ipv4 Address for this interface (Used with GE / XE Interfaces for VRRP protocol)";
           type jt:ipaddr;
         }
         leaf virtual-inet6-address {
           description "Virtual ipv6 Address for this interface (Used with GE / XE Interfaces for VRRP protocol)";
           type jt:ipaddr;
         }
         leaf local-inet-address {
           description "Local ipv4 Address for this interface (Used with PS Interfaces for Pseudo-Wire protocol)";
           type jt:ipaddr;
         }
         leaf local-inet6-address {
           description "Local ipv6 Address for this interface (Used with PS Interfaces for Pseudo-Wire protocol)";
           type jt:ipaddr;
         }
         leaf shared-key {
           description "Shared Key for topology discovery match (Used with PS Interfaces for Pseudo-Wire protocol)";
           type string {
             length "1 .. 64";
           }
         }
       }
       container protocol {
         description "Underlying redundancy protocol";
         uses apply-advanced;
         leaf vrrp {
           description "Use vrrp as redundancy protocol";
           type empty;
         }
         leaf pseudo-wire {
           description "Use Pseudo Wire as redundancy protocol";
           type empty;
         }
       }
       leaf re-authenticate-on-failover {
         description "Re-authenticate the subscribers on interface fail over";
         type empty;
       }
       leaf no-advertise-routes-on-backup {
         description "Do not advertise subscriber routes on redundancy backup";
         type empty;
       }
       leaf route-operation-interval {
         description "The time interval for route operation after failover";
         default "20";
         units "seconds";
         type union {
           type string {
             pattern "<.*>|$.*";
           }
           type uint32 {
             range "1 .. 100";
           }
         }
       }
       list group {
         key name;
         description "Redundancy Group";
         leaf name {
           description "Redundany Group Name";
           type string;
         }
         uses apply-advanced;
         list interface {
           key name;
           description "Interface configuration";
           leaf name {
             description "Interfaces participating in redundancy";
             type union {
               type jt:interface-name;
               type string {
                 pattern "<.*>|$.*";
               }
             }
           }
           uses apply-advanced;
           container standby-mode {
             description "Program PFE in standby-mode at Backup";
             uses apply-advanced;
             leaf standby-mode-choice {
               type enumeration {
                 enum "hot-standby" {
                   description "Hot-standby programming";
                 }
                 enum "service-activation-on-failover" {
                   description "Activate services after failover";
                 }
               }
             }
           }
         }
       }
     }
     list interfaces {
       key name;
       ordered-by user;
       description "Interface configuration";
       leaf name {
         description "Interface name";
         type string;
       }
       uses apply-advanced;
       list unit {
         key name;
         description "Logical interface";
         leaf name {
           type union {
             type string {
               pattern "<.*>|$.*";
             }
             type uint32 {
               range "0 .. 1073741823";
             }
           }
         }
         uses apply-advanced;
       }
       leaf interface-tag {
         description "Interface tag name";
         type string {
           length "1 .. 64";
         }
       }
     }
     container inline-napt {
       description "Inline NAPT configuration";
       uses apply-advanced;
       container routing-instance-pool-map {
         description "Map nat source pools to routing-instance";
         uses apply-advanced;
         list routing-instance {
           key name;
           ordered-by user;
           description "Routing instance";
           leaf name {
             description "Routing instance name";
             type string {
             }
           }
           uses apply-advanced;
           container pool {
             presence "enable pool";
             description "NAT source pool";
             uses apply-advanced;
             leaf pool-name {
               description "Pool name";
               type string {
                 length "1 .. 63";
               }
             }
           }
         }
       }
     }
     leaf location {
       description "Location name for APM partition of aggregated BNG";
       type string {
         length "1 .. 32";
       }
     }
     leaf static-framed-route {
       description "Enable static framed route feature";
       type empty;
     }
   }
   grouping smid-maintain-subscriber-type {
     description "Maintain subscriber options for subscriber management";
     uses apply-advanced;
     leaf interface-delete {
       description "Maintain subscriber on interface delete events";
       type empty;
     }
   }
   grouping smid-traceoptions-type {
     description "Trace options for Subscriber management";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Subscriber management replication operations to include in debugging trace";
       leaf name {
         type enumeration {
           enum "database" {
             description "Database operations";
           }
           enum "ui" {
             description "User Interface operations";
           }
           enum "general" {
             description "Miscellaneous operations";
           }
           enum "session-db" {
             description "Session database operations";
           }
           enum "server" {
             description "Server operations";
           }
           enum "issu" {
             description "ISSU operations";
           }
           enum "all" {
             description "All operations";
           }
         }
       }
     }
   }
   grouping snmp_scripts_file_type {
     leaf name {
       description "Local filename of the script file";
       type string {
         length "1 .. 254";
       }
     }
     uses apply-advanced;
     list oid {
       key name;
       ordered-by user;
       description "Oid implemented by this script";
       leaf name {
         description "Oid";
         type string;
       }
       uses apply-advanced;
       leaf priority {
         description "Registration priority";
         default "128";
         type union {
           type string {
             pattern "<.*>|$.*";
           }
           type uint32 {
             range "1 .. 255";
           }
         }
       }
     }
     leaf source {
       description "URL of source for this script";
       type string {
         length "1 .. 254";
       }
     }
     leaf cert-file {
       description "Specify the ca certificate file name";
       type string;
     }
     leaf routing-instance {
       description "Routing instance";
       type string {
       }
     }
     leaf python-script-user {
       description "Run the python snmp script with privileges of user";
       type string;
     }
     container start {
       description "Start snmp scripts with start-criteria check";
       uses apply-advanced;
       container start-options {
         description "Start options for snmp scripts";
         uses apply-advanced;
         leaf mem-factor {
           description "Memory factor at which to start/stop";
           type union {
             type string {
               pattern "<.*>|$.*";
             }
             type uint32 {
               range "1 .. 100";
             }
           }
         }
       }
     }
     leaf refresh {
       description "Refresh all snmp scripts from their source";
       type empty;
     }
     leaf refresh-from {
       description "Refresh all snmp scripts from a given base URL";
       type string {
         length "1 .. 254";
       }
     }
     container checksum {
       description "Checksum of this script";
       uses apply-advanced;
       leaf sha-256 {
         description "SHA-256 checksum of this script";
         type string {
           length "1 .. 254";
         }
       }
     }
   }
   grouping ssd-traceoptions-type {
     description "Trace options for SSD";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of sdk-service daemon to enable debugging output";
       leaf name {
         type enumeration {
           enum "infrastructure" {
             description "Trace ssd infrastructure code";
           }
           enum "server" {
             description "Trace ssd server functionality code";
           }
           enum "routing-instance" {
             description "Trace ssd routing instance functionality code";
           }
           enum "client-management" {
             description "Trace ssd client management code";
           }
           enum "interfaces-management" {
             description "Trace ssd/jdaf interfaces management code";
           }
           enum "route-management" {
             description "Trace ssd/jdaf route management code";
           }
           enum "nexthop-management" {
             description "Trace ssd nexthop route management code";
           }
           enum "firewall-management" {
             description "Trace JDAF-based firewall service";
           }
           enum "nexthop-group-management" {
             description "Trace ssd nexthop group management code";
           }
           enum "cli" {
             description "Trace ssd cli interaction code";
           }
           enum "cfg" {
             description "Trace ssd cli interaction code";
           }
           enum "all" {
             description "Trace all areas of ssd code";
           }
         }
       }
     }
   }
   grouping syslog-object {
     leaf name {
       description "Facility type";
       type enumeration {
         enum "any" {
           description "All facilities";
         }
         enum "authorization" {
           description "Authorization system";
         }
         enum "daemon" {
           description "Various system processes";
         }
         enum "ftp" {
           description "FTP process";
         }
         enum "ntp" {
           description "NTP process";
         }
         enum "security" {
           description "Security related";
         }
         enum "kernel" {
           description "Kernel";
         }
         enum "user" {
           description "User processes";
         }
         enum "dfc" {
           description "Dynamic flow capture";
         }
         enum "external" {
           description "Local external applications";
         }
         enum "firewall" {
           description "Firewall filtering system";
         }
         enum "pfe" {
           description "Packet Forwarding Engine";
         }
         enum "conflict-log" {
           description "Configuration conflict log";
         }
         enum "change-log" {
           description "Configuration change log";
         }
         enum "interactive-commands" {
           description "Commands executed by the UI";
         }
       }
     }
     choice level {
       case case_1 {
         leaf any {
           description "All levels";
           type empty;
         }
       }
       case case_2 {
         leaf emergency {
           description "Panic conditions";
           type empty;
         }
       }
       case case_3 {
         leaf alert {
           description "Conditions that should be corrected immediately";
           type empty;
         }
       }
       case case_4 {
         leaf critical {
           description "Critical conditions";
           type empty;
         }
       }
       case case_5 {
         leaf error {
           description "Error conditions";
           type empty;
         }
       }
       case case_6 {
         leaf warning {
           description "Warning messages";
           type empty;
         }
       }
       case case_7 {
         leaf notice {
           description "Conditions that should be handled specially";
           type empty;
         }
       }
       case case_8 {
         leaf info {
           description "Informational messages";
           type empty;
         }
       }
       case case_9 {
         leaf none {
           description "No messages";
           type empty;
         }
       }
     }
   }
   grouping tacplus-server-object {
     leaf name {
       description "TACACS+ authentication server address";
       type jt:hostname;
     }
     uses apply-advanced;
     leaf routing-instance {
       description "Routing instance";
       type string {
       }
     }
     leaf port {
       description "TACACS+ authentication server port number";
       default "49";
       type union {
         type uint16;
         type string {
           pattern "<.*>|$.*";
         }
       }
     }
     leaf secret {
       description "Shared secret with the authentication server";
       type jt:unreadable;
     }
     leaf timeout {
       description "Request timeout period";
       default "3";
       units "seconds";
       type union {
         type string {
           pattern "<.*>|$.*";
         }
         type uint32 {
           range "1 .. 90";
         }
       }
     }
     leaf single-connection {
       description "Optimize TCP connection attempts";
       type empty;
     }
     leaf source-address {
       description "Use specified address as source address";
       type jt:hostname;
     }
   }
   grouping tty_port_object {
     description "RS-232 configuration";
     uses apply-advanced;
     leaf-list authentication-order {
       ordered-by user;
       type enumeration {
         enum "radius" {
           description "Remote Authentication Dial-In User Service";
         }
         enum "tacplus" {
           description "TACACS+ authentication services";
         }
         enum "password" {
           description "Traditional password authentication";
         }
       }
     }
     leaf log-out-on-disconnect {
       description "Log out the console session when cable is unplugged";
       type empty;
     }
     leaf port-type {
       description "Switch console between RJ45 and mini-USB";
       type enumeration {
         enum "rj45" {
           description "Enable RJ45";
         }
         enum "mini-usb" {
           description "Enable mini-USB";
         }
       }
     }
     leaf disable {
       description "Disable console";
       type empty;
     }
     leaf insecure {
       description "Disallow root user access";
       type empty;
     }
     leaf speed {
       description "Speed of the port";
       status deprecated;
       units "baud";
       type enumeration {
         enum "1200" {
           description "Standard terminal at 1200 baud";
           status deprecated;
         }
         enum "2400" {
           description "Standard terminal at 2400 baud";
           status deprecated;
         }
         enum "4800" {
           description "Standard terminal at 4800 baud";
           status deprecated;
         }
         enum "9600" {
           description "Standard terminal at 9600 baud";
           status deprecated;
         }
         enum "19200" {
           description "Standard terminal at 19200 baud";
           status deprecated;
         }
         enum "38400" {
           description "Standard terminal at 38400 baud";
           status deprecated;
         }
         enum "57600" {
           description "Standard terminal at 57600 baud";
           status deprecated;
         }
         enum "115200" {
           description "Standard terminal at 115200 baud";
           status deprecated;
         }
       }
     }
     leaf type {
       description "Terminal type";
       type enumeration {
         enum "ansi" {
           description "ANSI-compatible terminal";
         }
         enum "vt100" {
           description "VT100-compatible terminal";
         }
         enum "small-xterm" {
           description "Small (24-line) xterm window";
         }
         enum "xterm" {
           description "Large (65-line) xterm window";
         }
       }
     }
     leaf silent-with-modem {
       description "Make the console silent if modem is connected and no call is present on the modem";
       type empty;
     }
   }
 }
