/*
 * Copyright (c) 2025 Juniper Networks, Inc.
 * All rights reserved.
 */
 module junos-rpc-ospf {
   namespace "http://yang.juniper.net/junos/rpc/ospf";

   prefix ospf;

   import junos-common-types {
     prefix jt;
     revision-date 2025-01-01;
   }

   organization "Juniper Networks, Inc.";

   contact "yang-support@juniper.net";

   description "Junos RPC YANG module for ospf command(s)";

   revision 2025-01-01 {
     description "Junos: 25.2R1.9";
   }

   rpc get-ospf-overview-information {
     description "Show overview of OSPF information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "extensive" {
             description "Display extensive output";
           }
         }
       }
       leaf instance {
         description "Name of OSPF instance";
         type string;
       }
     }
     output {
       container ospf-overview-information {
         uses ospf-overview-information-block;
       }
     }
   }
   rpc get-ospf-database-information {
     description "Show OSPF link-state database";
     input {
       choice daemon-select {
         case logical-system {
           leaf logical-system {
             description "Name of logical system, or 'all'";
             type string {
             }
           }
         }
       }
       leaf flex-algorithm-id {
         description "Flex Algorithm id";
         type union {
           type string {
             pattern "<.*>|$.*";
           }
           type uint32 {
             range "128 .. 255";
           }
         }
       }
       leaf igp-instance {
         description "Name of igp-instance";
         type string;
       }
       leaf level {
         default "brief";
         type enumeration {
           enum "brief" {
             description "Display brief output (default)";
           }
           enum "detail" {
             description "Display detailed output";
           }
           enum "extensive" {
             description "Display extensive output";
           }
           enum "summary" {
             description "Display summary output";
           }
         }
       }
       leaf lsa-type {
         type enumeration {
           enum "router" {
             description "Router link-state advertisements";
           }
           enum "network" {
             description "Network link-state advertisements";
           }
           enum "netsummary" {
             description "Summary network link-state advertisements";
           }
           enum "asbrsummary" {
             description "Summary AS boundary router link-state advertisements";
           }
           enum "external" {
             description "External link-state advertisements";
           }
           enum "nssa" {
             description "Not-so-stubby area link-state advertisements";
           }
           enum "link-local" {
             description "Link local link-state advertisements";
           }
           enum "opaque-area" {
             description "Opaque area-scope link-state advertisements";
           }
           enum "opaque-as" {
             description "Opaque as-scope link-state advertisements";
           }
         }
       }
       leaf area {
         description "OSPF area ID";
         default "all";
         type string;
       }
       leaf lsa-id {
         description "Link-state advertisement ID";
         default "all";
         type string;
       }
       leaf advertising-router {
         description "Router ID of advertising router";
         type string;
       }
       leaf instance {
         description "Name of OSPF instance";
         type string;
       }
     }
     output {
       container ospf-database-information {
         uses ospf-database-information-block;
       }
     }
   }
   rpc get-ospf-database-ext-prefix-information {
     description "Opaque area extended prefix LSAs";
     input {
       choice daemon-select {
         case logical-system {
           leaf logical-system {
             description "Name of logical system, or 'all'";
             type string {
             }
           }
         }
       }
       leaf igp-instance {
         description "Name of igp-instance";
         type string;
       }
       leaf level {
         default "brief";
         type enumeration {
           enum "brief" {
             description "Display brief output (default)";
           }
           enum "detail" {
             description "Display detailed output";
           }
           enum "extensive" {
             description "Display extensive output";
           }
           enum "summary" {
             description "Display summary output";
           }
         }
       }
       leaf prefix {
         description "OSPF Extended Prefix";
         type jt:ipv4prefix;
       }
       leaf area {
         description "OSPF area ID";
         default "all";
         type string;
       }
       leaf lsa-id {
         description "Link-state advertisement ID";
         default "all";
         type string;
       }
       leaf advertising-router {
         description "Router ID of advertising router";
         type string;
       }
       leaf instance {
         description "Name of OSPF instance";
         type string;
       }
     }
     output {
       container ospf-database-information {
         uses ospf-database-information-block;
       }
     }
   }
   rpc get-ospf-database-ext-link-information {
     description "Opaque area extended link LSAs";
     input {
       choice daemon-select {
         case logical-system {
           leaf logical-system {
             description "Name of logical system, or 'all'";
             type string {
             }
           }
         }
       }
       leaf igp-instance {
         description "Name of igp-instance";
         type string;
       }
       leaf level {
         default "brief";
         type enumeration {
           enum "brief" {
             description "Display brief output (default)";
           }
           enum "detail" {
             description "Display detailed output";
           }
           enum "extensive" {
             description "Display extensive output";
           }
           enum "summary" {
             description "Display summary output";
           }
         }
       }
       leaf link-addr {
         description "OSPF Extended Link-Addr";
         default "all";
         type string;
       }
       leaf area {
         description "OSPF area ID";
         default "all";
         type string;
       }
       leaf lsa-id {
         description "Link-state advertisement ID";
         default "all";
         type string;
       }
       leaf advertising-router {
         description "Router ID of advertising router";
         type string;
       }
       leaf instance {
         description "Name of OSPF instance";
         type string;
       }
     }
     output {
       container ospf-database-information {
         uses ospf-database-information-block;
       }
     }
   }
   rpc get-ospf-backup-spf-information {
     description "Show OSPF backup SPF calculations information";
     input {
       choice daemon-select {
         case logical-system {
           leaf logical-system {
             description "Name of logical system, or 'all'";
             type string {
             }
           }
         }
       }
       leaf igp-instance {
         description "Name of igp-instance";
         type string;
       }
       leaf instance {
         description "Name of OSPF instance";
         type string;
       }
       leaf topology {
         description "Name of topology";
         type string;
       }
       leaf area {
         description "OSPF area ID";
         type jt:areaid;
       }
       leaf no-coverage {
         description "Entries with no backup coverage";
         type empty;
       }
       leaf node-id {
         description "Display nodes matching the node-id";
         type string;
       }
       leaf verbosity_level {
         default "brief";
         type enumeration {
           enum "brief" {
             description "Display brief output (default)";
           }
           enum "detail" {
             description "Display detailed output";
           }
         }
       }
     }
     output {
       container ospf-backup-spf-information {
         uses ospf-backup-spf-information-block;
       }
     }
   }
   rpc get-ospf-backup-coverage-information {
     description "Show OSPF backup coverage";
     input {
       choice daemon-select {
         case logical-system {
           leaf logical-system {
             description "Name of logical system, or 'all'";
             type string {
             }
           }
         }
       }
       leaf igp-instance {
         description "Name of igp-instance";
         type string;
       }
       leaf instance {
         description "Name of OSPF instance";
         type string;
       }
       leaf topology {
         description "Name of topology";
         type string;
       }
     }
     output {
       container ospf-backup-coverage-information {
         uses ospf-backup-coverage-information-block;
       }
     }
   }
   rpc get-ospf-backup-neighbor-information {
     description "Show OSPF backup neighbors";
     input {
       choice daemon-select {
         case logical-system {
           leaf logical-system {
             description "Name of logical system, or 'all'";
             type string {
             }
           }
         }
       }
       leaf igp-instance {
         description "Name of igp-instance";
         type string;
       }
       leaf instance {
         description "Name of OSPF instance";
         type string;
       }
       leaf topology {
         description "Name of topology";
         type string;
       }
       leaf area {
         description "OSPF area ID";
         type jt:areaid;
       }
     }
     output {
       container ospf-backup-neighbor-information {
         uses ospf-backup-neighbor-information-block;
       }
     }
   }
   rpc get-ospf-backup-lsp-information {
     description "Show OSPF MPLS backup LSP information";
     input {
       choice daemon-select {
         case logical-system {
           leaf logical-system {
             description "Name of logical system, or 'all'";
             type string {
             }
           }
         }
       }
       leaf igp-instance {
         description "Name of igp-instance";
         type string;
       }
     }
     output {
       container ospf-backup-mplsp-information {
         uses ospf-backup-mplsp-information-block;
       }
     }
   }
   rpc get-ospf-interface-information {
     description "Show OSPF interface status information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
           enum "extensive" {
             description "Display extensive output";
           }
         }
       }
       leaf interface-name {
         description "Name of logical interface";
         type string;
       }
       leaf area {
         description "OSPF area ID";
         type jt:areaid;
       }
       leaf instance {
         description "Name of OSPF instance";
         type string;
       }
     }
     output {
       container ospf-interface-information {
         uses ospf-interface-information-block;
       }
     }
   }
   rpc get-ospf-context-id-information {
     description "Show OSPF context identifier information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
         }
       }
       leaf context-id {
         description "IP address representing a context identifier";
         type string;
       }
       leaf area {
         description "OSPF area ID";
         type jt:areaid;
       }
       leaf instance {
         description "Name of OSPF instance";
         type string;
       }
     }
     output {
       container ospf-context-id-information {
         uses ospf-context-id-information-block;
       }
     }
   }
   rpc get-ospf-neighbor-information {
     description "Show OSPF neighbor status information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
           enum "extensive" {
             description "Display extensive output";
           }
         }
       }
       leaf interface {
         description "Name of logical interface";
         type string;
       }
       leaf area {
         description "OSPF area ID";
         type jt:areaid;
       }
       leaf neighbor {
         description "IP address or ID of neighbor";
         type string;
       }
       leaf instance {
         description "Name of OSPF instance";
         type string;
       }
     }
     output {
       choice output-choice {
         case output-choice-1 {
           container ospf-neighbor-information-logical-system-all {
             uses ospf-neighbor-information-logical-system-all-block;
           }
         }
         case output-choice-2 {
           container ospf-neighbor-information-all {
             uses ospf-neighbor-information-all-block;
           }
         }
         case output-choice-3 {
           container ospf-neighbor-information {
             uses ospf-neighbor-information-block;
           }
         }
       }
     }
   }
   rpc get-ospf-route-information {
     description "Show OSPF routing table";
     input {
       choice daemon-select {
         case logical-system {
           leaf logical-system {
             description "Name of logical system, or 'all'";
             type string {
             }
           }
         }
       }
       leaf flex-algorithm-id {
         description "Flex Algorithm id";
         type union {
           type string {
             pattern "<.*>|$.*";
           }
           type uint32 {
             range "128 .. 255";
           }
         }
       }
       leaf igp-instance {
         description "Name of igp-instance";
         type string;
       }
       leaf topology {
         description "Name of topology";
         type string;
       }
       leaf path-type {
         description "OSPF path type";
         type enumeration {
           enum "intra" {
             description "Display intra-area routes";
           }
           enum "inter" {
             description "Display inter-area routes";
           }
           enum "extern" {
             description "Display external routes";
           }
         }
       }
       leaf route-type {
         description "OSPF route type";
         type enumeration {
           enum "router" {
             description "Display routes to all routers";
           }
           enum "abr" {
             description "Display routes to area border routers";
           }
           enum "asbr" {
             description "Display routes to AS border routers";
           }
           enum "network" {
             description "Display routes to networks";
           }
         }
       }
       leaf no-backup-coverage {
         description "Display routes with no backup coverage";
         type empty;
       }
       leaf destination {
         description "IP address and optional prefix length of destination";
         type jt:ipv4prefix;
       }
       leaf verbosity_level {
         default "brief";
         type enumeration {
           enum "brief" {
             description "Display brief output (default)";
           }
           enum "detail" {
             description "Display detailed output";
           }
           enum "extensive" {
             description "Display extensive output";
           }
         }
       }
       leaf instance {
         description "Name of OSPF instance";
         type string;
       }
     }
     output {
       container ospf-route-information {
         uses ospf-route-information-block;
       }
     }
   }
   rpc get-ospf-statistics-information {
     description "Show OSPF statistics";
     input {
       choice daemon-select {
         case logical-system {
           leaf logical-system {
             description "Name of logical system, or 'all'";
             type string {
             }
           }
         }
       }
       leaf igp-instance {
         description "Name of igp-instance";
         type string;
       }
       leaf instance {
         description "Name of OSPF instance";
         type string;
       }
     }
     output {
       container ospf-statistics-information {
         uses ospf-statistics-information-block;
       }
     }
   }
   rpc get-ospf-intf-statistics-information {
     description "OSPF interface statistics information";
     input {
       choice daemon-select {
         case logical-system {
           leaf logical-system {
             description "Name of logical system, or 'all'";
             type string {
             }
           }
         }
       }
       leaf igp-instance {
         description "Name of igp-instance";
         type string;
       }
       leaf instance {
         description "Name of OSPF routing instance";
         type string;
       }
       leaf interface-name {
         description "Name of interface";
         type string;
       }
     }
     output {
       container ospf-intf-statistics-information {
         uses ospf-intf-statistics-information-block;
       }
     }
   }
   rpc get-ospf-io-statistics-information {
     description "Show OSPF I/O statistics";
     input {
       choice daemon-select {
         case logical-system {
           leaf logical-system {
             description "Name of logical system, or 'all'";
             type string {
             }
           }
         }
       }
       leaf igp-instance {
         description "Name of igp-instance";
         type string;
       }
     }
     output {
       container ospf-io-statistics-information {
         uses ospf-io-statistics-information-block;
       }
     }
   }
   rpc get-ospf-log-information {
     description "Show shortest-path-first calculations from OSPF log";
     input {
       choice daemon-select {
         case logical-system {
           leaf logical-system {
             description "Name of logical system, or 'all'";
             type string {
             }
           }
         }
       }
       leaf igp-instance {
         description "Name of igp-instance";
         type string;
       }
       leaf instance {
         description "Name of OSPF instance";
         type string;
       }
       leaf topology {
         description "Name of topology";
         type string;
       }
     }
     output {
       container ospf-log-information {
         uses ospf-log-information-block;
       }
     }
   }
   rpc get-ospf-bgporr-information {
     description "Show BGP optimal route-reflection groups";
     input {
       choice daemon-select {
         case logical-system {
           leaf logical-system {
             description "Name of logical system, or 'all'";
             type string {
             }
           }
         }
       }
       leaf igp-instance {
         description "Name of igp-instance";
         type string;
       }
       leaf topology {
         description "Name of topology";
         type string;
       }
       leaf path-type {
         description "OSPF path type";
         type enumeration {
           enum "intra" {
             description "Display intra-area routes";
           }
           enum "inter" {
             description "Display inter-area routes";
           }
           enum "extern" {
             description "Display external routes";
           }
         }
       }
       leaf route-type {
         description "OSPF route type";
         type enumeration {
           enum "router" {
             description "Display routes to all routers";
           }
           enum "abr" {
             description "Display routes to area border routers";
           }
           enum "asbr" {
             description "Display routes to AS border routers";
           }
           enum "network" {
             description "Display routes to networks";
           }
         }
       }
       leaf destination {
         description "IP address and optional prefix length of destination";
         type jt:ipv4prefix;
       }
       leaf instance {
         description "Name of OSPF instance";
         type string;
       }
       leaf group {
         description "BGP optimal route-reflection peer group name";
         type string;
       }
       leaf verbosity_level {
         default "brief";
         type enumeration {
           enum "brief" {
             description "Display brief output (default)";
           }
           enum "detail" {
             description "Display detailed output";
           }
           enum "extensive" {
             description "Display extensive output";
           }
         }
       }
     }
     output {
       container ospf-bgporr-route-information {
         uses ospf-bgporr-route-information-block;
       }
     }
   }
   rpc get-ospf-spring-flex-algorithm-information {
     description "Show SPRING flex-algorithm information";
     input {
       choice daemon-select {
         case logical-system {
           leaf logical-system {
             description "Name of logical system, or 'all'";
             type string {
             }
           }
         }
       }
       leaf igp-instance {
         description "Name of igp-instance";
         type string;
       }
       leaf flex-algorithm-id {
         description "Flex Algorithm id";
         type union {
           type string {
             pattern "<.*>|$.*";
           }
           type uint32 {
             range "128 .. 255";
           }
         }
       }
     }
     output {
       container ospf-spring-flex-algorithm-information {
         uses ospf-spring-flex-algorithm-information-block;
       }
     }
   }
   rpc get-ospf-spring-sensor-information {
     description "Show SPRING sensor info";
     input {
       choice daemon-select {
         case logical-system {
           leaf logical-system {
             description "Name of logical system, or 'all'";
             type string {
             }
           }
         }
       }
       leaf igp-instance {
         description "Name of igp-instance";
         type string;
       }
     }
     output {
       container ospf-spring-sensor-information {
         uses ospf-spring-sensor-information-block;
       }
     }
   }
   rpc get-ospf-spring-sid-database-information {
     description "Show SPRING SID Database";
     input {
       choice daemon-select {
         case logical-system {
           leaf logical-system {
             description "Name of logical system, or 'all'";
             type string {
             }
           }
         }
       }
       leaf igp-instance {
         description "Name of igp-instance";
         type string;
       }
     }
     output {
       container ospf-spring-sid-database-information {
         uses ospf-spring-sid-database-information-block;
       }
     }
   }
   rpc get-ospf-spring-pfx-sid-map-information {
     description "Show SPRING Prefix-SID Mapping";
     input {
       choice daemon-select {
         case logical-system {
           leaf logical-system {
             description "Name of logical system, or 'all'";
             type string {
             }
           }
         }
       }
       leaf igp-instance {
         description "Name of igp-instance";
         type string;
       }
     }
     output {
       container ospf-spring-pfx-sid-map-information {
         uses ospf-spring-pfx-sid-map-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ospf-overview-information-block {
     container ospf-overview {
       description "Overview information for an OSPF instance";
       leaf-list instance-name {
         type string;
       }
       leaf ospf-router-id {
         type jt:ipaddr;
         description "OSPF router ID";
       }
       leaf ospf-route-table-index {
         type uint32;
         description "Route table index";
       }
       leaf ospf-configured-overload {
         type empty;
         description "Instance is configured to be in overload";
       }
       leaf ospf-configured-overload-remaining-time {
         type string;
         description "Time remaining on configured overload timeout";
       }
       leaf ospf-abr {
         type empty;
         description "Router is an area border router";
       }
       leaf ospf-asbr {
         type empty;
         description "Router is an autonomous system boundary router";
       }
       leaf ospf-nssa-router {
         type empty;
         description "Router is a not-so-stubby area router";
       }
       leaf no-rfc-1583 {
         type empty;
         description "RFC1583 compatibility is disabled";
       }
       leaf forwarding-address-to-broadcast {
         type empty;
         description "Set forwarding address in Type 5 LSA in broadcast network";
       }
       leaf ospf-lsa-refresh-time {
         type uint32;
         description "Refresh period for link-state advertisement (in minutes)";
       }
       leaf ospf-traffic-engineering {
         type empty;
         description "Traffic engineering is enabled";
       }
       leaf ospf-dna-uncapable {
         type empty;
         description "Not safe to generate DoNotAge LSAs";
       }
       leaf ospf-as-dc-bit-clear-count {
         type uint32;
         description "Number of AS scope link-state advertisements received with DC bit clear";
       }
       leaf ospf-area-dc-bit-clear-count {
         type uint32;
         description "Number of area scope link-state advertisements received with DC bit clear";
       }
       leaf ospf-area-indications-count {
         type uint32;
         description "Number of indication link-state advertisements received";
       }
       leaf ospf-link-dc-bit-clear-count {
         type uint32;
         description "Number of link local scope link-state advertisements received with no DC bit clear";
       }
       container ospf-restart {
         description "OSPF restart parameters";
         leaf ospf-restart-enabled {
           type string;
           description "OSPF restart mode";
         }
         leaf ospf-restart-duration {
           type uint32;
           description "Duration of OSPF restart (seconds)";
         }
         leaf ospf-restart-grace-period {
           type uint32;
           description "Grace period for OSPF restart (seconds)";
         }
         leaf ospf-standard-graceful-restart-helper-mode {
           type string;
           description "OSPF graceful restart (RFC3623) helper mode";
         }
         leaf ospf-restart-signaling-helper-mode {
           type string;
           description "OSPF restart-signaling helper mode";
         }
       }
       container tracing-information {
         leaf flags {
           type string;
           description "Enabled trace flags";
         }
         leaf filename {
           type string;
           description "Name of the trace file";
         }
         leaf filesize {
           type int32;
           description "Maximum size of the trace file";
         }
         leaf filelimit {
           type int32;
           description "Maximum number of retained trace files";
         }
       }
       container ospf-db-protection-overview {
         description "OSPF database protection overview information";
         leaf ospf-db-protection-state {
           type string;
           description "Database protection state";
         }
         leaf ospf-db-protection-remaining-time {
           type uint32;
           description "Time remaining in the current state";
         }
         leaf ospf-db-protection-warning-threshold {
           type uint32;
           description "Warning threshold as percentage";
         }
         leaf ospf-db-protection-warning-only {
           type empty;
           description "Configured to generate warning only";
         }
         leaf ospf-db-protection-lsa-current {
           type uint32;
           description "Current number of non self-generated LSAs";
         }
         leaf ospf-db-protection-lsa-warning {
           type uint32;
           description "Warning number of non self-generated LSAs";
         }
         leaf ospf-db-protection-lsa-maximum {
           type uint32;
           description "Allowed number of non self-generated LSAs";
         }
         leaf ospf-db-protection-ignore-time {
           type uint32;
           description "Configured value of ignore time";
         }
         leaf ospf-db-protection-reset-time {
           type uint32;
           description "Configured value of reset time";
         }
         leaf ospf-db-protection-ignore-current {
           type uint32;
           description "Current number of transitions to Ignore state";
         }
         leaf ospf-db-protection-ignore-maximum {
           type uint32;
           description "Allowed number of transitions to Ignore state";
         }
       }
       list ospf-area-overview {
         description "Overview information for an OSPF area";
         leaf ospf-area {
           type string;
           description "Area ID";
         }
         leaf ospf-stub-type {
           type string;
           description "Stub type of area";
         }
         leaf ospf-stub-cost {
           type uint32;
           description "Cost of default route in stub area";
         }
         leaf ospf-virtual-transit {
           type empty;
           description "Area is transit for virtual links";
         }
         leaf authentication-type {
           type string;
           description "Type of authentication";
         }
         leaf ospf-abr-count {
           type uint32;
           description "Number of area border routers";
         }
         leaf ospf-asbr-count {
           type uint32;
           description "Number of autonomous system boundary routers";
         }
         leaf ospf-dna-uncapable {
           type empty;
           description "Not safe to generate DoNotAge LSAs";
         }
         leaf ospf-area-dc-bit-clear-count {
           type uint32;
           description "Number of area scope link-state advertisements received with DC bit clear";
         }
         leaf ospf-area-indications-count {
           type uint32;
           description "Number of indication link-state advertisements received";
         }
         leaf ospf-area-self-indicating {
           type empty;
           description "Router generated an indication link-state advertisement";
         }
         leaf ospf-link-dc-bit-clear-count {
           type uint32;
           description "Number of link local scope link-state advertisements received with no DC bit clear";
         }
         container ospf-nbr-overview {
           leaf ospf-nbr-up-count {
             type uint32;
             description "Number of neighbors in full state";
           }
         }
       }
       list ospf-topology-overview {
         description "OSPF topology specific overview information";
         leaf ospf-topology-name {
           type string;
           description "OSPF topology name";
         }
         leaf ospf-topology-id {
           type int32;
           description "OSPF topology id";
         }
         leaf ospf-topology-configured-overload {
           type empty;
           description "Topology is configured to be in overload";
         }
         leaf ospf-topology-dynamic-overload {
           type empty;
           description "Topology is in dynamic overload i.e. prefix limit was exceeded";
         }
         leaf ospf-prefix-export-count {
           type uint32;
           description "Number of prefixes exported into the topology";
         }
         leaf ospf-prefix-export-limit {
           type uint32;
           description "Number of prefixes we are allowed to exported into the topology";
         }
         leaf ospf-full-spf-count {
           type uint32;
           description "Number of full SPF calculations";
         }
         leaf ospf-spf-delay {
           type string;
           description "Delay before performing consecutive SPF calculations";
         }
         leaf ospf-spf-holddown {
           type string;
           description "Time to hold down before running an SPF";
         }
         leaf ospf-spf-rapid-runs {
           type string;
           description "Number of rapid SPF runs before SPF holddown";
         }
         leaf ospf-backup-spf-status {
           type string;
           description "Backup SPF status";
         }
         leaf ospf-backup-spf-remote-backup-calculation {
           type empty;
           description "Remote-LFA backup calculations enabled";
         }
         leaf ospf-backup-spf-downstream-only {
           type empty;
           description "Topology is configured to use only downstream backup paths";
         }
         leaf ospf-backup-spf-node-link-degradation {
           type empty;
           description "Topology is configured to use node link degradation";
         }
         leaf ospf-te-shortcuts {
           type empty;
           description "IP Traffic engineering shortcuts are enabled";
         }
         leaf ospf-te-shortcuts-mpls {
           type empty;
           description "MPLS Traffic engineering shortcuts are enabled";
         }
         leaf ospf-topo-sessid-count {
           type uint32;
           description "Number of Session IDs associated with routes in this toplogy";
         }
       }
       container ospf-spring-overview {
         description "OSPF spring parameters";
         leaf ospf-spring-enabled {
           type string;
           description "OSPF SPRING";
         }
         leaf ospf-srgb-allocation {
           type string;
           description "SRGB Block Allocation";
         }
         leaf ospf-node-segment-enabled {
           type string;
           description "OSPF node segments";
         }
         container ospf-srgb-config {
           description "SRGB block configuration related information";
           leaf ospf-srgb-config-block-header {
             type string;
             description "SRGB Config Block";
           }
           leaf ospf-srgb-start-label {
             type int32;
             description "Configuration of SRGB start label";
           }
           leaf ospf-srgb-index-range {
             type int32;
             description "Configuration of SRGB index range";
           }
         }
         container ospf-srgb-block {
           description "SRGB block related information";
           leaf ospf-srgb-start-index {
             type int32;
             description "Starting Index for SRGB Block";
           }
           leaf ospf-srgb-size {
             type int32;
             description "Size of the specific SRGB Block";
           }
           leaf ospf-srgb-first-label {
             type int32;
             description "First label allocated for SRGB Block";
           }
           leaf ospf-srgb-last-label {
             type int32;
             description "Last label allocated for SRGB Block";
           }
         }
         container ospf-node-segment {
           description "Node segments related information";
           leaf ospf-node-segment-ipv4-index {
             type int32;
             description "Ipv4 node segment index for this device";
           }
           leaf ospf-node-segment-index-range {
             type int32;
             description "Range of node segment indices configured";
           }
           leaf ospf-node-segment-block-header {
             type empty;
             description "Node segment blocks";
           }
           container ospf-node-segment-block {
             description "Node segment blocks related information";
             leaf ospf-node-segment-block-start-index {
               type int32;
               description "Starting index for the specific node segment block";
             }
             leaf ospf-node-segment-block-size {
               type int32;
               description "Size of the specific node segment block";
             }
             leaf ospf-node-segment-block-first-label {
               type int32;
               description "First label allocated for the specific node segment block";
             }
             leaf ospf-node-segment-block-last-label {
               type int32;
               description "Last label allocated for the specific node segment block";
             }
           }
         }
       }
       container ospf-tilfa-overview {
         description "OSPF Post Convergence Backup parameters";
         leaf ospf-tilfa-enabled {
           type string;
           description "Post Convergence Backup";
         }
         leaf ospf-tilfa-max-labels {
           type int32;
           description "Max labels";
         }
         leaf ospf-tilfa-max-spf {
           type int32;
           description "Max spf";
         }
         leaf ospf-tilfa-ecmp-backup {
           type int32;
           description "Post Convergence Max Ecmp Backup";
         }
       }
     }
   }
   grouping ospf-database-information-block {
     container ospf-area-header {
       leaf ospf-area {
         type string;
         description "Area ID";
       }
     }
     container ospf-intf-header {
       leaf ospf-intf {
         type string;
         description "Name of interface";
       }
       leaf ospf-area {
         type string;
         description "Area ID";
       }
     }
     list ospf-database {
       leaf-list ospf-database.external-heading {
         type string;
       }
       leaf-list ospf-database.heading {
         type string;
       }
       leaf lsa-type {
         type string;
       }
       leaf our-entry {
         type empty;
       }
       leaf lsa-id {
         type string;
       }
       leaf advertising-router {
         type jt:ipaddr;
       }
       leaf sequence-number {
         type int64;
         description "History event number";
       }
       leaf age {
         type string;
       }
       leaf ospf-do-not-age {
         type empty;
         description "DoNotAge bit is set on the link-state advertisement received";
       }
       leaf options {
         type int32;
       }
       leaf checksum {
         type int32;
       }
       leaf lsa-length {
         type int32;
       }
       container ospf-router-lsa {
         leaf bits {
           type int32;
         }
         leaf link-count {
           type int32;
         }
         list ospf-link {
           leaf link-id {
             type string;
           }
           leaf link-data {
             type string;
           }
           leaf link-type-name {
             type string;
             description "OSPF LSA link type";
           }
           leaf link-type-value {
             type int32;
           }
           leaf ospf-topology-count {
             type int32;
             description "Number of topologies advertised for this link";
           }
           leaf metric {
             type int32;
           }
           list ospf-router-link-topology {
             description "OSPF topology specific information for a router link";
             leaf ospf-topology-name {
               type string;
               description "OSPF topology name";
             }
             leaf ospf-topology-id {
               type int32;
               description "OSPF topology id";
             }
             leaf ospf-topology-metric {
               type int32;
               description "OSPF topology specific metric";
             }
           }
         }
         list ospf-lsa-topology {
           description "OSPF topology information for a LSA";
           leaf ospf-topology-name {
             type string;
             description "OSPF topology name";
           }
           leaf ospf-topology-id {
             type int32;
             description "OSPF topology id";
           }
           list ospf-lsa-topology-link {
             description "OSPF topology information for a set of links to a LSA";
             leaf link-type-name {
               type string;
               description "OSPF LSA link type";
             }
             leaf ospf-lsa-topology-link-node-id {
               type string;
               description "LSA ID of the node representing the remote LSA";
             }
             leaf ospf-lsa-topology-link-metric {
               type int32;
               description "Minimum metric of the set of links";
             }
             leaf ospf-lsa-topology-link-state {
               type string;
               description "State of the set of links";
             }
           }
         }
       }
       container ospf-network-lsa {
         leaf address-mask {
           type jt:ipaddr;
         }
         leaf-list attached-router {
           type jt:ipaddr;
         }
         list ospf-lsa-topology {
           description "OSPF topology information for a LSA";
           leaf ospf-topology-name {
             type string;
             description "OSPF topology name";
           }
           leaf ospf-topology-id {
             type int32;
             description "OSPF topology id";
           }
           list ospf-lsa-topology-link {
             description "OSPF topology information for a set of links to a LSA";
             leaf link-type-name {
               type string;
               description "OSPF LSA link type";
             }
             leaf ospf-lsa-topology-link-node-id {
               type string;
               description "LSA ID of the node representing the remote LSA";
             }
             leaf ospf-lsa-topology-link-metric {
               type int32;
               description "Minimum metric of the set of links";
             }
             leaf ospf-lsa-topology-link-state {
               type string;
               description "State of the set of links";
             }
           }
         }
       }
       list ospf-opaque-area-lsa {
         container tlv-block {
           leaf tlv-type-name {
             type string;
           }
           leaf tlv-type-value {
             type int32;
           }
           leaf tlv-length {
             type int32;
           }
           leaf bytes-left {
             type int32;
           }
           leaf-list formatted-tlv-data {
             type string;
           }
         }
         container te-subtlv {
           leaf tlv-type-name {
             type string;
           }
           leaf tlv-type-value {
             type int32;
           }
           leaf tlv-length {
             type int32;
           }
           leaf bytes-left {
             type int32;
           }
           leaf-list formatted-tlv-data {
             type string;
           }
         }
         container extended-link-tlv-block {
           leaf tlv-type-name {
             type string;
           }
           leaf tlv-type-value {
             type int32;
           }
           leaf tlv-length {
             type int32;
           }
           leaf bytes-left {
             type int32;
           }
           list ospf-extended-link-tlv-data {
             description "TLV data for OSPF Extended Link LSA";
             leaf ospf-ext-link-type {
               type int32;
               description "OSPF Extended Link Type";
             }
             leaf ospf-ext-link-id {
               type jt:ipaddr;
               description "OSPF Extended Link ID";
             }
             leaf ospf-ext-link-data {
               type jt:ipaddr;
               description "OSPF Extended Link Data";
             }
           }
           container adjacency-sid-subtlv {
             leaf tlv-type-name {
               type string;
             }
             leaf tlv-type-value {
               type int32;
             }
             leaf tlv-length {
               type int32;
             }
             leaf bytes-left {
               type int32;
             }
             list ospf-adjacency-sid-subtlv-data {
               description "SUBTLV data for Adjacency SID Subtlv under Extended Link TLV";
               leaf ospf-adjsid-flags {
                 type int32;
                 description "OSPF Extended Link Adjacency SID Flags";
               }
               leaf ospf-adjsid-mt-id {
                 type int32;
                 description "OSPF Extended Link Adjacency SID MT_ID";
               }
               leaf ospf-adjsid-weight {
                 type int32;
                 description "OSPF Extended Link Adjacency SID Weight";
               }
               leaf ospf-adjsid-label {
                 type int32;
                 description "OSPF Extended Link Adjacency SID Label";
               }
             }
           }
           container lan-adjacency-sid-subtlv {
             leaf tlv-type-name {
               type string;
             }
             leaf tlv-type-value {
               type int32;
             }
             leaf tlv-length {
               type int32;
             }
             leaf bytes-left {
               type int32;
             }
             list ospf-lan-adjacency-sid-subtlv-data {
               description "SUBTLV data for LAN Adjacency SID Subtlv under Extended Link TLV";
               leaf ospf-lan-adjsid-flags {
                 type int32;
                 description "OSPF Extended Link LAN Adjacency SID Flags";
               }
               leaf ospf-lan-adjsid-mt-id {
                 type int32;
                 description "OSPF Extended Link LAN Adjacency SID MT_ID";
               }
               leaf ospf-lan-adjsid-weight {
                 type int32;
                 description "OSPF Extended Link LAN Adjacency SID Weight";
               }
               leaf ospf-lan-adjsid-nbrid {
                 type jt:ipaddr;
                 description "OSPF Extended Link LAN Adjacency SID Neighbor ID";
               }
               leaf ospf-lan-adjsid-label {
                 type int32;
                 description "OSPF Extended Link LAN Adjacency SID Label";
               }
             }
           }
           container asla-subtlv {
             leaf tlv-type-name {
               type string;
             }
             leaf tlv-type-value {
               type int32;
             }
             leaf tlv-length {
               type int32;
             }
             leaf bytes-left {
               type int32;
             }
             list ospf-asla-subtlv-data {
               description "SUBTLV data for ASLA Subtlv under Extended Link TLV";
               leaf ospf-asla-sabm-len {
                 type int32;
                 description "OSPF Extended Link ASLA SABM Len";
               }
               leaf ospf-asla-udabm-len {
                 type int32;
                 description "OSPF Extended Link ASLA UDABM Len";
               }
               leaf ospf-asla-sabm {
                 type int32;
                 description "OSPF Extended Link ASLA SABM value";
               }
               leaf ospf-asla-udabm {
                 type int32;
                 description "OSPF Extended Link ASLA UDABM value";
               }
             }
             list asla-subsubtlv {
               container te-metric-subtlv {
                 leaf tlv-type-name {
                   type string;
                 }
                 leaf tlv-type-value {
                   type int32;
                 }
                 leaf tlv-length {
                   type int32;
                 }
                 leaf te-metric-subtlv-data {
                   type int32;
                 }
               }
               container te-color-subtlv {
                 leaf tlv-type-name {
                   type string;
                 }
                 leaf tlv-type-value {
                   type int32;
                 }
                 leaf tlv-length {
                   type int32;
                 }
                 leaf te-color-subtlv-data {
                   type int32;
                 }
               }
               container te-uni-link-delay-subtlv {
                 leaf tlv-type-name {
                   type string;
                 }
                 leaf tlv-type-value {
                   type int32;
                 }
                 leaf tlv-length {
                   type int32;
                 }
                 leaf te-uni-link-delay-subtlv-data {
                   type int32;
                 }
               }
               container te-minmax-uni-link-delay-subtlv {
                 leaf tlv-type-name {
                   type string;
                 }
                 leaf tlv-type-value {
                   type int32;
                 }
                 leaf tlv-length {
                   type int32;
                 }
                 leaf te-minmax-uni-link-delay-subtlv-data {
                   type string;
                 }
               }
               container te-uni-link-delay-vari-subtlv {
                 leaf tlv-type-name {
                   type string;
                 }
                 leaf tlv-type-value {
                   type int32;
                 }
                 leaf tlv-length {
                   type int32;
                 }
                 leaf te-uni-link-delay-vari-subtlv-data {
                   type int32;
                 }
               }
             }
           }
         }
       }
       list ospf-opaque-as-lsa {
         container tlv-block {
           leaf tlv-type-name {
             type string;
           }
           leaf tlv-type-value {
             type int32;
           }
           leaf tlv-length {
             type int32;
           }
           leaf bytes-left {
             type int32;
           }
           leaf-list formatted-tlv-data {
             type string;
           }
         }
         container te-subtlv {
           leaf tlv-type-name {
             type string;
           }
           leaf tlv-type-value {
             type int32;
           }
           leaf tlv-length {
             type int32;
           }
           leaf bytes-left {
             type int32;
           }
           leaf-list formatted-tlv-data {
             type string;
           }
         }
       }
       list ospf-opaque-link-local-lsa {
         container ospf-link-local-grace-lsa {
           leaf tlv-grace-type-name {
             type string;
           }
           leaf tlv-grace-value {
             type string;
           }
         }
         container ospf-link-local-te-lsa {
           container ospf-link-local-te-tlv {
             leaf link-local-te-tlv-type-name {
               type string;
             }
             leaf tlv-type-value {
               type int32;
             }
             leaf tlv-length {
               type int32;
             }
             leaf bytes-left {
               type int32;
             }
             leaf-list formatted-tlv-data {
               type string;
             }
           }
           container ospf-link-local-te-subtlv {
             leaf link-local-te-tlv-type-name {
               type string;
             }
             leaf tlv-type-value {
               type int32;
             }
             leaf tlv-length {
               type int32;
             }
             leaf bytes-left {
               type int32;
             }
             leaf-list formatted-tlv-data {
               type string;
             }
           }
         }
       }
       container ospf-summary-lsa {
         leaf address-mask {
           type jt:ipaddr;
         }
         list ospf-summary-lsa-topology {
           description "OSPF topology specific information for a summary LSA";
           leaf ospf-topology-name {
             type string;
             description "OSPF topology name";
           }
           leaf ospf-topology-id {
             type int32;
             description "OSPF topology id";
           }
           leaf ospf-topology-metric {
             type int32;
             description "OSPF topology specific metric";
           }
         }
       }
       container ospf-external-lsa {
         leaf address-mask {
           type jt:ipaddr;
         }
         list ospf-external-lsa-topology {
           description "OSPF topology specific information for an external LSA";
           leaf ospf-topology-name {
             type string;
             description "OSPF topology name";
           }
           leaf ospf-topology-id {
             type int32;
             description "OSPF topology id";
           }
           leaf type-value {
             type int32;
           }
           leaf ospf-topology-metric {
             type int32;
             description "OSPF topology specific metric";
           }
           leaf forward-address {
             type jt:ipaddr;
           }
           leaf tag {
             type jt:ipaddr;
           }
         }
       }
       container ospf-database-extensive {
         leaf generation-timer {
           type string;
         }
         leaf aging-timer {
           type string;
         }
         leaf installation-time {
           type string;
         }
         leaf expiration-time {
           type string;
         }
         leaf send-time {
           type string;
         }
         leaf lsa-changed-time {
           type string;
           description "Time elapsed since the link-state advertisement changed";
         }
         leaf lsa-change-count {
           type int32;
           description "Number of times link-state advertisement changed";
         }
         leaf indication-lsa {
           type empty;
           description "Indication link-state advertisement";
         }
         leaf database-entry-state {
           type string;
         }
         leaf database-telink-id {
           type int32;
         }
         leaf standby-flood-status {
           type string;
           description "Flooding status to standby Routing Engine";
         }
       }
     }
     container ospf-database-summary {
       leaf ospf-area {
         type string;
         description "Area ID";
       }
       leaf ospf-intf {
         type string;
         description "Name of interface";
       }
       leaf ospf-database-summary.external-heading {
         type string;
       }
       leaf ospf-lsa-count {
         type int32;
       }
       leaf ospf-lsa-type {
         type string;
       }
     }
   }
   grouping ospf-backup-spf-information-block {
     list ospf-topology-backup-spf {
       description "OSPF topology specific backup SPF results";
       leaf ospf-topology-name {
         type string;
         description "OSPF topology name";
       }
       list ospf-topology-area-backup-spf {
         description "OSPF topology area specific backup SPF results";
         leaf ospf-area {
           type string;
           description "Area ID";
         }
         list ospf-backup-spf-node {
           description "OSPF node specific backup SPF information";
           leaf ospf-node-metric {
             type int32;
             description "Self to destination metric";
           }
           container ospf-node-id {
             description "OSPF node ID";
             leaf lsa-id {
               type string;
             }
           }
           list ospf-parent-node-id {
             description "OSPF parent node ID";
             leaf ospf-parent-lsa-id {
               type string;
               description "LSA ID for the parent node";
             }
           }
           list ospf-next-hop {
             container next-hop-name {
               leaf interface-name {
                 type string;
                 description "Name of interface";
               }
             }
             container next-hop-address {
               leaf-list interface-address {
                 type jt:ipaddr;
               }
             }
           }
           container ospf-backup-next-hop {
             leaf ospf-backup-next-hop-interface {
               type string;
             }
             leaf ospf-backup-next-hop-address {
               type string;
             }
             leaf ospf-backup-next-hop-lsp {
               type string;
             }
             leaf ospf-backup-next-hop-lsp-out-if {
               type string;
             }
           }
           list ospf-backup-spf-result {
             description "OSPF backup SPF result";
             leaf ospf-backup-neighbor {
               type jt:ipaddr;
               description "Backup neighbor router-id";
             }
             leaf ospf-backup-neighbor-via {
               type string;
               description "Backup neighbor via direct/RSVP/LDP";
             }
             leaf ospf-backup-neighbor-is-lsp-endpoint {
               type empty;
               description "Backup neighbor is an LSP endpoint";
             }
             leaf ospf-backup-metric {
               type int32;
               description "Backup neighbor to destination metric";
             }
             leaf ospf-backup-neighbor-from-metric {
               type int32;
               description "Backup neighbor to self metric";
             }
             leaf ospf-backup-neighbor-to-metric {
               type int32;
               description "Self to backup neighbor metric";
             }
             leaf ospf-backup-preference {
               type int32;
               description "Backup neighbor preference";
             }
             leaf-list ospf-track-item {
               type string;
               description "Backup SPF result track item";
             }
             leaf-list ospf-rev-track-item {
               type string;
               description "Backup RSPF result track item";
             }
             leaf ospf-backup-result-status {
               type string;
               description "Backup SPF result status";
             }
             leaf ospf-backup-result-no-coverage-reason {
               type string;
               description "Backup SPF result no coverage reason";
             }
             leaf ospf-backup-spf-result-path {
               type empty;
               description "Path to the neighbour from backup root";
             }
             leaf ospf-backup-result-path-nodes {
               type string;
               description "Backup node in the path";
             }
             leaf ospf-backup-neighbors-protected {
               type int32;
               description "Number of neighbors protected by this PQ-node";
             }
             leaf ospf-backup-neighbor-is-selected {
               type empty;
               description "PQ node is selected";
             }
           }
         }
       }
     }
   }
   grouping ospf-backup-coverage-information-block {
     container ospf-topology-backup-coverage {
       leaf ospf-topology-name {
         type string;
         description "OSPF topology name";
       }
       container ospf-backup-node-coverage {
         leaf ospf-area {
           type string;
           description "Area ID";
         }
         leaf ospf-covered-nodes {
           type int32;
           description "Number of nodes covered by backup nexthops";
         }
         leaf ospf-total-nodes {
           type int32;
           description "Total number of nodes in the area";
         }
         leaf ospf-node-coverage {
           type string;
           description "Percent of nodes covered by backup nexthops";
         }
       }
       container ospf-backup-route-coverage {
         leaf ospf-path-type {
           type string;
           description "Route path type";
         }
         leaf ospf-covered-routes {
           type int32;
           description "Number of routes covered by backup nexthops";
         }
         leaf ospf-total-routes {
           type int32;
           description "Total number of routes in the area";
         }
         leaf ospf-route-coverage {
           type string;
           description "Percent of routes covered by backup nexthops";
         }
       }
     }
   }
   grouping ospf-backup-neighbor-information-block {
     list ospf-topology-backup-neighbor {
       description "OSPF topology specific backup neighbors";
       leaf ospf-topology-name {
         type string;
         description "OSPF topology name";
       }
       list ospf-topology-area-backup-neighbor {
         description "OSPF topology area specific backup neighbors";
         leaf ospf-area {
           type string;
           description "Area ID";
         }
         list ospf-backup-neighbor-node {
           description "OSPF backup neighbor node";
           leaf ospf-backup-neighbor {
             type jt:ipaddr;
             description "Backup neighbor router-id";
           }
           leaf ospf-backup-neighbor-via {
             type string;
             description "Backup neighbor via direct/RSVP/LDP";
           }
           leaf ospf-backup-neighbor-is-lsp-endpoint {
             type empty;
             description "Backup neighbor is an LSP endpoint";
           }
           leaf ospf-backup-neighbor-from-metric {
             type int32;
             description "Backup neighbor to self metric";
           }
           leaf ospf-backup-neighbor-to-metric {
             type int32;
             description "Self to backup neighbor metric";
           }
           leaf ospf-backup-neighbors-protected {
             type int32;
             description "Number of neighbors protected by this PQ-node";
           }
           leaf ospf-backup-neighbor-is-selected {
             type empty;
             description "PQ node is selected";
           }
           container ospf-backup-next-hop {
             leaf ospf-backup-next-hop-interface {
               type string;
             }
             leaf ospf-backup-next-hop-address {
               type string;
             }
             leaf ospf-backup-next-hop-lsp {
               type string;
             }
             leaf ospf-backup-next-hop-lsp-out-if {
               type string;
             }
           }
         }
       }
     }
   }
   grouping ospf-backup-mplsp-information-block {
     list ospf-backup-mplsp {
       leaf lsp-name {
         type string;
         description "Tunneled into an RSVP LSP";
       }
       leaf lsp-addr {
         type jt:ipaddr;
         description "LSP destination address";
       }
       leaf lsp-status {
         type string;
         description "LSP status";
       }
       leaf lsp-last-change {
         type string;
         description "Time of last LSP change";
       }
       leaf te-metric {
         type int32;
         description "LSP TE metric";
       }
       leaf metric {
         type int32;
       }
     }
   }
   grouping ospf-interface-information-block {
     list ospf-interface {
       leaf interface-name {
         type string;
         description "Name of interface";
       }
       leaf ospf-interface-state {
         type string;
       }
       leaf ospf-area {
         type string;
         description "Area ID";
       }
       leaf dr-id {
         type jt:ipaddr;
       }
       leaf bdr-id {
         type jt:ipaddr;
       }
       leaf neighbor-count {
         type int32;
         description "Number of neighbors on PIM interface";
       }
       leaf interface-type {
         type string;
       }
       leaf-list interface-address {
         type jt:ipaddr;
       }
       leaf address-mask {
         type jt:ipaddr;
       }
       leaf mtu {
         type int32;
         description "MTU along an interface";
       }
       leaf interface-cost {
         type int32;
         description "Cost associated with this interface";
       }
       leaf sham-link-local {
         type jt:ipaddr;
         description "Sham link local end point";
       }
       leaf sham-link-remote {
         type jt:ipaddr;
         description "Sham link remote end point";
       }
       leaf virtual-link-transit-area {
         type jt:ipaddr;
         description "Virtual link transit area";
       }
       leaf virtual-link-destination {
         type string;
         description "Virtual link destination address";
       }
       leaf dr-address {
         type jt:ipaddr;
         description "IP address of DR";
       }
       leaf bdr-address {
         type jt:ipaddr;
         description "IP address of BDR";
       }
       leaf router-priority {
         type int32;
         description "Router priority used in DR election on broadcast or NBMA interface";
       }
       leaf adj-count {
         type int32;
         description "Count of fully adjacent neighbors";
       }
       leaf interface-secondary {
         type empty;
         description "OSPF interface is secondary";
       }
       leaf interface-flood-reduction {
         type empty;
         description "Flood reduction is enabled";
       }
       leaf passive {
         type string;
       }
       leaf hello-interval {
         type int32;
         description "Interval between two successive hellos";
       }
       leaf poll-interval {
         type int32;
       }
       leaf dead-interval {
         type int32;
       }
       leaf retransmit-interval {
         type int32;
       }
       leaf ospf-stub-type {
         type string;
         description "Stub type of area";
       }
       leaf ipsec-sa {
         type string;
       }
       leaf authentication-key-chain {
         type string;
         description "Name of authentication key chain";
       }
       leaf authentication-type {
         type string;
         description "Type of authentication";
       }
       leaf-list active-key-id {
         type int32;
       }
       leaf active-key-start-time {
         type string;
       }
       leaf authentication-delete-key-if-unused {
         type string;
       }
       leaf authentication-key-algorithm {
         type string;
       }
       leaf ospf-interface-protection-type {
         type string;
       }
       leaf ospf-interface-no-eligible-backup {
         type empty;
       }
       leaf ospf-interface-no-eligible-remote-backup {
         type empty;
       }
       leaf ospf-interface-tilfa-prot-link {
         type string;
       }
       leaf ospf-interface-tilfa-prot-fate {
         type string;
       }
       leaf ospf-interface-tilfa-prot-srlg {
         type string;
       }
       leaf ospf-interface-tilfa-prot-node {
         type int32;
       }
       leaf igp-ldp-sync-state {
         type string;
         description "State of synchronization between Label Distribution Protocol (LDP) and the interior gateway protocol (IGP)";
       }
       leaf igp-ldp-sync-last-change {
         type string;
         description "Time since the state of synchronization between Label Distribution Protocol (LDP) and the interior gateway protocol (IGP) last changed";
       }
       leaf igp-ldp-sync-reason {
         type string;
         description "Reason for the change in the state of synchronization between Label Distribution Protocol (LDP) and the interior gateway protocol (IGP)";
       }
       leaf igp-ldp-sync-holdtime {
         type string;
         description "Length of time during which the maximum metric is advertised for an interface that is in the hold-down state because synchronization was lost between Label Distribution Protocol (LDP) and the interior gateway protocol (IGP)";
       }
       leaf igp-ldp-sync-timeleft {
         type int32;
         description "Remaining amount of time the interface will remain in the hold-down state because synchronization was lost between Label Distribution Protocol (LDP) and the interior gateway protocol (IGP)";
       }
       leaf lsa-list {
         type string;
       }
       leaf interface-flood-list-count {
         type int32;
       }
       leaf flood-list-count {
         type int32;
       }
       leaf interface-description-list {
         type string;
       }
       leaf unidirectional-link-delay {
         type uint32;
       }
       leaf min-unidirectional-link-delay {
         type uint32;
       }
       leaf max-unidirectional-link-delay {
         type uint32;
       }
       leaf unidirectional-delay-variation {
         type uint32;
       }
       leaf link-delay-normalization-interval {
         type uint32;
       }
       leaf link-delay-normalization-offset {
         type uint32;
       }
       leaf link-normalized-delay {
         type uint32;
       }
       leaf link-normalized-delay-time {
         type string;
       }
       list ospf-interface-topology {
         description "OSPF topology specific information for an interface";
         leaf ospf-topology-name {
           type string;
           description "OSPF topology name";
         }
         leaf ospf-topology-id {
           type int32;
           description "OSPF topology id";
         }
         leaf ospf-topology-passive {
           type empty;
           description "OSPF topology is passive";
         }
         leaf ospf-topology-disabled {
           type empty;
           description "OSPF topology is disabled";
         }
         leaf ospf-topology-down {
           type empty;
           description "OSPF topology is down";
         }
         leaf ospf-topology-metric {
           type int32;
           description "OSPF topology specific metric";
         }
       }
     }
   }
   grouping ospf-context-id-information-block {
     list ospf-context-id {
       leaf ospf-ctx-id {
         type jt:ipaddr;
         description "Context identifer advertised by this router";
       }
       leaf ospf-context-id-status {
         type string;
       }
       leaf ospf-context-id-metric {
         type int32;
         description "Cost to reach the context identifier";
       }
       leaf ospf-context-id-pe-role {
         type string;
       }
       leaf ospf-context-id-area {
         type string;
         description "Area ID";
       }
       leaf ospf-context-id-advertising-router {
         type jt:ipaddr;
         description "Advertising router id";
       }
       leaf ospf-context-id-type {
         type string;
         description "Stub link or inter area summary";
       }
       leaf ospf-context-id-adv-metric {
         type int32;
         description "Cost to reach the context indentifier via an advertising router";
       }
     }
   }
   grouping ospf-neighbor-information-logical-system-all-block {
     list logical-system {
       leaf name {
         type string;
       }
       container ospf-neighbor-information {
         description "Information about OSPF neighbors in a routing instance";
         list ospf-neighbor {
           leaf neighbor-address {
             type jt:ipaddr;
             description "IP address of this neighbor";
           }
           leaf interface-name {
             type string;
             description "Name of interface";
           }
           leaf ospf-neighbor-state {
             type string;
           }
           leaf neighbor-id {
             type jt:ipaddr;
           }
           leaf neighbor-priority {
             type int32;
           }
           leaf activity-timer {
             type int32;
           }
           leaf ospf-area {
             type string;
             description "Area ID";
           }
           leaf options {
             type int32;
           }
           leaf dr-address {
             type jt:ipaddr;
             description "IP address of DR";
           }
           leaf bdr-address {
             type jt:ipaddr;
             description "IP address of BDR";
           }
           leaf neighbor-secondary {
             type empty;
             description "OSPF neighbor is on secondary interface";
           }
           leaf neighbor-up-time {
             type string;
             description "Time when neighbor came up";
           }
           leaf neighbor-adjacency-time {
             type string;
             description "Time when neighbor became adjacent";
           }
           leaf neighbor-last-out-of-band-resync-time {
             type string;
             description "Time since last successful oob-resync";
           }
           leaf neighbor-suppress-hello {
             type int32;
             description "Time when neighbor suppressed hellos";
           }
           leaf adj-sid-list {
             type string;
           }
           leaf master-slave {
             type string;
           }
           leaf sequence-number {
             type int64;
             description "History event number";
           }
           leaf dbd-retransmit-time {
             type int32;
             description "Seconds until DBD is retransmitted";
           }
           leaf lsreq-retransmit-time {
             type int32;
             description "Seconds until LSREQ is retransmitted";
           }
           leaf lsreq-enqueued {
             type empty;
           }
           leaf lsreq-active {
             type empty;
           }
           leaf lsa-list {
             type string;
           }
           leaf neighbor-cost {
             type int32;
             description "Cost associated with this neighbor";
           }
           list ospf-neighbor-topology {
             description "OSPF topology specific neighbor information";
             leaf ospf-topology-name {
               type string;
               description "OSPF topology name";
             }
             leaf ospf-topology-id {
               type int32;
               description "OSPF topology id";
             }
             leaf ospf-neighbor-topology-state {
               type string;
               description "State of the neighbor in a topology";
             }
           }
         }
       }
       list ospf3-neighbor-information {
         list ospf3-neighbor {
           leaf neighbor-id {
             type jt:ipaddr;
           }
           leaf interface-name {
             type string;
             description "Name of interface";
           }
           leaf ospf-neighbor-state {
             type string;
           }
           leaf neighbor-priority {
             type int32;
           }
           leaf activity-timer {
             type int32;
           }
           leaf neighbor-address {
             type jt:ipaddr;
             description "IP address of this neighbor";
           }
           leaf ospf-area {
             type string;
             description "Area ID";
           }
           leaf options {
             type int32;
           }
           leaf neighbor-secondary {
             type empty;
             description "OSPF neighbor is on secondary interface";
           }
           leaf ospf3-interface-index {
             type int32;
           }
           leaf neighbor-cost {
             type int32;
             description "Cost associated with this neighbor";
           }
           leaf dr-id {
             type jt:ipaddr;
           }
           leaf bdr-id {
             type jt:ipaddr;
           }
           leaf neighbor-up-time {
             type string;
             description "Time when neighbor came up";
           }
           leaf neighbor-adjacency-time {
             type string;
             description "Time when neighbor became adjacent";
           }
           leaf neighbor-suppress-hello {
             type int32;
             description "Time when neighbor suppressed hellos";
           }
           leaf master-slave {
             type string;
           }
           leaf sequence-number {
             type int64;
             description "History event number";
           }
           leaf dbd-retransmit-time {
             type int32;
             description "Seconds until DBD is retransmitted";
           }
           leaf lsreq-retransmit-time {
             type int32;
             description "Seconds until LSREQ is retransmitted";
           }
           leaf lsreq-enqueued {
             type empty;
           }
           leaf lsreq-active {
             type empty;
           }
           leaf lsa-list {
             type string;
           }
         }
       }
       container isis-overview-information {
         description "ISIS overview information";
         container isis-overview {
           description "Overview information for an IS-IS instance";
           leaf-list instance-name {
             type string;
           }
           leaf isis-router-id {
             type jt:ipaddr;
             description "IS-IS router ID";
           }
           leaf isis-v6-router-id {
             type jt:ipv6addr;
             description "IS-IS IPv6 Router ID";
           }
           leaf isis-router-hostname {
             type string;
             description "IS-IS router hostname";
           }
           leaf isis-router-sysid {
             type string;
             description "IS-IS router sysid";
           }
           leaf isis-router-areaid {
             type string;
             description "IS-IS router areaid";
           }
           leaf isis-max-areas {
             type uint32;
             description "Maximum Number of Areas";
           }
           leaf isis-lsp-lifetime {
             type uint32;
             description "Maximum LSP lifetime";
           }
           leaf isis-lsp-lifetime-filter {
             type uint32;
             description "Low LSP life time filter";
           }
           leaf isis-reference-bandwidth {
             type uint64;
             description "Bandwidth for calculating metric defaults";
           }
           leaf isis-adjacency-holddown {
             type string;
             description "IS-IS Adjacency holddown status";
           }
           leaf isis-attached-bit-evaluation {
             type string;
             description "The IS-IS L1 attached bit evaluation";
           }
           leaf isis-layer2-map-enabled {
             type string;
             description "IS-IS controls kernel ARP/ND entries for its nexthops";
           }
           container isis-spf-information {
             description "SPF options";
             leaf isis-spf-delay {
               type string;
               description "Delay before performing SPF calculations";
             }
             leaf isis-spf-holddown {
               type string;
               description "Throttling delay between consecutive SPF calculations";
             }
             leaf isis-spf-rapid-runs {
               type uint32;
               description "Number of rapid SPF calculations before SPF holddown.";
             }
             leaf isis-uloop-avoidance {
               type string;
               description "Micro-loop avoidance status";
             }
             leaf isis-uloop-avoidance-method {
               type string;
               description "Micro-loop avoidance mechanism employed";
             }
             leaf isis-route-convergence-delay {
               type string;
               description "Delay before downloading routes to forwarding plane";
             }
             leaf isis-topo-sessid-count {
               type uint32;
               description "Number of Session IDs associated with routes in this topology";
             }
             container isis-spf {
               leaf node-count {
                 type int32;
               }
               container isis-spf-results-header {
                 leaf isis-topology-id {
                   type string;
                 }
                 leaf level {
                   type int32;
                   description "IS-IS Level";
                 }
               }
               list isis-spf-result {
                 leaf node-id {
                   type string;
                 }
                 leaf metric {
                   type int32;
                 }
                 leaf disconnected {
                   type empty;
                 }
                 leaf no-first-fragment {
                   type empty;
                 }
                 leaf-list node-address {
                   type string;
                 }
                 list next-hop-element {
                   leaf interface-name {
                     type string;
                     description "Name of interface";
                   }
                   leaf isis-next-hop-type {
                     type string;
                   }
                   leaf isis-next-hop {
                     type string;
                   }
                   leaf-list snpa {
                     type string;
                   }
                 }
                 list prefix-element {
                   leaf prefix-metric {
                     type int32;
                   }
                   leaf external-prefix-metric {
                     type int32;
                   }
                   leaf-list address-prefix {
                     type jt:ipaddr;
                   }
                 }
                 list end-system-element {
                   leaf end-system-metric {
                     type int32;
                   }
                   leaf end-system-id {
                     type string;
                     description "Six-octet ISO system ID for a end-system";
                   }
                 }
               }
               container isis-spf-log-header {
                 leaf isis-topology-id {
                   type string;
                 }
                 leaf level {
                   type int32;
                   description "IS-IS Level";
                 }
               }
               container isis-spf-log {
                 leaf start-time {
                   type string;
                 }
                 leaf elapsed-time {
                   type string;
                   description "Time this adjacency or session has been up or down";
                 }
                 leaf spf-trigger-count {
                   type int32;
                 }
                 leaf logging-reason {
                   type string;
                 }
                 leaf lsp-name {
                   type string;
                   description "Tunneled into an RSVP LSP";
                 }
                 leaf system-name {
                   type string;
                   description "Hostname for a system";
                 }
                 leaf interface-name {
                   type string;
                   description "Name of interface";
                 }
               }
               container isis-backup-spf-result {
                 leaf node-id {
                   type string;
                 }
                 leaf no-first-fragment {
                   type empty;
                 }
                 leaf backup-root {
                   type string;
                 }
                 leaf backup-root-metric {
                   type int32;
                 }
                 leaf metric {
                   type int32;
                 }
                 leaf backup-root-preference {
                   type int32;
                 }
                 leaf track-item {
                   type string;
                 }
                 leaf track-item-isnbr {
                   type string;
                 }
                 leaf rev-track-item {
                   type string;
                 }
                 leaf rev-track-item-isnbr {
                   type string;
                 }
                 leaf-list node-address {
                   type string;
                 }
                 list next-hop-element {
                   leaf interface-name {
                     type string;
                     description "Name of interface";
                   }
                   leaf isis-next-hop-type {
                     type string;
                   }
                   leaf isis-next-hop {
                     type string;
                   }
                   leaf-list snpa {
                     type string;
                   }
                 }
                 list backup-next-hop-element {
                   leaf interface-name {
                     type string;
                     description "Name of interface";
                   }
                   leaf isis-next-hop-type {
                     type string;
                   }
                   leaf isis-next-hop {
                     type string;
                   }
                   leaf-list snpa {
                     type string;
                   }
                   leaf isis-backup-prefix-refcount {
                     type uint32;
                     description "Number of prefixes that uses this nexthop as backup";
                   }
                   leaf isis-backup-score {
                     type string;
                   }
                 }
                 list no-coverage-reason-element {
                   leaf isis-next-hop-type {
                     type string;
                   }
                   leaf no-coverage-reason {
                     type string;
                   }
                 }
               }
             }
           }
           container isis-overload-information {
             description "Overload bit behaviour at startup";
             leaf isis-overload-enabled {
               type empty;
               description "Overload bit upon startup is set";
             }
             leaf isis-overload-high-metrics {
               type string;
               description "High metrics are used for Overload signaling";
             }
             leaf isis-overload-allow-route-leaking {
               type string;
               description "Allow route leaking when configured to be in overload";
             }
             leaf isis-overload-internal-prefixes {
               type string;
               description "Allow internal prefixes to be advertised with high metric";
             }
             leaf isis-overload-external-prefixes {
               type string;
               description "Allow external prefixes to be advertised with high metric";
             }
             leaf isis-overload-timeout {
               type int32;
               description "Clearance of the Overload bit after startup";
             }
             leaf isis-overload-remaining-time {
               type string;
               description "Time remaining on configured overload timeout";
             }
           }
           container isis-routing {
             description "List of routed IS-IS address families";
             leaf isis-routing-ipv4 {
               type empty;
               description "Routing IPv4 prefixes is enabled";
             }
             leaf isis-routing-ipv6 {
               type empty;
               description "Routing IPv6 prefixes is enabled";
             }
             leaf isis-routing-clns {
               type empty;
               description "Routing CLNS prefixes is enabled";
             }
             leaf isis-routing-spring-mpls {
               type empty;
               description "Routing CLNS prefixes is enabled";
             }
           }
           container isis-traffic-engineering {
             description "Traffic engineering";
             leaf isis-te-status {
               type string;
               description "Traffic engineering status";
             }
             leaf isis-ted-ipv6 {
               type string;
               description "Traffic Engineering v6 status";
             }
             leaf isis-te-shortcuts-ipv4 {
               type empty;
               description "IPv4 Traffic engineering shortcuts are enabled";
             }
             leaf isis-te-shortcuts-ipv6 {
               type empty;
               description "IPv6 Traffic engineering shortcuts are enabled";
             }
             leaf isis-te-shortcuts-ipv4-mpls {
               type empty;
               description "IPv4-MPLS Traffic engineering shortcuts are enabled";
             }
             leaf isis-te-shortcuts-ipv6-mpls {
               type empty;
               description "IPv6-MPLS Traffic engineering shortcuts are enabled";
             }
             leaf isis-te-shortcuts-clns {
               type empty;
               description "CLNS Traffic engineering shortcuts are enabled";
             }
             leaf isis-ipv4-multicast-rpf-routes {
               type empty;
               description "IPv4 routes for multicast RPF checks are installed into inet.2";
             }
             leaf isis-ignore-lsp-metrics {
               type empty;
               description "Label-switched path metrics when doing shortcuts are ignored";
             }
             leaf isis-ted-credibility-preference {
               type empty;
               description "Credibility follows protocol preference";
             }
           }
           container isis-restart {
             description "IS-IS restart parameters";
             leaf isis-restart-enabled {
               type string;
               description "IS-IS restart mode";
             }
             leaf isis-restart-duration {
               type uint32;
               description "Duration of IS-IS restart";
             }
             leaf isis-restart-helper-mode-enabled {
               type string;
               description "IS-IS helper mode";
             }
           }
           container isis-tilfa {
             description "IS-IS Post Convergence Backup parameters";
             leaf isis-tilfa-enabled {
               type string;
               description "Post Convergence Backup";
             }
             leaf isis-tilfa-max-labels {
               type int32;
               description "Max labels";
             }
             leaf isis-tilfa-max-srv6-sids {
               type int32;
               description "Max SRV6 SIDs";
             }
             leaf isis-tilfa-max-spf {
               type int32;
               description "Max spf";
             }
             leaf isis-tilfa-ecmp-backup {
               type int32;
               description "Post Convergence Max Ecmp Backup";
             }
           }
           container isis-spring {
             description "IS-IS SPRING parameters";
             leaf isis-spring-enabled {
               type string;
               description "Source Packet Routing";
             }
             leaf isis-srgb-allocation {
               type string;
               description "SRGB Block Allocation";
             }
             leaf isis-node-segment-enabled {
               type string;
               description "Node Segments Enabled";
             }
             leaf isis-srv6-enabled {
               type string;
               description "SRv6 Enabled";
             }
             container isis-srgb-config {
               description "SRGB block configuration related information";
               leaf isis-srgb-config-block-header {
                 type string;
                 description "SRGB Config Block";
               }
               leaf isis-srgb-start-label {
                 type int32;
                 description "Configuration of SRGB start label";
               }
               leaf isis-srgb-index-range {
                 type int32;
                 description "Configuration of SRGB index range";
               }
             }
             container isis-srgb-block {
               description "SRGB block related information";
               leaf isis-srgb-start-index {
                 type int32;
                 description "Starting Index for SRGB Block";
               }
               leaf isis-srgb-size {
                 type int32;
                 description "Size of the specific SRGB Block";
               }
               leaf isis-srgb-first-label {
                 type int32;
                 description "First label allocated for SRGB Block";
               }
               leaf isis-srgb-last-label {
                 type int32;
                 description "Last label allocated for SRGB Block";
               }
             }
             container isis-node-segment {
               description "Node Segments related information";
               leaf isis-node-segment-ipv4-index {
                 type int32;
                 description "IPv4 Node Segment index for this device";
               }
               leaf isis-node-segment-ipv6-index {
                 type int32;
                 description "IPv6 Node Segment index for this device";
               }
               leaf isis-node-segment-index-range {
                 type int32;
                 description "Range of Node Segment indices configured";
               }
               leaf isis-node-segment-block-header {
                 type empty;
                 description "Node Segment Blocks";
               }
               container isis-node-segment-block {
                 description "Node Segment Blocks related information";
                 leaf isis-node-segment-block-start-index {
                   type int32;
                   description "Starting Index for the specific Node Segment Block";
                 }
                 leaf isis-node-segment-block-size {
                   type int32;
                   description "Size of the specific Node Segment Block";
                 }
                 leaf isis-node-segment-block-first-label {
                   type int32;
                   description "First label allocated for the specific Node Segment Block";
                 }
                 leaf isis-node-segment-block-last-label {
                   type int32;
                   description "Last label allocated for the specific Node Segment Block";
                 }
               }
             }
             list isis-srv6-locator {
               description "SRv6 Locator information";
               leaf isis-srv6-locator-name {
                 type string;
                 description "Locator name";
               }
               leaf isis-srv6-locator-address {
                 type string;
                 description "Locator prefix";
               }
               leaf isis-srv6-locator-algorithm {
                 type uint32;
                 description "Locator algorithm";
               }
               leaf isis-prefix-attribute-flags {
                 type string;
               }
               container isis-srv6-end-sid {
                 description "SRv6 end sid entry";
                 leaf isis-srv6-end-sid-addr {
                   type jt:ipv6addr;
                   description "SRv6 End-SID prefix";
                 }
                 leaf-list isis-srv6-sid-flavor {
                   type string;
                 }
               }
               container isis-srv6-micro-node-sid {
                 description "SRv6 end sid entry";
                 leaf isis-srv6-micro-node-sid-addr {
                   type jt:ipv6addr;
                   description "SRv6 micro-node-SID address";
                 }
                 leaf-list isis-srv6-micro-sid-flavor {
                   type string;
                 }
               }
             }
           }
           list isis-level-information {
             description "IS-IS Level Information";
             leaf isis-level {
               type int32;
               description "IS-IS Level";
             }
             leaf isis-preference {
               type uint32;
               description "IS-IS internal route preference";
             }
             leaf isis-external-preference {
               type uint32;
               description "IS-IS external route preference";
             }
             leaf isis-prefix-export-limit {
               type uint32;
               description "IS-IS limit for external route export";
             }
             leaf isis-prefix-export-count {
               type uint32;
               description "Actual number of exported prefixes";
             }
             leaf isis-wide-metrics {
               type empty;
               description "Generation of wide metric TLVs is enabled";
             }
             leaf isis-narrow-metrics {
               type empty;
               description "Generation of narrow metric TLVs is enabled";
             }
             leaf isis-level-spring-enabled {
               type empty;
               description "Source Packet Routing is enabled";
             }
             leaf isis-adjacency-holddown-state {
               type string;
             }
             leaf isis-flood-reduction-enabled {
               type string;
               description "Distributed Optimized flood reduction";
             }
             leaf isis-flood-reduction-hash-reflooder-enabled {
               type string;
               description "Distributed Optimized flood reduction hash reflooder";
             }
             leaf isis-clos-miswiring-warning {
               type string;
             }
             leaf isis-purge-originator-info {
               type string;
               description "Type of POI that gets added to purged LSPs";
             }
           }
         }
       }
       container task-replication-state {
         description "Current state of task replication";
         leaf task-gres-state {
           type string;
           description "Current state of graceful Routing Engine Switchover";
         }
         leaf task-re-mode {
           type string;
           description "Current mastership state of Routing Engine";
         }
         list task-protocol-replication {
           description "Current state of task protocol replication";
           leaf task-protocol-replication-name {
             type string;
           }
           leaf task-protocol-replication-state {
             type string;
           }
         }
       }
     }
   }
   grouping ospf-neighbor-information-all-block {
     list ospf-instance-neighbor {
       description "Information about OSPF neighbors within this routing instance";
       leaf ospf-instance-name {
         type string;
         description "Name of OSPF instance";
       }
       list ospf-neighbor {
         leaf neighbor-address {
           type jt:ipaddr;
           description "IP address of this neighbor";
         }
         leaf interface-name {
           type string;
           description "Name of interface";
         }
         leaf ospf-neighbor-state {
           type string;
         }
         leaf neighbor-id {
           type jt:ipaddr;
         }
         leaf neighbor-priority {
           type int32;
         }
         leaf activity-timer {
           type int32;
         }
         leaf ospf-area {
           type string;
           description "Area ID";
         }
         leaf options {
           type int32;
         }
         leaf dr-address {
           type jt:ipaddr;
           description "IP address of DR";
         }
         leaf bdr-address {
           type jt:ipaddr;
           description "IP address of BDR";
         }
         leaf neighbor-secondary {
           type empty;
           description "OSPF neighbor is on secondary interface";
         }
         leaf neighbor-up-time {
           type string;
           description "Time when neighbor came up";
         }
         leaf neighbor-adjacency-time {
           type string;
           description "Time when neighbor became adjacent";
         }
         leaf neighbor-last-out-of-band-resync-time {
           type string;
           description "Time since last successful oob-resync";
         }
         leaf neighbor-suppress-hello {
           type int32;
           description "Time when neighbor suppressed hellos";
         }
         leaf adj-sid-list {
           type string;
         }
         leaf master-slave {
           type string;
         }
         leaf sequence-number {
           type int64;
           description "History event number";
         }
         leaf dbd-retransmit-time {
           type int32;
           description "Seconds until DBD is retransmitted";
         }
         leaf lsreq-retransmit-time {
           type int32;
           description "Seconds until LSREQ is retransmitted";
         }
         leaf lsreq-enqueued {
           type empty;
         }
         leaf lsreq-active {
           type empty;
         }
         leaf lsa-list {
           type string;
         }
         leaf neighbor-cost {
           type int32;
           description "Cost associated with this neighbor";
         }
         list ospf-neighbor-topology {
           description "OSPF topology specific neighbor information";
           leaf ospf-topology-name {
             type string;
             description "OSPF topology name";
           }
           leaf ospf-topology-id {
             type int32;
             description "OSPF topology id";
           }
           leaf ospf-neighbor-topology-state {
             type string;
             description "State of the neighbor in a topology";
           }
         }
       }
     }
   }
   grouping ospf-neighbor-information-block {
     list ospf-neighbor {
       leaf neighbor-address {
         type jt:ipaddr;
         description "IP address of this neighbor";
       }
       leaf interface-name {
         type string;
         description "Name of interface";
       }
       leaf ospf-neighbor-state {
         type string;
       }
       leaf neighbor-id {
         type jt:ipaddr;
       }
       leaf neighbor-priority {
         type int32;
       }
       leaf activity-timer {
         type int32;
       }
       leaf ospf-area {
         type string;
         description "Area ID";
       }
       leaf options {
         type int32;
       }
       leaf dr-address {
         type jt:ipaddr;
         description "IP address of DR";
       }
       leaf bdr-address {
         type jt:ipaddr;
         description "IP address of BDR";
       }
       leaf neighbor-secondary {
         type empty;
         description "OSPF neighbor is on secondary interface";
       }
       leaf neighbor-up-time {
         type string;
         description "Time when neighbor came up";
       }
       leaf neighbor-adjacency-time {
         type string;
         description "Time when neighbor became adjacent";
       }
       leaf neighbor-last-out-of-band-resync-time {
         type string;
         description "Time since last successful oob-resync";
       }
       leaf neighbor-suppress-hello {
         type int32;
         description "Time when neighbor suppressed hellos";
       }
       leaf adj-sid-list {
         type string;
       }
       leaf master-slave {
         type string;
       }
       leaf sequence-number {
         type int64;
         description "History event number";
       }
       leaf dbd-retransmit-time {
         type int32;
         description "Seconds until DBD is retransmitted";
       }
       leaf lsreq-retransmit-time {
         type int32;
         description "Seconds until LSREQ is retransmitted";
       }
       leaf lsreq-enqueued {
         type empty;
       }
       leaf lsreq-active {
         type empty;
       }
       leaf lsa-list {
         type string;
       }
       leaf neighbor-cost {
         type int32;
         description "Cost associated with this neighbor";
       }
       list ospf-neighbor-topology {
         description "OSPF topology specific neighbor information";
         leaf ospf-topology-name {
           type string;
           description "OSPF topology name";
         }
         leaf ospf-topology-id {
           type int32;
           description "OSPF topology id";
         }
         leaf ospf-neighbor-topology-state {
           type string;
           description "State of the neighbor in a topology";
         }
       }
     }
   }
   grouping ospf-route-information-block {
     list ospf-topology-route-table {
       description "OSPF topology specific routing table";
       leaf ospf-topology-name {
         type string;
         description "OSPF topology name";
       }
       list ospf-route {
         list ospf-route-entry {
           leaf-list address-prefix {
             type jt:ipaddr;
           }
           leaf route-path-type {
             type string;
           }
           leaf route-type {
             type string;
             description "Route type";
           }
           leaf next-hop-type {
             type string;
             description "Next-hop type";
           }
           leaf interface-cost {
             type int32;
             description "Cost associated with this interface";
           }
           leaf ospf-area {
             type string;
             description "Area ID";
           }
           leaf route-origin {
             type jt:ipaddr;
           }
           leaf type7 {
             type empty;
           }
           leaf pbit {
             type empty;
           }
           leaf forward-nz {
             type empty;
           }
           leaf optional-capability {
             type int32;
             description "VEB bits received in the router LSA";
           }
           leaf route-priority {
             type string;
           }
           leaf ospf-valid-backups {
             type empty;
           }
           leaf ospf-bgp-orr-gen-id {
             type uint32;
           }
           list ospf-next-hop {
             container next-hop-name {
               leaf interface-name {
                 type string;
                 description "Name of interface";
               }
               leaf interface-link-name {
                 type string;
               }
             }
             container next-hop-address {
               leaf-list interface-address {
                 type jt:ipaddr;
               }
               leaf lsp-name {
                 type string;
                 description "Tunneled into an RSVP LSP";
               }
             }
           }
           container ospf-backup-next-hop {
             leaf ospf-backup-next-hop-type {
               type string;
             }
             leaf ospf-backup-next-hop-interface {
               type string;
             }
             leaf ospf-backup-next-hop-address {
               type string;
             }
             leaf ospf-backup-next-hop-lsp {
               type string;
             }
             list ospf-backup-next-hop-sid-info {
               leaf ospf-backup-next-hop-label {
                 type uint32;
               }
               leaf ospf-backup-next-hop-label-type {
                 type string;
               }
               leaf ospf-backup-next-hop-sid-info-node-id {
                 type string;
               }
               leaf ospf-backup-next-hop-sid-info-adj-local-node-id {
                 type string;
               }
               leaf ospf-backup-next-hop-sid-info-adj-remote-node-id {
                 type string;
               }
               leaf ospf-backup-next-hop-sid-info-adj-local-v4-addr {
                 type jt:ipaddr;
               }
               leaf ospf-backup-next-hop-sid-info-adj-remote-v4-addr {
                 type jt:ipaddr;
               }
               leaf ospf-backup-next-hop-sid-info-adj-local-unnumbered-id {
                 type uint32;
               }
               leaf ospf-backup-next-hop-sid-info-adj-remote-unnumbered-id {
                 type uint32;
               }
             }
           }
           list ospf-rt-sessid {
             description "Session ID associated with the route";
             leaf-list ospf-rt-sessid-val {
               type uint32;
             }
             leaf-list ospf-rt-sessid-ver {
               type uint32;
             }
           }
           container ospf-valid-backup-next-hop {
             leaf ospf-valid-backup-next-hop-address {
               type string;
             }
             leaf ospf-valid-backup-next-hop-interface {
               type string;
             }
             leaf ospf-valid-backup-type {
               type string;
             }
             leaf ospf-valid-backup-next-hop-lsp {
               type string;
             }
             leaf ospf-valid-backup-next-hop-lsp-out-if {
               type string;
             }
             leaf ospf-valid-backup-lsp-type {
               type string;
             }
           }
           container ospf-computed-backup-paths {
             leaf ospf-computed-backup-paths-type {
               type string;
             }
             leaf ospf-computed-backup-paths-count {
               type uint32;
             }
             leaf ospf-computed-backup-paths-valid-count {
               type uint32;
             }
             leaf ospf-computed-backup-paths-rttype {
               type string;
             }
             list ospf-computed-backup-path {
               leaf ospf-computed-backup-path-id {
                 type uint32;
               }
               leaf ospf-computed-backup-path-sid-count {
                 type uint32;
               }
               leaf ospf-computed-backup-path-error {
                 type string;
               }
             }
           }
         }
       }
     }
   }
   grouping ospf-statistics-information-block {
     container ospf-statistics {
       leaf dbds-retransmit {
         type uint64;
       }
       leaf dbds-retransmit-5seconds {
         type int32;
       }
       leaf lsas-flooded {
         type uint64;
       }
       leaf lsas-flooded-5seconds {
         type int32;
       }
       leaf lsas-high-prio-flooded {
         type uint64;
       }
       leaf lsas-high-prio-flooded-5seconds {
         type int32;
       }
       leaf lsas-retransmit {
         type uint64;
       }
       leaf lsas-retransmit-5seconds {
         type int32;
       }
       leaf lsas-nbr-transmit {
         type uint64;
       }
       leaf lsas-nbr-transmit-5seconds {
         type int32;
       }
       leaf lsas-requested {
         type uint64;
       }
       leaf lsas-requested-5seconds {
         type int32;
       }
       leaf lsas-acknowledged {
         type uint64;
       }
       leaf lsas-acknowledged-5seconds {
         type int32;
       }
       leaf max-age-lsas-received {
         type uint64;
       }
       leaf max-age-lsas-received-5seconds {
         type int32;
       }
       leaf flood-queue-depth {
         type int32;
       }
       leaf total-retransmits {
         type int32;
       }
       leaf total-database-summaries {
         type int32;
       }
       leaf total-linkstate-request {
         type int32;
       }
       list packet-statistics {
         leaf-list ospf-packet-type {
           type string;
         }
         leaf packets-sent {
           type uint64;
         }
         leaf packets-received {
           type uint64;
         }
         leaf packets-sent-5seconds {
           type int32;
         }
         leaf packets-received-5seconds {
           type int32;
         }
       }
       container ospf-errors {
         leaf runt-header-error {
           type int32;
         }
         leaf short-packets-error {
           type int32;
         }
         leaf bad-version-error {
           type int32;
         }
         leaf truncated-packets-error {
           type int32;
         }
         leaf checksum-error {
           type int32;
         }
         leaf subnet-mismatch-error {
           type int32;
         }
         leaf virtual-link-error {
           type int32;
         }
         leaf area-mismatch-error {
           type int32;
         }
         leaf authentication-mismatch-error {
           type int32;
         }
         leaf authentication-failure-error {
           type int32;
         }
         leaf bad-packettype-error {
           type int32;
         }
         leaf netmask-mismatch-error {
           type int32;
         }
         leaf hello-interval-mismatch-error {
           type int32;
         }
         leaf dead-interval-mismatch-error {
           type int32;
         }
         leaf stub-area-mismatch-error {
           type int32;
         }
         leaf nssa-mismatch-error {
           type int32;
         }
         leaf default-exclusion-mismatch-error {
           type int32;
         }
         leaf mtu-mismatch-error {
           type int32;
         }
         leaf hello-received-error {
           type int32;
         }
         leaf no-router-id-error {
           type int32;
         }
         leaf instance-id-mismatch-error {
           type int32;
         }
         leaf lanp2p-cfgmismatch-error {
           type int32;
         }
         leaf no-error {
           type empty;
         }
       }
     }
   }
   grouping ospf-intf-statistics-information-block {
     list ospf-intf-statistics {
       leaf total-packets-received {
         type uint64;
       }
       leaf total-packets-sent {
         type uint64;
       }
       leaf intf-dbds-retransmit {
         type uint64;
       }
       leaf intf-lsas-flooded {
         type uint64;
       }
       leaf intf-lsas-high-prio-flooded {
         type uint64;
       }
       leaf intf-lsas-retransmit {
         type uint64;
       }
       leaf intf-lsas-nbr-transmit {
         type uint64;
       }
       leaf intf-lsas-requested {
         type uint64;
       }
       leaf intf-lsas-acknowledged {
         type uint64;
       }
       leaf intf-max-age-lsas-received {
         type uint64;
       }
       leaf intf-total-retransmits {
         type int32;
       }
       leaf intf-total-database-summaries {
         type int32;
       }
       leaf intf-total-linkstate-request {
         type int32;
       }
       leaf intf-name {
         type string;
       }
       list packet-statistics {
         leaf-list ospf-packet-type {
           type string;
         }
         leaf packets-sent {
           type uint64;
         }
         leaf packets-received {
           type uint64;
         }
       }
       container ospf-errors {
         leaf short-packets-error {
           type int32;
         }
         leaf subnet-mismatch-error {
           type int32;
         }
         leaf virtual-link-error {
           type int32;
         }
         leaf area-mismatch-error {
           type int32;
         }
         leaf bad-packettype-error {
           type int32;
         }
         leaf netmask-mismatch-error {
           type int32;
         }
         leaf hello-interval-mismatch-error {
           type int32;
         }
         leaf dead-interval-mismatch-error {
           type int32;
         }
         leaf default-exclusion-mismatch-error {
           type int32;
         }
         leaf mtu-mismatch-error {
           type int32;
         }
         leaf lanp2p-cfgmismatch-error {
           type int32;
         }
         leaf no-error {
           type empty;
         }
       }
     }
   }
   grouping ospf-io-statistics-information-block {
     container ospf-io-statistics {
       leaf packets-read {
         type int32;
       }
       leaf average-per-run {
         type string;
       }
       leaf max-run {
         type int32;
       }
       container ospf-errors {
         leaf no-interface-error {
           type int32;
         }
         leaf no-error {
           type empty;
         }
       }
     }
   }
   grouping ospf-log-information-block {
     list ospf-topology-log {
       description "OSPF topology specific SPF log information";
       leaf ospf-topology-name {
         type string;
         description "OSPF topology name";
       }
       container ospf-log-instance {
         list log-element {
           leaf timestamp {
             type string;
             description "Time when something occurs";
           }
           leaf ospf-log-type {
             type string;
           }
           leaf elapsed-time {
             type string;
             description "Time this adjacency or session has been up or down";
           }
         }
       }
       container ospf-log-maximum-length {
         list log-element {
           leaf timestamp {
             type string;
             description "Time when something occurs";
           }
           leaf ospf-log-type {
             type string;
           }
           leaf elapsed-time {
             type string;
             description "Time this adjacency or session has been up or down";
           }
         }
       }
       container ospf-log-events {
         leaf number-events {
           type int32;
         }
         list log-element {
           leaf timestamp {
             type string;
             description "Time when something occurs";
           }
           leaf ospf-log-type {
             type string;
           }
           leaf elapsed-time {
             type string;
             description "Time this adjacency or session has been up or down";
           }
         }
       }
     }
   }
   grouping ospf-bgporr-route-information-block {
     list ospf-topology-bgporr-route-table {
       description "OSPF topology specific bgp-orr routing table";
       leaf ospf-topology-name {
         type string;
         description "OSPF topology name";
       }
       container ospf-bgporr {
         leaf ospf-bgporr-name {
           type string;
         }
         leaf ospf-bgporr-primary {
           type jt:ipaddr;
         }
         leaf ospf-bgporr-primary-active-tag {
           type string;
         }
         leaf ospf-bgporr-backup {
           type jt:ipaddr;
         }
         leaf ospf-bgporr-backup-active-tag {
           type string;
         }
         list ospf-route {
           list ospf-route-entry {
             leaf-list address-prefix {
               type jt:ipaddr;
             }
             leaf route-path-type {
               type string;
             }
             leaf route-type {
               type string;
               description "Route type";
             }
             leaf interface-cost {
               type int32;
               description "Cost associated with this interface";
             }
             leaf ospf-area {
               type string;
               description "Area ID";
             }
             leaf route-origin {
               type jt:ipaddr;
             }
             leaf type7 {
               type empty;
             }
             leaf pbit {
               type empty;
             }
             leaf forward-nz {
               type empty;
             }
             leaf optional-capability {
               type int32;
               description "VEB bits received in the router LSA";
             }
             list ospf-next-hop {
             }
             container ospf-backup-next-hop {
             }
             container ospf-computed-backup-paths {
             }
           }
         }
         list ospf3-route {
           list ospf3-route-entry {
             leaf-list address-prefix {
               type jt:ipaddr;
             }
             leaf route-path-type {
               type string;
             }
             leaf route-type {
               type string;
               description "Route type";
             }
             leaf interface-cost {
               type int32;
               description "Cost associated with this interface";
             }
             leaf ospf-area {
               type string;
               description "Area ID";
             }
             leaf route-origin {
               type jt:ipaddr;
             }
             leaf type7 {
               type empty;
             }
             leaf pbit {
               type empty;
             }
             leaf forward-nz {
               type empty;
             }
             leaf optional-capability {
               type int32;
               description "VEB bits received in the router LSA";
             }
             list ospf-next-hop {
             }
             container ospf-backup-next-hop {
             }
           }
         }
       }
     }
   }
   grouping ospf-spring-flex-algorithm-information-block {
     leaf ospf-flex-algorithm-id {
       type uint32;
     }
     leaf ospf-area {
       type string;
       description "Area ID";
     }
     leaf ospf-flex-algorithm-color {
       type uint32;
     }
     leaf ospf-flex-algorithm-participation {
       type string;
     }
     leaf ospf-flex-algorithm-participation-reason {
       type string;
     }
     leaf ospf-flex-full-spf-runs {
       type int32;
     }
     leaf ospf-flex-prc-spf-runs {
       type int32;
     }
     leaf ospf-flex-algorithm-stat-spf-version {
       type uint32;
     }
     leaf ospf-flex-algorithm-stat-prtpn-toggle {
       type uint32;
     }
     leaf ospf-flex-algorithm-stat-topo-refresh {
       type uint32;
     }
     container ospf-flex-algorithm-winner-fad {
       container ospf-flex-algorithm-sub-tlv {
         leaf ospf-router-id {
           type jt:ipaddr;
           description "OSPF router ID";
         }
         leaf ospf-flex-algorithm-id {
           type uint32;
         }
         leaf ospf-flex-algorithm-metric-str {
           type string;
         }
         leaf ospf-flex-algorithm-calc-str {
           type string;
         }
         leaf ospf-flex-algorithm-metric-type {
           type uint32;
         }
         leaf ospf-flex-algorithm-calc-type {
           type uint32;
         }
         leaf ospf-flex-algorithm-priority {
           type uint32;
         }
         leaf ospf-flex-algorithm-include-any {
           type string;
         }
         leaf ospf-flex-algorithm-include-all {
           type string;
         }
         leaf ospf-flex-algorithm-exclude {
           type string;
         }
         leaf ospf-flex-algorithm-flags {
           type uint32;
         }
         leaf ospf-flex-algorithm-participation-reason {
           type string;
         }
         leaf ospf-flex-algorithm-po-flags {
           type uint32;
         }
         leaf ospf-flex-algorithm-po-res {
           type uint32;
         }
         leaf ospf-flex-algorithm-po-offset {
           type uint32;
         }
         container ospf-flex-algorithm-include-any-detail {
           container admin-groups {
             leaf color {
               type int32;
             }
             leaf no-group-flag {
               type empty;
             }
             leaf-list admin-group-name {
               type string;
               description "Name of the admin group";
             }
             leaf admin-group-number {
               type int32;
               description "Number of the admin group";
             }
           }
         }
         container ospf-flex-algorithm-include-all-detail {
           container admin-groups {
             leaf color {
               type int32;
             }
             leaf no-group-flag {
               type empty;
             }
             leaf-list admin-group-name {
               type string;
               description "Name of the admin group";
             }
             leaf admin-group-number {
               type int32;
               description "Number of the admin group";
             }
           }
         }
         container ospf-flex-algorithm-exclude-detail {
           container admin-groups {
             leaf color {
               type int32;
             }
             leaf no-group-flag {
               type empty;
             }
             leaf-list admin-group-name {
               type string;
               description "Name of the admin group";
             }
             leaf admin-group-number {
               type int32;
               description "Number of the admin group";
             }
           }
         }
       }
     }
     container ospf-flex-algorithm-loser-fad {
       container ospf-flex-algorithm-sub-tlv {
         leaf ospf-router-id {
           type jt:ipaddr;
           description "OSPF router ID";
         }
         leaf ospf-flex-algorithm-id {
           type uint32;
         }
         leaf ospf-flex-algorithm-metric-str {
           type string;
         }
         leaf ospf-flex-algorithm-calc-str {
           type string;
         }
         leaf ospf-flex-algorithm-metric-type {
           type uint32;
         }
         leaf ospf-flex-algorithm-calc-type {
           type uint32;
         }
         leaf ospf-flex-algorithm-priority {
           type uint32;
         }
         leaf ospf-flex-algorithm-include-any {
           type string;
         }
         leaf ospf-flex-algorithm-include-all {
           type string;
         }
         leaf ospf-flex-algorithm-exclude {
           type string;
         }
         leaf ospf-flex-algorithm-flags {
           type uint32;
         }
         leaf ospf-flex-algorithm-participation-reason {
           type string;
         }
         leaf ospf-flex-algorithm-po-flags {
           type uint32;
         }
         leaf ospf-flex-algorithm-po-res {
           type uint32;
         }
         leaf ospf-flex-algorithm-po-offset {
           type uint32;
         }
         container ospf-flex-algorithm-include-any-detail {
           container admin-groups {
             leaf color {
               type int32;
             }
             leaf no-group-flag {
               type empty;
             }
             leaf-list admin-group-name {
               type string;
               description "Name of the admin group";
             }
             leaf admin-group-number {
               type int32;
               description "Number of the admin group";
             }
           }
         }
         container ospf-flex-algorithm-include-all-detail {
           container admin-groups {
             leaf color {
               type int32;
             }
             leaf no-group-flag {
               type empty;
             }
             leaf-list admin-group-name {
               type string;
               description "Name of the admin group";
             }
             leaf admin-group-number {
               type int32;
               description "Number of the admin group";
             }
           }
         }
         container ospf-flex-algorithm-exclude-detail {
           container admin-groups {
             leaf color {
               type int32;
             }
             leaf no-group-flag {
               type empty;
             }
             leaf-list admin-group-name {
               type string;
               description "Name of the admin group";
             }
             leaf admin-group-number {
               type int32;
               description "Number of the admin group";
             }
           }
         }
       }
     }
   }
   grouping ospf-spring-sensor-information-block {
     leaf ospf-spring-sensor-information-attribute {
       type string;
     }
     container ospf-sensor-ingress {
       description "OSPF SPRING ingress sensor information";
       list ospf-sensor-ingress-entries {
         leaf ingress-sensor-name {
           type string;
         }
         leaf ingress-sensor-id {
           type int32;
         }
       }
     }
     container ospf-sensor-egress {
       description "OSPF SPRING egress sensor information";
       list ospf-sensor-egress-entries {
         leaf egress-sensor-name {
           type string;
         }
         leaf egress-sensor-id {
           type int32;
         }
       }
     }
     container ospf-sensor-per-sid {
       description "OSPF SPRING Per Sid ingress sensor information";
       list ospf-sensor-per-sid-entries {
         leaf per-sid-sensor-name {
           type string;
         }
         leaf per-sid-sensor-id {
           type int32;
         }
       }
     }
     container ospf-sensor-ip-mpls {
       description "OSPF SPRING Per Sid egress sensor information";
       list ospf-sensor-ip-mpls-entries {
         leaf per-sid-sensor-name {
           type string;
         }
         leaf per-sid-sensor-id {
           type int32;
         }
       }
     }
   }
   grouping ospf-spring-sid-database-information-block {
     container ospf-area-header {
       leaf ospf-area {
         type string;
         description "Area ID";
       }
     }
     list ospf-sid-database {
       leaf-list ospf-sid-database.external-heading {
         type string;
       }
       leaf-list ospf-sid-database.heading {
         type string;
       }
       leaf tlv-sid {
         type int32;
       }
       leaf-list address-prefix {
         type jt:ipaddr;
       }
       leaf advertising-router {
         type jt:ipaddr;
       }
       leaf route-path-type {
         type string;
       }
     }
   }
   grouping ospf-spring-pfx-sid-map-information-block {
     container ospf-area-header {
       leaf ospf-area {
         type string;
         description "Area ID";
       }
     }
     list ospf-sid-map-database {
       leaf-list ospf-sid-map-database.external-heading {
         type string;
       }
       leaf-list ospf-sid-map-database.heading {
         type string;
       }
       leaf tlv-sid {
         type int32;
       }
       leaf-list address-prefix {
         type jt:ipaddr;
       }
       leaf advertising-router {
         type jt:ipaddr;
       }
       leaf tlv-range {
         type int32;
       }
       leaf map-active {
         type string;
       }
     }
   }
 }
