/*
 * Copyright (c) 2025 Juniper Networks, Inc.
 * All rights reserved.
 */
 module junos-conf-event-options {
   namespace "http://yang.juniper.net/junos/conf/event-options";

   prefix jc-event-options;

   import junos-common-ddl-extensions {
     prefix junos;
     revision-date 2025-01-01;
   }

   import junos-common-types {
     prefix jt;
     revision-date 2025-01-01;
   }

   import junos-conf-root {
     prefix jc;
     revision-date 2025-01-01;
   }

   organization "Juniper Networks, Inc.";

   contact "yang-support@juniper.net";

   description "Junos event-options configuration module";

   revision 2025-01-01 {
     description "Junos: 25.2R1.9";
   }

   augment /jc:configuration {
     uses event-options-group;
   }
   augment /jc:configuration/jc:groups {
     uses event-options-group;
   }
   grouping event-options-group {
     container event-options {
       description "Event processing configuration";
       uses apply-advanced;
       leaf max-policies {
         description "Number of policies that can be executed simultaneously";
         default "15";
         type union {
           type string {
             pattern "<.*>|$.*";
           }
           type uint32 {
             range "0 .. 20";
           }
         }
       }
       list generate-event {
         key name;
         ordered-by user;
         junos:cli-feature "homogeneous";
         junos:cli-feature "oneliner";
         description "Generate an internal event";
         max-elements 10;
         leaf name {
           description "Name of the event to be generated";
           junos:cli-feature "nokeyword";
           type string {
             length "1 .. 63";
           }
         }
         choice time_choice {
           case case_1 {
             leaf time-of-day {
               description "Time of day at which to generate event (hh:mm:ss)";
               type jt:time-of-day;
             }
           }
           case case_2 {
             leaf time-interval {
               description "Frequency for generating the event";
               units "seconds";
               type union {
                 type string {
                   pattern "<.*>|$.*";
                 }
                 type uint32 {
                   range "60 .. 2592000";
                 }
               }
             }
           }
         }
         leaf start-time {
           description "Start-time to generate event (yyyy-mm-dd.hh:mm)";
           junos:must "((!(\".. time-of-day\") && \".. time-interval\"))";
           junos:must-message "'time-interval' is mandatory for 'start-time' configuration";
           type jt:time;
         }
         leaf no-drift {
           description "Avoid event generation delay propagating to next event";
           type empty;
         }
       }
       list policy {
         key name;
         ordered-by user;
         description "Event policy for event policy manager";
         leaf name {
           description "Name of policy";
           junos:cli-feature "nokeyword";
           type string {
             length "1 .. 63";
           }
         }
         uses apply-advanced;
         leaf-list events {
           ordered-by user;
           description "List of events that trigger this policy";
           type string;
         }
         list within {
           key name;
           ordered-by user;
           junos:cli-feature "oneliner-plus";
           description "List of events correlated with trigering events";
           leaf name {
             description "Time within which correlated events must occur (or not)";
             junos:cli-feature "nokeyword";
             units "seconds";
             type union {
               type string {
                 pattern "<.*>|$.*";
               }
               type uint32 {
                 range "1 .. 604800";
               }
             }
           }
           uses apply-advanced;
           container trigger {
             junos:cli-feature "oneliner";
             description "Correlate events based on the number of occurrences";
             choice when {
               case case_1 {
                 leaf until {
                   description "Trigger when occurrences of triggering event < 'count'";
                   type empty;
                 }
               }
               case case_2 {
                 leaf on {
                   description "Trigger when occurrences of triggering event = 'count'";
                   type empty;
                 }
               }
               case case_3 {
                 leaf after {
                   description "Trigger when occurrences of triggering event > 'count'";
                   type empty;
                 }
               }
             }
             leaf count {
               description "Number of occurrences of triggering event";
               junos:cli-feature "nokeyword";
               type union {
                 type uint32;
                 type string {
                   pattern "<.*>|$.*";
                 }
               }
             }
           }
           leaf-list events {
             ordered-by user;
             description "List of events that must occur within time interval";
             type string;
           }
           container not {
             junos:cli-feature "oneliner";
             description "Events must not occur within time interval";
             leaf-list events {
               ordered-by user;
               description "List of events that must not occur within time interval";
               type string;
             }
           }
         }
         list attributes-match {
           key "from-event-attribute condition to-event-attribute-value";
           ordered-by user;
           junos:cli-feature "homogeneous";
           junos:cli-feature "oneliner";
           description "List of attributes to compare for two events";
           leaf from-event-attribute {
             description "First attribute to compare";
             junos:cli-feature "nokeyword";
             type string {
               junos:posix-pattern "^([[:alnum:]]([[:alnum:]_-])*[.][[:alnum:]]([[:alnum:]_-])*)|(\\{[$]([[:alnum:]]([[:alnum:]_-])*|[$])[.][[:alnum:]]([[:alnum:]_-])*})$";
               junos:pattern-message "Must be either in event.attribute or {$$.attribute} or {$event.attribute} format where event and attribute start with an alphanumeric character and can consist of alphanumerics, underscores, or hyphens";
             }
           }
           leaf condition {
             description "Relationship that must hold between attributes";
             junos:cli-feature "nokeyword";
             type enumeration {
               enum "equals" {
                 description "Attributes match";
                 junos:must "(\".. .. within\")";
                 junos:must-message "within clause must be configured";
               }
               enum "starts-with" {
                 description "Second attribute starts with first attribute value";
                 junos:must "(\".. .. within\")";
                 junos:must-message "within clause must be configured";
               }
               enum "matches" {
                 description "Regular expression matching the first attribute value";
               }
             }
           }
           leaf to-event-attribute-value {
             description "Second attribute or value to compare";
             junos:cli-feature "nokeyword";
             type string;
           }
         }
         container then {
           description "List of actions to perform when policy matches";
           uses apply-advanced;
           leaf ignore {
             description "Do not log event or perform any other action";
             junos:must "(!((\".. upload\" || (\".. execute-commands\" || (\".. raise-trap\" || (\".. event-script\" || \".. priority-override\"))))))";
             junos:must-message "'ignore' must be specified as an action alone";
             type empty;
           }
           container priority-override {
             description "Change syslog priority value";
             uses apply-advanced;
             leaf facility {
               description "Facility type";
               type enumeration {
                 enum "authorization" {
                   description "Authorization system";
                 }
                 enum "daemon" {
                   description "Various system processes";
                 }
                 enum "ftp" {
                   description "FTP process";
                 }
                 enum "ntp" {
                   description "NTP process";
                 }
                 enum "security" {
                   description "Security related";
                 }
                 enum "kernel" {
                   description "Kernel";
                 }
                 enum "user" {
                   description "User processes";
                 }
                 enum "dfc" {
                   description "Dynamic flow capture";
                 }
                 enum "external" {
                   description "Local external applications";
                 }
                 enum "firewall" {
                   description "Firewall filtering system";
                 }
                 enum "pfe" {
                   description "Packet Forwarding Engine";
                 }
                 enum "conflict-log" {
                   description "Configuration conflict log";
                 }
                 enum "change-log" {
                   description "Configuration change log";
                 }
                 enum "interactive-commands" {
                   description "Commands executed by the UI";
                 }
               }
             }
             leaf severity {
               description "Severity type";
               type enumeration {
                 enum "emergency" {
                   description "Panic conditions";
                 }
                 enum "alert" {
                   description "Conditions that should be corrected immediately";
                 }
                 enum "critical" {
                   description "Critical conditions";
                 }
                 enum "error" {
                   description "Error conditions";
                 }
                 enum "warning" {
                   description "Warning messages";
                 }
                 enum "notice" {
                   description "Conditions that should be handled specially";
                 }
                 enum "info" {
                   description "Informational messages";
                 }
               }
             }
           }
           list upload {
             key "filename destination";
             ordered-by user;
             description "Upload file to specified destination";
             leaf filename {
               description "Name of file to upload";
               type string;
             }
             leaf destination {
               description "Location to which to output file";
               junos:must "(\"event-options destinations $$\")";
               junos:must-message "Destination is not defined";
               type string;
             }
             uses apply-advanced;
             leaf user-name {
               description "User under whose privileges upload action will execute";
               junos:must "(\"system login user $$\")";
               junos:must-message "User is not defined";
               type string;
             }
             leaf transfer-delay {
               description "Delay before uploading file to the destination";
               units "seconds";
               type union {
                 type uint32;
                 type string {
                   pattern "<.*>|$.*";
                 }
               }
             }
             container retry-count {
               junos:cli-feature "oneliner";
               description "Upload output-filename retry attempt count";
               leaf retry {
                 description "Number of retry attempts";
                 junos:cli-feature "nokeyword";
                 type union {
                   type string {
                     pattern "<.*>|$.*";
                   }
                   type uint8 {
                     range "0 .. 10";
                   }
                 }
               }
               leaf retry-interval {
                 description "Time interval between each retry";
                 units "seconds";
                 type union {
                   type uint32;
                   type string {
                     pattern "<.*>|$.*";
                   }
                 }
               }
             }
           }
           container change-configuration {
             description "Change configuration";
             uses apply-advanced;
             container retry {
               junos:cli-feature "oneliner";
               description "Change configuration retry attempt count";
               leaf count {
                 description "Number of retry attempts";
                 type union {
                   type string {
                     pattern "<.*>|$.*";
                   }
                   type uint8 {
                     range "0 .. 10";
                   }
                 }
               }
               leaf interval {
                 description "Time interval between each retry";
                 units "seconds";
                 type union {
                   type uint32;
                   type string {
                     pattern "<.*>|$.*";
                   }
                 }
               }
             }
             list commands {
               key name;
               ordered-by user;
               junos:cli-feature "homogeneous";
               description "List of configuration commands";
               leaf name {
                 description "Configuration command to issue";
                 junos:cli-feature "nokeyword";
                 type string;
               }
               uses apply-advanced;
             }
             leaf user-name {
               description "User under whose privileges configuration should be changed";
               junos:must "(\"system login user $$\")";
               junos:must-message "User is not defined";
               type string;
             }
             container commit-options {
               description "List of commit options";
               uses apply-advanced;
               container check {
                 presence "enable check";
                 description "Check correctness of syntax; do not apply changes";
                 uses apply-advanced;
                 leaf synchronize {
                   description "Synchronize commit on both Routing Engines";
                   type empty;
                 }
               }
               leaf synchronize {
                 description "Synchronize commit on both Routing Engines";
                 junos:must "(!(\".. check\"))";
                 junos:must-message "check clause must not be configured";
                 type empty;
               }
               leaf force {
                 description "Force commit on other Routing Engine (ignore warnings)";
                 junos:must "(!(\".. check\"))";
                 junos:must-message "check clause must not be configured";
                 type empty;
               }
               leaf log {
                 description "Message to write to commit log";
                 junos:must "(!(\".. check\"))";
                 junos:must-message "check clause must not be configured";
                 type string {
                   length "1 .. 512";
                 }
               }
             }
           }
           container execute-commands {
             description "Issue one or more CLI commands";
             uses apply-advanced;
             list commands {
               key name;
               ordered-by user;
               junos:cli-feature "homogeneous";
               description "List of CLI commands to issue";
               leaf name {
                 description "CLI command to issue";
                 junos:cli-feature "nokeyword";
                 type string;
               }
               uses apply-advanced;
             }
             leaf user-name {
               description "User under whose privileges command will execute";
               junos:must "(\"system login user $$\")";
               junos:must-message "User is not defined";
               type string;
             }
             leaf output-filename {
               description "Name of file in which to write command output";
               junos:must "(\".. destination\")";
               junos:must-message "'destination' statement must also be included";
               type string {
                 junos:posix-pattern "![/ %]";
                 junos:pattern-message "Must not contain \'/\', % or a space";
               }
             }
             list destination {
               key name;
               ordered-by user;
               junos:cli-feature "oneliner-plus";
               description "Location to which to upload command output";
               max-elements 1;
               leaf name {
                 description "Location to which to upload command output";
                 junos:cli-feature "nokeyword";
                 junos:must "(\".. .. output-filename\")";
                 junos:must-message "'output-filename' statement must also be included";
                 junos:must "(\"event-options destinations $$\")";
                 junos:must-message "Destination is not defined";
                 type string;
               }
               uses apply-advanced;
               leaf transfer-delay {
                 description "Delay before uploading file to the destination";
                 units "seconds";
                 type union {
                   type uint32;
                   type string {
                     pattern "<.*>|$.*";
                   }
                 }
               }
               container retry-count {
                 junos:cli-feature "oneliner";
                 description "Upload output-filename retry attempt count";
                 leaf retry {
                   description "Number of retry attempts";
                   junos:cli-feature "nokeyword";
                   type union {
                     type string {
                       pattern "<.*>|$.*";
                     }
                     type uint8 {
                       range "0 .. 10";
                     }
                   }
                 }
                 leaf retry-interval {
                   description "Time interval between each retry";
                   units "seconds";
                   type union {
                     type uint32;
                     type string {
                       pattern "<.*>|$.*";
                     }
                   }
                 }
               }
             }
             leaf output-format {
               description "Format of output from CLI commands";
               default "xml";
               type enumeration {
                 enum "text" {
                   description "Formatted ASCII text";
                 }
                 enum "xml" {
                   description "JUNOS XML tags";
                 }
               }
             }
           }
           list event-script {
             key name;
             ordered-by user;
             description "Invoke event scripts";
             leaf name {
               description "Local filename of the script file";
               junos:cli-feature "nokeyword";
               type string {
                 length "1 .. 254";
                 junos:posix-pattern "!/";
                 junos:pattern-message "File name cannot contain a \'/\'";
               }
             }
             uses apply-advanced;
             list arguments {
               key name;
               ordered-by user;
               junos:cli-feature "homogeneous";
               junos:cli-feature "oneliner";
               description "Command line argument to the script";
               leaf name {
                 description "Name of the argument";
                 junos:cli-feature "nokeyword";
                 type string {
                   length "1 .. 254";
                 }
               }
               leaf value {
                 description "Value of the argument";
                 junos:cli-feature "nokeyword";
                 type string;
               }
             }
             leaf user-name {
               description "User under whose privileges event script will execute";
               junos:must "(\"system login user $$\")";
               junos:must-message "User is not defined";
               type string;
             }
             leaf output-filename {
               description "Name of file in which to write event script output";
               junos:must "(\".. destination\")";
               junos:must-message "'destination' statement must also be included";
               type string {
                 junos:posix-pattern "![/ %]";
                 junos:pattern-message "Must not contain \'/\', % or a space";
               }
             }
             list destination {
               key name;
               ordered-by user;
               junos:cli-feature "oneliner-plus";
               description "Location to which to upload event script output";
               max-elements 1;
               leaf name {
                 description "Location to which to upload event script output";
                 junos:cli-feature "nokeyword";
                 junos:must "(\"event-options destinations $$\")";
                 junos:must-message "Destination is not defined";
                 type string;
               }
               uses apply-advanced;
               leaf transfer-delay {
                 description "Delay before uploading files";
                 units "seconds";
                 type union {
                   type uint32;
                   type string {
                     pattern "<.*>|$.*";
                   }
                 }
               }
               container retry-count {
                 junos:cli-feature "oneliner";
                 description "Upload output-filename retry attempt count";
                 leaf retry {
                   description "Number of retry attempts";
                   junos:cli-feature "nokeyword";
                   type union {
                     type string {
                       pattern "<.*>|$.*";
                     }
                     type uint8 {
                       range "0 .. 10";
                     }
                   }
                 }
                 leaf retry-interval {
                   description "Time interval between each retry";
                   units "seconds";
                   type union {
                     type uint32;
                     type string {
                       pattern "<.*>|$.*";
                     }
                   }
                 }
               }
             }
             leaf output-format {
               description "Format of output from event-script";
               type enumeration {
                 enum "text" {
                   description "Formatted ASCII text";
                 }
                 enum "xml" {
                   description "JUNOS XML tags";
                 }
               }
             }
           }
           leaf raise-trap {
             description "Raise SNMP trap";
             type empty;
           }
         }
       }
       container event-script {
         description "Configure event-scripts";
         uses apply-advanced;
         leaf optional {
           description "Allow commit to succeed if the script is missing";
           type empty;
         }
         leaf max-datasize {
           description "Maximum data segment size for scripts execution";
           units "bytes";
           type string;
         }
         container dampen {
           presence "enable dampen";
           description "Run event scripts in dampen mode";
           uses apply-advanced;
           container dampen-options {
             description "Dampen options for event scripts";
             uses apply-advanced;
             leaf cpu-factor {
               description "CPU factor at which to pause";
               type union {
                 type string {
                   pattern "<.*>|$.*";
                 }
                 type uint32 {
                   range "1 .. 100";
                 }
               }
             }
             leaf line-interval {
               description "Line interval at which to pause";
               type union {
                 type string {
                   pattern "<.*>|$.*";
                 }
                 type uint32 {
                   range "1 .. 4294967295";
                 }
               }
             }
             leaf time-interval {
               description "Time to pause";
               units "microseconds";
               type union {
                 type string {
                   pattern "<.*>|$.*";
                 }
                 type uint32 {
                   range "1 .. 4294967295";
                 }
               }
             }
           }
         }
         container start {
           description "Start event scripts with start-criteria check";
           uses apply-advanced;
           container start-options {
             description "Start options for event scripts";
             uses apply-advanced;
             leaf mem-factor {
               description "Memory factor at which to start/stop";
               type union {
                 type string {
                   pattern "<.*>|$.*";
                 }
                 type uint32 {
                   range "1 .. 100";
                 }
               }
             }
           }
         }
         container traceoptions {
           description "Trace options for event scripts";
           uses apply-advanced;
           leaf no-remote-trace {
             description "Disable remote tracing";
             junos:must "(\"system tracing\")";
             junos:must-message "'no-remote-trace' is valid only when [system tracing] is configured";
             type empty;
           }
           container file {
             junos:cli-feature "oneliner";
             description "Trace file information";
             leaf filename {
               description "Name of file in which to write trace information";
               junos:cli-feature "nokeyword";
               type string {
                 length "1 .. 1024";
                 junos:posix-pattern "![/ %]";
                 junos:pattern-message "Must not contain \'/\', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
           }
           list flag {
             key name;
             junos:cli-feature "oneliner";
             description "Tracing parameters";
             leaf name {
               junos:cli-feature "nokeyword";
               type enumeration {
                 enum "events" {
                   description "Trace important events";
                 }
                 enum "input" {
                   description "Trace script input data";
                 }
                 enum "offline" {
                   description "Generate data for offline development";
                 }
                 enum "output" {
                   description "Trace script output data";
                 }
                 enum "rpc" {
                   description "Trace script RPCs";
                 }
                 enum "xslt" {
                   description "Trace the XSLT library";
                 }
                 enum "all" {
                   description "Trace all operations";
                 }
               }
             }
           }
         }
         list file {
           key name;
           ordered-by user;
           description "File name for event script";
           leaf name {
             description "Local filename of the script file";
             junos:cli-feature "nokeyword";
             type string {
               length "1 .. 254";
               junos:posix-pattern "!/";
               junos:pattern-message "File name cannot contain a \'/\'";
             }
           }
           uses apply-advanced;
           leaf source {
             description "URL of source for this script";
             type string {
               length "1 .. 254";
             }
           }
           leaf cert-file {
             description "Specify the ca certificate file name";
             junos:must "(\".. source\")";
             junos:must-message "source must be defined";
             type string;
           }
           leaf python-script-user {
             description "Run the python event script with privileges of user";
             junos:must "(\"system login user $$\")";
             junos:must-message "User is not defined";
             type string;
           }
           container dampen {
             presence "enable dampen";
             description "Run script in dampen mode";
             uses apply-advanced;
             container dampen-options {
               description "Dampen options for the script";
               uses apply-advanced;
               leaf cpu-factor {
                 description "CPU factor at which to pause";
                 type union {
                   type string {
                     pattern "<.*>|$.*";
                   }
                   type uint32 {
                     range "1 .. 100";
                   }
                 }
               }
               leaf line-interval {
                 description "Line interval at which to pause";
                 type union {
                   type string {
                     pattern "<.*>|$.*";
                   }
                   type uint32 {
                     range "1 .. 4294967295";
                   }
                 }
               }
               leaf time-interval {
                 description "Time to pause";
                 units "microseconds";
                 type union {
                   type string {
                     pattern "<.*>|$.*";
                   }
                   type uint32 {
                     range "1 .. 4294967295";
                   }
                 }
               }
             }
           }
           container start {
             description "Start script with start-criteria check";
             uses apply-advanced;
             container start-options {
               description "Start options for the event script";
               uses apply-advanced;
               leaf mem-factor {
                 description "Memory factor at which to start/stop";
                 type union {
                   type string {
                     pattern "<.*>|$.*";
                   }
                   type uint32 {
                     range "1 .. 100";
                   }
                 }
               }
             }
           }
           leaf routing-instance {
             description "Routing instance";
             junos:must "(\"routing-instances $$\")";
             junos:must-message "Referenced routing instance must be defined under [edit routing-instances] hierarchy level";
             type string {
               junos:posix-pattern "!^((__.*__)|(all)|(.*[ ].*)|(\"\")|(.{129,}))$";
               junos:pattern-message "Must be a non-reserved string of 128 characters or less with no spaces.";
             }
           }
           leaf refresh {
             description "Refresh all operation scripts from their source";
             type empty;
           }
           leaf refresh-from {
             description "Refresh all operation scripts from a given base URL";
             type string {
               length "1 .. 254";
             }
           }
           container checksum {
             junos:cli-feature "oneliner-plus";
             description "Checksum of this script";
             uses apply-advanced;
             leaf sha-256 {
               description "SHA-256 checksum of this script";
               type string {
                 length "1 .. 254";
               }
             }
           }
           list remote-execution {
             key name;
             ordered-by user;
             junos:cli-feature "homogeneous";
             description "Remote login username and password details for script";
             leaf name {
               description "Remote hostname";
               junos:cli-feature "nokeyword";
               type string {
                 length "1 .. 255";
                 junos:posix-pattern "^[[:alnum:]._-]+$";
                 junos:pattern-message "Must be a string of alphanumericals, dashes or underscores";
               }
             }
             uses apply-advanced;
             leaf username {
               description "SSH username for login into the remote host";
               type string {
                 junos:posix-pattern "^[[:alnum:]_]{1,}[.]{0,1}[[:alnum:]_-]{0,}[.]{0,1}[[:alnum:]_-]{0,}$";
                 junos:pattern-message "Must contain characters (alphanumerics, underscores or hyphens) beginning with an alphanumeric or an underscore character.";
               }
             }
             leaf passphrase {
               description "SSH passphrase for login into the remote host";
               type jt:unreadable;
             }
           }
         }
         leaf refresh {
           description "Refresh all operation scripts from their source";
           type empty;
         }
         leaf refresh-from {
           description "Refresh all operation scripts from a given base URL";
           type string {
             length "1 .. 254";
           }
         }
       }
       list destinations {
         key name;
         ordered-by user;
         junos:cli-feature "homogeneous";
         description "List of destinations referred to in 'then' clause";
         leaf name {
           description "Destination name";
           junos:cli-feature "nokeyword";
           type string;
         }
         uses apply-advanced;
         leaf transfer-delay {
           description "Delay before transferring files";
           default "0";
           units "seconds";
           type union {
             type uint32;
             type string {
               pattern "<.*>|$.*";
             }
           }
         }
         list archive-sites {
           key name;
           ordered-by user;
           junos:cli-feature "homogeneous";
           junos:cli-feature "oneliner";
           description "List of archive destinations";
           leaf name {
             description "URL of destination for file";
             junos:cli-feature "nokeyword";
             type string;
           }
           leaf password {
             description "Password for login into the archive site";
             type jt:unreadable;
           }
         }
       }
       container traceoptions {
         description "Trace options for the event processing daemon";
         uses apply-advanced;
         leaf no-remote-trace {
           description "Disable remote tracing";
           junos:must "(\"system tracing\")";
           junos:must-message "'no-remote-trace' is valid only when [system tracing] is configured";
           type empty;
         }
         container file {
           junos:cli-feature "oneliner";
           description "Trace file information";
           leaf filename {
             description "Name of file in which to write trace information";
             junos:cli-feature "nokeyword";
             type string {
               length "1 .. 1024";
               junos:posix-pattern "![/ %]";
               junos:pattern-message "Must not contain \'/\', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           junos:cli-feature "oneliner";
           description "List of event types to include in trace";
           leaf name {
             junos:cli-feature "nokeyword";
             type enumeration {
               enum "server" {
                 description "Communication with processes that are generating events";
               }
               enum "configuration" {
                 description "Reading of configuration";
               }
               enum "events" {
                 description "Event processing";
               }
               enum "timer-events" {
                 description "Internally generated events";
               }
               enum "database" {
                 description "Events involving storage and retrieval in events database";
               }
               enum "policy" {
                 description "Policy processing";
               }
               enum "registration" {
                 description "Event registration";
               }
               enum "syslogd" {
                 description "Syslog related traces";
               }
               enum "all" {
                 description "Everything";
               }
             }
           }
         }
       }
       list redundancy-event {
         key name;
         ordered-by user;
         description "Events for policies to take action on";
         uses srd-events-object;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       junos:cli-feature "nokeyword";
       type string;
     }
     list data {
       key name;
       uses macro-data-type;
       junos:cli-feature "nokeyword";
       junos:cli-feature "homogeneous";
       junos:cli-feature "oneliner";
     }
   }
   grouping macro-data-type {
     junos:cli-feature "nokeyword";
     junos:cli-feature "homogeneous";
     junos:cli-feature "oneliner";
     leaf name {
       description "Keyword part of the keyword-value pair";
       junos:cli-feature "nokeyword";
       type string;
     }
     leaf value {
       description "Value part of the keyword-value pair";
       junos:cli-feature "nokeyword";
       type string;
     }
   }
   grouping srd-events-object {
     description "Events for policies to take action on";
     leaf name {
       description "Redundancy event name";
       junos:cli-feature "nokeyword";
       type string {
         length "1 .. 63";
       }
     }
     uses apply-advanced;
     container monitor {
       description "Interfaces to be tracked";
       uses apply-advanced;
       list link-down {
         key name;
         junos:cli-feature "homogeneous";
         description "Interfaces to be monitored for link-down events";
         leaf name {
           description "Name of the interface for monitoring link-down events";
           junos:cli-feature "nokeyword";
           type string;
         }
         uses apply-advanced;
       }
       container process {
         description "Processes related events";
         uses apply-advanced;
         container routing {
           description "Routing process related events";
           uses apply-advanced;
           leaf restart {
             description "Routing protocol restart event";
             type empty;
           }
           leaf abort {
             description "Routing protocol abort event";
             type empty;
           }
         }
       }
       container peer {
         description "Events from remote peers";
         uses apply-advanced;
         leaf event {
           description "Peer Events";
           junos:cli-feature "nokeyword";
           type enumeration {
             enum "mastership-release" {
               description "Received mastership-release message from peer";
             }
             enum "mastership-acquire" {
               description "Received mastership-acquire message from peer";
             }
           }
         }
       }
     }
   }
 }
