/*
 * Copyright (c) 2025 Juniper Networks, Inc.
 * All rights reserved.
 */
 module junos-es-conf-chassis {
   namespace "http://yang.juniper.net/junos-es/conf/chassis";

   prefix jc-chassis;

   import junos-common-ddl-extensions {
     prefix junos;
     revision-date 2025-01-01;
   }

   import junos-common-types {
     prefix jt;
     revision-date 2025-01-01;
   }

   import junos-es-conf-root {
     prefix jc;
     revision-date 2025-01-01;
   }

   organization "Juniper Networks, Inc.";

   contact "yang-support@juniper.net";

   description "Junos chassis configuration module";

   revision 2025-01-01 {
     description "Junos: 25.2R1.9";
   }

   augment /jc:configuration {
     uses chassis-group;
   }
   augment /jc:configuration/jc:groups {
     uses chassis-group;
   }
   grouping chassis-group {
     container chassis {
       description "Chassis configuration";
       uses chassis_type;
     }
   }
   grouping chassis_type {
     uses apply-advanced;
     container psu {
       description "Power Supply Unit redundancy configuration";
       uses apply-advanced;
       container redundancy {
         description "PSU Redundancy settings";
         uses apply-advanced;
         leaf n-plus-n {
           description "PSU redundancy: N+N configuration";
           type empty;
         }
       }
     }
     container optics {
       presence "enable optics";
       description "Optics specific config";
       uses apply-advanced;
       leaf display-3po-pn {
         description "To display third party optics part number";
         type empty;
       }
     }
     leaf craft-lockout {
       description "Disable craft interface input";
       type empty;
     }
     container config-button {
       junos:cli-feature "oneliner";
       description "Config button behavior settings";
       leaf no-rescue {
         description "Don't reset to rescue configuration";
         type empty;
       }
       leaf no-clear {
         description "Don't reset to factory-default configuration";
         type empty;
       }
     }
     leaf routing-engine-power-off-button-disable {
       description "Disable RE power off button";
       type empty;
     }
     choice source-route-choice {
       leaf source-route {
         description "Enable IP source-route processing";
         status deprecated;
         type empty;
       }
       leaf no-source-route {
         description "Don't enable IP source-route processing";
         status deprecated;
         type empty;
       }
     }
     choice packet-scheduling-choice {
       leaf packet-scheduling {
         description "Enable DX2.0 packet scheduling";
         type empty;
       }
       leaf no-packet-scheduling {
         description "Don't enable DX2.0 packet scheduling";
         type empty;
       }
     }
     container icmp {
       description "ICMP protocol";
       uses apply-advanced;
       leaf per-iff-rate-limit {
         description "Configure icmp per iff rate limit value in the range 50-500";
         default "50";
         type union {
           type string {
             pattern "<.*>|$.*";
           }
           type uint32 {
             range "50 .. 500";
           }
         }
       }
     }
     container icmp6 {
       description "ICMP version 6 protocol";
       uses apply-advanced;
       leaf per-iff-rate-limit {
         description "Configure icmp6 per iff rate limit value in the range 50-500";
         default "50";
         type union {
           type string {
             pattern "<.*>|$.*";
           }
           type uint32 {
             range "50 .. 500";
           }
         }
       }
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
           junos:must "(!(\"system processes routing force-32-bit\"))";
           junos:must-message "32-bit rpd doesn't support ecmp greater than 128";
         }
         enum "192" {
           description "Maximum 192 ECMP routes";
           junos:must "(!(\"system processes routing force-32-bit\"))";
           junos:must-message "32-bit rpd doesn't support ecmp greater than 128";
         }
         enum "224" {
           description "Maximum 224 ECMP routes";
           junos:must "(!(\"system processes routing force-32-bit\"))";
           junos:must-message "32-bit rpd doesn't support ecmp greater than 128";
         }
         enum "256" {
           description "Maximum 256 ECMP routes";
           junos:must "(!(\"system processes routing force-32-bit\"))";
           junos:must-message "32-bit rpd doesn't support ecmp greater than 128";
         }
         enum "288" {
           description "Maximum 288 ECMP routes";
           junos:must "(!(\"system processes routing force-32-bit\"))";
           junos:must-message "32-bit rpd doesn't support ecmp greater than 128";
         }
         enum "320" {
           description "Maximum 320 ECMP routes";
           junos:must "(!(\"system processes routing force-32-bit\"))";
           junos:must-message "32-bit rpd doesn't support ecmp greater than 128";
         }
         enum "352" {
           description "Maximum 352 ECMP routes";
           junos:must "(!(\"system processes routing force-32-bit\"))";
           junos:must-message "32-bit rpd doesn't support ecmp greater than 128";
         }
         enum "384" {
           description "Maximum 384 ECMP routes";
           junos:must "(!(\"system processes routing force-32-bit\"))";
           junos:must-message "32-bit rpd doesn't support ecmp greater than 128";
         }
         enum "416" {
           description "Maximum 416 ECMP routes";
           junos:must "(!(\"system processes routing force-32-bit\"))";
           junos:must-message "32-bit rpd doesn't support ecmp greater than 128";
         }
         enum "448" {
           description "Maximum 448 ECMP routes";
           junos:must "(!(\"system processes routing force-32-bit\"))";
           junos:must-message "32-bit rpd doesn't support ecmp greater than 128";
         }
         enum "480" {
           description "Maximum 480 ECMP routes";
           junos:must "(!(\"system processes routing force-32-bit\"))";
           junos:must-message "32-bit rpd doesn't support ecmp greater than 128";
         }
         enum "512" {
           description "Maximum 512 ECMP routes";
           junos:must "(!(\"system processes routing force-32-bit\"))";
           junos:must-message "32-bit rpd doesn't support ecmp greater than 128";
         }
       }
     }
     container redundancy {
       description "Redundancy settings";
       uses chassis_redundancy_type;
     }
     container routing-engine {
       description "Routing Engine settings";
       uses chassis_routing_engine_type;
     }
     container aggregated-devices {
       description "Aggregated devices configuration";
       uses chassis_agg_dev_type;
     }
     list disk-partition {
       key name;
       ordered-by user;
       description "Chassis disk monitor configuration";
       leaf name {
         description "Choose disk partition to monitor";
         junos:cli-feature "nokeyword";
         type enumeration {
           enum "/var" {
             description "Monitor /var partition";
           }
           enum "/config" {
             description "Monitor /config partition";
           }
         }
       }
       uses apply-advanced;
       list level {
         key name;
         ordered-by user;
         description "Threshold level";
         leaf name {
           junos:cli-feature "nokeyword";
           type enumeration {
             enum "high" {
               description "Set high level of threshold";
             }
             enum "full" {
               description "Set full level of threshold";
             }
           }
         }
         uses apply-advanced;
         container free-space {
           junos:cli-feature "oneliner";
           description "Enter threshold value & choose the metric";
           leaf thres-free {
             description "Enter free space threshold value";
             junos:cli-feature "nokeyword";
             type union {
               type string {
                 pattern "<.*>|$.*";
               }
               type uint32 {
                 range "0 .. 100";
               }
             }
           }
           choice thres-metric {
             case case_1 {
               leaf percent {
                 description "Free space threshold in %";
                 type empty;
               }
             }
             case case_2 {
               leaf mb {
                 description "Free space threshold in MB";
                 type empty;
               }
             }
           }
         }
       }
     }
     container container-devices {
       description "Container devices configuration";
       uses chassisd_agg_container_type;
     }
     container pseudowire-service {
       description "Pseudowire L3 termination device configuration";
       presence "enable pseudowire-service";
       uses chassis-pw-type;
     }
     container fabric {
       description "Switch fabric settings";
       junos:cli-feature "oneliner-plus";
       uses chassis_fabric_type;
     }
     list fpc {
       key name;
       description "Flexible PIC Concentrator parameters";
       junos:must "((!(any \". <*> vpn-localization\") || !(\"virtual-chassis\")))";
       junos:must-message "vpn-localization cannot be configured on virtual-chassis";
       uses chassis_fpc_type;
     }
     leaf node-id {
       description "Chassis identifier";
       status deprecated;
       junos:must "(!(any \"chassis fpc <*> pfe <*> node $$\"))";
       junos:must-message "node-id needs to be unique across chassis fpc<> pfe<> node<>";
       type union {
         type string {
           pattern "<.*>|$.*";
         }
         type uint64 {
           range "1 .. 18446744073709551615";
         }
       }
     }
     container p4rt {
       presence "enable p4rt";
       description "Chassis p4rt";
       uses apply-advanced;
       leaf node-id {
         description "Chassis identifier";
         junos:must "(!(any \"chassis fpc <*> pfe <*> node $$\"))";
         junos:must-message "node-id needs to be unique across chassis fpc<> pfe<> node<>";
         type union {
           type string {
             pattern "<.*>|$.*";
           }
           type uint64 {
             range "1 .. 18446744073709551615";
           }
         }
       }
     }
     list cb {
       key name;
       description "Control Board parameters";
       uses chassis_cb_type;
     }
     leaf disable-power-management {
       description "Disable Power Management in this chassis";
       type empty;
     }
     leaf dedicated-ukern-cpu {
       description "Run Microkernel on a dedicated CPU core";
       junos:must "(!(\"chassis realtime-ukern-thread\"))";
       junos:must-message "dedicated-ukern-cpu and  realtime-ukern-thread are mutually exclusive";
       type empty;
     }
     leaf realtime-ukern-thread {
       description "Run Microkernel on a realtime CPU thread";
       junos:must "(!(\"chassis dedicated-ukern-cpu\"))";
       junos:must-message "dedicated-ukern-cpu and  realtime-ukern-thread are mutually exclusive";
       type empty;
     }
     container fpc-feb-connectivity {
       description "Connectivity between Flexible PIC Concentrators and Forwarding Engine Boards";
       uses apply-advanced;
       list fpc {
         key name;
         leaf name {
           description "FPC slot number";
           junos:cli-feature "nokeyword";
           type union {
             type string {
               pattern "<.*>|$.*";
             }
             type uint32;
           }
         }
         uses apply-advanced;
         container feb {
           junos:cli-feature "oneliner";
           description "FEB slot number";
           choice feb-slot-choice {
             case case_1 {
               leaf none {
                 description "FPC not connected to any FEB";
                 type empty;
               }
             }
             case case_2 {
               leaf feb-slot {
                 description "FEB slot number";
                 junos:cli-feature "nokeyword";
                 type union {
                   type string {
                     pattern "<.*>|$.*";
                   }
                   type uint32;
                 }
               }
             }
           }
         }
       }
     }
     container ioc-npc-connectivity {
       description "Connectivity between IOC and NPC";
       uses apply-advanced;
       list ioc {
         key name;
         leaf name {
           description "IOC-FPC slot number";
           junos:cli-feature "nokeyword";
           type union {
             type string {
               pattern "<.*>|$.*";
             }
             type uint32;
           }
         }
         uses apply-advanced;
         container npc {
           junos:cli-feature "oneliner";
           description "NPC-FPC slot number";
           choice npc-slot-choice {
             case case_1 {
               leaf none {
                 description "IOC not connected to any NPC";
                 type empty;
               }
             }
             case case_2 {
               leaf npc-slot {
                 description "NPC-FPC slot number";
                 junos:cli-feature "nokeyword";
                 type union {
                   type string {
                     pattern "<.*>|$.*";
                   }
                   type uint32;
                 }
               }
             }
           }
         }
       }
     }
     container pem {
       description "Power supply (PEM) parameters";
       uses chassis_pem_type;
     }
     container sib {
       description "Switch Interface Board parameters";
       uses chassis_sib_type;
     }
     container fabric-card {
       description "Fabric card parameters";
       presence "enable fabric-card";
       uses chassis_fabric_cards_type;
     }
     container tfeb {
       description "Taz Forwarding Engine Board parameters";
       uses chassis_feb_type;
     }
     container alarm {
       description "Global alarm settings";
       uses chassis_alarm_type;
     }
     leaf slow-pfe-alarm {
       description "Enable slow (potential) PFE alarm";
       type empty;
     }
     leaf onbox-av-load-flavor {
       description "Select onbox anti-virus traffic load flavor";
       type enumeration {
         enum "heavy" {
           description "Allocates additional resources for improved performance";
           junos:must "(!(\"security forwarding-options resource-manager enhanced-logging\"))";
           junos:must-message "cannot configure onbox-av-load-flavor when enhanced logging is configured";
         }
       }
     }
     leaf ambient-temperature {
       description "Chassis ambient-temperature value in degree celsius";
       type enumeration {
         enum "55C" {
           description "55 degree celsius";
         }
         enum "40C" {
           description "40 degree celsius";
         }
         enum "25C" {
           description "25 degree celsius";
         }
         enum "32C" {
           description "32 degree celsius";
         }
       }
     }
     container resource-watch {
       description "Chassis routing engine resource watch configuration";
       uses apply-advanced;
       leaf resource-watch-enable {
         description "Enable resource watch";
         type empty;
       }
       leaf cpu-statistics {
         description "Set statistics collection, 0 disable";
         units "seconds";
         type union {
           type string {
             pattern "<.*>|$.*";
           }
           type uint32 {
             range "0 .. 604800";
           }
         }
       }
       leaf junos-statistics {
         description "Set statistics collection, 0 disable";
         units "seconds";
         type union {
           type string {
             pattern "<.*>|$.*";
           }
           type uint32 {
             range "0 .. 604800";
           }
         }
       }
       leaf orange-zone-enable {
         description "Enable orange zone";
         type empty;
       }
       leaf orange-zone-threshold {
         description "Set orange zone value (CPU idle %), default 20";
         type union {
           type string {
             pattern "<.*>|$.*";
           }
           type uint32 {
             range "1 .. 99";
           }
         }
       }
       leaf red-zone-enable {
         description "Enable red zone";
         type empty;
       }
       leaf red-zone-cpu-threshold {
         description "Set red zone value (CPU idle %), default 10";
         type union {
           type string {
             pattern "<.*>|$.*";
           }
           type uint32 {
             range "1 .. 99";
           }
         }
       }
       leaf red-zone-jkl-threshold {
         description "Set red zone value (Junos load %), default 50";
         type union {
           type string {
             pattern "<.*>|$.*";
           }
           type uint32 {
             range "1 .. 99";
           }
         }
       }
       leaf red-zone-snmp-enable {
         description "Enable red zone snmp";
         type empty;
       }
     }
     leaf network-services {
       description "Chassis network services configuration";
       type enumeration {
         enum "ip" {
           description "IP network services";
         }
         enum "ethernet" {
           description "Ethernet network services";
           junos:must "((!(any \"interfaces <*> unit <*> family inet accounting source-class-usage\") && (!(any \"interfaces <*> unit <*> family inet accounting destination-class-usage\") && (!(any \"interfaces <*> unit <*> family inet6 accounting source-class-usage\") && (!(any \"interfaces <*> unit <*> family inet6 accounting destination-class-usage\") && (!(any \"logical-systems <*> interfaces <*> unit <*> family inet accounting source-class-usage\") && (!(any \"logical-systems <*> interfaces <*> unit <*> family inet accounting destination-class-usage\") && (!(any \"logical-systems <*> interfaces <*> unit <*> family inet6 accounting source-class-usage\") && !(any \"logical-systems <*> interfaces <*> unit <*> family inet6 accounting destination-class-usage\")))))))))";
           junos:must-message "Cannot configure 'accounting source-class-usage or destination-class-usage' under network-services ethernet";
           junos:must "((!(\"routing-options forwarding-table unicast-reverse-path\") && (!(any \"routing-instances <*> routing-options forwarding-table unicast-reverse-path\") && (!(any \"logical-systems <*> routing-options forwarding-table unicast-reverse-path\") && !(any \"logical-systems <*> routing-instances <*> routing-options forwarding-table unicast-reverse-path\")))))";
           junos:must-message "Cannot configure 'unicast-reverse-path' under network-services ethernet";
           junos:must "((!(any \"interfaces <*> unit <*> family inet rpf-check\") && (!(any \"interfaces <*> unit <*> family inet6 rpf-check\") && (!(any \"logical-systems <*> interfaces <*> unit <*> family inet rpf-check\") && !(any \"logical-systems <*> interfaces <*> unit <*> family inet6 rpf-check\")))))";
           junos:must-message "Cannot configure 'rpf-check' under network-services ethernet";
           junos:must "((!(any \"policy-options policy-statement <*> then source-class\") && (!(any \"policy-options policy-statement <*> term <*> then source-class\") && (!(any \"policy-options policy-statement <*> then destination-class\") && (!(any \"policy-options policy-statement <*> term <*> then destination-class\") && (!(any \"policy-options policy-statement <*> from route-filter <*> <*>  source-class\") && (!(any \"policy-options policy-statement <*> term <*> from route-filter <*> <*>  source-class\") && (!(any \"policy-options policy-statement <*> from route-filter <*> <*> destination-class\") && (!(any \"policy-options policy-statement <*> term <*> from route-filter <*> <*>  destination-class\") && (!(any \"logical-systems <*> policy-options policy-statement <*> then source-class\") && (!(any \"logical-systems <*> policy-options policy-statement <*> term <*> then source-class\") && (!(any \"logical-systems <*> policy-options policy-statement <*> then destination-class\") && (!(any \"logical-systems <*> policy-options policy-statement <*> term <*> then destination-class\") && (!(any \"logical-systems <*> policy-options policy-statement <*> from route-filter <*> <*>  source-class\") && (!(any \"logical-systems <*> policy-options policy-statement <*> term <*> from route-filter <*> <*>  source-class\") && (!(any \"logical-systems <*> policy-options policy-statement <*> from route-filter <*> <*> destination-class\") && !(any \"logical-systems <*> policy-options policy-statement <*> term <*> from route-filter <*> <*>  destination-class\")))))))))))))))))";
           junos:must-message "Cannot configure 'destination-class|source-class' under network-services ethernet";
           junos:must "((!(\"protocols bgp family inet any\") && (!(\"protocols bgp family inet flow\") && (!(\"protocols bgp family inet multicast\") && (!(any \"protocols bgp group <*> family inet any\") && (!(any \"protocols bgp group <*> family inet flow\") && (!(any \"protocols bgp group <*> family inet multicast\") && (!(any \"protocols bgp group <*> neighbor <*> family inet any\") && (!(any \"protocols bgp group <*> neighbor <*> family inet flow\") && (!(any \"protocols bgp group <*> neighbor <*> family inet multicast\") && (!(\"protocols bgp family inet-vpn any\") && (!(\"protocols bgp family inet-vpn flow\") && (!(\"protocols bgp family inet-vpn multicast\") && (!(any \"protocols bgp group <*> family inet-vpn any\") && (!(any \"protocols bgp group <*> family inet-vpn flow\") && (!(any \"protocols bgp group <*> family inet-vpn multicast\") && (!(any \"protocols bgp group <*> neighbor <*> family inet-vpn any\") && (!(any \"protocols bgp group <*> neighbor <*> family inet-vpn flow\") && (!(any \"protocols bgp group <*> neighbor <*> family inet-vpn multicast\") && (!(\"protocols bgp family inet6\") && (!(any \"protocols bgp group <*> family inet6\") && (!(any \"protocols bgp group <*> neighbor <*> family inet6\") && (!(\"protocols bgp family inet6-vpn\") && (!(any \"protocols bgp group <*> family inet6-vpn\") && (!(any \"protocols bgp group <*> neighbor <*> family inet6-vpn\") && (!(\"protocols bgp family inet-mvpn\") && (!(any \"protocols bgp group <*> family inet-mvpn\") && (!(any \"protocols bgp group <*> neighbor <*> family inet-mvpn\") && (!(\"protocols bgp family inet6-mvpn\") && (!(any \"protocols bgp group <*> family inet6-mvpn\") && (!(any \"protocols bgp group <*> neighbor <*> family inet6-mvpn\") && (!(\"protocols bgp family iso\") && (!(any \"protocols bgp group <*> family iso\") && (!(any \"protocols bgp group <*> neighbor <*> family iso\") && (!(\"protocols bgp family iso-vpn\") && (!(any \"protocols bgp group <*> family iso-vpn\") && (!(any \"protocols bgp group <*> neighbor <*> family iso-vpn\") && (!(\"protocols bgp family atmvpn\") && (!(any \"protocols bgp group <*> family atmvpn\") && (!(any \"protocols bgp group <*> neighbor <*> family atmvpn\") && (!(any \"logical-systems <*> protocols bgp family inet any\") && (!(any \"logical-systems <*> protocols bgp family inet flow\") && (!(any \"logical-systems <*> protocols bgp family inet multicast\") && (!(any \"logical-systems <*> protocols bgp group <*> family inet any\") && (!(any \"logical-systems <*> protocols bgp group <*> family inet flow\") && (!(any \"logical-systems <*> protocols bgp group <*> family inet multicast\") && (!(any \"logical-systems <*> protocols bgp group <*> neighbor <*> family inet any\") && (!(any \"logical-systems <*> protocols bgp group <*> neighbor <*> family inet flow\") && (!(any \"logical-systems <*> protocols bgp group <*> neighbor <*> family inet multicast\") && (!(any \"logical-systems <*> protocols bgp family inet-vpn any\") && (!(any \"logical-systems <*> protocols bgp family inet-vpn flow\") && (!(any \"logical-systems <*> protocols bgp family inet-vpn multicast\") && (!(any \"logical-systems <*> protocols bgp group <*> family inet-vpn any\") && (!(any \"logical-systems <*> protocols bgp group <*> family inet-vpn flow\") && (!(any \"logical-systems <*> protocols bgp group <*> family inet-vpn multicast\") && (!(any \"logical-systems <*> protocols bgp group <*> neighbor <*> family inet-vpn any\") && (!(any \"logical-systems <*> protocols bgp group <*> neighbor <*> family inet-vpn flow\") && (!(any \"logical-systems <*> protocols bgp group <*> neighbor <*> family inet-vpn multicast\") && (!(any \"logical-systems <*> protocols bgp family inet6\") && (!(any \"logical-systems <*> protocols bgp group <*> family inet6\") && (!(any \"logical-systems <*> protocols bgp group <*> neighbor <*> family inet6\") && (!(any \"logical-systems <*> protocols bgp family inet6-vpn\") && (!(any \"logical-systems <*> protocols bgp group <*> family inet6-vpn\") && (!(any \"protocols bgp group <*> neighbor <*> family inet6-vpn\") && (!(any \"logical-systems <*> protocols bgp family inet-mvpn\") && (!(any \"logical-systems <*> protocols bgp group <*> family inet-mvpn\") && (!(any \"protocols bgp group <*> neighbor <*> family inet-mvpn\") && (!(any \"logical-systems <*> protocols bgp family inet6-mvpn\") && (!(any \"logical-systems <*> protocols bgp group <*> family inet6-mvpn\") && (!(any \"logical-systems <*> protocols bgp group <*> neighbor <*> family inet6-mvpn\") && (!(any \"logical-systems <*> protocols bgp family iso\") && (!(any \"logical-systems <*> protocols bgp group <*> family iso\") && (!(any \"protocols bgp group <*> neighbor <*> family iso\") && (!(any \"logical-systems <*> protocols bgp family iso-vpn\") && (!(any \"logical-systems <*> protocols bgp group <*> family iso-vpn\") && (!(any \"logical-systems <*> protocols bgp group <*> neighbor <*> family iso-vpn\") && (!(any \"logical-systems <*> protocols bgp family atmvpn\") && (!(any \"logical-systems <*> protocols bgp group <*> family atmvpn\") && !(any \"protocols bgp group <*> neighbor <*> family atmvpn\")))))))))))))))))))))))))))))))))))))))))))))))))))))))))))))))))))))))))))))))";
           junos:must-message "Only BGP groups with 'family inet unicast, inet labeled-unicast, inet-vpn unicast, l2vpn and route-target' are supported under network-services ethernet";
         }
         enum "enhanced-ip" {
           description "Enhanced IP network services";
         }
         enum "enhanced-ethernet" {
           description "Enhanced ethernet network services";
         }
         enum "enhanced-mode" {
           description "Enhanced network services";
         }
         enum "lan" {
           description "Ethernet LAN services";
         }
       }
     }
     container usb {
       description "USB control flags";
       uses apply-advanced;
       container storage {
         description "USB storage flags";
         uses apply-advanced;
         leaf disable {
           description "Disable USB storage";
           type empty;
         }
       }
     }
     list lcc {
       key name;
       description "Line-card chassis configuration";
       leaf name {
         description "LCC number";
         junos:cli-feature "nokeyword";
         type union {
           type string {
             pattern "<.*>|$.*";
           }
           type uint32;
         }
       }
       uses apply-advanced;
       list fpc {
         key name;
         description "Flexible PIC Concentrator parameters";
         junos:must "((!(any \". <*> vpn-localization\") || !(\"virtual-chassis\")))";
         junos:must-message "vpn-localization cannot be configured on virtual-chassis";
         uses chassis_fpc_type;
       }
       container pem {
         description "Power supply (PEM) parameters";
         uses chassis_pem_type;
       }
       choice state {
         case case_1 {
           leaf online-expected {
             description "LCC is expected to be online";
             type empty;
           }
         }
         case case_2 {
           leaf offline {
             description "LCC is expected to be offline";
             type empty;
           }
         }
       }
     }
     container lcd {
       description "Chassis LCD";
       status deprecated;
       uses apply-advanced;
       choice menu-item {
         case case_1 {
           leaf maintenance-menu {
             description "LCD maintenance menu";
             type empty;
           }
         }
       }
       choice enable-disable {
         case case_1 {
           leaf disable {
             description "Disable maintenance-menu";
             type empty;
           }
         }
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               type empty;
             }
             leaf unicast-in-lpm {
               description "Install unicast host entries in LPM table";
               type empty;
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:16K, needs reboot for VC; restarts PFE if standalone";
           }
         }
         case case_8 {
           container vxlan-gbp-l2-profile {
             presence "enable vxlan-gbp-l2-profile";
             description "MAC: 64K L3-host: 32K LPM: 16K EM:16K, needs reboot for VC; restarts PFE if standalone";
           }
         }
         case case_9 {
           container vxlan-gbp-l3-profile {
             presence "enable vxlan-gbp-l3-profile";
             description "MAC: 32K L3-host: 64K LPM: 16K EM:16K, needs reboot for VC; restarts PFE if standalone";
           }
         }
         case case_10 {
           container em-hw-profile {
             presence "enable em-hw-profile";
             description "MAC: 48K L3-host: 48K LPM: 16K EM:32K, needs reboot for VC; restarts PFE if standalone";
           }
         }
         case case_11 {
           container default-profile {
             presence "enable default-profile";
             description "MAC: 64K L3-host: 32K LPM: 24K IFP: 12K, needs reboot for VC; restarts PFE if standalone";
           }
         }
         case case_12 {
           container ifp-profile {
             presence "enable ifp-profile";
             description "MAC: 64K L3-host: 32K LPM: 12K IFP: 18K, needs reboot for VC; restarts PFE if standalone";
           }
         }
         case case_13 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     leaf loopback-firewallv6-optimization {
       description "Increase ACL scale for loopback IPv6 filters; restarts PFE";
       junos:must "(\"chassis loopback-firewall-optimization\")";
       junos:must-message "Enable loopback-firewall-optimization";
       type empty;
     }
     leaf input-firewall-optimized-profile {
       description "Optimal default filter usage when IFA/FCoe/FIPsnooping is not used; restarts PFE";
       type empty;
     }
     leaf ivacl-firewall-no-portrange-profile {
       description "L4 Src/Dst Port range optimize is not needed; restarts PFE";
       junos:must "(!(\"chassis ipvacl-firewall-l2-profile\"))";
       junos:must-message "Cannot configure ivacl-firewall-no-portrange-profile when ipvacl-firewall-l2-profile is enabled";
       type empty;
     }
     leaf iracl-firewall-ipv4-profile {
       description "IPv6 address match is not needed for IRACL filters; restarts PFE";
       type empty;
     }
     leaf ipvacl-firewall-l2-profile {
       description "Only Src/Dst MAC,VLAN,EtherType match is needed for IPACL/IVACL filters; restarts PFE";
       junos:must "(!(\"chassis ivacl-firewall-no-portrange-profile\"))";
       junos:must-message "Cannot configure ipvacl-firewall-l2-profile when ivacl-firewall-no-portrange-profile is enabled";
       type empty;
     }
     leaf loopback-firewall-optimization {
       description "Optimal TCAM use,restarts PFE(for IP rsrved multicast dest & IP ttl=0/1,config explicitly)";
       type empty;
     }
     leaf epacl-firewall-optimization {
       description "Maximizes Egress Port ACLs TCAM use and restarts PFE";
       type empty;
     }
     leaf per-logical-interface-firewall {
       description "Ingress port firewall can be supported per logical interface, restarts PFE";
       type empty;
     }
     leaf fru-poweron-sequence {
       description "FRUs power on sequence like 0 1 2 3 ... within double quotes";
       type string {
         junos:posix-pattern "^[0-9 ]+$";
         junos:pattern-message "FRU in fru poweron sequence must be a number";
       }
     }
     leaf fru-local-storage-disable {
       description "Disable and erase local storage on FPC.(FPC reboot required)";
       type empty;
     }
     leaf fpc-empolicy-profile {
       description "FPC EM Policy Profile";
       type enumeration {
         enum "low-power-mode" {
           description "Set low power mode";
         }
       }
     }
     container psm {
       description "Power supply module";
       uses apply-advanced;
     }
     leaf auto-image-upgrade {
       description "Auto image upgrade using DHCP";
       type empty;
     }
     container error {
       description "Error level configuration for all FPC";
       uses chassis_junos_fru_error_type;
     }
     container oss-map {
       description "Translate Operation Supported System's requirements";
       uses apply-advanced;
       leaf model-name {
         description "Override chassis model name for specific show/snmp output";
         type enumeration {
           enum "t640" {
             description "Set to T640's model";
           }
           enum "t1600" {
             description "Set to T1600's model";
           }
         }
       }
     }
     container jnu-management {
       description "JNU Management configuration";
       uses apply-advanced;
       leaf mode {
         description "JNU Mode";
         type enumeration {
           enum "feature-rich" {
             description "Feature Rich Mode";
           }
           enum "bng-control-plane" {
             description "BNG control-plane mode";
           }
         }
       }
       leaf satellite-name {
         description "Satellite name";
         type string;
       }
       leaf device-group {
         description "Satellite device group";
         type string;
       }
       list device-group-map {
         key name;
         ordered-by user;
         description "Common groups mapping to device groups";
         leaf name {
           description "Satellite Device Group";
           junos:cli-feature "nokeyword";
           type string;
         }
         uses apply-advanced;
         leaf-list include-groups {
           ordered-by user;
           description "Common groups list";
           type string;
         }
       }
       list satellite {
         key name;
         ordered-by user;
         description "List of satellites";
         leaf name {
           description "Satellite name";
           junos:cli-feature "nokeyword";
           type string;
         }
         uses apply-advanced;
         leaf device-group {
           description "Satellite Device Group";
           type string;
         }
         leaf model {
           description "Satellite model";
           type string;
         }
         leaf version {
           description "Satellite version";
           type string {
             junos:posix-pattern "^[[:digit:]][[:alnum:]_.-]+$";
             junos:pattern-message "Version should begin with a number";
           }
         }
       }
       leaf user {
         description "Satellite User Name";
         type string;
       }
       leaf-list controller {
         ordered-by user;
         description "Controller Name";
         type string;
       }
       leaf other-controller {
         description "Dual controller Name";
         type string;
       }
       leaf authentication {
         description "Authentication string";
         type jt:unreadable;
       }
     }
     list satellite {
       key name;
       ordered-by user;
       description "List of available satellite configurations";
       leaf name {
         description "Satellite name";
         junos:cli-feature "nokeyword";
         type string;
       }
       uses apply-advanced;
     }
     container thermal-health-check {
       presence "enable thermal-health-check";
       description "Enable Thermal Health check of the chassis";
       uses apply-advanced;
       container fet-failure-check {
         presence "enable fet-failure-check";
         uses apply-advanced;
         leaf action-onfail {
           description "Set the action when Oring FET detected";
           default "none";
           type enumeration {
             enum "none" {
               description "No action when Oring FET detected";
             }
             enum "auto-shutdown" {
               description "Shutdown when Oring FET detected";
             }
           }
         }
       }
     }
     container system-domains {
       presence "enable system-domains";
       description "Root and protected system domain configuration";
       uses apply-advanced;
       leaf root-domain-id {
         description "Root domain identifier";
         type union {
           type string {
             pattern "<.*>|$.*";
           }
           type uint32 {
             range "1 .. 3";
           }
         }
       }
       list protected-system-domains {
         key name;
         description "Protected system domain configuration";
         uses juniper-protected-system-domain;
         junos:cli-feature "homogeneous";
       }
       container traceoptions {
         description "Protected system domain traceoptions";
         uses juniper-protected-system-domain-traceoptions;
       }
     }
     container cluster {
       junos:must "((!(\"interfaces st0 unit 16000\") && (!(\"interfaces st0 unit 16001\") && (!(\"interfaces st0 unit 16002\") && (!(\"interfaces st0 unit 16003\") && (!(\"interfaces st0 unit 16004\") && (!(\"interfaces st0 unit 16005\") && (!(\"interfaces st0 unit 16006\") && (!(\"interfaces st0 unit 16007\") && (!(\"interfaces st0 unit 16008\") && (!(\"interfaces st0 unit 16009\") && (!(\"interfaces st0 unit 16010\") && (!(\"interfaces st0 unit 16011\") && (!(\"interfaces st0 unit 16012\") && (!(\"interfaces st0 unit 16013\") && (!(\"interfaces st0 unit 16014\") && (!(\"interfaces st0 unit 16015\") && (!(\"interfaces st0 unit 16016\") && (!(\"interfaces st0 unit 16017\") && (!(\"interfaces st0 unit 16018\") && (!(\"interfaces st0 unit 16019\") && (!(\"interfaces st0 unit 16020\") && (!(\"interfaces st0 unit 16021\") && (!(\"interfaces st0 unit 16022\") && (!(\"interfaces st0 unit 16023\") && (!(\"interfaces st0 unit 16024\") && (!(\"interfaces st0 unit 16025\") && (!(\"interfaces st0 unit 16026\") && (!(\"interfaces st0 unit 16027\") && (!(\"interfaces st0 unit 16028\") && (!(\"interfaces st0 unit 16029\") && (!(\"interfaces st0 unit 16030\") && (!(\"interfaces st0 unit 16031\") && (!(\"interfaces st0 unit 16032\") && (!(\"interfaces st0 unit 16033\") && (!(\"interfaces st0 unit 16034\") && (!(\"interfaces st0 unit 16035\") && (!(\"interfaces st0 unit 16036\") && (!(\"interfaces st0 unit 16037\") && (!(\"interfaces st0 unit 16038\") && (!(\"interfaces st0 unit 16039\") && (!(\"interfaces st0 unit 16d40\") && (!(\"interfaces st0 unit 16041\") && (!(\"interfaces st0 unit 16042\") && (!(\"interfaces st0 unit 16043\") && (!(\"interfaces st0 unit 16044\") && (!(\"interfaces st0 unit 16045\") && (!(\"interfaces st0 unit 16046\") && (!(\"interfaces st0 unit 16047\") && (!(\"interfaces st0 unit 16048\") && (!(\"interfaces st0 unit 16049\") && (!(\"interfaces st0 unit 16050\") && (!(\"interfaces st0 unit 16051\") && (!(\"interfaces st0 unit 16052\") && (!(\"interfaces st0 unit 16053\") && (!(\"interfaces st0 unit 16054\") && (!(\"interfaces st0 unit 16055\") && (!(\"interfaces st0 unit 16056\") && (!(\"interfaces st0 unit 16057\") && (!(\"interfaces st0 unit 16058\") && (!(\"interfaces st0 unit 16059\") && (!(\"interfaces st0 unit 16060\") && (!(\"interfaces st0 unit 16061\") && (!(\"interfaces st0 unit 16062\") && (!(\"interfaces st0 unit 16063\") && (!(\"interfaces st0 unit 16064\") && (!(\"interfaces st0 unit 16065\") && (!(\"interfaces st0 unit 16066\") && (!(\"interfaces st0 unit 16067\") && (!(\"interfaces st0 unit 16068\") && (!(\"interfaces st0 unit 16069\") && (!(\"interfaces st0 unit 16070\") && (!(\"interfaces st0 unit 16071\") && (!(\"interfaces st0 unit 16072\") && (!(\"interfaces st0 unit 16073\") && (!(\"interfaces st0 unit 16074\") && (!(\"interfaces st0 unit 16075\") && (!(\"interfaces st0 unit 16076\") && (!(\"interfaces st0 unit 16077\") && (!(\"interfaces st0 unit 16078\") && (!(\"interfaces st0 unit 16079\") && (!(\"interfaces st0 unit 16080\") && (!(\"interfaces st0 unit 16081\") && (!(\"interfaces st0 unit 16082\") && (!(\"interfaces st0 unit 16083\") && (!(\"interfaces st0 unit 16084\") && (!(\"interfaces st0 unit 16085\") && (!(\"interfaces st0 unit 16086\") && (!(\"interfaces st0 unit 16087\") && (!(\"interfaces st0 unit 16088\") && (!(\"interfaces st0 unit 16089\") && (!(\"interfaces st0 unit 16090\") && (!(\"interfaces st0 unit 16091\") && (!(\"interfaces st0 unit 16092\") && (!(\"interfaces st0 unit 16093\") && (!(\"interfaces st0 unit 16094\") && (!(\"interfaces st0 unit 16095\") && (!(\"interfaces st0 unit 16096\") && (!(\"interfaces st0 unit 16097\") && (!(\"interfaces st0 unit 16098\") && (!(\"interfaces st0 unit 16099\") && (!(\"interfaces st0 unit 16100\") && (!(\"interfaces st0 unit 16101\") && (!(\"interfaces st0 unit 16102\") && (!(\"interfaces st0 unit 16103\") && (!(\"interfaces st0 unit 16104\") && (!(\"interfaces st0 unit 16105\") && (!(\"interfaces st0 unit 16106\") && (!(\"interfaces st0 unit 16107\") && (!(\"interfaces st0 unit 16108\") && (!(\"interfaces st0 unit 16109\") && (!(\"interfaces st0 unit 16110\") && (!(\"interfaces st0 unit 16111\") && (!(\"interfaces st0 unit 16112\") && (!(\"interfaces st0 unit 16113\") && (!(\"interfaces st0 unit 16114\") && (!(\"interfaces st0 unit 16115\") && (!(\"interfaces st0 unit 16116\") && (!(\"interfaces st0 unit 16117\") && (!(\"interfaces st0 unit 16118\") && (!(\"interfaces st0 unit 16119\") && (!(\"interfaces st0 unit 16120\") && (!(\"interfaces st0 unit 16121\") && (!(\"interfaces st0 unit 16122\") && (!(\"interfaces st0 unit 16123\") && (!(\"interfaces st0 unit 16124\") && (!(\"interfaces st0 unit 16125\") && (!(\"interfaces st0 unit 16126\") && (!(\"interfaces st0 unit 16127\") && (!(\"interfaces st0 unit 16128\") && (!(\"interfaces st0 unit 16129\") && (!(\"interfaces st0 unit 16130\") && (!(\"interfaces st0 unit 16131\") && (!(\"interfaces st0 unit 16132\") && (!(\"interfaces st0 unit 16133\") && (!(\"interfaces st0 unit 16134\") && (!(\"interfaces st0 unit 16135\") && (!(\"interfaces st0 unit 16136\") && (!(\"interfaces st0 unit 16137\") && (!(\"interfaces st0 unit 16138\") && (!(\"interfaces st0 unit 16139\") && (!(\"interfaces st0 unit 16140\") && (!(\"interfaces st0 unit 16141\") && (!(\"interfaces st0 unit 16142\") && (!(\"interfaces st0 unit 16143\") && (!(\"interfaces st0 unit 16144\") && (!(\"interfaces st0 unit 16145\") && (!(\"interfaces st0 unit 16146\") && (!(\"interfaces st0 unit 16147\") && (!(\"interfaces st0 unit 16148\") && (!(\"interfaces st0 unit 16149\") && (!(\"interfaces st0 unit 16150\") && (!(\"interfaces st0 unit 16151\") && (!(\"interfaces st0 unit 16152\") && (!(\"interfaces st0 unit 16153\") && (!(\"interfaces st0 unit 16154\") && (!(\"interfaces st0 unit 16155\") && (!(\"interfaces st0 unit 16156\") && (!(\"interfaces st0 unit 16157\") && (!(\"interfaces st0 unit 16158\") && (!(\"interfaces st0 unit 16159\") && (!(\"interfaces st0 unit 16160\") && (!(\"interfaces st0 unit 16161\") && (!(\"interfaces st0 unit 16162\") && (!(\"interfaces st0 unit 16163\") && (!(\"interfaces st0 unit 16164\") && (!(\"interfaces st0 unit 16165\") && (!(\"interfaces st0 unit 16166\") && (!(\"interfaces st0 unit 16167\") && (!(\"interfaces st0 unit 16168\") && (!(\"interfaces st0 unit 16169\") && (!(\"interfaces st0 unit 16170\") && (!(\"interfaces st0 unit 16171\") && (!(\"interfaces st0 unit 16172\") && (!(\"interfaces st0 unit 16173\") && (!(\"interfaces st0 unit 16174\") && (!(\"interfaces st0 unit 16175\") && (!(\"interfaces st0 unit 16176\") && (!(\"interfaces st0 unit 16177\") && (!(\"interfaces st0 unit 16178\") && (!(\"interfaces st0 unit 16179\") && (!(\"interfaces st0 unit 16180\") && (!(\"interfaces st0 unit 16181\") && (!(\"interfaces st0 unit 16182\") && (!(\"interfaces st0 unit 16183\") && (!(\"interfaces st0 unit 16184\") && (!(\"interfaces st0 unit 16185\") && (!(\"interfaces st0 unit 16186\") && (!(\"interfaces st0 unit 16187\") && (!(\"interfaces st0 unit 16188\") && (!(\"interfaces st0 unit 16189\") && (!(\"interfaces st0 unit 16190\") && (!(\"interfaces st0 unit 16191\") && (!(\"interfaces st0 unit 16192\") && (!(\"interfaces st0 unit 16193\") && (!(\"interfaces st0 unit 16194\") && (!(\"interfaces st0 unit 16195\") && (!(\"interfaces st0 unit 16196\") && (!(\"interfaces st0 unit 16197\") && (!(\"interfaces st0 unit 16198\") && (!(\"interfaces st0 unit 16199\") && (!(\"interfaces st0 unit 16200\") && (!(\"interfaces st0 unit 16201\") && (!(\"interfaces st0 unit 16202\") && (!(\"interfaces st0 unit 16203\") && (!(\"interfaces st0 unit 16204\") && (!(\"interfaces st0 unit 16205\") && (!(\"interfaces st0 unit 16206\") && (!(\"interfaces st0 unit 16207\") && (!(\"interfaces st0 unit 16208\") && (!(\"interfaces st0 unit 16209\") && (!(\"interfaces st0 unit 16210\") && (!(\"interfaces st0 unit 16211\") && (!(\"interfaces st0 unit 16212\") && (!(\"interfaces st0 unit 16213\") && (!(\"interfaces st0 unit 16214\") && (!(\"interfaces st0 unit 16215\") && (!(\"interfaces st0 unit 16216\") && (!(\"interfaces st0 unit 16217\") && (!(\"interfaces st0 unit 16218\") && (!(\"interfaces st0 unit 16219\") && (!(\"interfaces st0 unit 16220\") && (!(\"interfaces st0 unit 16221\") && (!(\"interfaces st0 unit 16222\") && (!(\"interfaces st0 unit 16223\") && (!(\"interfaces st0 unit 16224\") && (!(\"interfaces st0 unit 16225\") && (!(\"interfaces st0 unit 16226\") && (!(\"interfaces st0 unit 16227\") && (!(\"interfaces st0 unit 16228\") && (!(\"interfaces st0 unit 16229\") && (!(\"interfaces st0 unit 16230\") && (!(\"interfaces st0 unit 16231\") && (!(\"interfaces st0 unit 16232\") && (!(\"interfaces st0 unit 16233\") && (!(\"interfaces st0 unit 16234\") && (!(\"interfaces st0 unit 16235\") && (!(\"interfaces st0 unit 16236\") && (!(\"interfaces st0 unit 16237\") && (!(\"interfaces st0 unit 16238\") && (!(\"interfaces st0 unit 16239\") && (!(\"interfaces st0 unit 16240\") && (!(\"interfaces st0 unit 16241\") && (!(\"interfaces st0 unit 16242\") && (!(\"interfaces st0 unit 16243\") && (!(\"interfaces st0 unit 16244\") && (!(\"interfaces st0 unit 16245\") && (!(\"interfaces st0 unit 16246\") && (!(\"interfaces st0 unit 16247\") && (!(\"interfaces st0 unit 16248\") && (!(\"interfaces st0 unit 16249\") && (!(\"interfaces st0 unit 16250\") && (!(\"interfaces st0 unit 16251\") && (!(\"interfaces st0 unit 16252\") && (!(\"interfaces st0 unit 16253\") && (!(\"interfaces st0 unit 16254\") && (!(\"interfaces st0 unit 16255\") && (!(\"interfaces st0 unit 16256\") && (!(\"interfaces st0 unit 16257\") && (!(\"interfaces st0 unit 16258\") && (!(\"interfaces st0 unit 16259\") && (!(\"interfaces st0 unit 16260\") && (!(\"interfaces st0 unit 16261\") && (!(\"interfaces st0 unit 16262\") && (!(\"interfaces st0 unit 16263\") && (!(\"interfaces st0 unit 16264\") && (!(\"interfaces st0 unit 16265\") && (!(\"interfaces st0 unit 16266\") && (!(\"interfaces st0 unit 16267\") && (!(\"interfaces st0 unit 16268\") && (!(\"interfaces st0 unit 16269\") && (!(\"interfaces st0 unit 16270\") && (!(\"interfaces st0 unit 16271\") && (!(\"interfaces st0 unit 16272\") && (!(\"interfaces st0 unit 16273\") && (!(\"interfaces st0 unit 16274\") && (!(\"interfaces st0 unit 16275\") && (!(\"interfaces st0 unit 16276\") && (!(\"interfaces st0 unit 16277\") && (!(\"interfaces st0 unit 16278\") && (!(\"interfaces st0 unit 16279\") && (!(\"interfaces st0 unit 16280\") && (!(\"interfaces st0 unit 16281\") && (!(\"interfaces st0 unit 16282\") && (!(\"interfaces st0 unit 16283\") && (!(\"interfaces st0 unit 16284\") && (!(\"interfaces st0 unit 16285\") && (!(\"interfaces st0 unit 16286\") && (!(\"interfaces st0 unit 16287\") && (!(\"interfaces st0 unit 16288\") && (!(\"interfaces st0 unit 16289\") && (!(\"interfaces st0 unit 16290\") && (!(\"interfaces st0 unit 16291\") && (!(\"interfaces st0 unit 16292\") && (!(\"interfaces st0 unit 16293\") && (!(\"interfaces st0 unit 16294\") && (!(\"interfaces st0 unit 16295\") && (!(\"interfaces st0 unit 16296\") && (!(\"interfaces st0 unit 16297\") && (!(\"interfaces st0 unit 16298\") && (!(\"interfaces st0 unit 16299\") && (!(\"interfaces st0 unit 16300\") && (!(\"interfaces st0 unit 16301\") && (!(\"interfaces st0 unit 16302\") && (!(\"interfaces st0 unit 16303\") && (!(\"interfaces st0 unit 16304\") && (!(\"interfaces st0 unit 16305\") && (!(\"interfaces st0 unit 16306\") && (!(\"interfaces st0 unit 16307\") && (!(\"interfaces st0 unit 16308\") && (!(\"interfaces st0 unit 16309\") && (!(\"interfaces st0 unit 16310\") && (!(\"interfaces st0 unit 16311\") && (!(\"interfaces st0 unit 16312\") && (!(\"interfaces st0 unit 16313\") && (!(\"interfaces st0 unit 16314\") && (!(\"interfaces st0 unit 16315\") && (!(\"interfaces st0 unit 16316\") && (!(\"interfaces st0 unit 16317\") && (!(\"interfaces st0 unit 16318\") && (!(\"interfaces st0 unit 16319\") && (!(\"interfaces st0 unit 16320\") && (!(\"interfaces st0 unit 16321\") && (!(\"interfaces st0 unit 16322\") && (!(\"interfaces st0 unit 16323\") && (!(\"interfaces st0 unit 16324\") && (!(\"interfaces st0 unit 16325\") && (!(\"interfaces st0 unit 16326\") && (!(\"interfaces st0 unit 16327\") && (!(\"interfaces st0 unit 16328\") && (!(\"interfaces st0 unit 16329\") && (!(\"interfaces st0 unit 16330\") && (!(\"interfaces st0 unit 16331\") && (!(\"interfaces st0 unit 16332\") && (!(\"interfaces st0 unit 16333\") && (!(\"interfaces st0 unit 16334\") && (!(\"interfaces st0 unit 16335\") && (!(\"interfaces st0 unit 16336\") && (!(\"interfaces st0 unit 16337\") && (!(\"interfaces st0 unit 16338\") && (!(\"interfaces st0 unit 16339\") && (!(\"interfaces st0 unit 16340\") && (!(\"interfaces st0 unit 16341\") && (!(\"interfaces st0 unit 16342\") && (!(\"interfaces st0 unit 16343\") && (!(\"interfaces st0 unit 16344\") && (!(\"interfaces st0 unit 16345\") && (!(\"interfaces st0 unit 16346\") && (!(\"interfaces st0 unit 16347\") && (!(\"interfaces st0 unit 16348\") && (!(\"interfaces st0 unit 16349\") && (!(\"interfaces st0 unit 16350\") && (!(\"interfaces st0 unit 16351\") && (!(\"interfaces st0 unit 16352\") && (!(\"interfaces st0 unit 16353\") && (!(\"interfaces st0 unit 16354\") && (!(\"interfaces st0 unit 16355\") && (!(\"interfaces st0 unit 16356\") && (!(\"interfaces st0 unit 16357\") && (!(\"interfaces st0 unit 16358\") && (!(\"interfaces st0 unit 16359\") && (!(\"interfaces st0 unit 16360\") && (!(\"interfaces st0 unit 16361\") && (!(\"interfaces st0 unit 16362\") && (!(\"interfaces st0 unit 16363\") && (!(\"interfaces st0 unit 16364\") && (!(\"interfaces st0 unit 16365\") && (!(\"interfaces st0 unit 16366\") && (!(\"interfaces st0 unit 16367\") && (!(\"interfaces st0 unit 16368\") && (!(\"interfaces st0 unit 16369\") && (!(\"interfaces st0 unit 16370\") && (!(\"interfaces st0 unit 16371\") && (!(\"interfaces st0 unit 16372\") && (!(\"interfaces st0 unit 16373\") && (!(\"interfaces st0 unit 16374\") && (!(\"interfaces st0 unit 16375\") && (!(\"interfaces st0 unit 16376\") && (!(\"interfaces st0 unit 16377\") && (!(\"interfaces st0 unit 16378\") && (!(\"interfaces st0 unit 16379\") && (!(\"interfaces st0 unit 16380\") && (!(\"interfaces st0 unit 16381\") && (!(\"interfaces st0 unit 16382\") && (!(\"interfaces st0 unit 16383\") && (!(\"interfaces st0 unit 16384\") && !(\"interfaces st0 unit 16385\")))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))";
       junos:must-message "st0 unit 16000 to 16385 is disallowed in SRX HA mode";
       description "Chassis cluster configuration";
       uses apply-advanced;
       container traceoptions {
         description "Set chassis cluster traceoptions";
         uses apply-advanced;
         leaf no-remote-trace {
           description "Disable remote tracing";
           junos:must "(\"system tracing\")";
           junos:must-message "'no-remote-trace' is valid only when [system tracing] is configured";
           type empty;
         }
         container file {
           junos:cli-feature "oneliner";
           description "Trace file information";
           leaf filename {
             description "Name of file in which to write trace information";
             junos:cli-feature "nokeyword";
             type string {
               length "1 .. 1024";
               junos:posix-pattern "![/ %]";
               junos:pattern-message "Must not contain \'/\', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           junos:cli-feature "oneliner";
           description "Tracing parameters";
           leaf name {
             junos:cli-feature "nokeyword";
             type enumeration {
               enum "cli" {
                 description "Trace CLI events";
               }
               enum "configuration" {
                 description "Trace configuration events";
               }
               enum "eventlib" {
                 description "Trace event library events";
               }
               enum "fsm" {
                 description "Trace finite state machine events";
               }
               enum "heartbeat" {
                 description "Trace JSRPD heartbeats";
               }
               enum "interface" {
                 description "Trace interface related events";
               }
               enum "routing-socket" {
                 description "Trace routing socket events";
               }
               enum "uspipc" {
                 description "Trace USP IPC events";
               }
               enum "init" {
                 description "Trace initialization events";
               }
               enum "socket" {
                 description "Trace socket events";
               }
               enum "snmp" {
                 description "Trace snmp events";
               }
               enum "ip-monitoring" {
                 description "Trace IP monitoring events";
               }
               enum "hw-monitoring" {
                 description "Trace HW  monitoring events";
               }
               enum "fabric-monitoring" {
                 description "Trace fabric monitoring events";
               }
               enum "health-monitoring" {
                 description "Trace health monitoring events";
               }
               enum "schedule-monitoring" {
                 description "Trace schedule monitoring events";
               }
               enum "heartbeat-tlv" {
                 description "Trace TLV based heart-beat";
               }
               enum "ha-peer" {
                 description "Trace HA peer related info";
               }
               enum "srg" {
                 description "Trace HA srg related info";
               }
               enum "all" {
                 description "Trace all events";
               }
             }
           }
         }
         leaf level {
           description "Set level of tracing";
           default "info";
           type enumeration {
             enum "emergency" {
               description "Match emergency conditions";
             }
             enum "alert" {
               description "Match alert conditions";
             }
             enum "critical" {
               description "Match critical conditions";
             }
             enum "error" {
               description "Match error conditions";
             }
             enum "warning" {
               description "Match warning messages";
             }
             enum "notice" {
               description "Match notice level messages";
             }
             enum "info" {
               description "Match informational messages";
             }
             enum "debug" {
               description "Match debug messages";
             }
             enum "all" {
               description "Match all levels";
             }
           }
         }
       }
       leaf control-link-recovery {
         description "Enable automatic control link recovery";
         type empty;
       }
       leaf health-monitoring {
         description "Enable ha health monitoring";
         type empty;
       }
       leaf redundancy-mode {
         description "Redundancy mode for the cluster (Reboot all nodes simultaneously after change)";
         default "active-active";
         type enumeration {
           enum "active-active" {
             description "Primary and secondary nodes in active mode";
           }
           enum "active-backup" {
             description "Primary in active, secondary in backup mode";
           }
         }
       }
       leaf reth-count {
         description "Number of redundant ethernet interfaces";
         type union {
           type string {
             pattern "<.*>|$.*";
           }
           type uint16;
         }
       }
       container control-interface {
         description "Disable/enable HA control-link interface";
         uses apply-advanced;
         list node {
           key name;
           ordered-by user;
           junos:cli-feature "oneliner";
           description "Set node specific parameters";
           leaf name {
             description "Node identifier";
             junos:cli-feature "nokeyword";
             type union {
               type string {
                 pattern "<.*>|$.*";
               }
               type uint32 {
                 range "0 .. 1";
               }
             }
           }
           leaf disable {
             description "Disable HA control interface";
             type empty;
           }
         }
       }
       list control-ports {
         key "fpc port";
         ordered-by user;
         junos:cli-feature "homogeneous";
         junos:cli-feature "oneliner";
         description "Enable specific chassis cluster control ports";
         leaf fpc {
           description "FPC slot number";
           type union {
             type string {
               pattern "<.*>|$.*";
             }
             type uint32;
           }
         }
         leaf port {
           description "Port number";
           type union {
             type string {
               pattern "<.*>|$.*";
             }
             type uint32 {
               range "0 .. 2";
             }
           }
         }
       }
       list scb-control-ports {
         key name;
         ordered-by user;
         junos:cli-feature "homogeneous";
         junos:cli-feature "oneliner";
         description "Enable specific chassis cluster SCB control ports";
         leaf name {
           description "Control Board number";
           junos:cli-feature "nokeyword";
           type union {
             type string {
               pattern "<.*>|$.*";
             }
             type uint32 {
               range "0 .. 2";
             }
           }
         }
       }
       leaf heartbeat-interval {
         description "Interval between successive heartbeats";
         default "1000";
         units "milliseconds";
         type union {
           type string {
             pattern "<.*>|$.*";
           }
           type uint32;
         }
       }
       leaf heartbeat-threshold {
         description "Number of consecutive missed heartbeats to indicate device failure";
         default "3";
         type union {
           type string {
             pattern "<.*>|$.*";
           }
           type uint32;
         }
       }
       container network-management {
         description "Define parameters for network management";
         uses apply-advanced;
         leaf cluster-master {
           description "Enable in-band management on cluster-master";
           type empty;
         }
       }
       list node {
         key name;
         ordered-by user;
         description "Set the list of nodes in the cluster";
         status deprecated;
         leaf name {
           description "Node identifier";
           junos:cli-feature "nokeyword";
           type enumeration {
             enum "0" {
               description "Node identifier 0";
             }
             enum "1" {
               description "Node identifier 1";
             }
           }
         }
         uses apply-advanced;
       }
       list redundancy-group {
         key name;
         ordered-by user;
         description "Set redundancy-group parameters";
         leaf name {
           description "Redundancy-group number";
           junos:cli-feature "nokeyword";
           type union {
             type string {
               pattern "<.*>|$.*";
             }
             type uint8;
           }
         }
         uses apply-advanced;
         list node {
           key name;
           ordered-by user;
           junos:cli-feature "oneliner";
           description "Set node specific parameters";
           leaf name {
             description "Node identifier";
             junos:cli-feature "nokeyword";
             type enumeration {
               enum "0" {
                 description "Node identifier 0";
               }
               enum "1" {
                 description "Node identifier 1";
               }
             }
           }
           leaf priority {
             description "Priority of the node in the redundancy-group";
             type union {
               type string {
                 pattern "<.*>|$.*";
               }
               type uint8 {
                 range "1 .. 254";
               }
             }
           }
         }
         container preempt {
           presence "enable preempt";
           description "Allow preemption of primaryship based on priority";
           uses apply-advanced;
           leaf delay {
             description "Time to wait before taking over mastership";
             units "seconds";
             type union {
               type string {
                 pattern "<.*>|$.*";
               }
               type uint16 {
                 range "1 .. 21600";
               }
             }
           }
           leaf limit {
             description "Max number of preemptive failovers allowed";
             type union {
               type string {
                 pattern "<.*>|$.*";
               }
               type uint16 {
                 range "1 .. 50";
               }
             }
           }
           leaf period {
             description "Time period during which the limit is applied";
             units "seconds";
             type union {
               type string {
                 pattern "<.*>|$.*";
               }
               type uint16 {
                 range "1 .. 1400";
               }
             }
           }
         }
         leaf gratuitous-arp-count {
           description "Number of gratuitous ARPs to send on an active interface after failover";
           type union {
             type string {
               pattern "<.*>|$.*";
             }
             type uint8 {
               range "1 .. 16";
             }
           }
         }
         leaf hold-down-interval {
           description "RG failover interval. RG0(300-1800) RG1+(0-1800)";
           units "seconds";
           type union {
             type string {
               pattern "<.*>|$.*";
             }
             type uint16 {
               range "0 .. 1800";
             }
           }
         }
         list interface-monitor {
           key name;
           ordered-by user;
           junos:cli-feature "homogeneous";
           junos:cli-feature "oneliner";
           description "Define interfaces to monitor";
           leaf name {
             description "Name of the interface to monitor";
             junos:cli-feature "nokeyword";
             junos:must "(\"interfaces $$\")";
             junos:must-message "Interface must be defined before configuring monitoring";
             type union {
               type jt:interface-device;
               type string {
                 pattern "<.*>|$.*";
               }
             }
           }
           leaf weight {
             description "Weight assigned to this interface that influences failover";
             type union {
               type string {
                 pattern "<.*>|$.*";
               }
               type uint16 {
                 range "0 .. 255";
               }
             }
           }
         }
         container ip-monitoring {
           description "Define parameters for IP monitoring feature";
           uses apply-advanced;
           leaf global-weight {
             description "Define global weight for IP monitoring";
             default "255";
             type union {
               type string {
                 pattern "<.*>|$.*";
               }
               type uint16 {
                 range "0 .. 255";
               }
             }
           }
           leaf global-threshold {
             description "Define global threshold for IP monitoring";
             default "0";
             type union {
               type string {
                 pattern "<.*>|$.*";
               }
               type uint16 {
                 range "0 .. 255";
               }
             }
           }
           leaf retry-interval {
             description "Define the time interval in seconds between retries.";
             default "1";
             type union {
               type string {
                 pattern "<.*>|$.*";
               }
               type uint16 {
                 range "1 .. 30";
               }
             }
           }
           leaf retry-count {
             description "Number of retries needed to declare reachablity failure";
             default "5";
             type union {
               type string {
                 pattern "<.*>|$.*";
               }
               type uint16 {
                 range "5 .. 15";
               }
             }
           }
           container family {
             description "Define protocol family";
             uses apply-advanced;
             container inet {
               description "Define IPv4 related parameters";
               uses apply-advanced;
               list address {
                 key name;
                 description "Define IP address related parameters";
                 uses ip-monitoring-address-type;
                 junos:cli-feature "nokeyword";
                 junos:cli-feature "homogeneous";
                 junos:cli-feature "oneliner-plus";
               }
             }
           }
         }
       }
       container configuration-synchronize {
         description "Cluster configuration action";
         uses apply-advanced;
         leaf no-secondary-bootup-auto {
           description "Disable auto configuration synchronize on secondary bootup";
           type empty;
         }
       }
       leaf use-actual-mac-on-physical-interfaces {
         description "Use Hypervisor provided MAC for physical interfaces on virtual platforms";
         type empty;
       }
       leaf use-active-child-mac-on-reth {
         description "Copy Child's physical MAC on RETH parent's current MAC";
         type empty;
       }
     }
     container high-availability {
       presence "enable high-availability";
       junos:must "((!(\"interfaces st0 unit 16000\") && (!(\"interfaces st0 unit 16001\") && (!(\"interfaces st0 unit 16002\") && (!(\"interfaces st0 unit 16003\") && (!(\"interfaces st0 unit 16004\") && (!(\"interfaces st0 unit 16005\") && (!(\"interfaces st0 unit 16006\") && (!(\"interfaces st0 unit 16007\") && (!(\"interfaces st0 unit 16008\") && (!(\"interfaces st0 unit 16009\") && (!(\"interfaces st0 unit 16010\") && (!(\"interfaces st0 unit 16011\") && (!(\"interfaces st0 unit 16012\") && (!(\"interfaces st0 unit 16013\") && (!(\"interfaces st0 unit 16014\") && (!(\"interfaces st0 unit 16015\") && (!(\"interfaces st0 unit 16016\") && (!(\"interfaces st0 unit 16017\") && (!(\"interfaces st0 unit 16018\") && (!(\"interfaces st0 unit 16019\") && (!(\"interfaces st0 unit 16020\") && (!(\"interfaces st0 unit 16021\") && (!(\"interfaces st0 unit 16022\") && (!(\"interfaces st0 unit 16023\") && (!(\"interfaces st0 unit 16024\") && (!(\"interfaces st0 unit 16025\") && (!(\"interfaces st0 unit 16026\") && (!(\"interfaces st0 unit 16027\") && (!(\"interfaces st0 unit 16028\") && (!(\"interfaces st0 unit 16029\") && (!(\"interfaces st0 unit 16030\") && (!(\"interfaces st0 unit 16031\") && (!(\"interfaces st0 unit 16032\") && (!(\"interfaces st0 unit 16033\") && (!(\"interfaces st0 unit 16034\") && (!(\"interfaces st0 unit 16035\") && (!(\"interfaces st0 unit 16036\") && (!(\"interfaces st0 unit 16037\") && (!(\"interfaces st0 unit 16038\") && (!(\"interfaces st0 unit 16039\") && (!(\"interfaces st0 unit 16d40\") && (!(\"interfaces st0 unit 16041\") && (!(\"interfaces st0 unit 16042\") && (!(\"interfaces st0 unit 16043\") && (!(\"interfaces st0 unit 16044\") && (!(\"interfaces st0 unit 16045\") && (!(\"interfaces st0 unit 16046\") && (!(\"interfaces st0 unit 16047\") && (!(\"interfaces st0 unit 16048\") && (!(\"interfaces st0 unit 16049\") && (!(\"interfaces st0 unit 16050\") && (!(\"interfaces st0 unit 16051\") && (!(\"interfaces st0 unit 16052\") && (!(\"interfaces st0 unit 16053\") && (!(\"interfaces st0 unit 16054\") && (!(\"interfaces st0 unit 16055\") && (!(\"interfaces st0 unit 16056\") && (!(\"interfaces st0 unit 16057\") && (!(\"interfaces st0 unit 16058\") && (!(\"interfaces st0 unit 16059\") && (!(\"interfaces st0 unit 16060\") && (!(\"interfaces st0 unit 16061\") && (!(\"interfaces st0 unit 16062\") && (!(\"interfaces st0 unit 16063\") && (!(\"interfaces st0 unit 16064\") && (!(\"interfaces st0 unit 16065\") && (!(\"interfaces st0 unit 16066\") && (!(\"interfaces st0 unit 16067\") && (!(\"interfaces st0 unit 16068\") && (!(\"interfaces st0 unit 16069\") && (!(\"interfaces st0 unit 16070\") && (!(\"interfaces st0 unit 16071\") && (!(\"interfaces st0 unit 16072\") && (!(\"interfaces st0 unit 16073\") && (!(\"interfaces st0 unit 16074\") && (!(\"interfaces st0 unit 16075\") && (!(\"interfaces st0 unit 16076\") && (!(\"interfaces st0 unit 16077\") && (!(\"interfaces st0 unit 16078\") && (!(\"interfaces st0 unit 16079\") && (!(\"interfaces st0 unit 16080\") && (!(\"interfaces st0 unit 16081\") && (!(\"interfaces st0 unit 16082\") && (!(\"interfaces st0 unit 16083\") && (!(\"interfaces st0 unit 16084\") && (!(\"interfaces st0 unit 16085\") && (!(\"interfaces st0 unit 16086\") && (!(\"interfaces st0 unit 16087\") && (!(\"interfaces st0 unit 16088\") && (!(\"interfaces st0 unit 16089\") && (!(\"interfaces st0 unit 16090\") && (!(\"interfaces st0 unit 16091\") && (!(\"interfaces st0 unit 16092\") && (!(\"interfaces st0 unit 16093\") && (!(\"interfaces st0 unit 16094\") && (!(\"interfaces st0 unit 16095\") && (!(\"interfaces st0 unit 16096\") && (!(\"interfaces st0 unit 16097\") && (!(\"interfaces st0 unit 16098\") && (!(\"interfaces st0 unit 16099\") && (!(\"interfaces st0 unit 16100\") && (!(\"interfaces st0 unit 16101\") && (!(\"interfaces st0 unit 16102\") && (!(\"interfaces st0 unit 16103\") && (!(\"interfaces st0 unit 16104\") && (!(\"interfaces st0 unit 16105\") && (!(\"interfaces st0 unit 16106\") && (!(\"interfaces st0 unit 16107\") && (!(\"interfaces st0 unit 16108\") && (!(\"interfaces st0 unit 16109\") && (!(\"interfaces st0 unit 16110\") && (!(\"interfaces st0 unit 16111\") && (!(\"interfaces st0 unit 16112\") && (!(\"interfaces st0 unit 16113\") && (!(\"interfaces st0 unit 16114\") && (!(\"interfaces st0 unit 16115\") && (!(\"interfaces st0 unit 16116\") && (!(\"interfaces st0 unit 16117\") && (!(\"interfaces st0 unit 16118\") && (!(\"interfaces st0 unit 16119\") && (!(\"interfaces st0 unit 16120\") && (!(\"interfaces st0 unit 16121\") && (!(\"interfaces st0 unit 16122\") && (!(\"interfaces st0 unit 16123\") && (!(\"interfaces st0 unit 16124\") && (!(\"interfaces st0 unit 16125\") && (!(\"interfaces st0 unit 16126\") && (!(\"interfaces st0 unit 16127\") && (!(\"interfaces st0 unit 16128\") && (!(\"interfaces st0 unit 16129\") && (!(\"interfaces st0 unit 16130\") && (!(\"interfaces st0 unit 16131\") && (!(\"interfaces st0 unit 16132\") && (!(\"interfaces st0 unit 16133\") && (!(\"interfaces st0 unit 16134\") && (!(\"interfaces st0 unit 16135\") && (!(\"interfaces st0 unit 16136\") && (!(\"interfaces st0 unit 16137\") && (!(\"interfaces st0 unit 16138\") && (!(\"interfaces st0 unit 16139\") && (!(\"interfaces st0 unit 16140\") && (!(\"interfaces st0 unit 16141\") && (!(\"interfaces st0 unit 16142\") && (!(\"interfaces st0 unit 16143\") && (!(\"interfaces st0 unit 16144\") && (!(\"interfaces st0 unit 16145\") && (!(\"interfaces st0 unit 16146\") && (!(\"interfaces st0 unit 16147\") && (!(\"interfaces st0 unit 16148\") && (!(\"interfaces st0 unit 16149\") && (!(\"interfaces st0 unit 16150\") && (!(\"interfaces st0 unit 16151\") && (!(\"interfaces st0 unit 16152\") && (!(\"interfaces st0 unit 16153\") && (!(\"interfaces st0 unit 16154\") && (!(\"interfaces st0 unit 16155\") && (!(\"interfaces st0 unit 16156\") && (!(\"interfaces st0 unit 16157\") && (!(\"interfaces st0 unit 16158\") && (!(\"interfaces st0 unit 16159\") && (!(\"interfaces st0 unit 16160\") && (!(\"interfaces st0 unit 16161\") && (!(\"interfaces st0 unit 16162\") && (!(\"interfaces st0 unit 16163\") && (!(\"interfaces st0 unit 16164\") && (!(\"interfaces st0 unit 16165\") && (!(\"interfaces st0 unit 16166\") && (!(\"interfaces st0 unit 16167\") && (!(\"interfaces st0 unit 16168\") && (!(\"interfaces st0 unit 16169\") && (!(\"interfaces st0 unit 16170\") && (!(\"interfaces st0 unit 16171\") && (!(\"interfaces st0 unit 16172\") && (!(\"interfaces st0 unit 16173\") && (!(\"interfaces st0 unit 16174\") && (!(\"interfaces st0 unit 16175\") && (!(\"interfaces st0 unit 16176\") && (!(\"interfaces st0 unit 16177\") && (!(\"interfaces st0 unit 16178\") && (!(\"interfaces st0 unit 16179\") && (!(\"interfaces st0 unit 16180\") && (!(\"interfaces st0 unit 16181\") && (!(\"interfaces st0 unit 16182\") && (!(\"interfaces st0 unit 16183\") && (!(\"interfaces st0 unit 16184\") && (!(\"interfaces st0 unit 16185\") && (!(\"interfaces st0 unit 16186\") && (!(\"interfaces st0 unit 16187\") && (!(\"interfaces st0 unit 16188\") && (!(\"interfaces st0 unit 16189\") && (!(\"interfaces st0 unit 16190\") && (!(\"interfaces st0 unit 16191\") && (!(\"interfaces st0 unit 16192\") && (!(\"interfaces st0 unit 16193\") && (!(\"interfaces st0 unit 16194\") && (!(\"interfaces st0 unit 16195\") && (!(\"interfaces st0 unit 16196\") && (!(\"interfaces st0 unit 16197\") && (!(\"interfaces st0 unit 16198\") && (!(\"interfaces st0 unit 16199\") && (!(\"interfaces st0 unit 16200\") && (!(\"interfaces st0 unit 16201\") && (!(\"interfaces st0 unit 16202\") && (!(\"interfaces st0 unit 16203\") && (!(\"interfaces st0 unit 16204\") && (!(\"interfaces st0 unit 16205\") && (!(\"interfaces st0 unit 16206\") && (!(\"interfaces st0 unit 16207\") && (!(\"interfaces st0 unit 16208\") && (!(\"interfaces st0 unit 16209\") && (!(\"interfaces st0 unit 16210\") && (!(\"interfaces st0 unit 16211\") && (!(\"interfaces st0 unit 16212\") && (!(\"interfaces st0 unit 16213\") && (!(\"interfaces st0 unit 16214\") && (!(\"interfaces st0 unit 16215\") && (!(\"interfaces st0 unit 16216\") && (!(\"interfaces st0 unit 16217\") && (!(\"interfaces st0 unit 16218\") && (!(\"interfaces st0 unit 16219\") && (!(\"interfaces st0 unit 16220\") && (!(\"interfaces st0 unit 16221\") && (!(\"interfaces st0 unit 16222\") && (!(\"interfaces st0 unit 16223\") && (!(\"interfaces st0 unit 16224\") && (!(\"interfaces st0 unit 16225\") && (!(\"interfaces st0 unit 16226\") && (!(\"interfaces st0 unit 16227\") && (!(\"interfaces st0 unit 16228\") && (!(\"interfaces st0 unit 16229\") && (!(\"interfaces st0 unit 16230\") && (!(\"interfaces st0 unit 16231\") && (!(\"interfaces st0 unit 16232\") && (!(\"interfaces st0 unit 16233\") && (!(\"interfaces st0 unit 16234\") && (!(\"interfaces st0 unit 16235\") && (!(\"interfaces st0 unit 16236\") && (!(\"interfaces st0 unit 16237\") && (!(\"interfaces st0 unit 16238\") && (!(\"interfaces st0 unit 16239\") && (!(\"interfaces st0 unit 16240\") && (!(\"interfaces st0 unit 16241\") && (!(\"interfaces st0 unit 16242\") && (!(\"interfaces st0 unit 16243\") && (!(\"interfaces st0 unit 16244\") && (!(\"interfaces st0 unit 16245\") && (!(\"interfaces st0 unit 16246\") && (!(\"interfaces st0 unit 16247\") && (!(\"interfaces st0 unit 16248\") && (!(\"interfaces st0 unit 16249\") && (!(\"interfaces st0 unit 16250\") && (!(\"interfaces st0 unit 16251\") && (!(\"interfaces st0 unit 16252\") && (!(\"interfaces st0 unit 16253\") && (!(\"interfaces st0 unit 16254\") && (!(\"interfaces st0 unit 16255\") && (!(\"interfaces st0 unit 16256\") && (!(\"interfaces st0 unit 16257\") && (!(\"interfaces st0 unit 16258\") && (!(\"interfaces st0 unit 16259\") && (!(\"interfaces st0 unit 16260\") && (!(\"interfaces st0 unit 16261\") && (!(\"interfaces st0 unit 16262\") && (!(\"interfaces st0 unit 16263\") && (!(\"interfaces st0 unit 16264\") && (!(\"interfaces st0 unit 16265\") && (!(\"interfaces st0 unit 16266\") && (!(\"interfaces st0 unit 16267\") && (!(\"interfaces st0 unit 16268\") && (!(\"interfaces st0 unit 16269\") && (!(\"interfaces st0 unit 16270\") && (!(\"interfaces st0 unit 16271\") && (!(\"interfaces st0 unit 16272\") && (!(\"interfaces st0 unit 16273\") && (!(\"interfaces st0 unit 16274\") && (!(\"interfaces st0 unit 16275\") && (!(\"interfaces st0 unit 16276\") && (!(\"interfaces st0 unit 16277\") && (!(\"interfaces st0 unit 16278\") && (!(\"interfaces st0 unit 16279\") && (!(\"interfaces st0 unit 16280\") && (!(\"interfaces st0 unit 16281\") && (!(\"interfaces st0 unit 16282\") && (!(\"interfaces st0 unit 16283\") && (!(\"interfaces st0 unit 16284\") && (!(\"interfaces st0 unit 16285\") && (!(\"interfaces st0 unit 16286\") && (!(\"interfaces st0 unit 16287\") && (!(\"interfaces st0 unit 16288\") && (!(\"interfaces st0 unit 16289\") && (!(\"interfaces st0 unit 16290\") && (!(\"interfaces st0 unit 16291\") && (!(\"interfaces st0 unit 16292\") && (!(\"interfaces st0 unit 16293\") && (!(\"interfaces st0 unit 16294\") && (!(\"interfaces st0 unit 16295\") && (!(\"interfaces st0 unit 16296\") && (!(\"interfaces st0 unit 16297\") && (!(\"interfaces st0 unit 16298\") && (!(\"interfaces st0 unit 16299\") && (!(\"interfaces st0 unit 16300\") && (!(\"interfaces st0 unit 16301\") && (!(\"interfaces st0 unit 16302\") && (!(\"interfaces st0 unit 16303\") && (!(\"interfaces st0 unit 16304\") && (!(\"interfaces st0 unit 16305\") && (!(\"interfaces st0 unit 16306\") && (!(\"interfaces st0 unit 16307\") && (!(\"interfaces st0 unit 16308\") && (!(\"interfaces st0 unit 16309\") && (!(\"interfaces st0 unit 16310\") && (!(\"interfaces st0 unit 16311\") && (!(\"interfaces st0 unit 16312\") && (!(\"interfaces st0 unit 16313\") && (!(\"interfaces st0 unit 16314\") && (!(\"interfaces st0 unit 16315\") && (!(\"interfaces st0 unit 16316\") && (!(\"interfaces st0 unit 16317\") && (!(\"interfaces st0 unit 16318\") && (!(\"interfaces st0 unit 16319\") && (!(\"interfaces st0 unit 16320\") && (!(\"interfaces st0 unit 16321\") && (!(\"interfaces st0 unit 16322\") && (!(\"interfaces st0 unit 16323\") && (!(\"interfaces st0 unit 16324\") && (!(\"interfaces st0 unit 16325\") && (!(\"interfaces st0 unit 16326\") && (!(\"interfaces st0 unit 16327\") && (!(\"interfaces st0 unit 16328\") && (!(\"interfaces st0 unit 16329\") && (!(\"interfaces st0 unit 16330\") && (!(\"interfaces st0 unit 16331\") && (!(\"interfaces st0 unit 16332\") && (!(\"interfaces st0 unit 16333\") && (!(\"interfaces st0 unit 16334\") && (!(\"interfaces st0 unit 16335\") && (!(\"interfaces st0 unit 16336\") && (!(\"interfaces st0 unit 16337\") && (!(\"interfaces st0 unit 16338\") && (!(\"interfaces st0 unit 16339\") && (!(\"interfaces st0 unit 16340\") && (!(\"interfaces st0 unit 16341\") && (!(\"interfaces st0 unit 16342\") && (!(\"interfaces st0 unit 16343\") && (!(\"interfaces st0 unit 16344\") && (!(\"interfaces st0 unit 16345\") && (!(\"interfaces st0 unit 16346\") && (!(\"interfaces st0 unit 16347\") && (!(\"interfaces st0 unit 16348\") && (!(\"interfaces st0 unit 16349\") && (!(\"interfaces st0 unit 16350\") && (!(\"interfaces st0 unit 16351\") && (!(\"interfaces st0 unit 16352\") && (!(\"interfaces st0 unit 16353\") && (!(\"interfaces st0 unit 16354\") && (!(\"interfaces st0 unit 16355\") && (!(\"interfaces st0 unit 16356\") && (!(\"interfaces st0 unit 16357\") && (!(\"interfaces st0 unit 16358\") && (!(\"interfaces st0 unit 16359\") && (!(\"interfaces st0 unit 16360\") && (!(\"interfaces st0 unit 16361\") && (!(\"interfaces st0 unit 16362\") && (!(\"interfaces st0 unit 16363\") && (!(\"interfaces st0 unit 16364\") && (!(\"interfaces st0 unit 16365\") && (!(\"interfaces st0 unit 16366\") && (!(\"interfaces st0 unit 16367\") && (!(\"interfaces st0 unit 16368\") && (!(\"interfaces st0 unit 16369\") && (!(\"interfaces st0 unit 16370\") && (!(\"interfaces st0 unit 16371\") && (!(\"interfaces st0 unit 16372\") && (!(\"interfaces st0 unit 16373\") && (!(\"interfaces st0 unit 16374\") && (!(\"interfaces st0 unit 16375\") && (!(\"interfaces st0 unit 16376\") && (!(\"interfaces st0 unit 16377\") && (!(\"interfaces st0 unit 16378\") && (!(\"interfaces st0 unit 16379\") && (!(\"interfaces st0 unit 16380\") && (!(\"interfaces st0 unit 16381\") && (!(\"interfaces st0 unit 16382\") && (!(\"interfaces st0 unit 16383\") && (!(\"interfaces st0 unit 16384\") && !(\"interfaces st0 unit 16385\")))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))))";
       junos:must-message "st0 unit 16000 to 16385 is disallowed in SRX HA mode";
       description "Enable High Availability mode";
       uses apply-advanced;
       leaf software-upgrade {
         description "Enable software upgrade state";
         type empty;
       }
       leaf hardware-upgrade {
         description "Enable hardware upgrade state";
         type empty;
       }
       container local-id {
         junos:cli-feature "oneliner-plus";
         description "Local Identifier";
         uses apply-advanced;
         leaf id {
           description "Local identifier number";
           junos:cli-feature "nokeyword";
           junos:must "(!(\"chassis high-availability peer-id $$\"))";
           junos:must-message "high-availability local-id must be different with peer-id";
           junos:must "(\"chassis high-availability peer-id\")";
           junos:must-message "high-availability peer-id must be defined";
           type union {
             type string {
               pattern "<.*>|$.*";
             }
             type uint8 {
               range "1 .. 10";
             }
           }
         }
         leaf local-ip {
           description "Local IPv4/IPv6 address";
           type jt:ipaddr;
         }
         container local-forwarding-ip {
           junos:cli-feature "oneliner-plus";
           description "Local Forwarding ip";
           uses apply-advanced;
           leaf loopback-address {
             description "Local IPv4/IPv6 loopback address";
             junos:cli-feature "nokeyword";
             junos:must "(!(\".. .. local-ip $$\"))";
             junos:must-message "local-forwarding-ip must be different from local-ip address";
             type jt:ipaddr;
           }
         }
       }
       list peer-id {
         key name;
         ordered-by user;
         junos:cli-feature "oneliner-plus";
         description "Peer related information";
         leaf name {
           description "Peer Identifier";
           junos:cli-feature "nokeyword";
           junos:must "(!(\"chassis high-availability local-id $$\"))";
           junos:must-message "high-availability local-id must be different with peer-id";
           junos:must "(\"chassis high-availability local-id\")";
           junos:must-message "high-availability local-id must be defined";
           type union {
             type string {
               pattern "<.*>|$.*";
             }
             type uint8 {
               range "1 .. 10";
             }
           }
         }
         uses apply-advanced;
         leaf desc {
           description "Peer Description";
           type string {
             length "1 .. 255";
           }
         }
         leaf peer-ip {
           description "Peer IPv4/IPv6 address";
           type jt:ipaddr;
         }
         leaf interface {
           description "Name of the interface";
           junos:must "(!((\"protocols l2-learning global-mode switching\" && \"interfaces $$ family ethernet-switching\")))";
           junos:must-message "Referenced interface must not be ethernet-switching interface of switching mode";
           type union {
             type jt:interface-name;
             type string {
               pattern "<.*>|$.*";
             }
           }
         }
         leaf routing-instance {
           description "Routing instance to locate the peer route";
           junos:must "(\"routing-instances $$ instance-type virtual-router\")";
           junos:must-message "'instance-type' for the referenced routing-instance must be configured as virtual-router";
           junos:must "((\"routing-instances $$\" || any \"tenants <*> routing-instances $$\"))";
           junos:must-message "referenced routing-instance must be defined";
           type string {
             junos:posix-pattern "!^((__.*__)|(all)|(.*[ ].*)|(\"\")|(.{129,}))$";
             junos:pattern-message "Must be a non-reserved string of 128 characters or less with no spaces.";
           }
         }
         leaf vpn-profile {
           description "VPN Profile name for HA link Encryption";
           junos:must "(\"security ipsec vpn $$ ha-link-encryption\")";
           junos:must-message "Referenced vpn object must have ha-link-encryption flag defined";
           junos:must "(\"security ipsec vpn $$\")";
           junos:must-message "Referenced vpn object must be defined under [edit security ipsec vpn]";
           type string {
             length "1 .. 255";
           }
         }
         container peer-forwarding-ip {
           junos:must "(\".. .. local-id local-forwarding-ip\")";
           junos:must-message "Local forwarding ip must be configured";
           junos:cli-feature "oneliner-plus";
           description "Peer Forwarding ip";
           uses apply-advanced;
           leaf loopback-address {
             description "Peer IPv4/IPv6 loopback address";
             junos:cli-feature "nokeyword";
             junos:must "(!(\".. .. peer-ip $$\"))";
             junos:must-message "peer-forwarding-ip must be different from peer-ip address";
             junos:must "(!(\".. .. .. local-id local-forwarding-ip $$\"))";
             junos:must-message "peer-forwarding-ip must be different from local-forwarding-ip";
             type jt:ipaddr;
           }
           leaf interface {
             description "Name of the interface";
             junos:must "(!((\"protocols l2-learning global-mode switching\" && \"interfaces $$ family ethernet-switching\")))";
             junos:must-message "Referenced interface must not be ethernet-switching interface of switching mode";
             type union {
               type jt:interface-name;
               type string {
                 pattern "<.*>|$.*";
               }
             }
           }
           container liveness-detection {
             presence "enable liveness-detection";
             description "Bidirectional Forwarding IP Detection options for ICD link";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32;
               }
             }
             leaf minimum-transmit-interval {
               description "Minimum transmit interval";
               status deprecated;
               units "milliseconds";
               type union {
                 type string {
                   pattern "<.*>|$.*";
                 }
                 type uint32;
               }
             }
             leaf minimum-receive-interval {
               description "Minimum receive interval";
               units "milliseconds";
               type union {
                 type string {
                   pattern "<.*>|$.*";
                 }
                 type uint32;
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32;
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
           }
         }
         container liveness-detection {
           presence "enable liveness-detection";
           description "Bidirectional Forwarding Detection options for the peer";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32;
             }
           }
           leaf minimum-transmit-interval {
             description "Minimum transmit interval";
             status deprecated;
             units "milliseconds";
             type union {
               type string {
                 pattern "<.*>|$.*";
               }
               type uint32;
             }
           }
           leaf minimum-receive-interval {
             description "Minimum receive interval";
             units "milliseconds";
             type union {
               type string {
                 pattern "<.*>|$.*";
               }
               type uint32;
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32;
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
       container traceoptions {
         description "Set chassis l3-ha traceoptions";
         uses apply-advanced;
         leaf no-remote-trace {
           description "Disable remote tracing";
           junos:must "(\"system tracing\")";
           junos:must-message "'no-remote-trace' is valid only when [system tracing] is configured";
           type empty;
         }
         container file {
           junos:cli-feature "oneliner";
           description "Trace file information";
           leaf filename {
             description "Name of file in which to write trace information";
             junos:cli-feature "nokeyword";
             type string {
               length "1 .. 1024";
               junos:posix-pattern "![/ %]";
               junos:pattern-message "Must not contain \'/\', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           junos:cli-feature "oneliner";
           description "Tracing parameters";
           leaf name {
             junos:cli-feature "nokeyword";
             type enumeration {
               enum "cli" {
                 description "Trace CLI events";
               }
               enum "configuration" {
                 description "Trace configuration events";
               }
               enum "eventlib" {
                 description "Trace event library events";
               }
               enum "fsm" {
                 description "Trace finite state machine events";
               }
               enum "heartbeat" {
                 description "Trace JSRPD heartbeats";
               }
               enum "interface" {
                 description "Trace interface related events";
               }
               enum "routing-socket" {
                 description "Trace routing socket events";
               }
               enum "uspipc" {
                 description "Trace USP IPC events";
               }
               enum "init" {
                 description "Trace initialization events";
               }
               enum "socket" {
                 description "Trace socket events";
               }
               enum "snmp" {
                 description "Trace snmp events";
               }
               enum "ip-monitoring" {
                 description "Trace IP monitoring events";
               }
               enum "hw-monitoring" {
                 description "Trace HW  monitoring events";
               }
               enum "fabric-monitoring" {
                 description "Trace fabric monitoring events";
               }
               enum "health-monitoring" {
                 description "Trace health monitoring events";
               }
               enum "schedule-monitoring" {
                 description "Trace schedule monitoring events";
               }
               enum "heartbeat-tlv" {
                 description "Trace TLV based heart-beat";
               }
               enum "ha-peer" {
                 description "Trace HA peer related info";
               }
               enum "srg" {
                 description "Trace HA srg related info";
               }
               enum "all" {
                 description "Trace all events";
               }
             }
           }
         }
         leaf level {
           description "Set level of tracing";
           default "info";
           type enumeration {
             enum "emergency" {
               description "Match emergency conditions";
             }
             enum "alert" {
               description "Match alert conditions";
             }
             enum "critical" {
               description "Match critical conditions";
             }
             enum "error" {
               description "Match error conditions";
             }
             enum "warning" {
               description "Match warning messages";
             }
             enum "notice" {
               description "Match notice level messages";
             }
             enum "info" {
               description "Match informational messages";
             }
             enum "debug" {
               description "Match debug messages";
             }
             enum "all" {
               description "Match all levels";
             }
           }
         }
       }
       list services-redundancy-group {
         key name;
         ordered-by user;
         description "Define the services level failover domain";
         leaf name {
           description "Services redundancy group identifier";
           junos:cli-feature "nokeyword";
           type union {
             type string {
               pattern "<.*>|$.*";
             }
             type uint8 {
               range "0 .. 20";
             }
           }
         }
         uses apply-advanced;
         list shutdown-on-failure {
           key name;
           ordered-by user;
           junos:cli-feature "homogeneous";
           description "Interfaces to be shut down in case of internal failures";
           leaf name {
             description "Name of the interface";
             junos:cli-feature "nokeyword";
             type union {
               type jt:interface-device;
               type string {
                 pattern "<.*>|$.*";
               }
             }
           }
           uses apply-advanced;
         }
         leaf deployment-type {
           description "Deployment type of the Services Redundancy Group";
           default "routing";
           type enumeration {
             enum "cloud" {
               description "Cloud deployment";
               junos:must "(!(\".. monitor bfd-liveliness\"))";
               junos:must-message " BFD monitoring is not supported in cloud mode";
               junos:must "(!(\".. monitor ip\"))";
               junos:must-message " IP monitoring is not supported in cloud mode";
               junos:must "(!(\".. backup-signal-route\"))";
               junos:must-message " backup-signal-route is not allowed in cloud deployment type";
               junos:must "(!(\".. active-signal-route\"))";
               junos:must-message " active-signal-route is not allowed in cloud deployment type";
               junos:must "(!(\".. virtual-ip\"))";
               junos:must-message " virtual-ip is not allowed for cloud deployment type";
               junos:must "(!(\".. activeness-probe\"))";
               junos:must-message " activeness-probe is not allowed for cloud deployment type";
             }
             enum "hybrid" {
               description "Hybrid deployment";
               junos:must "(!(\".. .. services-redundancy-group 1 deployment-type cloud\"))";
               junos:must-message " hybrid SRG is not supported in public cloud mode";
               junos:must "(\".. backup-signal-route\")";
               junos:must-message " backup-signal-route is mandatory for hybrid deployment type";
               junos:must "(\".. active-signal-route\")";
               junos:must-message " active-signal-route is mandatory for hybrid deployment type";
               junos:must "(\".. virtual-ip 1\")";
               junos:must-message " virtual-ip index 1 is mandatory for hybrid deployment type";
             }
             enum "routing" {
               description "Routing deployment";
               junos:must "(!(\".. .. services-redundancy-group 1 deployment-type cloud\"))";
               junos:must-message " routing SRG is not supported in public cloud mode";
               junos:must "(!(\".. virtual-ip\"))";
               junos:must-message " virtual-ip is not allowed for routing deployment type";
               junos:must "(\".. backup-signal-route\")";
               junos:must-message " backup-signal-route is mandatory for routing deployment type";
               junos:must "(\".. active-signal-route\")";
               junos:must-message " active-signal-route is mandatory for routing deployment type";
               junos:must "(\".. activeness-probe dest-ip\")";
               junos:must-message " activeness-probe dest-ip is mandatory for routing deployment type";
             }
             enum "switching" {
               description "Switching deployment";
               junos:must "(!(\".. .. services-redundancy-group 1 deployment-type cloud\"))";
               junos:must-message " switching SRG is not supported in public cloud mode";
               junos:must "(!(\".. activeness-probe dest-ip\"))";
               junos:must-message " activeness-probe dest-ip is not allowed in switching  deployment type";
               junos:must "(!(\".. backup-signal-route\"))";
               junos:must-message " backup-signal-route is not allowed in switching  deployment type";
               junos:must "(!(\".. active-signal-route\"))";
               junos:must-message " active-signal-route is not allowed in switching deployment type";
               junos:must "(\".. virtual-ip 2\")";
               junos:must-message " virtual-ip index 2 is mandatory for switching deployment type";
               junos:must "(\".. virtual-ip 1\")";
               junos:must-message " virtual-ip index 1 is mandatory for switching deployment type";
             }
           }
         }
         container peer-id {
           presence "enable peer-id";
           junos:must "(((\".. activeness-probe dest-ip\" || \".. deployment-type\") || \".. .. services-redundancy-group 0\"))";
           junos:must-message "activeness-probe dest-ip is mandatory for routing deployment";
           description "Peer related information";
           uses apply-advanced;
           leaf id {
             description "Peer Identifier";
             junos:cli-feature "nokeyword";
             junos:must "(\"chassis high-availability peer-id $$\")";
             junos:must-message "above peer-id should be configured at chassis high-availability stanza";
             junos:must "(\"chassis high-availability peer-id\")";
             junos:must-message "high-availability peer-id must be defined";
             type union {
               type string {
                 pattern "<.*>|$.*";
               }
               type uint8 {
                 range "1 .. 10";
               }
             }
           }
         }
         container activeness-probe {
           description "The probe destination IP for activeness determination";
           uses apply-advanced;
           container dest-ip {
             junos:must "(!(\".. bfd-liveliness\"))";
             junos:must-message "activeness-probe bfd-liveliness must not be defined";
             junos:must "((\".. .. floating-ip\" || \".. .. activeness-probe dest-ip src-ip\"))";
             junos:must-message "activeness-probe src-ip is mandatory";
             description "Destination IPV4/IPV6 address";
             uses apply-advanced;
             leaf ip-address {
               description "Destination IPV4/IPV6 address";
               junos:cli-feature "nokeyword";
               type jt:ipaddr;
             }
             leaf src-ip {
               description "Source IPV4/IPV6 address for activeness probe";
               junos:must "(!(\".. .. .. floating-ip\"))";
               junos:must-message "floating-ip is not allowed when activeness-probe src-ip is defined";
               type jt:ipaddr;
             }
             leaf routing-instance {
               description "Routing instance";
               junos:must "(\"routing-instances $$ instance-type virtual-router\")";
               junos:must-message "'instance-type' for the referenced routing-instance must be configured as virtual-router";
               junos:must "((\"routing-instances $$\" || any \"tenants <*> routing-instances $$\"))";
               junos:must-message "referenced routing-instance must be defined";
               type string {
                 junos:posix-pattern "!^((__.*__)|(all)|(.*[ ].*)|(\"\")|(.{129,}))$";
                 junos:pattern-message "Must be a non-reserved string of 128 characters or less with no spaces.";
               }
             }
           }
           leaf minimum-interval {
             description "Define the time interval in milliseconds between activeness probing retries.";
             junos:must "(!(\".. dest-ip\"))";
             junos:must-message "activeness-probe dest-ip is not allowed when activeness-probe minimum-interval is configured";
             junos:must "((\".. .. deployment-type switching\" || \".. .. deployment-type hybrid\"))";
             junos:must-message "activeness-probe minimum-interval is only allowed in switching or hybrid deployment";
             type union {
               type string {
                 pattern "<.*>|$.*";
               }
               type uint32 {
                 range 1000;
               }
             }
           }
           leaf multiplier {
             description "Number of retries needed to declare activeness probing failure";
             junos:must "(!(\".. dest-ip\"))";
             junos:must-message "activeness-probe dest-ip is not allowed when activeness-probe multiplier is configured";
             junos:must "((\".. .. deployment-type switching\" || \".. .. deployment-type hybrid\"))";
             junos:must-message "activeness-probe multiplier is only allowed in switching or hybrid deployment";
             type union {
               type string {
                 pattern "<.*>|$.*";
               }
               type uint8 {
                 range "2 .. 15";
               }
             }
           }
           container bfd-liveliness {
             junos:must "((\".. .. deployment-type switching\" || \".. .. deployment-type hybrid\"))";
             junos:must-message "activeness-probe bfd-liveliness can only be configured in switching or hybrid deployment SRG";
             junos:must "(!(\".. multiplier\"))";
             junos:must-message "activeness-probe multiplier must not be defined";
             junos:must "(!(\".. minimum-interval\"))";
             junos:must-message "activeness-probe minimum-interval must not be defined";
             junos:must "(!(\".. dest-ip\"))";
             junos:must-message "activeness-probe dest-ip must not be defined";
             description "Configure BFD monitoring";
             uses apply-advanced;
             leaf source-ip {
               description "Source IPV4/IPV6 address for BFD monitoring";
               type jt:ipaddr;
             }
             leaf destination-ip {
               description "Destination IPV4/IPV6 address for BFD monitoring";
               type jt:ipaddr;
             }
             leaf interface {
               description "Name of the interface for single-hop sessions";
               junos:must "((\"interfaces $$-IFL family inet\" || \"interfaces $$-IFL family inet6\"))";
               junos:must-message "Family inet or inet6 must be defined on this logical interface";
               junos:must "(!(\".. session-type multihop\"))";
               junos:must-message "Interface name not allowed for multihop bfd monitoring sessions";
               junos:must "(!((\"protocols l2-learning global-mode switching\" && \"interfaces $$ family ethernet-switching\")))";
               junos:must-message "Referenced interface must not be ethernet-switching interface of switching mode";
               type union {
                 type jt:interface-name;
                 type string {
                   pattern "<.*>|$.*";
                 }
               }
             }
             leaf routing-instance {
               description "Routing instance to locate the route";
               junos:must "(\"routing-instances $$ instance-type virtual-router\")";
               junos:must-message "'instance-type' for the referenced routing-instance must be configured as virtual-router";
               junos:must "((\"routing-instances $$\" || any \"tenants <*> routing-instances $$\"))";
               junos:must-message "referenced routing-instance must be defined";
               type string {
                 junos:posix-pattern "!^((__.*__)|(all)|(.*[ ].*)|(\"\")|(.{129,}))$";
                 junos:pattern-message "Must be a non-reserved string of 128 characters or less with no spaces.";
               }
             }
             leaf minimum-interval {
               description "Minimum transmit and receive interval";
               units "milliseconds";
               type union {
                 type string {
                   pattern "<.*>|$.*";
                 }
                 type uint32;
               }
             }
             leaf multiplier {
               description "Detection time multiplier";
               type union {
                 type string {
                   pattern "<.*>|$.*";
                 }
                 type uint32 {
                   range "1 .. 255";
                 }
               }
             }
           }
         }
         list virtual-ip {
           key name;
           ordered-by user;
           description "HA virtual IP ";
           leaf name {
             description "Virtual IP Identifier";
             junos:cli-feature "nokeyword";
             type union {
               type string {
                 pattern "<.*>|$.*";
               }
               type uint8 {
                 range "1 .. 32";
               }
             }
           }
           uses apply-advanced;
           leaf ip {
             description "IPV4/IPV6 prefix, should be in the same subnet as the interface IP";
             junos:must "(unique \"chassis high-availability services-redundancy-group <*> virtual-ip <*> ip $$\")";
             junos:must-message "Virtual IPs must be unique";
             type jt:ipprefix-mandatory;
           }
           leaf interface {
             description "Name of the interface";
             junos:must "(unique \"chassis high-availability services-redundancy-group <*> virtual-ip <*> interface $$\")";
             junos:must-message "Virtual IP interfaces must be unique";
             junos:must "((\"interfaces $$-IFL family inet\" || \"interfaces $$-IFL family inet6\"))";
             junos:must-message "Family inet or inet6 must be defined on this logical interface";
             junos:must "(!((\"protocols l2-learning global-mode switching\" && \"interfaces $$ family ethernet-switching\")))";
             junos:must-message "Referenced interface must not be ethernet-switching interface of switching mode";
             type union {
               type jt:interface-name;
               type string {
                 pattern "<.*>|$.*";
               }
             }
           }
           leaf use-virtual-mac {
             description "Use virtual mac for SRG role enforcement";
             type empty;
           }
         }
         container monitor {
           description "Configure the BFD and IP monitoring";
           uses apply-advanced;
           list ip {
             key name;
             ordered-by user;
             description "Destination IPV4/IPV6 address for monitoring";
             leaf name {
               description "Destination IPV4/IPV6 address";
               junos:cli-feature "nokeyword";
               type jt:ipaddr;
             }
             uses apply-advanced;
             leaf routing-instance {
               description "Routing instance to locate the destination route";
               junos:must "(\"routing-instances $$ instance-type virtual-router\")";
               junos:must-message "'instance-type' for the referenced routing-instance must be configured as virtual-router";
               junos:must "((\"routing-instances $$\" || any \"tenants <*> routing-instances $$\"))";
               junos:must-message "referenced routing-instance must be defined";
               type string {
                 junos:posix-pattern "!^((__.*__)|(all)|(.*[ ].*)|(\"\")|(.{129,}))$";
                 junos:pattern-message "Must be a non-reserved string of 128 characters or less with no spaces.";
               }
             }
           }
           list bfd-liveliness {
             key name;
             ordered-by user;
             description "Configure BFD monitoring";
             leaf name {
               description "Destination IPV4/IPV6 address for BFD monitoring";
               junos:cli-feature "nokeyword";
               type jt:ipaddr;
             }
             uses apply-advanced;
             leaf src-ip {
               description "Source IPV4/IPV6 address for BFD monitoring";
               type jt:ipaddr;
             }
             leaf routing-instance {
               description "Routing instance to locate the route";
               junos:must "(\"routing-instances $$ instance-type virtual-router\")";
               junos:must-message "'instance-type' for the referenced routing-instance must be configured as virtual-router";
               junos:must "((\"routing-instances $$\" || any \"tenants <*> routing-instances $$\"))";
               junos:must-message "referenced routing-instance must be defined";
               type string {
                 junos:posix-pattern "!^((__.*__)|(all)|(.*[ ].*)|(\"\")|(.{129,}))$";
                 junos:pattern-message "Must be a non-reserved string of 128 characters or less with no spaces.";
               }
             }
             leaf session-type {
               description "BFD Mon Session Type";
               type enumeration {
                 enum "singlehop" {
                   description "Single hop";
                   junos:must "(\".. interface\")";
                   junos:must-message "Interface should be mentioned for singlehop bfd monitoring sessions";
                 }
                 enum "multihop" {
                   description "Multihop";
                 }
               }
             }
             leaf interface {
               description "Name of the interface for single-hop sessions";
               junos:must "((\"interfaces $$-IFL family inet\" || \"interfaces $$-IFL family inet6\"))";
               junos:must-message "Family inet or inet6 must be defined on this logical interface";
               junos:must "(!(\".. session-type multihop\"))";
               junos:must-message "Interface name not allowed for multihop bfd monitoring sessions";
               junos:must "(!((\"protocols l2-learning global-mode switching\" && \"interfaces $$ family ethernet-switching\")))";
               junos:must-message "Referenced interface must not be ethernet-switching interface of switching mode";
               type union {
                 type jt:interface-name;
                 type string {
                   pattern "<.*>|$.*";
                 }
               }
             }
           }
           list interface {
             key name;
             ordered-by user;
             junos:cli-feature "homogeneous";
             description "Define interfaces to monitor";
             leaf name {
               description "Name of the interface to monitor";
               junos:cli-feature "nokeyword";
               junos:must "(\"interfaces $$\")";
               junos:must-message "Interface must be defined before configuring monitoring";
               type union {
                 type jt:interface-device;
                 type string {
                   pattern "<.*>|$.*";
                 }
               }
             }
             uses apply-advanced;
           }
           list monitor-object {
             key name;
             ordered-by user;
             description "SRG monitoring object";
             junos:must "(!(\".. interface\"))";
             junos:must-message "monitor interface must not be defined";
             junos:must "(!(\".. bfd-liveliness\"))";
             junos:must-message "monitor bfd-liveliness must not be defined";
             junos:must "(!(\".. ip\"))";
             junos:must-message "monitor ip must not be defined";
             junos:must "(\".. srg-threshold\")";
             junos:must-message "srg-threshold must be defined";
             leaf name {
               description "SRG monitoring object name 1..32 characters";
               junos:cli-feature "nokeyword";
               type string {
                 junos:posix-pattern "^.{1,32}$";
                 junos:pattern-message "must be a string of 32 characters or less";
               }
             }
             uses apply-advanced;
             leaf object-threshold {
               description "SRG monitoring object threshold value";
               junos:must "((\".. ip\" || (\".. bfd-liveliness\" || \".. interface\")))";
               junos:must-message "one or more monitor entry needs to be defined under this monitor-object!";
               type union {
                 type string {
                   pattern "<.*>|$.*";
                 }
                 type uint32 {
                   range "1 .. 1000";
                 }
               }
             }
             container ip {
               presence "enable ip";
               description "Configure IP monitoring";
               uses apply-advanced;
               leaf threshold {
                 description "SRG monitoring object ip monitoring threshold value";
                 junos:must "(\".. destination-ip\")";
                 junos:must-message "at least one ip destination-ip must be defined";
                 type union {
                   type string {
                     pattern "<.*>|$.*";
                   }
                   type uint32 {
                     range "1 .. 1000";
                   }
                 }
               }
               list destination-ip {
                 key name;
                 ordered-by user;
                 description "Destination IPV4/IPV6 address for monitoring";
                 leaf name {
                   description "Destination IPV4/IPV6 address";
                   junos:cli-feature "nokeyword";
                   type jt:ipaddr;
                 }
                 uses apply-advanced;
                 leaf routing-instance {
                   description "Routing instance to locate the destination route";
                   junos:must "(\"routing-instances $$ instance-type virtual-router\")";
                   junos:must-message "'instance-type' for the referenced routing-instance must be configured as virtual-router";
                   junos:must "((\"routing-instances $$\" || any \"tenants <*> routing-instances $$\"))";
                   junos:must-message "referenced routing-instance must be defined";
                   type string {
                     junos:posix-pattern "!^((__.*__)|(all)|(.*[ ].*)|(\"\")|(.{129,}))$";
                     junos:pattern-message "Must be a non-reserved string of 128 characters or less with no spaces.";
                   }
                 }
                 leaf weight {
                   description "SRG monitoring object ip monitoring entry weight";
                   type union {
                     type string {
                       pattern "<.*>|$.*";
                     }
                     type uint32 {
                       range "1 .. 1000";
                     }
                   }
                 }
               }
             }
             container bfd-liveliness {
               presence "enable bfd-liveliness";
               description "Configure BFD monitoring";
               uses apply-advanced;
               leaf threshold {
                 description "SRG monitoring object BFD monitoring threshold value";
                 junos:must "(\".. destination-ip\")";
                 junos:must-message "at least one bfd-liveliness destination-ip must be defined";
                 type union {
                   type string {
                     pattern "<.*>|$.*";
                   }
                   type uint32 {
                     range "1 .. 1000";
                   }
                 }
               }
               list destination-ip {
                 key name;
                 ordered-by user;
                 description "Destination IPV4/IPV6 address for monitoring";
                 leaf name {
                   description "Destination IPV4/IPV6 address for BFD monitoring";
                   junos:cli-feature "nokeyword";
                   type jt:ipaddr;
                 }
                 uses apply-advanced;
                 leaf src-ip {
                   description "Source IPV4/IPV6 address for BFD monitoring";
                   type jt:ipaddr;
                 }
                 leaf routing-instance {
                   description "Routing instance to locate the route";
                   junos:must "(\"routing-instances $$ instance-type virtual-router\")";
                   junos:must-message "'instance-type' for the referenced routing-instance must be configured as virtual-router";
                   junos:must "((\"routing-instances $$\" || any \"tenants <*> routing-instances $$\"))";
                   junos:must-message "referenced routing-instance must be defined";
                   type string {
                     junos:posix-pattern "!^((__.*__)|(all)|(.*[ ].*)|(\"\")|(.{129,}))$";
                     junos:pattern-message "Must be a non-reserved string of 128 characters or less with no spaces.";
                   }
                 }
                 leaf session-type {
                   description "BFD Mon Session Type";
                   type enumeration {
                     enum "singlehop" {
                       description "Single hop";
                       junos:must "(\".. interface\")";
                       junos:must-message "Interface should be mentioned for singlehop bfd monitoring sessions";
                     }
                     enum "multihop" {
                       description "Multihop";
                     }
                   }
                 }
                 leaf interface {
                   description "Name of the interface for single-hop sessions";
                   junos:must "((\"interfaces $$-IFL family inet\" || \"interfaces $$-IFL family inet6\"))";
                   junos:must-message "Family inet or inet6 must be defined on this logical interface";
                   junos:must "(!(\".. session-type multihop\"))";
                   junos:must-message "Interface name not allowed for multihop bfd monitoring sessions";
                   junos:must "(!((\"protocols l2-learning global-mode switching\" && \"interfaces $$ family ethernet-switching\")))";
                   junos:must-message "Referenced interface must not be ethernet-switching interface of switching mode";
                   type union {
                     type jt:interface-name;
                     type string {
                       pattern "<.*>|$.*";
                     }
                   }
                 }
                 leaf weight {
                   description "SRG monitoring object bfd monitoring entry weight";
                   type union {
                     type string {
                       pattern "<.*>|$.*";
                     }
                     type uint32 {
                       range "1 .. 1000";
                     }
                   }
                 }
               }
             }
             container interface {
               presence "enable interface";
               description "Define interfaces to monitor";
               uses apply-advanced;
               leaf threshold {
                 description "SRG monitoring object interface monitoring threshold value";
                 junos:must "(\".. interface-name\")";
                 junos:must-message "at least one interface-name must be defined";
                 type union {
                   type string {
                     pattern "<.*>|$.*";
                   }
                   type uint32 {
                     range "1 .. 1000";
                   }
                 }
               }
               list interface-name {
                 key name;
                 ordered-by user;
                 junos:cli-feature "homogeneous";
                 description "Destination IPV4/IPV6 address for monitoring";
                 leaf name {
                   description "Name of the interface to monitor";
                   junos:cli-feature "nokeyword";
                   junos:must "(\"interfaces $$\")";
                   junos:must-message "Interface must be defined before configuring monitoring";
                   type union {
                     type jt:interface-device;
                     type string {
                       pattern "<.*>|$.*";
                     }
                   }
                 }
                 uses apply-advanced;
                 leaf weight {
                   description "SRG monitoring object interface monitoring entry weight";
                   type union {
                     type string {
                       pattern "<.*>|$.*";
                     }
                     type uint32 {
                       range "1 .. 1000";
                     }
                   }
                 }
               }
             }
           }
           leaf srg-threshold {
             description "SRG monitoring threshold value";
             junos:must "(\".. monitor-object\")";
             junos:must-message "monitor-object must be defined";
             type union {
               type string {
                 pattern "<.*>|$.*";
               }
               type uint32 {
                 range "1 .. 1000";
               }
             }
           }
         }
         container active-signal-route {
           description "Configure the active signal route";
           uses apply-advanced;
           leaf ip-address {
             description "Active IPv4 address";
             junos:cli-feature "nokeyword";
             junos:must "(!(any \"chassis high-availability services-redundancy-group <*> backup-signal-route $$\"))";
             junos:must-message "active-signal-route must be different from backup-signal-route";
             junos:must "(unique \"chassis high-availability services-redundancy-group <*> active-signal-route $$\")";
             junos:must-message "active-signal-route must be unique";
             type jt:ipv4addr;
           }
           leaf routing-instance {
             description "Routing instance to install the active signal route";
             junos:must "(\"routing-instances $$ instance-type virtual-router\")";
             junos:must-message "'instance-type' for the referenced routing-instance must be configured as virtual-router";
             junos:must "((\"routing-instances $$\" || any \"tenants <*> routing-instances $$\"))";
             junos:must-message "referenced routing-instance must be defined";
             type string {
               junos:posix-pattern "!^((__.*__)|(all)|(.*[ ].*)|(\"\")|(.{129,}))$";
               junos:pattern-message "Must be a non-reserved string of 128 characters or less with no spaces.";
             }
           }
         }
         container backup-signal-route {
           description "Configure the backup signal route";
           uses apply-advanced;
           leaf ip-address {
             description "Backup IPv4 address";
             junos:cli-feature "nokeyword";
             junos:must "(!(any \"chassis high-availability services-redundancy-group <*> active-signal-route $$\"))";
             junos:must-message "backup-signal-route must be different from active-signal-route";
             junos:must "(unique \"chassis high-availability services-redundancy-group <*> backup-signal-route $$\")";
             junos:must-message "backup-signal-route must be unique";
             type jt:ipv4addr;
           }
           leaf routing-instance {
             description "Routing instance to install the backup signal route";
             junos:must "(\"routing-instances $$ instance-type virtual-router\")";
             junos:must-message "'instance-type' for the referenced routing-instance must be configured as virtual-router";
             junos:must "((\"routing-instances $$\" || any \"tenants <*> routing-instances $$\"))";
             junos:must-message "referenced routing-instance must be defined";
             type string {
               junos:posix-pattern "!^((__.*__)|(all)|(.*[ ].*)|(\"\")|(.{129,}))$";
               junos:pattern-message "Must be a non-reserved string of 128 characters or less with no spaces.";
             }
           }
         }
         container install-on-failure-route {
           description "Configure the signal route to install upon failure";
           uses apply-advanced;
           leaf ip-address {
             description "Install on failure IPv4 address";
             junos:cli-feature "nokeyword";
             type jt:ipv4addr;
           }
           leaf routing-instance {
             description "Routing instance to install the failure signal route";
             junos:must "(\"routing-instances $$ instance-type virtual-router\")";
             junos:must-message "'instance-type' for the referenced routing-instance must be configured as virtual-router";
             junos:must "((\"routing-instances $$\" || any \"tenants <*> routing-instances $$\"))";
             junos:must-message "referenced routing-instance must be defined";
             type string {
               junos:posix-pattern "!^((__.*__)|(all)|(.*[ ].*)|(\"\")|(.{129,}))$";
               junos:pattern-message "Must be a non-reserved string of 128 characters or less with no spaces.";
             }
           }
         }
         list prefix-list {
           key name;
           ordered-by user;
           description "Define a named set of address prefixes";
           leaf name {
             description "Prefix list name";
             junos:cli-feature "nokeyword";
             junos:must "(\"policy-options prefix-list $$\")";
             junos:must-message "Prefix-list name must be configured under policy-options prefix-list";
             type string;
           }
           uses apply-advanced;
           leaf routing-instance {
             description "Routing instance";
             junos:must "(\"routing-instances $$ instance-type virtual-router\")";
             junos:must-message "'instance-type' for the referenced routing-instance must be configured as virtual-router";
             junos:must "((\"routing-instances $$\" || any \"tenants <*> routing-instances $$\"))";
             junos:must-message "referenced routing-instance must be defined";
             type string {
               junos:posix-pattern "!^((__.*__)|(all)|(.*[ ].*)|(\"\")|(.{129,}))$";
               junos:pattern-message "Must be a non-reserved string of 128 characters or less with no spaces.";
             }
           }
         }
         list managed-services {
           key name;
           junos:cli-feature "oneliner";
           description "Define a named set of services to be applicable for this SRG";
           leaf name {
             junos:cli-feature "nokeyword";
             type enumeration {
               enum "ipsec" {
                 description "IPsec VPN Service";
                 junos:must "(!(\" .. .. mode active-active\"))";
                 junos:must-message " IPsec-VPN service is not allowed to be defined in active-active SRG";
               }
             }
           }
         }
         leaf preemption {
           description "Allow preemption of activeness based on priority";
           type empty;
         }
         leaf process-packet-on-backup {
           description "Enable PFE to process packets on backup node";
           type empty;
         }
         leaf activeness-priority {
           description "Activeness Priority of the node for this SRG";
           type union {
             type string {
               pattern "<.*>|$.*";
             }
             type uint8 {
               range "1 .. 254";
             }
           }
         }
       }
     }
     list node {
       key name;
       description "Set node specific parameters";
       leaf name {
         description "Node identifier";
         junos:cli-feature "nokeyword";
         type union {
           type string {
             pattern "<.*>|$.*";
           }
           type uint32 {
             range "0 .. 1";
           }
         }
       }
       uses apply-advanced;
       list fpc {
         key name;
         description "Flexible PIC Concentrator parameters";
         junos:must "((!(any \". <*> vpn-localization\") || !(\"virtual-chassis\")))";
         junos:must-message "vpn-localization cannot be configured on virtual-chassis";
         uses chassis_fpc_type;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       junos:cli-feature "nokeyword";
       type string;
     }
     list data {
       key name;
       uses macro-data-type;
       junos:cli-feature "nokeyword";
       junos:cli-feature "homogeneous";
       junos:cli-feature "oneliner";
     }
   }
   grouping chassis-pw-type {
     uses apply-advanced;
     leaf device-count {
       description "Number of pseudo-wire ps devices";
       type union {
         type string {
           pattern "<.*>|$.*";
         }
         type uint32 {
           range "1 .. 18000";
         }
       }
     }
   }
   grouping chassis_agg_dev_type {
     uses apply-advanced;
     container ethernet {
       description "Aggregated device options for Ethernet";
       uses chassisd_agg_enet_type;
     }
     container sonet {
       description "Aggregated device options for SONET";
       uses chassisd_agg_pos_type;
     }
     leaf maximum-links {
       description "Maximum links limit for aggregated devices (16, 32, or 64)";
       type union {
         type int32;
         type string {
           pattern "<.*>|$.*";
         }
       }
     }
   }
   grouping chassis_alarm_type {
     uses apply-advanced;
     container management-ethernet {
       description "Management Ethernet alarms";
       uses chassis_alarm_ethernet_type;
     }
     container otn-odu {
       description "OTN ODU alarms";
       uses chassis_alarm_otn_odu_type;
     }
     container otn-otu {
       description "OTN OTU alarms";
       uses chassis_alarm_otn_otu_type;
     }
     container sonet {
       description "SONET alarms";
       uses chassis_alarm_sonet_type;
     }
     container t3 {
       description "DS3 alarms";
       uses chassis_alarm_ds3_type;
     }
     container ds1 {
       description "DS1 alarms";
       uses chassis_alarm_ds1_type;
     }
     container ethernet {
       description "Ethernet alarms";
       uses chassis_alarm_ethernet_type;
     }
     container l2-chan-err-ethernet {
       description "L2 channel error ethernet alarms";
       uses chassis_alarm_l2_chan_err_type;
     }
     container integrated-services {
       description "Integrated services alarms";
       uses chassis_alarm_integrated_services_type;
     }
     container services {
       description "Services PIC alarms";
       uses chassis_alarm_services_type;
     }
     container serial {
       description "Serial alarms";
       uses chassis_alarm_serial_type;
     }
     container fibre-channel {
       description "Fibre Channel alarms";
       uses chassis_alarm_fibre-channel_type;
     }
     leaf pem-absence {
       description "Power supply module absence";
       type enumeration {
         enum "ignore" {
           description "Ignore the power supply module absence alarm";
         }
       }
     }
     container fru-absence {
       description "FRU module absence";
       uses apply-advanced;
       container ignore {
         description "Ignore the power supply module absence alarm";
         uses apply-advanced;
         list fpc {
           key name;
           ordered-by user;
           description "FPC Slot Number";
           uses chassis_fpc_type_slot;
         }
       }
     }
     leaf ignore-fan-speed-check {
       description "Ignore the Fan speed check alarms";
       type empty;
     }
   }
   grouping chassis_alarm_ds1_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ds3_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf exz {
       description "Excessive zeros";
       type enumeration {
         enum "red" {
           description "Assert red system alarm";
         }
         enum "yellow" {
           description "Assert yellow system alarm";
         }
         enum "ignore" {
           description "Do not assert any alarm signals";
         }
       }
     }
     leaf ferf {
       description "Far-end failure";
       type enumeration {
         enum "red" {
           description "Assert red system alarm";
         }
         enum "yellow" {
           description "Assert yellow system alarm";
         }
         enum "ignore" {
           description "Do not assert any alarm signals";
         }
       }
     }
     leaf idle {
       description "Idle alarm";
       type enumeration {
         enum "red" {
           description "Assert red system alarm";
         }
         enum "yellow" {
           description "Assert yellow system alarm";
         }
         enum "ignore" {
           description "Do not assert any alarm signals";
         }
       }
     }
     leaf lcv {
       description "Line code violation";
       type enumeration {
         enum "red" {
           description "Assert red system alarm";
         }
         enum "yellow" {
           description "Assert yellow system alarm";
         }
         enum "ignore" {
           description "Do not assert any alarm signals";
         }
       }
     }
     leaf lof {
       description "Loss of frame";
       type enumeration {
         enum "red" {
           description "Assert red system alarm";
         }
         enum "yellow" {
           description "Assert yellow system alarm";
         }
         enum "ignore" {
           description "Do not assert any alarm signals";
         }
       }
     }
     leaf los {
       description "Loss of signal";
       type enumeration {
         enum "red" {
           description "Assert red system alarm";
         }
         enum "yellow" {
           description "Assert yellow system alarm";
         }
         enum "ignore" {
           description "Do not assert any alarm signals";
         }
       }
     }
     leaf pll {
       description "Phase-locked loop out of lock";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ethernet_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_fibre-channel_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_integrated_services_type {
     uses apply-advanced;
     leaf failure {
       description "Integrated Services failure";
       type enumeration {
         enum "red" {
           description "Assert red system alarm";
         }
         enum "yellow" {
           description "Assert yellow system alarm";
         }
         enum "ignore" {
           description "Do not assert any alarm signals";
         }
       }
     }
   }
   grouping chassis_alarm_l2_chan_err_type {
     uses apply-advanced;
     leaf l2-channel-errors {
       description "Received L2 channel error";
       type enumeration {
         enum "red" {
           description "Assert red system alarm";
         }
         enum "yellow" {
           description "Assert yellow system alarm";
         }
         enum "ignore" {
           description "Do not assert any alarm signals";
         }
       }
     }
     leaf l2-channel-error-threshold {
       description "L2 channel error threshold - 50,000 as default";
       type union {
         type string {
           pattern "<.*>|$.*";
         }
         type uint32 {
           range "1 .. 4294967295";
         }
       }
     }
   }
   grouping chassis_alarm_otn_odu_type {
     uses apply-advanced;
     leaf odu-bdi {
       description "ODU backward-defect-indicator, ODU-BDI failure";
       type enumeration {
         enum "red" {
           description "Assert red system alarm";
         }
         enum "yellow" {
           description "Assert yellow system alarm";
         }
         enum "ignore" {
           description "Do not assert any alarm signals";
         }
       }
     }
     leaf odu-ttim {
       description "ODU trail-trace-identifier-mismatch, ODU-TTIM failure";
       type enumeration {
         enum "red" {
           description "Assert red system alarm";
         }
         enum "yellow" {
           description "Assert yellow system alarm";
         }
         enum "ignore" {
           description "Do not assert any alarm signals";
         }
       }
     }
     leaf odu-ptim {
       description "ODU payload-type-mismatch, ODU-PTIM failure";
       type enumeration {
         enum "red" {
           description "Assert red system alarm";
         }
         enum "yellow" {
           description "Assert yellow system alarm";
         }
         enum "ignore" {
           description "Do not assert any alarm signals";
         }
       }
     }
   }
   grouping chassis_alarm_otn_otu_type {
     uses apply-advanced;
     leaf oc-los {
       description "Loss of signal, LOS failure";
       type enumeration {
         enum "red" {
           description "Assert red system alarm";
         }
         enum "yellow" {
           description "Assert yellow system alarm";
         }
         enum "ignore" {
           description "Do not assert any alarm signals";
         }
       }
     }
     leaf oc-lof {
       description "Loss of framing, LOF failure";
       type enumeration {
         enum "red" {
           description "Assert red system alarm";
         }
         enum "yellow" {
           description "Assert yellow system alarm";
         }
         enum "ignore" {
           description "Do not assert any alarm signals";
         }
       }
     }
     leaf oc-lom {
       description "Loss of multiframe, LOM failure";
       type enumeration {
         enum "red" {
           description "Assert red system alarm";
         }
         enum "yellow" {
           description "Assert yellow system alarm";
         }
         enum "ignore" {
           description "Do not assert any alarm signals";
         }
       }
     }
     leaf wavelength-lock {
       description "Wavelength lock alarm";
       type enumeration {
         enum "red" {
           description "Assert red system alarm";
         }
         enum "yellow" {
           description "Assert yellow system alarm";
         }
         enum "ignore" {
           description "Do not assert any alarm signals";
         }
       }
     }
     leaf otu-bdi {
       description "OTU backward-defect-indicator, OTU-BDI failure";
       type enumeration {
         enum "red" {
           description "Assert red system alarm";
         }
         enum "yellow" {
           description "Assert yellow system alarm";
         }
         enum "ignore" {
           description "Do not assert any alarm signals";
         }
       }
     }
     leaf otu-iae {
       description "OTU incoming-alignment-error, OTU-IAE failure";
       type enumeration {
         enum "red" {
           description "Assert red system alarm";
         }
         enum "yellow" {
           description "Assert yellow system alarm";
         }
         enum "ignore" {
           description "Do not assert any alarm signals";
         }
       }
     }
     leaf otu-ttim {
       description "OTU trail-trace-identifier-mismatch, OTU-TTIM failure";
       type enumeration {
         enum "red" {
           description "Assert red system alarm";
         }
         enum "yellow" {
           description "Assert yellow system alarm";
         }
         enum "ignore" {
           description "Do not assert any alarm signals";
         }
       }
     }
     leaf otu-fec-excessive-errs {
       description "OTU fec-excessive-errors, OTU-FEC_EXE failure";
       type enumeration {
         enum "red" {
           description "Assert red system alarm";
         }
         enum "yellow" {
           description "Assert yellow system alarm";
         }
         enum "ignore" {
           description "Do not assert any alarm signals";
         }
       }
     }
   }
   grouping chassis_alarm_serial_type {
     uses apply-advanced;
     leaf loss-of-rx-clock {
       description "RX clock absent";
       type enumeration {
         enum "red" {
           description "Assert red system alarm";
         }
         enum "yellow" {
           description "Assert yellow system alarm";
         }
         enum "ignore" {
           description "Do not assert any alarm signals";
         }
       }
     }
     leaf loss-of-tx-clock {
       description "TX clock absent";
       type enumeration {
         enum "red" {
           description "Assert red system alarm";
         }
         enum "yellow" {
           description "Assert yellow system alarm";
         }
         enum "ignore" {
           description "Do not assert any alarm signals";
         }
       }
     }
     leaf dcd-absent {
       description "DCD signal absent";
       type enumeration {
         enum "red" {
           description "Assert red system alarm";
         }
         enum "yellow" {
           description "Assert yellow system alarm";
         }
         enum "ignore" {
           description "Do not assert any alarm signals";
         }
       }
     }
     leaf cts-absent {
       description "CTS signal absent";
       type enumeration {
         enum "red" {
           description "Assert red system alarm";
         }
         enum "yellow" {
           description "Assert yellow system alarm";
         }
         enum "ignore" {
           description "Do not assert any alarm signals";
         }
       }
     }
     leaf dsr-absent {
       description "DSR signal absent";
       type enumeration {
         enum "red" {
           description "Assert red system alarm";
         }
         enum "yellow" {
           description "Assert yellow system alarm";
         }
         enum "ignore" {
           description "Do not assert any alarm signals";
         }
       }
     }
     leaf tm-absent {
       description "TM signal absent";
       type enumeration {
         enum "red" {
           description "Assert red system alarm";
         }
         enum "yellow" {
           description "Assert yellow system alarm";
         }
         enum "ignore" {
           description "Do not assert any alarm signals";
         }
       }
     }
   }
   grouping chassis_alarm_services_type {
     uses apply-advanced;
     leaf pic-reset {
       description "Services PIC reset";
       type enumeration {
         enum "red" {
           description "Assert red system alarm";
         }
         enum "yellow" {
           description "Assert yellow system alarm";
         }
         enum "ignore" {
           description "Do not assert any alarm signals";
         }
       }
     }
     leaf pic-hold-reset {
       description "Services PIC held in reset";
       type enumeration {
         enum "red" {
           description "Assert red system alarm";
         }
         enum "yellow" {
           description "Assert yellow system alarm";
         }
         enum "ignore" {
           description "Do not assert any alarm signals";
         }
       }
     }
     leaf linkdown {
       description "Services PIC linkdown";
       type enumeration {
         enum "red" {
           description "Assert red system alarm";
         }
         enum "yellow" {
           description "Assert yellow system alarm";
         }
         enum "ignore" {
           description "Do not assert any alarm signals";
         }
       }
     }
     leaf rx-errors {
       description "Services PIC excessive rx errors";
       type enumeration {
         enum "red" {
           description "Assert red system alarm";
         }
         enum "yellow" {
           description "Assert yellow system alarm";
         }
         enum "ignore" {
           description "Do not assert any alarm signals";
         }
       }
     }
     leaf tx-errors {
       description "Services PIC excessive tx errors";
       type enumeration {
         enum "red" {
           description "Assert red system alarm";
         }
         enum "yellow" {
           description "Assert yellow system alarm";
         }
         enum "ignore" {
           description "Do not assert any alarm signals";
         }
       }
     }
     leaf sw-down {
       description "Services PIC software problem";
       type enumeration {
         enum "red" {
           description "Assert red system alarm";
         }
         enum "yellow" {
           description "Assert yellow system alarm";
         }
         enum "ignore" {
           description "Do not assert any alarm signals";
         }
       }
     }
     leaf hw-down {
       description "Services PIC hardware problem";
       type enumeration {
         enum "red" {
           description "Assert red system alarm";
         }
         enum "yellow" {
           description "Assert yellow system alarm";
         }
         enum "ignore" {
           description "Do not assert any alarm signals";
         }
       }
     }
   }
   grouping chassis_alarm_sonet_type {
     uses apply-advanced;
     leaf lol {
       description "Loss of light";
       type enumeration {
         enum "red" {
           description "Assert red system alarm";
         }
         enum "yellow" {
           description "Assert yellow system alarm";
         }
         enum "ignore" {
           description "Do not assert any alarm signals";
         }
       }
     }
     leaf pll {
       description "Phase locked loop out of lock";
       type enumeration {
         enum "red" {
           description "Assert red system alarm";
         }
         enum "yellow" {
           description "Assert yellow system alarm";
         }
         enum "ignore" {
           description "Do not assert any alarm signals";
         }
       }
     }
     leaf lof {
       description "Loss of framing, LOF failure";
       type enumeration {
         enum "red" {
           description "Assert red system alarm";
         }
         enum "yellow" {
           description "Assert yellow system alarm";
         }
         enum "ignore" {
           description "Do not assert any alarm signals";
         }
       }
     }
     leaf los {
       description "Loss of signal, LOS failure";
       type enumeration {
         enum "red" {
           description "Assert red system alarm";
         }
         enum "yellow" {
           description "Assert yellow system alarm";
         }
         enum "ignore" {
           description "Do not assert any alarm signals";
         }
       }
     }
     leaf ais-l {
       description "Line alarm indication signal, AIS-L failure";
       type enumeration {
         enum "red" {
           description "Assert red system alarm";
         }
         enum "yellow" {
           description "Assert yellow system alarm";
         }
         enum "ignore" {
           description "Do not assert any alarm signals";
         }
       }
     }
     leaf ais-p {
       description "Path alarm indication signal, AIS-P failure";
       type enumeration {
         enum "red" {
           description "Assert red system alarm";
         }
         enum "yellow" {
           description "Assert yellow system alarm";
         }
         enum "ignore" {
           description "Do not assert any alarm signals";
         }
       }
     }
     leaf lop-p {
       description "Loss of pointer, LOP-P failure";
       type enumeration {
         enum "red" {
           description "Assert red system alarm";
         }
         enum "yellow" {
           description "Assert yellow system alarm";
         }
         enum "ignore" {
           description "Do not assert any alarm signals";
         }
       }
     }
     leaf ber-sd {
       description "Signal Degrade (SD), bit error rate > 1E-6";
       type enumeration {
         enum "red" {
           description "Assert red system alarm";
         }
         enum "yellow" {
           description "Assert yellow system alarm";
         }
         enum "ignore" {
           description "Do not assert any alarm signals";
         }
       }
     }
     leaf ber-sf {
       description "Signal Fail (SF), bit error rate > 1E-3";
       type enumeration {
         enum "red" {
           description "Assert red system alarm";
         }
         enum "yellow" {
           description "Assert yellow system alarm";
         }
         enum "ignore" {
           description "Do not assert any alarm signals";
         }
       }
     }
     leaf rfi-l {
       description "Line remote failure indication, RFI-L, line FERF";
       type enumeration {
         enum "red" {
           description "Assert red system alarm";
         }
         enum "yellow" {
           description "Assert yellow system alarm";
         }
         enum "ignore" {
           description "Do not assert any alarm signals";
         }
       }
     }
     leaf rfi-p {
       description "Path remote failure indication, RFI-P, STS path yellow";
       type enumeration {
         enum "red" {
           description "Assert red system alarm";
         }
         enum "yellow" {
           description "Assert yellow system alarm";
         }
         enum "ignore" {
           description "Do not assert any alarm signals";
         }
       }
     }
     leaf uneq-p {
       description "STS Path (C2) unequipped, UNEQ-P failure";
       type enumeration {
         enum "red" {
           description "Assert red system alarm";
         }
         enum "yellow" {
           description "Assert yellow system alarm";
         }
         enum "ignore" {
           description "Do not assert any alarm signals";
         }
       }
     }
     leaf locd {
       description "Loss of cell delineation (ATM only)";
       type enumeration {
         enum "red" {
           description "Assert red system alarm";
         }
         enum "yellow" {
           description "Assert yellow system alarm";
         }
         enum "ignore" {
           description "Do not assert any alarm signals";
         }
       }
     }
     leaf plm-p {
       description "STS payload label (C2) mismatch, PLM-P failure";
       type enumeration {
         enum "red" {
           description "Assert red system alarm";
         }
         enum "yellow" {
           description "Assert yellow system alarm";
         }
         enum "ignore" {
           description "Do not assert any alarm signals";
         }
       }
     }
   }
   grouping chassis_cb_type {
     leaf name {
       description "CB slot number";
       junos:cli-feature "nokeyword";
       type union {
         type string {
           pattern "<.*>|$.*";
         }
         type uint32;
       }
     }
     uses apply-advanced;
     container temperature-threshold {
       description "CB temperature thresholds";
       uses chassis-temperature-threshold-type;
     }
   }
   grouping chassis-temperature-threshold-type {
     description "Chassis temperature thresholds";
     uses apply-advanced;
     leaf fans-to-normal-speed {
       description "Threshold at which fans return to normal speed";
       units "degrees C";
       type union {
         type uint32;
         type string {
           pattern "<.*>|$.*";
         }
       }
     }
     leaf fans-on-intermediate-speed {
       description "Threshold at which fans run intermediate speed";
       units "degrees C";
       type union {
         type uint32;
         type string {
           pattern "<.*>|$.*";
         }
       }
     }
     leaf fans-on-full-speed {
       description "Threshold at which fans run full speed";
       units "degrees C";
       type union {
         type uint32;
         type string {
           pattern "<.*>|$.*";
         }
       }
     }
     leaf fans-on-full-speed-if-failed-fan {
       description "Threshold at which fans run full speed when bad fan present";
       units "degrees C";
       type union {
         type uint32;
         type string {
           pattern "<.*>|$.*";
         }
       }
     }
     leaf yellow-alarm {
       description "Threshold at which yellow alarm is set";
       units "degrees C";
       type union {
         type uint32;
         type string {
           pattern "<.*>|$.*";
         }
       }
     }
     leaf yellow-alarm-if-failed-fan {
       description "Threshold at which yellow alarm is set when bad fan present";
       units "degrees C";
       type union {
         type uint32;
         type string {
           pattern "<.*>|$.*";
         }
       }
     }
     leaf red-alarm {
       description "Threshold at which red alarm is set";
       units "degrees C";
       type union {
         type uint32;
         type string {
           pattern "<.*>|$.*";
         }
       }
     }
     leaf red-alarm-if-failed-fan {
       description "Threshold at which red alarm is set when bad fan present";
       units "degrees C";
       type union {
         type uint32;
         type string {
           pattern "<.*>|$.*";
         }
       }
     }
     leaf fire-shutdown {
       description "Threshold at which router will be shutdown within 10 seconds";
       units "degrees C";
       type union {
         type uint32;
         type string {
           pattern "<.*>|$.*";
         }
       }
     }
   }
   grouping chassis_fabric_cards_type {
     uses apply-advanced;
     leaf reset-count {
       description "Number of times sib can be reset by cmerror";
       type union {
         type string {
           pattern "<.*>|$.*";
         }
         type uint32 {
           range "1 .. 10";
         }
       }
     }
   }
   grouping chassis_fabric_type {
     junos:cli-feature "oneliner-plus";
     uses apply-advanced;
     leaf upgrade-mode {
       description "Enable online switch fabric upgrade";
       type enumeration {
         enum "default" {
           description "Fabric upgrade";
         }
         enum "t4000" {
           description "T4000 Fabric upgrade";
           junos:must "(!(any \"class-of-service schedulers <*> drop-profile-map loss-priority <*> protocol non-tcp drop-profile <*>\"))";
           junos:must-message "protocol based classification not allowed, only 'any' protocol config allowed";
           junos:must "(!(any \"class-of-service schedulers <*> drop-profile-map loss-priority <*> protocol tcp drop-profile <*>\"))";
           junos:must-message "protocol based classification not allowed, only 'any' protocol config allowed";
         }
         enum "3d-fabric" {
           description "TXP-3D Fabric upgrade";
           junos:must "(!(any \"class-of-service schedulers <*> drop-profile-map loss-priority <*> protocol non-tcp drop-profile <*>\"))";
           junos:must-message "protocol based classification not allowed, only 'any' protocol config allowed";
           junos:must "(!(any \"class-of-service schedulers <*> drop-profile-map loss-priority <*> protocol tcp drop-profile <*>\"))";
           junos:must-message "protocol based classification not allowed, only 'any' protocol config allowed";
         }
       }
     }
     container event {
       description "Fabric events";
       uses apply-advanced;
       container link-failure {
         presence "enable link-failure";
         description "Fabric link failure";
         uses apply-advanced;
         container action {
           presence "enable action";
           description "Fabric action to be taken";
           uses apply-advanced;
         }
       }
       container reachability-fault {
         presence "enable reachability-fault";
         description "Fabric reachability fault detection";
         uses apply-advanced;
         container degraded {
           presence "enable degraded";
           description "Degraded fabric configuration";
           uses apply-advanced;
           container error-threshold {
             presence "enable error-threshold";
             description "Fabric error threshold for degraded case";
             uses apply-advanced;
             container degradation {
               presence "enable degradation";
               description "Degradation attributes";
               uses apply-advanced;
             }
           }
         }
         container actions {
           description "Reachability fault actions";
           uses apply-advanced;
           container recovery-failure {
             description "Recovery failure action to be taken for FHP";
             uses apply-advanced;
           }
         }
       }
     }
     container oam {
       description "Fabric OAM configuration";
       uses apply-advanced;
     }
     container degraded {
       presence "enable degraded";
       description "Degraded fabric configuration";
       uses apply-advanced;
       leaf action-fpc-restart-disable {
         description "Limit degraded fabric actions to Plane restart only";
         type empty;
       }
     }
     container redundancy-mode {
       description "Fabric redundancy mode";
       uses apply-advanced;
       choice mode {
         case case_1 {
           leaf redundant {
             description "Fabric is configured in redundant mode";
             type empty;
           }
         }
         case case_2 {
           leaf increased-bandwidth {
             description "Fabric is configured in increased bandwidth mode";
             type empty;
           }
         }
       }
     }
   }
   grouping chassis_feb_type {
     uses apply-advanced;
     container sanity-poll {
       description "FPC register sanity poll";
       uses apply-advanced;
       leaf retry-count {
         description "Number of retries before reporting error";
         default "10";
         type union {
           type string {
             pattern "<.*>|$.*";
           }
           type uint32 {
             range "1 .. 30";
           }
         }
       }
       container on-error {
         description "Actions to be taken if inconsistencies are detected";
         uses apply-advanced;
         leaf raise-alarm {
           description "Raise emergency alarm";
           type empty;
         }
         leaf power {
           description "Power cycle or power off FPC";
           type enumeration {
             enum "cycle" {
               description "Write coredump and reboot FPC";
             }
             enum "off" {
               description "Power down FPC indefinitely";
             }
           }
         }
         leaf write-coredump {
           description "Write coredump and continue";
           type empty;
         }
       }
     }
   }
   grouping chassis_fpc_type {
     leaf name {
       description "FPC slot number";
       junos:cli-feature "nokeyword";
       type union {
         type string {
           pattern "<.*>|$.*";
         }
         type uint32;
       }
     }
     uses apply-advanced;
     container auto-speed-detection {
       description "Disables auto-speed detection";
       uses apply-advanced;
       choice auto-speed-detections {
         case case_1 {
           leaf disable {
             description "Disables automatic speed detection";
             type empty;
           }
         }
       }
     }
     container linkscan-per-fpc {
       presence "enable linkscan-per-fpc";
       description "Configure linkscan per FPC";
       uses apply-advanced;
       leaf fpc-linkscan-interval {
         description " setting linkscan interval of FPC in microsecond";
         type union {
           type string {
             pattern "<.*>|$.*";
           }
           type uint32 {
             range "10000 .. 500000";
           }
         }
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               type empty;
             }
             leaf unicast-in-lpm {
               description "Install unicast host entries in LPM table";
               type empty;
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:16K, needs reboot for VC; restarts PFE if standalone";
           }
         }
         case case_8 {
           container vxlan-gbp-l2-profile {
             presence "enable vxlan-gbp-l2-profile";
             description "MAC: 64K L3-host: 32K LPM: 16K EM:16K, needs reboot for VC; restarts PFE if standalone";
           }
         }
         case case_9 {
           container vxlan-gbp-l3-profile {
             presence "enable vxlan-gbp-l3-profile";
             description "MAC: 32K L3-host: 64K LPM: 16K EM:16K, needs reboot for VC; restarts PFE if standalone";
           }
         }
         case case_10 {
           container em-hw-profile {
             presence "enable em-hw-profile";
             description "MAC: 48K L3-host: 48K LPM: 16K EM:32K, needs reboot for VC; restarts PFE if standalone";
           }
         }
         case case_11 {
           container default-profile {
             presence "enable default-profile";
             description "MAC: 64K L3-host: 32K LPM: 24K IFP: 12K, needs reboot for VC; restarts PFE if standalone";
           }
         }
         case case_12 {
           container ifp-profile {
             presence "enable ifp-profile";
             description "MAC: 64K L3-host: 32K LPM: 12K IFP: 18K, needs reboot for VC; restarts PFE if standalone";
           }
         }
         case case_13 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     list pic {
       key name;
       description "Physical Interface Card number";
       uses chassis_pic_type;
     }
     list mic {
       key name;
       description "Modular Interface Card number";
       uses chassis_mic_type;
     }
     leaf power {
       description "Power FPCs on or off";
       type enumeration {
         enum "off" {
           description "Do not provide power to FPCs";
         }
         enum "on" {
           description "Provide power to FPCs";
         }
       }
     }
     choice mode {
       case case_1 {
         leaf disable-power {
           description "Do not provide power to the card";
           status deprecated;
           type empty;
         }
       }
       case case_2 {
         leaf allow-sram-parity-errors {
           description "Do not power cycle FPC when SRAM parity errors occur";
           type empty;
         }
       }
     }
     choice riot-mode {
       case case_1 {
       }
       case case_2 {
       }
     }
     leaf services-offload {
       description "Enable services offload on fpc";
       status deprecated;
       type empty;
     }
     leaf cfp-to-et {
       description "Enable ET interface and remove CFP client";
       type empty;
     }
     container lossless-flow-control {
       presence "enable lossless-flow-control";
       description "Lossless buffer config for Ethernet Mac pause";
       uses apply-advanced;
       choice enable_choice {
         case case_1 {
           leaf lossless-flow-control-enable {
             description "Enable Lossless buffer config for Ethernet Mac pause";
             type empty;
           }
         }
         case case_2 {
           leaf no-lossless-flow-control-enable {
             description "Disable Lossless buffer config for Ethernet Mac pause";
             type empty;
           }
         }
       }
     }
     leaf np-cache {
       description "Enable NP cache and services offload on fpc";
       status deprecated;
       type empty;
     }
     leaf np-cache-disable {
       description "Disable NP cache and services offload on fpc";
       type empty;
     }
     leaf offline {
       description "Keep FPC offline";
       type empty;
     }
     leaf offline-on-fabric-bandwidth-reduction {
       description "Bring FPC offline when running with reduced fabric bandwidth";
       type empty;
     }
     container fabric {
       presence "enable fabric";
       uses apply-advanced;
       leaf blackhole-action {
         description "Action taken upon fabric plane blackhole involving the FPC";
         type enumeration {
           enum "log-only" {
             description "Log the detected blackhole condition";
           }
           enum "offline" {
             description "Offline the FPC";
           }
           enum "restart" {
             description "Restart the FPC";
           }
           enum "restart-then-offline" {
             description "Restart the FPC and offline in subsequent action. ";
           }
         }
       }
       container bandwidth-degradation {
         description "Take FPC recovery action when FPC running with reduced fabric bandwidth";
         uses apply-advanced;
         leaf percentage {
           description "The percentage of PFE bandwidth degradation to trigger action";
           type union {
             type string {
               pattern "<.*>|$.*";
             }
             type uint32 {
               range "1 .. 99";
             }
           }
         }
         leaf no-fabric-switchover {
           description "Do not perform switchover to spare CB";
           type empty;
         }
         leaf action {
           description "Type of action to trigger";
           type enumeration {
             enum "log-only" {
               description "Log the bandwidth degradation only";
             }
             enum "offline" {
               description "Offline the FPC, default action";
             }
             enum "restart" {
               description "Restart the FPC";
             }
             enum "restart-then-offline" {
               description "Restart the FPC and offline in subsequent action";
             }
           }
         }
       }
     }
     list port-mirror-instance {
       key name;
       ordered-by user;
       max-elements 2;
       leaf name {
         description "Associate a port mirroring instance with the FPC";
         junos:cli-feature "nokeyword";
         junos:must "(!(\"forwarding-options port-mirroring instance $$ input-parameters-instance\"))";
         junos:must-message "Derived instance cannot be binded";
         junos:must "(((!(\"chassis network-services lan\") && (\"forwarding-options port-mirroring instance $$\" || \"forwarding-options analyzer $$\")) || \"chassis network-services lan\"))";
         junos:must-message "Referenced port-mirroring instance does not exist";
         type string {
           length "1 .. 64";
         }
       }
       uses apply-advanced;
     }
     list sampling-instance {
       key name;
       ordered-by user;
       max-elements 1;
       leaf name {
         description "Associate a sampling instance with the FPC";
         junos:cli-feature "nokeyword";
         junos:must "(\"forwarding-options sampling instance $$\")";
         junos:must-message "Referenced sampling instance does not exist";
         type string {
           length "1 .. 64";
         }
       }
       uses apply-advanced;
     }
     container inline-services {
       uses apply-advanced;
       leaf report-zero-oif-gw-on-discard {
         description "Jflow reports value zero in OIF and GW when traffic is not forwarded";
         type empty;
       }
       leaf flex-flow-sizing {
         description "No fixed size allocation of flow tables for proto families";
         junos:must "(!((\".. flow-table-size ipv4-flow-table-size\" || (\".. flow-table-size ipv6-flow-table-size\" || (\".. flow-table-size vpls-flow-table-size\" || (\".. flow-table-size bridge-flow-table-size\" || \".. flow-table-size mpls-flow-table-size\"))))))";
         junos:must-message "flex-flow-sizing and flow-table-size are mutually exclusive";
         type empty;
       }
       leaf use-extended-flow-memory {
         description "Use extended memory for flow records";
         type empty;
       }
       container flow-table-size {
         uses apply-advanced;
         leaf ipv4-flow-table-size {
           description "IPv4 flow table size in units of 256k";
           junos:must "(!(\".. .. flex-flow-sizing\"))";
           junos:must-message "flex-flow-sizing and flow-table-size are mutually exclusive";
           type union {
             type string {
               pattern "<.*>|$.*";
             }
             type uint32 {
               range "1 .. 245";
             }
           }
         }
         leaf ipv6-flow-table-size {
           description "IPv6 flow table size in units of 256k";
           junos:must "(!(\".. .. flex-flow-sizing\"))";
           junos:must-message "flex-flow-sizing and flow-table-size are mutually exclusive";
           type union {
             type string {
               pattern "<.*>|$.*";
             }
             type uint32 {
               range "1 .. 245";
             }
           }
         }
         leaf vpls-flow-table-size {
           description "VPLS flow table size in units of 256k";
           status deprecated;
           junos:must "(!(\".. .. flex-flow-sizing\"))";
           junos:must-message "flex-flow-sizing and flow-table-size are mutually exclusive";
           type union {
             type string {
               pattern "<.*>|$.*";
             }
             type uint32 {
               range "1 .. 245";
             }
           }
         }
         leaf bridge-flow-table-size {
           description "BRIDGE flow table size in units of 256k";
           junos:must "(!(\".. .. flex-flow-sizing\"))";
           junos:must-message "flex-flow-sizing and flow-table-size are mutually exclusive";
           junos:must "(!(\".. vpls-flow-table-size\"))";
           junos:must-message "Both vpls-flow-table-size and bridge-flow-table-size can not be configured/allowed";
           type union {
             type string {
               pattern "<.*>|$.*";
             }
             type uint32 {
               range "1 .. 245";
             }
           }
         }
         leaf ipv6-extended-attrib {
           description "Enable extended flow attribute";
           type empty;
         }
         leaf mpls-flow-table-size {
           description "MPLS flow table size in units of 256k";
           junos:must "(!(\".. .. flex-flow-sizing\"))";
           junos:must-message "flex-flow-sizing and flow-table-size are mutually exclusive";
           type union {
             type string {
               pattern "<.*>|$.*";
             }
             type uint32 {
               range "1 .. 245";
             }
           }
         }
       }
     }
     container inline-video-monitoring {
       uses apply-advanced;
       leaf maximum-flows-count {
         description "Maximum number of inline video monitoring flows per PFE instance.";
         status deprecated;
         type union {
           type string {
             pattern "<.*>|$.*";
           }
           type uint32 {
             range "16 .. 8192";
           }
         }
       }
       leaf flow-table-size {
         description "Size of flow table size per PFE instance";
         type union {
           type string {
             pattern "<.*>|$.*";
           }
           type uint32 {
             range "16 .. 8192";
           }
         }
       }
     }
     container slamon-services {
       description "SLA monitoring services";
       uses apply-advanced;
     }
     list pfe {
       key name;
       description "Packet forwarding engine parameters";
       uses chassis_pfe_type;
     }
     container error {
       description "Error level configuration for FPC";
       uses chassis_fpc_error_type;
     }
   }
   grouping chassis_fpc_error_type {
     description "Chassis Fpc Error level";
     uses apply-advanced;
     container fatal {
       description "FPC Fatal errors (default threshold = 1)";
       uses chassis_fpc_error_level_major_fatal;
     }
     container major {
       description "FPC Major Level errors (default threshold = 1)";
       uses chassis_fpc_error_level_major_fatal;
     }
     container minor {
       description "FPC Minor Level errors (default threshold = 10)";
       uses chassis_fpc_error_level_minor;
     }
   }
   grouping chassis_fpc_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         junos:cli-feature "nokeyword";
         type enumeration {
           enum "reset" {
             description "Reset FPC";
             junos:must "(!(\".. .. action offline-pfe\"))";
             junos:must-message "'reset' and 'offline-pfe' cannot be both configured";
             junos:must "(!(\".. .. action reset-pfe\"))";
             junos:must-message "'reset' and 'reset-pfe' cannot be both configured";
             junos:must "(!(\".. .. action offline\"))";
             junos:must-message "'reset' and 'offline' cannot be both configured";
           }
           enum "offline" {
             description "Offline FPC";
             junos:must "(!(\".. .. action offline-pfe\"))";
             junos:must-message "'offline' and 'offline-pfe' cannot be both configured";
             junos:must "(!(\".. .. action reset-pfe\"))";
             junos:must-message "'offline' and 'reset-pfe' cannot be both configured";
             junos:must "(!(\".. .. action reset\"))";
             junos:must-message "'offline' and 'reset' cannot be both configured";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
             junos:must "(!(\".. .. action offline\"))";
             junos:must-message "'reset-pfe' and 'offline' cannot be both configured";
             junos:must "(!(\".. .. action reset\"))";
             junos:must-message "'reset-pfe' and 'reset' cannot be both configured";
             junos:must "(!(\".. .. action offline-pfe\"))";
             junos:must-message "'reset-pfe' and 'offline-pfe' cannot be both configured";
             junos:must "(!(\".. .. action disable-pfe\"))";
             junos:must-message "'reset-pfe' and 'disable-pfe' cannot be both configured";
           }
           enum "offline-pic" {
             description "Offline PICs associated with PFE on FPC";
           }
           enum "trap" {
             description "Raise FPC trap";
           }
         }
       }
       uses apply-advanced;
     }
   }
   grouping chassis_fpc_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         junos:cli-feature "nokeyword";
         type enumeration {
           enum "reset" {
             description "Reset FPC";
             junos:must "(!(\".. .. action offline-pfe\"))";
             junos:must-message "'reset' and 'offline-pfe' cannot be both configured";
             junos:must "(!(\".. .. action reset-pfe\"))";
             junos:must-message "'reset' and 'reset-pfe' cannot be both configured";
             junos:must "(!(\".. .. action offline\"))";
             junos:must-message "'reset' and 'offline' cannot be both configured";
           }
           enum "offline" {
             description "Offline FPC";
             junos:must "(!(\".. .. action offline-pfe\"))";
             junos:must-message "'offline' and 'offline-pfe' cannot be both configured";
             junos:must "(!(\".. .. action reset-pfe\"))";
             junos:must-message "'offline' and 'reset-pfe' cannot be both configured";
             junos:must "(!(\".. .. action reset\"))";
             junos:must-message "'offline' and 'reset' cannot be both configured";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
             junos:must "(!(\".. .. action offline\"))";
             junos:must-message "'reset-pfe' and 'offline' cannot be both configured";
             junos:must "(!(\".. .. action reset\"))";
             junos:must-message "'reset-pfe' and 'reset' cannot be both configured";
             junos:must "(!(\".. .. action offline-pfe\"))";
             junos:must-message "'reset-pfe' and 'offline-pfe' cannot be both configured";
             junos:must "(!(\".. .. action disable-pfe\"))";
             junos:must-message "'reset-pfe' and 'disable-pfe' cannot be both configured";
           }
           enum "offline-pic" {
             description "Offline PICs associated with PFE on FPC";
           }
           enum "trap" {
             description "Raise FPC trap";
           }
         }
       }
       uses apply-advanced;
     }
   }
   grouping chassis_fpc_type_slot {
     leaf name {
       description "FPC slot number";
       junos:cli-feature "nokeyword";
       type string;
     }
     uses apply-advanced;
     list pem {
       key name;
       ordered-by user;
       description "Power Supply Module slot";
       uses chassis_pem_type_slot;
     }
   }
   grouping chassis_junos_fru_error_type {
     description "Chassis Fru Error level";
     uses apply-advanced;
     container fatal {
       description "FRU Fatal errors (default threshold = 1)";
       uses chassis_fru_error_level_major_fatal;
     }
     container major {
       description "FRU Major errors (default threshold = 1)";
       uses chassis_fru_error_level_major_fatal;
     }
     container minor {
       description "FRU Minor errors (default threshold = 10)";
       uses chassis_fru_error_level_minor;
     }
   }
   grouping chassis_fru_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         junos:cli-feature "nokeyword";
         type enumeration {
           enum "reset" {
             description "Reset FRU";
             junos:must "(!(\".. .. action disable-pfe\"))";
             junos:must-message "'reset' and 'disable-pfe' cannot be both configured";
             junos:must "(!(\".. .. action offline\"))";
             junos:must-message "'reset' and 'offline' cannot be both configured";
           }
           enum "offline" {
             description "Offline FRU";
             junos:must "(!(\".. .. action disable-pfe\"))";
             junos:must-message "'offline' and 'disable-pfe' cannot be both configured";
           }
           enum "alarm" {
             description "Raise FRU alarm";
           }
           enum "get-state" {
             description "Retrieve FRU state for debugging";
           }
           enum "log" {
             description "Log occurrence to system log file";
           }
           enum "disable-pfe" {
             description "Disable PFE interfaces on FPC";
             junos:must "(!(\".. .. action reset-pfe\"))";
             junos:must-message "'disable-pfe' and 'reset-pfe' cannot be both configured";
             junos:must "(!(\".. .. action offline-pfe\"))";
             junos:must-message "'disable-pfe' and 'offline-pfe' cannot be both configured";
           }
           enum "reset-pfe" {
             description "Reset PFE on FPC";
             junos:must "(!(\".. .. action offline-pfe\"))";
             junos:must-message "'reset-pfe' and 'offline-pfe' cannot be both configured";
             junos:must "(!(\".. .. action disable-pfe\"))";
             junos:must-message "'reset-pfe' and 'disable-pfe' cannot be both configured";
           }
           enum "offline-pic" {
             description "Offline PICs associated with PFE on FPC";
           }
           enum "trap" {
             description "Raise FPC trap";
           }
           enum "offline-pfe" {
             description "Offline PFE on FPC";
             junos:must "(!(\".. .. action reset-pfe\"))";
             junos:must-message "'offline-pfe' and 'reset-pfe' cannot be both configured";
             junos:must "(!(\".. .. action disable-pfe\"))";
             junos:must-message "'offline-pfe' and 'disable-pfe' cannot be both configured";
           }
         }
       }
       uses apply-advanced;
     }
   }
   grouping chassis_fru_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         junos:cli-feature "nokeyword";
         type enumeration {
           enum "reset" {
             description "Reset FRU";
             junos:must "(!(\".. .. action disable-pfe\"))";
             junos:must-message "'reset' and 'disable-pfe' cannot be both configured";
             junos:must "(!(\".. .. action offline\"))";
             junos:must-message "'reset' and 'offline' cannot be both configured";
           }
           enum "offline" {
             description "Offline FRU";
             junos:must "(!(\".. .. action disable-pfe\"))";
             junos:must-message "'offline' and 'disable-pfe' cannot be both configured";
           }
           enum "alarm" {
             description "Raise FRU alarm";
           }
           enum "get-state" {
             description "Retrieve FRU state for debugging";
           }
           enum "log" {
             description "Log occurrence to system log file";
           }
           enum "disable-pfe" {
             description "Disable PFE interfaces on FPC";
             junos:must "(!(\".. .. action reset-pfe\"))";
             junos:must-message "'disable-pfe' and 'reset-pfe' cannot be both configured";
             junos:must "(!(\".. .. action offline-pfe\"))";
             junos:must-message "'disable-pfe' and 'offline-pfe' cannot be both configured";
           }
           enum "reset-pfe" {
             description "Reset PFE on FPC";
             junos:must "(!(\".. .. action offline-pfe\"))";
             junos:must-message "'reset-pfe' and 'offline-pfe' cannot be both configured";
             junos:must "(!(\".. .. action disable-pfe\"))";
             junos:must-message "'reset-pfe' and 'disable-pfe' cannot be both configured";
           }
           enum "offline-pic" {
             description "Offline PICs associated with PFE on FPC";
           }
           enum "trap" {
             description "Raise FPC trap";
           }
           enum "offline-pfe" {
             description "Offline PFE on FPC";
             junos:must "(!(\".. .. action reset-pfe\"))";
             junos:must-message "'offline-pfe' and 'reset-pfe' cannot be both configured";
             junos:must "(!(\".. .. action disable-pfe\"))";
             junos:must-message "'offline-pfe' and 'disable-pfe' cannot be both configured";
           }
         }
       }
       uses apply-advanced;
     }
   }
   grouping chassis_mic_type {
     leaf name {
       description "MIC slot number";
       junos:cli-feature "nokeyword";
       type union {
         type string {
           pattern "<.*>|$.*";
         }
         type uint32;
       }
     }
     uses apply-advanced;
     leaf power {
       description "Power off MIC";
       type enumeration {
         enum "off" {
           description "Do not provide power to MIC";
         }
       }
     }
   }
   grouping chassis_pem_type {
     uses apply-advanced;
     leaf minimum {
       description "Minimum number of power supplies required for normal operation";
       type union {
         type string {
           pattern "<.*>|$.*";
         }
         type uint32;
       }
     }
     leaf input-current {
       description "Input current (Amps) in each feed ";
       default "60";
       type enumeration {
         enum "40" {
           description "40 Amps in each Feed";
           junos:must "((!(\"chassis pem feeds\") || \"chassis pem feeds 6\"))";
           junos:must-message "Must configured with 6 feeds";
         }
         enum "60" {
           description "60 Amps in each Feed";
         }
       }
     }
     container redundancy {
       description "PEM Source/Feed Redundancy configuration";
       uses apply-advanced;
       leaf source-redundancy {
         description "Toggle Source Redundancy for PEM";
         type empty;
       }
       container feed-redundancy {
         description "Toggle Feed Redundancy for a PEM slot";
         uses apply-advanced;
         list slot {
           key name;
           description "PEM Slot Number";
           leaf name {
             description "Select PEM slot";
             junos:cli-feature "nokeyword";
             type union {
               type string {
                 pattern "<.*>|$.*";
               }
               type uint32;
             }
           }
           uses apply-advanced;
         }
       }
     }
   }
   grouping chassis_pem_type_slot {
     leaf name {
       description "PEM slot number";
       junos:cli-feature "nokeyword";
       type string;
     }
     uses apply-advanced;
   }
   grouping chassis_pfe_type {
     description "PFE(Packet forwarding engine)";
     leaf name {
       description "PFE(Packet forwarding engine) identifier";
       junos:cli-feature "nokeyword";
       type union {
         type string {
           pattern "<.*>|$.*";
         }
         type uint32;
       }
     }
     uses apply-advanced;
     container forwarding-packages {
       description "Associated forwarding package configuration";
       uses apply-advanced;
       container mobility {
         junos:cli-feature "oneliner-plus";
         description "Mobility related PFE configuration";
         uses apply-advanced;
         choice package-type {
           case case_1 {
             leaf user-plane {
               description "User plane function";
               type empty;
             }
           }
         }
       }
     }
     leaf power {
       description "Power PFEs on or off";
       type enumeration {
         enum "off" {
           description "Power off PFE";
         }
         enum "on" {
           description "Power on PFE";
         }
       }
     }
     leaf node {
       description "PFE(Packet forwarding engine) global identifier";
       junos:must "(unique \"chassis fpc <*> pfe <*> node $$\")";
       junos:must-message "Duplicated node-id can not be configured";
       type union {
         type string {
           pattern "<.*>|$.*";
         }
         type uint64 {
           range "1 .. 18446744073709551615";
         }
       }
     }
     leaf tunnel-services {
       description "Tunnel services configuration";
       type empty;
     }
   }
   grouping chassis_pic_type {
     leaf name {
       description "PIC slot number";
       junos:cli-feature "nokeyword";
       type union {
         type string {
           pattern "<.*>|$.*";
         }
         type uint32;
       }
     }
     uses apply-advanced;
     leaf pic-mode {
       description "PIC mode configuration";
       type enumeration {
         enum "1G" {
           description "1GE mode";
         }
         enum "10G" {
           description "10GE mode";
         }
         enum "25G" {
           description "25GE mode";
         }
         enum "40G" {
           description "40GE mode";
         }
         enum "50G" {
           description "50GE mode";
         }
         enum "100G" {
           description "100GE mode";
         }
         enum "400G" {
           description "400GE mode";
         }
         enum "1G10G" {
           description "1/10GE mode";
         }
         enum "A-1X400G-1X100G-4X50G" {
           description "Port0(400G) Port2(100G) Port6-9(50G)";
         }
         enum "B-1X400G-2X100G-2X50G" {
           description "Port0(400G) Port2,4(100G) Port6,8(50G)";
         }
         enum "C-6X100G-2X50G" {
           description "Port0-5(100G) Port10,12(50G)";
         }
         enum "D-3X100G-8X50G" {
           description "Port0-2(100G) Port6-13(50G)";
         }
         enum "E-4X100G-6X50G" {
           description "Port0-3(100G) Port7,9-13(50G)";
         }
       }
     }
     list port-profile {
       key name;
       ordered-by user;
       description "Port Profile configuration";
       junos:must "(!((\"chassis fpc $$={1} pic ${pic} pic-mode\" || \"chassis fpc $$={1} pic ${pic} port\")))";
       junos:must-message " port-profile config can not co-exist with pic <> pic-mode or port level config";
       max-elements 1;
       leaf name {
         description "Profile mode options";
         junos:cli-feature "nokeyword";
         type enumeration {
           enum "A-1X400G-1X100G-4X50G" {
             description "Port0(400G/100G/40G) Port2(100G) Port6-9(50G/25G/10G/1G)";
             junos:must "(((\"chassis fpc $$={1} pic ${pic} port-profile $$={A-1X400G-1X100G-4X50G} port-num $$={7} speed $$={50g}\" && \"chassis fpc $$={1} pic ${pic} port-profile $$={A-1X400G-1X100G-4X50G} port-num $$={9} speed $$={50g}\") || ((\"chassis fpc $$={1} pic ${pic} port-profile $$={A-1X400G-1X100G-4X50G} port-num $$={7} speed $$={25g}\" && \"chassis fpc $$={1} pic ${pic} port-profile $$={A-1X400G-1X100G-4X50G} port-num $$={9} speed $$={25g}\") || ((\"chassis fpc $$={1} pic ${pic} port-profile $$={A-1X400G-1X100G-4X50G} port-num $$={7} speed $$={10g}\" && \"chassis fpc $$={1} pic ${pic} port-profile $$={A-1X400G-1X100G-4X50G} port-num $$={9} speed $$={10g}\") || ((\"chassis fpc $$={1} pic ${pic} port-profile $$={A-1X400G-1X100G-4X50G} port-num $$={7} speed $$={1g}\" && \"chassis fpc $$={1} pic ${pic} port-profile $$={A-1X400G-1X100G-4X50G} port-num $$={9} speed $$={1g}\") || (!(\"chassis fpc $$={1} pic ${pic} port-profile $$={A-1X400G-1X100G-4X50G} port-num $$={7} speed\") && !(\"chassis fpc $$={1} pic ${pic} port-profile $$={A-1X400G-1X100G-4X50G} port-num $$={9} speed\")))))))";
             junos:must-message "For port-pair(7, 9) both ports need to be configured to same speed (1g, 10g, 25g, 50g)";
             junos:must "(((\"chassis fpc $$={1} pic ${pic} port-profile $$={A-1X400G-1X100G-4X50G} port-num $$={6} speed $$={50g}\" && \"chassis fpc $$={1} pic ${pic} port-profile $$={A-1X400G-1X100G-4X50G} port-num $$={8} speed $$={50g}\") || ((\"chassis fpc $$={1} pic ${pic} port-profile $$={A-1X400G-1X100G-4X50G} port-num $$={6} speed $$={25g}\" && \"chassis fpc $$={1} pic ${pic} port-profile $$={A-1X400G-1X100G-4X50G} port-num $$={8} speed $$={25g}\") || ((\"chassis fpc $$={1} pic ${pic} port-profile $$={A-1X400G-1X100G-4X50G} port-num $$={6} speed $$={10g}\" && \"chassis fpc $$={1} pic ${pic} port-profile $$={A-1X400G-1X100G-4X50G} port-num $$={8} speed $$={10g}\") || ((\"chassis fpc $$={1} pic ${pic} port-profile $$={A-1X400G-1X100G-4X50G} port-num $$={6} speed $$={1g}\" && \"chassis fpc $$={1} pic ${pic} port-profile $$={A-1X400G-1X100G-4X50G} port-num $$={8} speed $$={1g}\") || (!(\"chassis fpc $$={1} pic ${pic} port-profile $$={A-1X400G-1X100G-4X50G} port-num $$={6} speed\") && !(\"chassis fpc $$={1} pic ${pic} port-profile $$={A-1X400G-1X100G-4X50G} port-num $$={8} speed\")))))))";
             junos:must-message "For port-pair(6, 8) both ports need to be configured to same speed (1g, 10g, 25g, 50g)";
             junos:must "(!(\"chassis fpc $$={1} pic ${pic} port-profile $$={A-1X400G-1X100G-4X50G} port-num $$={13} speed\"))";
             junos:must-message "Port 13, this port is not part of the port-profile";
             junos:must "(!(\"chassis fpc $$={1} pic ${pic} port-profile $$={A-1X400G-1X100G-4X50G} port-num $$={12} speed\"))";
             junos:must-message "Port 12, this port is not part of the port-profile";
             junos:must "(!(\"chassis fpc $$={1} pic ${pic} port-profile $$={A-1X400G-1X100G-4X50G} port-num $$={11} speed\"))";
             junos:must-message "Port 11, this port is not part of the port-profile";
             junos:must "(!(\"chassis fpc $$={1} pic ${pic} port-profile $$={A-1X400G-1X100G-4X50G} port-num $$={10} speed\"))";
             junos:must-message "Port 10, this port is not part of the port-profile";
             junos:must "((\"chassis fpc $$={1} pic ${pic} port-profile $$={A-1X400G-1X100G-4X50G} port-num $$={9} speed $$={50g}\" || (\"chassis fpc $$={1} pic ${pic} port-profile $$={A-1X400G-1X100G-4X50G} port-num $$={9} speed $$={25g}\" || (\"chassis fpc $$={1} pic ${pic} port-profile $$={A-1X400G-1X100G-4X50G} port-num $$={9} speed $$={10g}\" || (\"chassis fpc $$={1} pic ${pic} port-profile $$={A-1X400G-1X100G-4X50G} port-num $$={9} speed $$={1g}\" || !(\"chassis fpc $$={1} pic ${pic} port-profile $$={A-1X400G-1X100G-4X50G} port-num $$={9} speed\"))))))";
             junos:must-message "Port 9, configurable speed (50g/25g/10g/1g) only";
             junos:must "((\"chassis fpc $$={1} pic ${pic} port-profile $$={A-1X400G-1X100G-4X50G} port-num $$={8} speed $$={50g}\" || (\"chassis fpc $$={1} pic ${pic} port-profile $$={A-1X400G-1X100G-4X50G} port-num $$={8} speed $$={25g}\" || (\"chassis fpc $$={1} pic ${pic} port-profile $$={A-1X400G-1X100G-4X50G} port-num $$={8} speed $$={10g}\" || (\"chassis fpc $$={1} pic ${pic} port-profile $$={A-1X400G-1X100G-4X50G} port-num $$={8} speed $$={1g}\" || !(\"chassis fpc $$={1} pic ${pic} port-profile $$={A-1X400G-1X100G-4X50G} port-num $$={8} speed\"))))))";
             junos:must-message "Port 8, configurable speed (50g/25g/10g/1g) only";
             junos:must "((\"chassis fpc $$={1} pic ${pic} port-profile $$={A-1X400G-1X100G-4X50G} port-num $$={7} speed $$={50g}\" || (\"chassis fpc $$={1} pic ${pic} port-profile $$={A-1X400G-1X100G-4X50G} port-num $$={7} speed $$={25g}\" || (\"chassis fpc $$={1} pic ${pic} port-profile $$={A-1X400G-1X100G-4X50G} port-num $$={7} speed $$={10g}\" || (\"chassis fpc $$={1} pic ${pic} port-profile $$={A-1X400G-1X100G-4X50G} port-num $$={7} speed $$={1g}\" || !(\"chassis fpc $$={1} pic ${pic} port-profile $$={A-1X400G-1X100G-4X50G} port-num $$={7} speed\"))))))";
             junos:must-message "Port 7, configurable speed (50g/25g/10g/1g) only";
             junos:must "((\"chassis fpc $$={1} pic ${pic} port-profile $$={A-1X400G-1X100G-4X50G} port-num $$={6} speed $$={50g}\" || (\"chassis fpc $$={1} pic ${pic} port-profile $$={A-1X400G-1X100G-4X50G} port-num $$={6} speed $$={25g}\" || (\"chassis fpc $$={1} pic ${pic} port-profile $$={A-1X400G-1X100G-4X50G} port-num $$={6} speed $$={10g}\" || (\"chassis fpc $$={1} pic ${pic} port-profile $$={A-1X400G-1X100G-4X50G} port-num $$={6} speed $$={1g}\" || !(\"chassis fpc $$={1} pic ${pic} port-profile $$={A-1X400G-1X100G-4X50G} port-num $$={6} speed\"))))))";
             junos:must-message "Port 6, configurable speed (50g/25g/10g/1g) only";
             junos:must "(!(\"chassis fpc $$={1} pic ${pic} port-profile $$={A-1X400G-1X100G-4X50G} port-num $$={5} speed\"))";
             junos:must-message "Port 5, this port is not part of the port-profile";
             junos:must "(!(\"chassis fpc $$={1} pic ${pic} port-profile $$={A-1X400G-1X100G-4X50G} port-num $$={4} speed\"))";
             junos:must-message "Port 4, this port is not part of the port-profile";
             junos:must "(!(\"chassis fpc $$={1} pic ${pic} port-profile $$={A-1X400G-1X100G-4X50G} port-num $$={3} speed\"))";
             junos:must-message "Port 3, this port is not part of the port-profile";
             junos:must "((\"chassis fpc $$={1} pic ${pic} port-profile $$={A-1X400G-1X100G-4X50G} port-num $$={2} speed $$={100g}\" || !(\"chassis fpc $$={1} pic ${pic} port-profile $$={A-1X400G-1X100G-4X50G} port-num $$={2} speed\")))";
             junos:must-message "Port 2, configurable speed (100g) only";
             junos:must "(!(\"chassis fpc $$={1} pic ${pic} port-profile $$={A-1X400G-1X100G-4X50G} port-num $$={1} speed\"))";
             junos:must-message "Port 1, this port is not part of the port-profile";
             junos:must "((\"chassis fpc $$={1} pic ${pic} port-profile $$={A-1X400G-1X100G-4X50G} port-num $$={0} speed $$={400g}\" || (\"chassis fpc $$={1} pic ${pic} port-profile $$={A-1X400G-1X100G-4X50G} port-num $$={0} speed $$={100g}\" || (\"chassis fpc $$={1} pic ${pic} port-profile $$={A-1X400G-1X100G-4X50G} port-num $$={0} speed $$={40g}\" || !(\"chassis fpc $$={1} pic ${pic} port-profile $$={A-1X400G-1X100G-4X50G} port-num $$={0} speed\")))))";
             junos:must-message "Port 0, configurable speed (400g/100g/40g) only";
           }
           enum "B-1X400G-2X100G-2X50G" {
             description "Port0(400G/100G/40G) Port2,4(100G) Port6,8(50G/25G/10G/1G)";
             junos:must "(((\"chassis fpc $$={1} pic ${pic} port-profile $$={B-1X400G-2X100G-2X50G} port-num $$={6} speed $$={50g}\" && \"chassis fpc $$={1} pic ${pic} port-profile $$={B-1X400G-2X100G-2X50G} port-num $$={8} speed $$={50g}\") || ((\"chassis fpc $$={1} pic ${pic} port-profile $$={B-1X400G-2X100G-2X50G} port-num $$={6} speed $$={25g}\" && \"chassis fpc $$={1} pic ${pic} port-profile $$={B-1X400G-2X100G-2X50G} port-num $$={8} speed $$={25g}\") || ((\"chassis fpc $$={1} pic ${pic} port-profile $$={B-1X400G-2X100G-2X50G} port-num $$={6} speed $$={10g}\" && \"chassis fpc $$={1} pic ${pic} port-profile $$={B-1X400G-2X100G-2X50G} port-num $$={8} speed $$={10g}\") || ((\"chassis fpc $$={1} pic ${pic} port-profile $$={B-1X400G-2X100G-2X50G} port-num $$={6} speed $$={1g}\" && \"chassis fpc $$={1} pic ${pic} port-profile $$={B-1X400G-2X100G-2X50G} port-num $$={8} speed $$={1g}\") || (!(\"chassis fpc $$={1} pic ${pic} port-profile $$={B-1X400G-2X100G-2X50G} port-num $$={6} speed\") && !(\"chassis fpc $$={1} pic ${pic} port-profile $$={B-1X400G-2X100G-2X50G} port-num $$={8} speed\")))))))";
             junos:must-message "For port-pair(6, 8) both ports need to be configured to same speed (1g, 10g, 25g, 50g)";
             junos:must "(!(\"chassis fpc $$={1} pic ${pic} port-profile $$={B-1X400G-2X100G-2X50G} port-num $$={13} speed\"))";
             junos:must-message "Port 13, this port is not part of the port-profile";
             junos:must "(!(\"chassis fpc $$={1} pic ${pic} port-profile $$={B-1X400G-2X100G-2X50G} port-num $$={12} speed\"))";
             junos:must-message "Port 12, this port is not part of the port-profile";
             junos:must "(!(\"chassis fpc $$={1} pic ${pic} port-profile $$={B-1X400G-2X100G-2X50G} port-num $$={11} speed\"))";
             junos:must-message "Port 11, this port is not part of the port-profile";
             junos:must "(!(\"chassis fpc $$={1} pic ${pic} port-profile $$={B-1X400G-2X100G-2X50G} port-num $$={10} speed\"))";
             junos:must-message "Port 10, this port is not part of the port-profile";
             junos:must "(!(\"chassis fpc $$={1} pic ${pic} port-profile $$={B-1X400G-2X100G-2X50G} port-num $$={9} speed\"))";
             junos:must-message "Port 9, this port is not part of the port-profile";
             junos:must "((\"chassis fpc $$={1} pic ${pic} port-profile $$={B-1X400G-2X100G-2X50G} port-num $$={8} speed $$={50g}\" || (\"chassis fpc $$={1} pic ${pic} port-profile $$={B-1X400G-2X100G-2X50G} port-num $$={8} speed $$={25g}\" || (\"chassis fpc $$={1} pic ${pic} port-profile $$={B-1X400G-2X100G-2X50G} port-num $$={8} speed $$={10g}\" || (\"chassis fpc $$={1} pic ${pic} port-profile $$={B-1X400G-2X100G-2X50G} port-num $$={8} speed $$={1g}\" || !(\"chassis fpc $$={1} pic ${pic} port-profile $$={B-1X400G-2X100G-2X50G} port-num $$={8} speed\"))))))";
             junos:must-message "Port 8, configurable speed (50g/25g/10g/1g) only";
             junos:must "(!(\"chassis fpc $$={1} pic ${pic} port-profile $$={B-1X400G-2X100G-2X50G} port-num $$={7} speed\"))";
             junos:must-message "Port 7, this port is not part of the port-profile";
             junos:must "((\"chassis fpc $$={1} pic ${pic} port-profile $$={B-1X400G-2X100G-2X50G} port-num $$={6} speed $$={50g}\" || (\"chassis fpc $$={1} pic ${pic} port-profile $$={B-1X400G-2X100G-2X50G} port-num $$={6} speed $$={25g}\" || (\"chassis fpc $$={1} pic ${pic} port-profile $$={B-1X400G-2X100G-2X50G} port-num $$={6} speed $$={10g}\" || (\"chassis fpc $$={1} pic ${pic} port-profile $$={B-1X400G-2X100G-2X50G} port-num $$={6} speed $$={1g}\" || !(\"chassis fpc $$={1} pic ${pic} port-profile $$={B-1X400G-2X100G-2X50G} port-num $$={6} speed\"))))))";
             junos:must-message "Port 6, configurable speed (50g/25g/10g/1g) only";
             junos:must "(!(\"chassis fpc $$={1} pic ${pic} port-profile $$={B-1X400G-2X100G-2X50G} port-num $$={5} speed\"))";
             junos:must-message "Port 5, this port is not part of the port-profile";
             junos:must "((\"chassis fpc $$={1} pic ${pic} port-profile $$={B-1X400G-2X100G-2X50G} port-num $$={4} speed $$={100g}\" || !(\"chassis fpc $$={1} pic ${pic} port-profile $$={B-1X400G-2X100G-2X50G} port-num $$={4} speed\")))";
             junos:must-message "Port 4, configurable speed (100g) only";
             junos:must "(!(\"chassis fpc $$={1} pic ${pic} port-profile $$={B-1X400G-2X100G-2X50G} port-num $$={3} speed\"))";
             junos:must-message "Port 3, this port is not part of the port-profile";
             junos:must "((\"chassis fpc $$={1} pic ${pic} port-profile $$={B-1X400G-2X100G-2X50G} port-num $$={2} speed $$={100g}\" || !(\"chassis fpc $$={1} pic ${pic} port-profile $$={B-1X400G-2X100G-2X50G} port-num $$={2} speed\")))";
             junos:must-message "Port 2, configurable speed (100g) only";
             junos:must "(!(\"chassis fpc $$={1} pic ${pic} port-profile $$={B-1X400G-2X100G-2X50G} port-num $$={1} speed\"))";
             junos:must-message "Port 1, this port is not part of the port-profile";
             junos:must "((\"chassis fpc $$={1} pic ${pic} port-profile $$={B-1X400G-2X100G-2X50G} port-num $$={0} speed $$={400g}\" || (\"chassis fpc $$={1} pic ${pic} port-profile $$={B-1X400G-2X100G-2X50G} port-num $$={0} speed $$={100g}\" || (\"chassis fpc $$={1} pic ${pic} port-profile $$={B-1X400G-2X100G-2X50G} port-num $$={0} speed $$={40g}\" || !(\"chassis fpc $$={1} pic ${pic} port-profile $$={B-1X400G-2X100G-2X50G} port-num $$={0} speed\")))))";
             junos:must-message "Port 0, configurable speed (400g/100g/40g) only";
           }
           enum "C-6X100G-2X50G" {
             description "Port0-5(100G) Port10,12(50G/25G/10G/1G)";
             junos:must "(((\"chassis fpc $$={1} pic ${pic} port-profile $$={C-6X100G-2X50G} port-num $$={10} speed $$={50g}\" && \"chassis fpc $$={1} pic ${pic} port-profile $$={C-6X100G-2X50G} port-num $$={12} speed $$={50g}\") || ((\"chassis fpc $$={1} pic ${pic} port-profile $$={C-6X100G-2X50G} port-num $$={10} speed $$={25g}\" && \"chassis fpc $$={1} pic ${pic} port-profile $$={C-6X100G-2X50G} port-num $$={12} speed $$={25g}\") || ((\"chassis fpc $$={1} pic ${pic} port-profile $$={C-6X100G-2X50G} port-num $$={10} speed $$={10g}\" && \"chassis fpc $$={1} pic ${pic} port-profile $$={C-6X100G-2X50G} port-num $$={12} speed $$={10g}\") || ((\"chassis fpc $$={1} pic ${pic} port-profile $$={C-6X100G-2X50G} port-num $$={10} speed $$={1g}\" && \"chassis fpc $$={1} pic ${pic} port-profile $$={C-6X100G-2X50G} port-num $$={12} speed $$={1g}\") || (!(\"chassis fpc $$={1} pic ${pic} port-profile $$={C-6X100G-2X50G} port-num $$={10} speed\") && !(\"chassis fpc $$={1} pic ${pic} port-profile $$={C-6X100G-2X50G} port-num $$={12} speed\")))))))";
             junos:must-message "For port-pair(10, 12) both ports need to be configured to same speed (1g, 10g, 25g, 50g)";
             junos:must "(!(\"chassis fpc $$={1} pic ${pic} port-profile $$={C-6X100G-2X50G} port-num $$={13} speed\"))";
             junos:must-message "Port 13, this port is not part of the port-profile";
             junos:must "((\"chassis fpc $$={1} pic ${pic} port-profile $$={C-6X100G-2X50G} port-num $$={12} speed $$={50g}\" || (\"chassis fpc $$={1} pic ${pic} port-profile $$={C-6X100G-2X50G} port-num $$={12} speed $$={25g}\" || (\"chassis fpc $$={1} pic ${pic} port-profile $$={C-6X100G-2X50G} port-num $$={12} speed $$={10g}\" || (\"chassis fpc $$={1} pic ${pic} port-profile $$={C-6X100G-2X50G} port-num $$={12} speed $$={1g}\" || !(\"chassis fpc $$={1} pic ${pic} port-profile $$={C-6X100G-2X50G} port-num $$={12} speed\"))))))";
             junos:must-message "Port 12, configurable speed (50g/25g/10g/1g) only";
             junos:must "(!(\"chassis fpc $$={1} pic ${pic} port-profile $$={C-6X100G-2X50G} port-num $$={11} speed\"))";
             junos:must-message "Port 11, this port is not part of the port-profile";
             junos:must "((\"chassis fpc $$={1} pic ${pic} port-profile $$={C-6X100G-2X50G} port-num $$={10} speed $$={50g}\" || (\"chassis fpc $$={1} pic ${pic} port-profile $$={C-6X100G-2X50G} port-num $$={10} speed $$={25g}\" || (\"chassis fpc $$={1} pic ${pic} port-profile $$={C-6X100G-2X50G} port-num $$={10} speed $$={10g}\" || (\"chassis fpc $$={1} pic ${pic} port-profile $$={C-6X100G-2X50G} port-num $$={10} speed $$={1g}\" || !(\"chassis fpc $$={1} pic ${pic} port-profile $$={C-6X100G-2X50G} port-num $$={10} speed\"))))))";
             junos:must-message "Port 10, configurable speed (50g/25g/10g/1g) only";
             junos:must "(!(\"chassis fpc $$={1} pic ${pic} port-profile $$={C-6X100G-2X50G} port-num $$={9} speed\"))";
             junos:must-message "Port 9, this port is not part of the port-profile";
             junos:must "(!(\"chassis fpc $$={1} pic ${pic} port-profile $$={C-6X100G-2X50G} port-num $$={8} speed\"))";
             junos:must-message "Port 8, this port is not part of the port-profile";
             junos:must "(!(\"chassis fpc $$={1} pic ${pic} port-profile $$={C-6X100G-2X50G} port-num $$={7} speed\"))";
             junos:must-message "Port 7, this port is not part of the port-profile";
             junos:must "(!(\"chassis fpc $$={1} pic ${pic} port-profile $$={C-6X100G-2X50G} port-num $$={6} speed\"))";
             junos:must-message "Port 6, this port is not part of the port-profile";
             junos:must "((\"chassis fpc $$={1} pic ${pic} port-profile $$={C-6X100G-2X50G} port-num $$={5} speed $$={100g}\" || !(\"chassis fpc $$={1} pic ${pic} port-profile $$={C-6X100G-2X50G} port-num $$={5} speed\")))";
             junos:must-message "Port 5, configurable speed (100g) only";
             junos:must "((\"chassis fpc $$={1} pic ${pic} port-profile $$={C-6X100G-2X50G} port-num $$={4} speed $$={100g}\" || !(\"chassis fpc $$={1} pic ${pic} port-profile $$={C-6X100G-2X50G} port-num $$={4} speed\")))";
             junos:must-message "Port 4, configurable speed (100g) only";
             junos:must "((\"chassis fpc $$={1} pic ${pic} port-profile $$={C-6X100G-2X50G} port-num $$={3} speed $$={100g}\" || !(\"chassis fpc $$={1} pic ${pic} port-profile $$={C-6X100G-2X50G} port-num $$={3} speed\")))";
             junos:must-message "Port 3, configurable speed (100g) only";
             junos:must "((\"chassis fpc $$={1} pic ${pic} port-profile $$={C-6X100G-2X50G} port-num $$={2} speed $$={100g}\" || !(\"chassis fpc $$={1} pic ${pic} port-profile $$={C-6X100G-2X50G} port-num $$={2} speed\")))";
             junos:must-message "Port 2, configurable speed (100g) only";
             junos:must "((\"chassis fpc $$={1} pic ${pic} port-profile $$={C-6X100G-2X50G} port-num $$={1} speed $$={100g}\" || !(\"chassis fpc $$={1} pic ${pic} port-profile $$={C-6X100G-2X50G} port-num $$={1} speed\")))";
             junos:must-message "Port 1, configurable speed (100g) only";
             junos:must "((\"chassis fpc $$={1} pic ${pic} port-profile $$={C-6X100G-2X50G} port-num $$={0} speed $$={100g}\" || !(\"chassis fpc $$={1} pic ${pic} port-profile $$={C-6X100G-2X50G} port-num $$={0} speed\")))";
             junos:must-message "Port 0, configurable speed (100g) only";
           }
           enum "D-3X100G-8X50G" {
             description "Port0-2(100G) Port6-13(50G/25G/10G/1G)";
             junos:must "(((\"chassis fpc $$={1} pic ${pic} port-profile $$={D-3X100G-8X50G} port-num $$={11} speed $$={50g}\" && \"chassis fpc $$={1} pic ${pic} port-profile $$={D-3X100G-8X50G} port-num $$={13} speed $$={50g}\") || ((\"chassis fpc $$={1} pic ${pic} port-profile $$={D-3X100G-8X50G} port-num $$={11} speed $$={25g}\" && \"chassis fpc $$={1} pic ${pic} port-profile $$={D-3X100G-8X50G} port-num $$={13} speed $$={25g}\") || ((\"chassis fpc $$={1} pic ${pic} port-profile $$={D-3X100G-8X50G} port-num $$={11} speed $$={10g}\" && \"chassis fpc $$={1} pic ${pic} port-profile $$={D-3X100G-8X50G} port-num $$={13} speed $$={10g}\") || ((\"chassis fpc $$={1} pic ${pic} port-profile $$={D-3X100G-8X50G} port-num $$={11} speed $$={1g}\" && \"chassis fpc $$={1} pic ${pic} port-profile $$={D-3X100G-8X50G} port-num $$={13} speed $$={1g}\") || (!(\"chassis fpc $$={1} pic ${pic} port-profile $$={D-3X100G-8X50G} port-num $$={11} speed\") && !(\"chassis fpc $$={1} pic ${pic} port-profile $$={D-3X100G-8X50G} port-num $$={13} speed\")))))))";
             junos:must-message "For port-pair(11, 13) both ports need to be configured to same speed (1g, 10g, 25g, 50g)";
             junos:must "(((\"chassis fpc $$={1} pic ${pic} port-profile $$={D-3X100G-8X50G} port-num $$={10} speed $$={50g}\" && \"chassis fpc $$={1} pic ${pic} port-profile $$={D-3X100G-8X50G} port-num $$={12} speed $$={50g}\") || ((\"chassis fpc $$={1} pic ${pic} port-profile $$={D-3X100G-8X50G} port-num $$={10} speed $$={25g}\" && \"chassis fpc $$={1} pic ${pic} port-profile $$={D-3X100G-8X50G} port-num $$={12} speed $$={25g}\") || ((\"chassis fpc $$={1} pic ${pic} port-profile $$={D-3X100G-8X50G} port-num $$={10} speed $$={10g}\" && \"chassis fpc $$={1} pic ${pic} port-profile $$={D-3X100G-8X50G} port-num $$={12} speed $$={10g}\") || ((\"chassis fpc $$={1} pic ${pic} port-profile $$={D-3X100G-8X50G} port-num $$={10} speed $$={1g}\" && \"chassis fpc $$={1} pic ${pic} port-profile $$={D-3X100G-8X50G} port-num $$={12} speed $$={1g}\") || (!(\"chassis fpc $$={1} pic ${pic} port-profile $$={D-3X100G-8X50G} port-num $$={10} speed\") && !(\"chassis fpc $$={1} pic ${pic} port-profile $$={D-3X100G-8X50G} port-num $$={12} speed\")))))))";
             junos:must-message "For port-pair(10, 12) both ports need to be configured to same speed (1g, 10g, 25g, 50g)";
             junos:must "(((\"chassis fpc $$={1} pic ${pic} port-profile $$={D-3X100G-8X50G} port-num $$={7} speed $$={50g}\" && \"chassis fpc $$={1} pic ${pic} port-profile $$={D-3X100G-8X50G} port-num $$={9} speed $$={50g}\") || ((\"chassis fpc $$={1} pic ${pic} port-profile $$={D-3X100G-8X50G} port-num $$={7} speed $$={25g}\" && \"chassis fpc $$={1} pic ${pic} port-profile $$={D-3X100G-8X50G} port-num $$={9} speed $$={25g}\") || ((\"chassis fpc $$={1} pic ${pic} port-profile $$={D-3X100G-8X50G} port-num $$={7} speed $$={10g}\" && \"chassis fpc $$={1} pic ${pic} port-profile $$={D-3X100G-8X50G} port-num $$={9} speed $$={10g}\") || ((\"chassis fpc $$={1} pic ${pic} port-profile $$={D-3X100G-8X50G} port-num $$={7} speed $$={1g}\" && \"chassis fpc $$={1} pic ${pic} port-profile $$={D-3X100G-8X50G} port-num $$={9} speed $$={1g}\") || (!(\"chassis fpc $$={1} pic ${pic} port-profile $$={D-3X100G-8X50G} port-num $$={7} speed\") && !(\"chassis fpc $$={1} pic ${pic} port-profile $$={D-3X100G-8X50G} port-num $$={9} speed\")))))))";
             junos:must-message "For port-pair(7, 9) both ports need to be configured to same speed (1g, 10g, 25g, 50g)";
             junos:must "(((\"chassis fpc $$={1} pic ${pic} port-profile $$={D-3X100G-8X50G} port-num $$={6} speed $$={50g}\" && \"chassis fpc $$={1} pic ${pic} port-profile $$={D-3X100G-8X50G} port-num $$={8} speed $$={50g}\") || ((\"chassis fpc $$={1} pic ${pic} port-profile $$={D-3X100G-8X50G} port-num $$={6} speed $$={25g}\" && \"chassis fpc $$={1} pic ${pic} port-profile $$={D-3X100G-8X50G} port-num $$={8} speed $$={25g}\") || ((\"chassis fpc $$={1} pic ${pic} port-profile $$={D-3X100G-8X50G} port-num $$={6} speed $$={10g}\" && \"chassis fpc $$={1} pic ${pic} port-profile $$={D-3X100G-8X50G} port-num $$={8} speed $$={10g}\") || ((\"chassis fpc $$={1} pic ${pic} port-profile $$={D-3X100G-8X50G} port-num $$={6} speed $$={1g}\" && \"chassis fpc $$={1} pic ${pic} port-profile $$={D-3X100G-8X50G} port-num $$={8} speed $$={1g}\") || (!(\"chassis fpc $$={1} pic ${pic} port-profile $$={D-3X100G-8X50G} port-num $$={6} speed\") && !(\"chassis fpc $$={1} pic ${pic} port-profile $$={D-3X100G-8X50G} port-num $$={8} speed\")))))))";
             junos:must-message "For port-pair(6, 8) both ports need to be configured to same speed (1g, 10g, 25g, 50g)";
             junos:must "((\"chassis fpc $$={1} pic ${pic} port-profile $$={D-3X100G-8X50G} port-num $$={13} speed $$={50g}\" || (\"chassis fpc $$={1} pic ${pic} port-profile $$={D-3X100G-8X50G} port-num $$={13} speed $$={25g}\" || (\"chassis fpc $$={1} pic ${pic} port-profile $$={D-3X100G-8X50G} port-num $$={13} speed $$={10g}\" || (\"chassis fpc $$={1} pic ${pic} port-profile $$={D-3X100G-8X50G} port-num $$={13} speed $$={1g}\" || !(\"chassis fpc $$={1} pic ${pic} port-profile $$={D-3X100G-8X50G} port-num $$={13} speed\"))))))";
             junos:must-message "Port 13, configurable speed (50g/25g/10g/1g) only";
             junos:must "((\"chassis fpc $$={1} pic ${pic} port-profile $$={D-3X100G-8X50G} port-num $$={12} speed $$={50g}\" || (\"chassis fpc $$={1} pic ${pic} port-profile $$={D-3X100G-8X50G} port-num $$={12} speed $$={25g}\" || (\"chassis fpc $$={1} pic ${pic} port-profile $$={D-3X100G-8X50G} port-num $$={12} speed $$={10g}\" || (\"chassis fpc $$={1} pic ${pic} port-profile $$={D-3X100G-8X50G} port-num $$={12} speed $$={1g}\" || !(\"chassis fpc $$={1} pic ${pic} port-profile $$={D-3X100G-8X50G} port-num $$={12} speed\"))))))";
             junos:must-message "Port 12, configurable speed (50g/25g/10g/1g) only";
             junos:must "((\"chassis fpc $$={1} pic ${pic} port-profile $$={D-3X100G-8X50G} port-num $$={11} speed $$={50g}\" || (\"chassis fpc $$={1} pic ${pic} port-profile $$={D-3X100G-8X50G} port-num $$={11} speed $$={25g}\" || (\"chassis fpc $$={1} pic ${pic} port-profile $$={D-3X100G-8X50G} port-num $$={11} speed $$={10g}\" || (\"chassis fpc $$={1} pic ${pic} port-profile $$={D-3X100G-8X50G} port-num $$={11} speed $$={1g}\" || !(\"chassis fpc $$={1} pic ${pic} port-profile $$={D-3X100G-8X50G} port-num $$={11} speed\"))))))";
             junos:must-message "Port 11, configurable speed (50g/25g/10g/1g) only";
             junos:must "((\"chassis fpc $$={1} pic ${pic} port-profile $$={D-3X100G-8X50G} port-num $$={10} speed $$={50g}\" || (\"chassis fpc $$={1} pic ${pic} port-profile $$={D-3X100G-8X50G} port-num $$={10} speed $$={25g}\" || (\"chassis fpc $$={1} pic ${pic} port-profile $$={D-3X100G-8X50G} port-num $$={10} speed $$={10g}\" || (\"chassis fpc $$={1} pic ${pic} port-profile $$={D-3X100G-8X50G} port-num $$={10} speed $$={1g}\" || !(\"chassis fpc $$={1} pic ${pic} port-profile $$={D-3X100G-8X50G} port-num $$={10} speed\"))))))";
             junos:must-message "Port 10, configurable speed (50g/25g/10g/1g) only";
             junos:must "((\"chassis fpc $$={1} pic ${pic} port-profile $$={D-3X100G-8X50G} port-num $$={9} speed $$={50g}\" || (\"chassis fpc $$={1} pic ${pic} port-profile $$={D-3X100G-8X50G} port-num $$={9} speed $$={25g}\" || (\"chassis fpc $$={1} pic ${pic} port-profile $$={D-3X100G-8X50G} port-num $$={9} speed $$={10g}\" || (\"chassis fpc $$={1} pic ${pic} port-profile $$={D-3X100G-8X50G} port-num $$={9} speed $$={1g}\" || !(\"chassis fpc $$={1} pic ${pic} port-profile $$={D-3X100G-8X50G} port-num $$={9} speed\"))))))";
             junos:must-message "Port 9, configurable speed (50g/25g/10g/1g) only";
             junos:must "((\"chassis fpc $$={1} pic ${pic} port-profile $$={D-3X100G-8X50G} port-num $$={8} speed $$={50g}\" || (\"chassis fpc $$={1} pic ${pic} port-profile $$={D-3X100G-8X50G} port-num $$={8} speed $$={25g}\" || (\"chassis fpc $$={1} pic ${pic} port-profile $$={D-3X100G-8X50G} port-num $$={8} speed $$={10g}\" || (\"chassis fpc $$={1} pic ${pic} port-profile $$={D-3X100G-8X50G} port-num $$={8} speed $$={1g}\" || !(\"chassis fpc $$={1} pic ${pic} port-profile $$={D-3X100G-8X50G} port-num $$={8} speed\"))))))";
             junos:must-message "Port 8, configurable speed (50g/25g/10g/1g) only";
             junos:must "((\"chassis fpc $$={1} pic ${pic} port-profile $$={D-3X100G-8X50G} port-num $$={7} speed $$={50g}\" || (\"chassis fpc $$={1} pic ${pic} port-profile $$={D-3X100G-8X50G} port-num $$={7} speed $$={25g}\" || (\"chassis fpc $$={1} pic ${pic} port-profile $$={D-3X100G-8X50G} port-num $$={7} speed $$={10g}\" || (\"chassis fpc $$={1} pic ${pic} port-profile $$={D-3X100G-8X50G} port-num $$={7} speed $$={1g}\" || !(\"chassis fpc $$={1} pic ${pic} port-profile $$={D-3X100G-8X50G} port-num $$={7} speed\"))))))";
             junos:must-message "Port 7, configurable speed (50g/25g/10g/1g) only";
             junos:must "((\"chassis fpc $$={1} pic ${pic} port-profile $$={D-3X100G-8X50G} port-num $$={6} speed $$={50g}\" || (\"chassis fpc $$={1} pic ${pic} port-profile $$={D-3X100G-8X50G} port-num $$={6} speed $$={25g}\" || (\"chassis fpc $$={1} pic ${pic} port-profile $$={D-3X100G-8X50G} port-num $$={6} speed $$={10g}\" || (\"chassis fpc $$={1} pic ${pic} port-profile $$={D-3X100G-8X50G} port-num $$={6} speed $$={1g}\" || !(\"chassis fpc $$={1} pic ${pic} port-profile $$={D-3X100G-8X50G} port-num $$={6} speed\"))))))";
             junos:must-message "Port 6, configurable speed (50g/25g/10g/1g) only";
             junos:must "(!(\"chassis fpc $$={1} pic ${pic} port-profile $$={D-3X100G-8X50G} port-num $$={5} speed\"))";
             junos:must-message "Port 5, this port is not part of the port-profile";
             junos:must "(!(\"chassis fpc $$={1} pic ${pic} port-profile $$={D-3X100G-8X50G} port-num $$={4} speed\"))";
             junos:must-message "Port 4, this port is not part of the port-profile";
             junos:must "(!(\"chassis fpc $$={1} pic ${pic} port-profile $$={D-3X100G-8X50G} port-num $$={3} speed\"))";
             junos:must-message "Port 3, this port is not part of the port-profile";
             junos:must "((\"chassis fpc $$={1} pic ${pic} port-profile $$={D-3X100G-8X50G} port-num $$={2} speed $$={100g}\" || !(\"chassis fpc $$={1} pic ${pic} port-profile $$={D-3X100G-8X50G} port-num $$={2} speed\")))";
             junos:must-message "Port 2, configurable speed (100g) only";
             junos:must "((\"chassis fpc $$={1} pic ${pic} port-profile $$={D-3X100G-8X50G} port-num $$={1} speed $$={100g}\" || !(\"chassis fpc $$={1} pic ${pic} port-profile $$={D-3X100G-8X50G} port-num $$={1} speed\")))";
             junos:must-message "Port 1, configurable speed (100g) only";
             junos:must "((\"chassis fpc $$={1} pic ${pic} port-profile $$={D-3X100G-8X50G} port-num $$={0} speed $$={100g}\" || !(\"chassis fpc $$={1} pic ${pic} port-profile $$={D-3X100G-8X50G} port-num $$={0} speed\")))";
             junos:must-message "Port 0, configurable speed (100g) only";
           }
           enum "E-4X100G-6X50G" {
             description "Port0-3(100G) Port7,9-13(50G/25G/10G/1G)";
             junos:must "(((\"chassis fpc $$={1} pic ${pic} port-profile $$={E-4X100G-6X50G} port-num $$={11} speed $$={50g}\" && \"chassis fpc $$={1} pic ${pic} port-profile $$={E-4X100G-6X50G} port-num $$={13} speed $$={50g}\") || ((\"chassis fpc $$={1} pic ${pic} port-profile $$={E-4X100G-6X50G} port-num $$={11} speed $$={25g}\" && \"chassis fpc $$={1} pic ${pic} port-profile $$={E-4X100G-6X50G} port-num $$={13} speed $$={25g}\") || ((\"chassis fpc $$={1} pic ${pic} port-profile $$={E-4X100G-6X50G} port-num $$={11} speed $$={10g}\" && \"chassis fpc $$={1} pic ${pic} port-profile $$={E-4X100G-6X50G} port-num $$={13} speed $$={10g}\") || ((\"chassis fpc $$={1} pic ${pic} port-profile $$={E-4X100G-6X50G} port-num $$={11} speed $$={1g}\" && \"chassis fpc $$={1} pic ${pic} port-profile $$={E-4X100G-6X50G} port-num $$={13} speed $$={1g}\") || (!(\"chassis fpc $$={1} pic ${pic} port-profile $$={E-4X100G-6X50G} port-num $$={11} speed\") && !(\"chassis fpc $$={1} pic ${pic} port-profile $$={E-4X100G-6X50G} port-num $$={13} speed\")))))))";
             junos:must-message "For port-pair(11, 13) both ports need to be configured to same speed (1g, 10g, 25g, 50g)";
             junos:must "(((\"chassis fpc $$={1} pic ${pic} port-profile $$={E-4X100G-6X50G} port-num $$={10} speed $$={50g}\" && \"chassis fpc $$={1} pic ${pic} port-profile $$={E-4X100G-6X50G} port-num $$={12} speed $$={50g}\") || ((\"chassis fpc $$={1} pic ${pic} port-profile $$={E-4X100G-6X50G} port-num $$={10} speed $$={25g}\" && \"chassis fpc $$={1} pic ${pic} port-profile $$={E-4X100G-6X50G} port-num $$={12} speed $$={25g}\") || ((\"chassis fpc $$={1} pic ${pic} port-profile $$={E-4X100G-6X50G} port-num $$={10} speed $$={10g}\" && \"chassis fpc $$={1} pic ${pic} port-profile $$={E-4X100G-6X50G} port-num $$={12} speed $$={10g}\") || ((\"chassis fpc $$={1} pic ${pic} port-profile $$={E-4X100G-6X50G} port-num $$={10} speed $$={1g}\" && \"chassis fpc $$={1} pic ${pic} port-profile $$={E-4X100G-6X50G} port-num $$={12} speed $$={1g}\") || (!(\"chassis fpc $$={1} pic ${pic} port-profile $$={E-4X100G-6X50G} port-num $$={10} speed\") && !(\"chassis fpc $$={1} pic ${pic} port-profile $$={E-4X100G-6X50G} port-num $$={12} speed\")))))))";
             junos:must-message "For port-pair(10, 12) both ports need to be configured to same speed (1g, 10g, 25g, 50g)";
             junos:must "(((\"chassis fpc $$={1} pic ${pic} port-profile $$={E-4X100G-6X50G} port-num $$={7} speed $$={50g}\" && \"chassis fpc $$={1} pic ${pic} port-profile $$={E-4X100G-6X50G} port-num $$={9} speed $$={50g}\") || ((\"chassis fpc $$={1} pic ${pic} port-profile $$={E-4X100G-6X50G} port-num $$={7} speed $$={25g}\" && \"chassis fpc $$={1} pic ${pic} port-profile $$={E-4X100G-6X50G} port-num $$={9} speed $$={25g}\") || ((\"chassis fpc $$={1} pic ${pic} port-profile $$={E-4X100G-6X50G} port-num $$={7} speed $$={10g}\" && \"chassis fpc $$={1} pic ${pic} port-profile $$={E-4X100G-6X50G} port-num $$={9} speed $$={10g}\") || ((\"chassis fpc $$={1} pic ${pic} port-profile $$={E-4X100G-6X50G} port-num $$={7} speed $$={1g}\" && \"chassis fpc $$={1} pic ${pic} port-profile $$={E-4X100G-6X50G} port-num $$={9} speed $$={1g}\") || (!(\"chassis fpc $$={1} pic ${pic} port-profile $$={E-4X100G-6X50G} port-num $$={7} speed\") && !(\"chassis fpc $$={1} pic ${pic} port-profile $$={E-4X100G-6X50G} port-num $$={9} speed\")))))))";
             junos:must-message "For port-pair(7, 9) both ports need to be configured to same speed (1g, 10g, 25g, 50g)";
             junos:must "((\"chassis fpc $$={1} pic ${pic} port-profile $$={E-4X100G-6X50G} port-num $$={13} speed $$={50g}\" || (\"chassis fpc $$={1} pic ${pic} port-profile $$={E-4X100G-6X50G} port-num $$={13} speed $$={25g}\" || (\"chassis fpc $$={1} pic ${pic} port-profile $$={E-4X100G-6X50G} port-num $$={13} speed $$={10g}\" || (\"chassis fpc $$={1} pic ${pic} port-profile $$={E-4X100G-6X50G} port-num $$={13} speed $$={1g}\" || !(\"chassis fpc $$={1} pic ${pic} port-profile $$={E-4X100G-6X50G} port-num $$={13} speed\"))))))";
             junos:must-message "Port 13, configurable speed (50g/25g/10g/1g) only";
             junos:must "((\"chassis fpc $$={1} pic ${pic} port-profile $$={E-4X100G-6X50G} port-num $$={12} speed $$={50g}\" || (\"chassis fpc $$={1} pic ${pic} port-profile $$={E-4X100G-6X50G} port-num $$={12} speed $$={25g}\" || (\"chassis fpc $$={1} pic ${pic} port-profile $$={E-4X100G-6X50G} port-num $$={12} speed $$={10g}\" || (\"chassis fpc $$={1} pic ${pic} port-profile $$={E-4X100G-6X50G} port-num $$={12} speed $$={1g}\" || !(\"chassis fpc $$={1} pic ${pic} port-profile $$={E-4X100G-6X50G} port-num $$={12} speed\"))))))";
             junos:must-message "Port 12, configurable speed (50g/25g/10g/1g) only";
             junos:must "((\"chassis fpc $$={1} pic ${pic} port-profile $$={E-4X100G-6X50G} port-num $$={11} speed $$={50g}\" || (\"chassis fpc $$={1} pic ${pic} port-profile $$={E-4X100G-6X50G} port-num $$={11} speed $$={25g}\" || (\"chassis fpc $$={1} pic ${pic} port-profile $$={E-4X100G-6X50G} port-num $$={11} speed $$={10g}\" || (\"chassis fpc $$={1} pic ${pic} port-profile $$={E-4X100G-6X50G} port-num $$={11} speed $$={1g}\" || !(\"chassis fpc $$={1} pic ${pic} port-profile $$={E-4X100G-6X50G} port-num $$={11} speed\"))))))";
             junos:must-message "Port 11, configurable speed (50g/25g/10g/1g) only";
             junos:must "((\"chassis fpc $$={1} pic ${pic} port-profile $$={E-4X100G-6X50G} port-num $$={10} speed $$={50g}\" || (\"chassis fpc $$={1} pic ${pic} port-profile $$={E-4X100G-6X50G} port-num $$={10} speed $$={25g}\" || (\"chassis fpc $$={1} pic ${pic} port-profile $$={E-4X100G-6X50G} port-num $$={10} speed $$={10g}\" || (\"chassis fpc $$={1} pic ${pic} port-profile $$={E-4X100G-6X50G} port-num $$={10} speed $$={1g}\" || !(\"chassis fpc $$={1} pic ${pic} port-profile $$={E-4X100G-6X50G} port-num $$={10} speed\"))))))";
             junos:must-message "Port 10, configurable speed (50g/25g/10g/1g) only";
             junos:must "((\"chassis fpc $$={1} pic ${pic} port-profile $$={E-4X100G-6X50G} port-num $$={9} speed $$={50g}\" || (\"chassis fpc $$={1} pic ${pic} port-profile $$={E-4X100G-6X50G} port-num $$={9} speed $$={25g}\" || (\"chassis fpc $$={1} pic ${pic} port-profile $$={E-4X100G-6X50G} port-num $$={9} speed $$={10g}\" || (\"chassis fpc $$={1} pic ${pic} port-profile $$={E-4X100G-6X50G} port-num $$={9} speed $$={1g}\" || !(\"chassis fpc $$={1} pic ${pic} port-profile $$={E-4X100G-6X50G} port-num $$={9} speed\"))))))";
             junos:must-message "Port 9, configurable speed (50g/25g/10g/1g) only";
             junos:must "(!(\"chassis fpc $$={1} pic ${pic} port-profile $$={E-4X100G-6X50G} port-num $$={8} speed\"))";
             junos:must-message "Port 8, this port is not part of the port-profile";
             junos:must "((\"chassis fpc $$={1} pic ${pic} port-profile $$={E-4X100G-6X50G} port-num $$={7} speed $$={50g}\" || (\"chassis fpc $$={1} pic ${pic} port-profile $$={E-4X100G-6X50G} port-num $$={7} speed $$={25g}\" || (\"chassis fpc $$={1} pic ${pic} port-profile $$={E-4X100G-6X50G} port-num $$={7} speed $$={10g}\" || (\"chassis fpc $$={1} pic ${pic} port-profile $$={E-4X100G-6X50G} port-num $$={7} speed $$={1g}\" || !(\"chassis fpc $$={1} pic ${pic} port-profile $$={E-4X100G-6X50G} port-num $$={7} speed\"))))))";
             junos:must-message "Port 7, configurable speed (50g/25g/10g/1g) only";
             junos:must "(!(\"chassis fpc $$={1} pic ${pic} port-profile $$={E-4X100G-6X50G} port-num $$={6} speed\"))";
             junos:must-message "Port 6, this port is not part of the port-profile";
             junos:must "(!(\"chassis fpc $$={1} pic ${pic} port-profile $$={E-4X100G-6X50G} port-num $$={5} speed\"))";
             junos:must-message "Port 5, this port is not part of the port-profile";
             junos:must "(!(\"chassis fpc $$={1} pic ${pic} port-profile $$={E-4X100G-6X50G} port-num $$={4} speed\"))";
             junos:must-message "Port 4, this port is not part of the port-profile";
             junos:must "((\"chassis fpc $$={1} pic ${pic} port-profile $$={E-4X100G-6X50G} port-num $$={3} speed $$={100g}\" || !(\"chassis fpc $$={1} pic ${pic} port-profile $$={E-4X100G-6X50G} port-num $$={3} speed\")))";
             junos:must-message "Port 3, configurable speed (100g) only";
             junos:must "((\"chassis fpc $$={1} pic ${pic} port-profile $$={E-4X100G-6X50G} port-num $$={2} speed $$={100g}\" || !(\"chassis fpc $$={1} pic ${pic} port-profile $$={E-4X100G-6X50G} port-num $$={2} speed\")))";
             junos:must-message "Port 2, configurable speed (100g) only";
             junos:must "((\"chassis fpc $$={1} pic ${pic} port-profile $$={E-4X100G-6X50G} port-num $$={1} speed $$={100g}\" || !(\"chassis fpc $$={1} pic ${pic} port-profile $$={E-4X100G-6X50G} port-num $$={1} speed\")))";
             junos:must-message "Port 1, configurable speed (100g) only";
             junos:must "((\"chassis fpc $$={1} pic ${pic} port-profile $$={E-4X100G-6X50G} port-num $$={0} speed $$={100g}\" || !(\"chassis fpc $$={1} pic ${pic} port-profile $$={E-4X100G-6X50G} port-num $$={0} speed\")))";
             junos:must-message "Port 0, configurable speed (100g) only";
           }
         }
       }
       uses apply-advanced;
       list port-num {
         key name;
         ordered-by user;
         description "Port number";
         leaf name {
           description "Refer 'show chassis pic port-profile' for valid port. Commit port-profile change first";
           junos:cli-feature "nokeyword";
           type union {
             type string {
               pattern "<.*>|$.*";
             }
             type uint32 {
               range "0 .. 13";
             }
           }
         }
         uses apply-advanced;
         leaf speed {
           description "Port speed";
           type enumeration {
             enum "1g" {
               description "Refer 'show chassis pic port-profile' for valid speed. Commit port-profile change first";
             }
             enum "10g" {
             }
             enum "25g" {
             }
             enum "40g" {
             }
             enum "50g" {
             }
             enum "100g" {
             }
             enum "400g" {
             }
           }
         }
       }
     }
     choice adaptive-or-monitoring {
       case case_1 {
       }
       case case_2 {
         container monitoring-services {
           description "Monitoring services configuration";
           uses apply-advanced;
           leaf application {
             description "Application mode";
             type enumeration {
               enum "dynamic-flow-capture" {
                 description "Dynamic flow capture mode";
               }
               enum "flow-collector" {
                 description "Flow collector mode";
               }
               enum "monitor" {
                 description "Monitor mode";
               }
             }
           }
         }
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
         enum "lan" {
           description "LAN mode";
         }
       }
     }
     leaf vtmapping {
       description "Virtual tunnel mapping mode";
       type enumeration {
         enum "klm" {
           description "KLM mode";
         }
         enum "itu-t" {
           description "ITU-T mode";
         }
       }
     }
     leaf no-concatenate {
       description "Do not concatenate channels";
       type empty;
     }
     leaf no-multi-rate {
       description "Disable multi-rate mode";
       type empty;
     }
     leaf speed {
       description "Port speed";
       type enumeration {
         enum "1G" {
           description "1GE-Gigabit Ethernet";
         }
       }
     }
     leaf aggregate-ports {
       description "Aggregate multiple ports on a PIC as a single port";
       type empty;
     }
     leaf number-of-ports {
       description "Number of physical ports to enable on PIC";
       type union {
         type string {
           pattern "<.*>|$.*";
         }
         type uint32;
       }
     }
     leaf power {
       description "Power off PIC";
       type enumeration {
         enum "off" {
           description "Do not provide power to PIC";
         }
       }
     }
     leaf sparse-dlcis {
       description "Run in sparse data-link connection identifier mode";
       type empty;
     }
     container q-pic-large-buffer {
       presence "enable q-pic-large-buffer";
       description "Run in large delay buffer mode";
       uses apply-advanced;
       choice buffer-type {
         case case_1 {
           leaf small-scale {
             description "Supports less number of interfaces";
             type empty;
           }
         }
         case case_2 {
           leaf large-scale {
             description "Supports large number of interfaces";
             type empty;
           }
         }
       }
     }
     container red-buffer-occupancy {
       description "Computation type for RED buffer occupancy";
       uses apply-advanced;
       container weighted-averaged {
         presence "enable weighted-averaged";
         description "Weighted-average computation";
         uses apply-advanced;
         leaf instant-usage-weight-exponent {
           description "Weight for instant buffer usage (negative exponent of 2)";
           type union {
             type uint8;
             type string {
               pattern "<.*>|$.*";
             }
           }
         }
       }
     }
     container traffic-manager {
       description "Configure traffic manager attributes";
       uses apply-advanced;
       leaf ingress-shaping-overhead {
         description "Number of CoS shaping overhead bytes in ingress";
         units "bytes";
         type union {
           type string {
             pattern "<.*>|$.*";
           }
           type int32 {
             range "-62 .. 192";
           }
         }
       }
       leaf egress-shaping-overhead {
         description "Number of CoS shaping overhead bytes in egress";
         units "bytes";
         type union {
           type string {
             pattern "<.*>|$.*";
           }
           type int32 {
             range "-62 .. 192";
           }
         }
       }
       leaf queue-buffer-size {
         description "Set the buffer size of output queue";
         type enumeration {
           enum "small" {
             description "Use small buffer size";
           }
         }
       }
       leaf mode {
         description "Configure traffic manager mode";
         type enumeration {
           enum "egress-only" {
             description "Egress traffic manager enabled, ingress traffic manager disabled";
           }
           enum "session-shaping" {
             description "Enable egress session shaping";
           }
           enum "ingress-and-egress" {
             description "Enable the ingress and egress traffic managers";
           }
         }
       }
     }
     container idle-cell-format {
       description "ATM idle cell configuration";
       uses apply-advanced;
       leaf itu-t {
         description "ITU-T idle cell header format";
         type empty;
       }
       leaf payload-pattern {
         description "Payload pattern byte (0x00-0xff)";
         type string;
       }
     }
     container atm-l2circuit-mode {
       description "Enable ATM Layer 2 circuit transport mode";
       uses apply-advanced;
       choice mode_choice {
         case case_1 {
           leaf aal5 {
             description "ATM Layer 2 circuit AAL5 mode";
             type empty;
           }
         }
         case case_2 {
           leaf cell {
             description "ATM Layer 2 circuit cell mode";
             type empty;
           }
         }
         case case_3 {
           container trunk {
             presence "enable trunk";
             description "Set ATM Layer 2 circuit trunk mode";
             uses apply-advanced;
             choice trunk-mode {
               case case_1 {
                 container uni {
                   presence "enable uni";
                   description "ATM Layer 2 circuit user-to-network interface trunk mode";
                   uses apply-advanced;
                 }
               }
               case case_2 {
                 container nni {
                   presence "enable nni";
                   description "ATM Layer 2 circuit network-to-network interface trunk mode";
                   uses apply-advanced;
                 }
               }
             }
           }
         }
       }
     }
     leaf atm-cell-relay-accumulation {
       description "Enable ATM cell-relay accumulation mode";
       type empty;
     }
     container services-offload {
       presence "enable services-offload";
       description "Enable services offload";
       uses apply-advanced;
       leaf per-session-statistics {
         description "Keep per session statistics in NP";
         junos:must "(!(\".. packet-copy\"))";
         junos:must-message "packet-copy and per-session-statistics options are mutual exclusive";
         type empty;
       }
       leaf low-latency {
         description "Bypass Traffic Management stage to achieve low latency";
         type empty;
       }
     }
     leaf mlfr-uni-nni-bundles {
       description "Number of multilink Frame Relay UNI NNI (FRF.16) bundles to allocate on PIC";
       type union {
         type string {
           pattern "<.*>|$.*";
         }
         type uint32 {
           range "1 .. 255";
         }
       }
     }
     leaf mlfr-uni-nni-bundles-inline {
       description "Number of inline multilink frame relay UNI NNI bundles";
       type union {
         type string {
           pattern "<.*>|$.*";
         }
         type uint32 {
           range "1 .. 255";
         }
       }
     }
     container ct3 {
       description "CT3 NxDS0 PIC configuration";
       uses apply-advanced;
       list port {
         key name;
         description "CT3 port";
         uses ct3_port_type;
       }
     }
     container ce1 {
       description "CE1 NxDS0 PIC configuration";
       uses apply-advanced;
       list e1 {
         key name;
         description "E1 link";
         uses ce1_channel_type;
       }
     }
     leaf max-queues-per-interface {
       description "Maximum number of queues per interface on QOS-capable PIC";
       type enumeration {
         enum "4" {
           description "Maximum 4 queues per interface";
         }
         enum "8" {
           description "Maximum 8 queues per interface";
         }
       }
     }
     container shdsl {
       description "SHDSL chassis configuration";
       uses apply-advanced;
       leaf pic-mode {
         description "PIC mode";
         default "2-port-atm";
         type enumeration {
           enum "1-port-atm" {
             description "Single port ATM, 4 wire mode";
           }
           enum "2-port-atm" {
             description "Two port ATM, 2 wire mode";
           }
           enum "4-port-atm" {
             description "Four port ATM, 2 wire mode";
           }
           enum "efm" {
             description "Single port EFM, 2 wire mode";
           }
         }
       }
     }
     container ethernet {
       description "J-series Ethernet PIM mode configuration";
       uses apply-advanced;
       leaf pic-mode {
         description "PIC mode";
         default "routing";
         type enumeration {
           enum "switching" {
             description "Switched mode of operation";
           }
           enum "routing" {
             description "Routing mode of operation";
           }
           enum "enhanced-switching" {
             description "Enhanced switching mode of operation";
             junos:must "(unique \"chassis fpc <*> pic <*> ethernet pic-mode enhanced-switching\")";
             junos:must-message "Enhanced-switching can be configured only on single PIM";
           }
         }
       }
     }
     leaf tunnel-queuing {
       description "Enable queueing for GRE/IPIP tunnels";
       type empty;
     }
     list port-mirror-instance {
       key name;
       ordered-by user;
       max-elements 2;
       leaf name {
         description "Associate a port mirroring instance with the PIC";
         junos:cli-feature "nokeyword";
         junos:must "(!(\"forwarding-options port-mirroring instance $$ input-parameters-instance\"))";
         junos:must-message "Derived instance cannot be binded";
         junos:must "(((!(\"chassis network-services lan\") && (\"forwarding-options port-mirroring instance $$\" || \"forwarding-options analyzer $$\")) || \"chassis network-services lan\"))";
         junos:must-message "Referenced port-mirroring instance does not exist";
         type string {
           length "1 .. 64";
         }
       }
       uses apply-advanced;
     }
     list port {
       key name;
       description "Port number";
       uses chassis_pic_port_framing;
     }
     container fibre-channel {
       description "Fibre channel configuration option";
       junos:cli-feature "oneliner-plus";
       uses chassis_fibre_channel_type;
     }
     leaf ingress-policer-overhead {
       description "Number of policer overhead bytes in ingress";
       units "bytes";
       type union {
         type string {
           pattern "<.*>|$.*";
         }
         type uint32 {
           range "0 .. 255";
         }
       }
     }
     leaf account-layer2-overhead {
       description "Account Layer2 overhead in egress and ingress IFD/IFL stats";
       type empty;
     }
   }
   grouping ce1_channel_type {
     leaf name {
       description "E1 link number";
       junos:cli-feature "nokeyword";
       type union {
         type string {
           pattern "<.*>|$.*";
         }
         type uint32 {
           range "0 .. 9";
         }
       }
     }
     uses apply-advanced;
     list channel-group {
       key name;
       junos:cli-feature "oneliner";
       description "Define channel group";
       leaf name {
         description "Channel group number";
         junos:cli-feature "nokeyword";
         type union {
           type string {
             pattern "<.*>|$.*";
           }
           type uint32 {
             range "0 .. 23";
           }
         }
       }
       leaf timeslots {
         description "DS0 timeslots (1..31); for example, 1-3,4,9,22-24 (no spaces)";
         type string;
       }
     }
   }
   grouping chassis_fibre_channel_type {
     junos:cli-feature "oneliner-plus";
     description "Fibre channel configuration option";
     uses apply-advanced;
     list port-range {
       key "port-range-low port-range-high";
       ordered-by user;
       description "Fibre channel port range";
       leaf port-range-low {
         description "Port range low number";
         junos:cli-feature "nokeyword";
         type union {
           type string {
             pattern "<.*>|$.*";
           }
           type uint32 {
             range "0 .. 47";
           }
         }
       }
       leaf port-range-high {
         description "Port range high number";
         junos:cli-feature "nokeyword";
         type union {
           type string {
             pattern "<.*>|$.*";
           }
           type uint32 {
             range "0 .. 47";
           }
         }
       }
       uses apply-advanced;
     }
   }
   grouping chassis_pic_port_framing {
     leaf name {
       description "Port number";
       junos:cli-feature "nokeyword";
       type union {
         type string {
           pattern "<.*>|$.*";
         }
         type uint32;
       }
     }
     uses apply-advanced;
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
       }
     }
     leaf number-of-sub-ports {
       description "Number of subports per physical port";
       type union {
         type string {
           pattern "<.*>|$.*";
         }
         type uint32;
       }
     }
     leaf unused {
       description "Keep the port unused.";
       type empty;
     }
     leaf speed {
       description "Port speed";
       junos:must "(!((\".. .. pic-mode\" || \".. .. number-of-ports\")))";
       junos:must-message " speed config can neither co-exist with pic <> number-of-ports <> nor pic <> pic-mode config";
       type enumeration {
         enum "oc3-stm1" {
           description "OC3 or STM1";
         }
         enum "oc12-stm4" {
           description "OC12 or STM4";
         }
         enum "oc48-stm16" {
           description "OC48 or STM16";
         }
         enum "1G" {
           description "1GE-Gigabit Ethernet";
         }
         enum "10g" {
           description "Sets the interface mode to 10Gbps";
         }
         enum "25g" {
           description "Sets the interface mode to 25Gbps";
         }
         enum "40g" {
           description "Sets the interface mode to 40Gbps";
         }
         enum "100g" {
           description "Sets the interface mode to 100Gbps";
         }
         enum "50g" {
           description "Sets the interface mode to 50Gbps";
         }
         enum "200g" {
           description "Sets the interface mode to 200 Gbps";
         }
         enum "400g" {
           description "Sets the interface mode to 400Gbps";
         }
       }
     }
     leaf channel-speed {
       description "Port channel speed";
       type enumeration {
         enum "10g" {
           description "Set the port speed to 10G. This will restart PFE on some platforms.";
         }
         enum "25g" {
           description "Set the port speed to 25G.";
         }
         enum "50g" {
           description "Set the port speed to 50G.";
         }
         enum "disable-auto-speed-detection" {
           description "Disables automatic speed detection";
         }
       }
     }
   }
   grouping chassis_redundancy_type {
     uses apply-advanced;
     list routing-engine {
       key name;
       description "Redundancy options for Routing Engines";
       uses chassis_rdd_re_type;
       junos:cli-feature "oneliner";
     }
     container failover {
       description "Failover to other Routing Engine";
       presence "enable failover";
       junos:cli-feature "oneliner-plus";
       uses chassis_rdd_failover_type;
     }
     leaf keepalive-time {
       description "Time before Routing Engine failover";
       units "seconds";
       junos:must "(!(\"chassis redundancy graceful-switchover\"))";
       junos:must-message "Graceful switchover configured, cannot change the default keepalive interval";
       type union {
         type string {
           pattern "<.*>|$.*";
         }
         type uint32 {
           range "2 .. 10000";
         }
       }
     }
     container graceful-switchover {
       description "Enable graceful switchover on supported hardware";
       presence "enable graceful-switchover";
       junos:must "(!(any \"chassis fpc <*> pic <*> monitoring-services application\"))";
       junos:must-message "Graceful Switchover is not supported on monitoring-services application";
       uses chassis_non_stop_forwarding_type;
     }
   }
   grouping chassis_non_stop_forwarding_type {
     junos:must "((!(\"system inet6-backup-router\") || \"system inet6-backup-router destination\"))";
     junos:must-message "Please define destination subnet with the inet6-backup-router configuration";
     junos:must "((!(\"system backup-router\") || \"system backup-router destination\"))";
     junos:must-message "Please define destination subnet with the backup-router configuration";
     uses apply-advanced;
     container traceoptions {
       description "Graceful switchover trace options";
       status deprecated;
       uses apply-advanced;
       list flag {
         key name;
         ordered-by user;
         junos:cli-feature "oneliner";
         description "Tracing parameters";
         leaf name {
           junos:cli-feature "nokeyword";
           type enumeration {
             enum "update" {
               description "Trace state updates";
             }
             enum "all" {
               description "Trace everything";
             }
           }
         }
       }
     }
   }
   grouping chassis_rdd_failover_type {
     junos:cli-feature "oneliner-plus";
     uses apply-advanced;
     container category {
       description "Failover category";
       presence "enable category";
       uses chassis_rdd_fail_cat_type;
     }
     leaf on-loss-of-keepalives {
       description "Failover on loss of keepalives";
       type empty;
     }
     leaf on-re-to-fpc-stale {
       description "Failover on loss of communication between the re and fpc";
       type empty;
     }
     leaf on-disk-failure {
       description "Failover on disk failure";
       junos:must "((\"chassis redundancy failover on-loss-of-keepalives\" || \"chassis redundancy graceful-switchover\"))";
       junos:must-message "Option on-loss-of-keepalives or graceful-switchover must be set";
       type empty;
     }
     leaf not-on-disk-underperform {
       description "Prevent gstatd from initiating failovers in response to slow disks";
       type empty;
     }
     leaf disk-read-threshold {
       description "Read threshold (ms) on disk underperform monitoring";
       type union {
         type string {
           pattern "<.*>|$.*";
         }
         type uint32 {
           range "1000 .. 10000";
         }
       }
     }
     leaf disk-write-threshold {
       description "Write threshold (ms) on disk underperform monitoring";
       type union {
         type string {
           pattern "<.*>|$.*";
         }
         type uint32 {
           range "1000 .. 10000";
         }
       }
     }
     leaf on-loss-of-vm-host-connection {
       description "Failover on loss of vm host connection";
       type empty;
     }
   }
   grouping chassis_rdd_fail_cat_type {
     uses apply-advanced;
     container component-failure {
       description "Failover due to component failure";
       presence "enable component-failure";
       uses chassis_rdd_fail_cat_sev_type;
     }
     container software-failure {
       description "Failover due to software failure";
       presence "enable software-failure";
       uses chassis_rdd_fail_cat_sev_type;
     }
     container power-failure {
       description "Failover due to power failure";
       presence "enable power-failure";
       uses chassis_rdd_fail_cat_sev_type;
     }
     container clock-failure {
       description "Failover due to clock failure";
       presence "enable clock-failure";
       uses chassis_rdd_fail_cat_sev_type;
     }
     container link-failure {
       description "Failover due to link failure";
       presence "enable link-failure";
       uses chassis_rdd_fail_cat_sev_type;
     }
     container degraded-health {
       description "Failover due to degraded health";
       presence "enable degraded-health";
       uses chassis_rdd_fail_cat_sev_type;
     }
   }
   grouping chassis_rdd_fail_cat_sev_type {
     uses apply-advanced;
     container critical {
       description "Critical severity";
       presence "enable critical";
       uses chassis_rdd_fail_cat_sev_act_type;
     }
     container important {
       description "Important severity";
       presence "enable important";
       uses chassis_rdd_fail_cat_sev_act_type;
     }
   }
   grouping chassis_rdd_fail_cat_sev_act_type {
     uses apply-advanced;
     leaf disable {
       description "Disable action";
       type empty;
     }
   }
   grouping chassis_rdd_re_type {
     junos:cli-feature "oneliner";
     leaf name {
       description "Routing Engine slot number";
       junos:cli-feature "nokeyword";
       type union {
         type string {
           pattern "<.*>|$.*";
         }
         type uint32 {
           range "0 .. 1";
         }
       }
     }
     choice priority {
       case case_1 {
         leaf master {
           description "Master Routing Engine";
           type empty;
         }
       }
       case case_2 {
         leaf backup {
           description "Backup Routing Engine";
           type empty;
         }
       }
       case case_3 {
         leaf disabled {
           description "Routing Engine disabled";
           type empty;
         }
       }
     }
   }
   grouping chassis_routing_engine_type {
     uses apply-advanced;
     container on-disk-failure {
       description "Action to take when Routing Engine disk fails";
       junos:cli-feature "oneliner";
       uses chassis_re_on_disk_failure;
     }
     container control-interface {
       presence "enable control-interface";
       description "Configure recovery method and pause frame for control interface";
       uses apply-advanced;
       leaf recovery-method {
         description "Select the recovery method";
         type enumeration {
           enum "disable-recovery" {
             description "Don't enable recovery";
           }
           enum "socket" {
             description "Recovery by using socket";
           }
           enum "counter" {
             description "Recovery by using BCM-Counters";
           }
         }
       }
       leaf pause-frame {
         description "Enable or disable Pause frame generation";
         type empty;
       }
     }
     container bios {
       description "Routing Engine BIOS";
       uses apply-advanced;
       leaf no-auto-upgrade {
         description "Disable routing-engine BIOS auto-upgrade";
         type empty;
       }
       leaf uninterrupt {
         description "Set routing-engine BIOS uninterruptable";
         type empty;
       }
     }
     container disk {
       description "Action to take for Routing Engine disk";
       uses apply-advanced;
       leaf write-threshold-rate {
         description "Write threshold rate";
         default "4";
         units "MBPS";
         type union {
           type string {
             pattern "<.*>|$.*";
           }
           type uint32 {
             range "1 .. 20";
           }
         }
       }
       leaf write-threshold-duration {
         description "Write threshold duration";
         default "1000";
         units "seconds";
         type union {
           type string {
             pattern "<.*>|$.*";
           }
           type uint32 {
             range "300 .. 2592000";
           }
         }
       }
       leaf smart-check {
         description "Enable smart check command to disk";
         type empty;
       }
       list ssd-series {
         key name;
         ordered-by user;
         description "Specify the ssd vendor series";
         leaf name {
           description "SSD series name";
           junos:cli-feature "nokeyword";
           type string {
             length "1 .. 40";
           }
         }
         uses apply-advanced;
         list id {
           key name;
           ordered-by user;
           description "Attribute ids to monitor of this series type";
           max-elements 30;
           leaf name {
             description "SSD smart attribute id";
             junos:cli-feature "nokeyword";
             type union {
               type string {
                 pattern "<.*>|$.*";
               }
               type uint32 {
                 range "1 .. 255";
               }
             }
           }
           uses apply-advanced;
           leaf id-threshold {
             description "SSD smart attribute threshold";
             type union {
               type string {
                 pattern "<.*>|$.*";
               }
               type uint32 {
                 range "1 .. 4294967295";
               }
             }
           }
           leaf id-value {
             description "SSD attribute value";
             type enumeration {
               enum "raw" {
                 description "Raw value to be used for this smart id";
               }
               enum "norm" {
                 description "Normalised value to be used for this smart id";
               }
             }
           }
           leaf id-flag {
             description "SSD attribute flag";
             type enumeration {
               enum "low" {
                 description "Check if value is less than smart threshold";
               }
               enum "high" {
                 description "Check if value is greater than smart threshold";
               }
             }
           }
         }
       }
     }
     container usb-wwan {
       description "Enable WWAN (3G) access on the USB port";
       uses apply-advanced;
       leaf port {
         description "Select the port";
         type enumeration {
           enum "0" {
             description "Select port 0 to enable WWAN access";
           }
           enum "1" {
             description "Select port 1 to enable WWAN access";
           }
         }
       }
     }
   }
   grouping chassis_re_on_disk_failure {
     junos:cli-feature "oneliner";
     choice reboot_or_halt {
       case case_1 {
         leaf reboot {
           description "Reboot on disk failure";
           status deprecated;
           type empty;
         }
       }
       case case_2 {
         leaf disk-failure-action {
           type enumeration {
             enum "reboot" {
               description "Reboot on disk failure";
             }
             enum "halt" {
               description "Halt on disk failure";
             }
           }
         }
       }
     }
     leaf failover {
       description "Redundancy group 0 failover on disk failure";
       type empty;
     }
   }
   grouping chassis_sib_type {
     uses apply-advanced;
   }
   grouping chassisd_agg_container_type {
     uses apply-advanced;
     leaf device-count {
       description "Number of container devices";
       type union {
         type string {
           pattern "<.*>|$.*";
         }
         type uint32 {
           range "1 .. 128";
         }
       }
     }
   }
   grouping chassisd_agg_enet_type {
     uses apply-advanced;
     leaf device-count {
       description "Number of aggregated Ethernet devices";
       type union {
         type string {
           pattern "<.*>|$.*";
         }
         type uint32;
       }
     }
     container lacp {
       description "Global Link Aggregation Control Protocol configuration";
       uses apply-advanced;
       leaf system-priority {
         description "Priority of the system (0 ... 65535)";
         type string;
       }
       container link-protection {
         presence "enable link-protection";
         uses apply-advanced;
         leaf non-revertive {
           description "Don't revert links when better priority link comes up";
           type empty;
         }
       }
     }
   }
   grouping chassisd_agg_pos_type {
     uses apply-advanced;
     leaf device-count {
       description "Number of aggregated SONET devices";
       type union {
         type string {
           pattern "<.*>|$.*";
         }
         type uint32 {
           range "1 .. 64";
         }
       }
     }
   }
   grouping ct3_port_type {
     leaf name {
       description "CT3  L2NG_PRODUCTSport number";
       junos:cli-feature "nokeyword";
       type union {
         type string {
           pattern "<.*>|$.*";
         }
         type int32 {
           range "0 .. 1";
         }
       }
     }
     uses apply-advanced;
     list t1 {
       key name;
       description "T1 link";
       uses ct3_channel_type;
     }
   }
   grouping ct3_channel_type {
     leaf name {
       description "T1 link number";
       junos:cli-feature "nokeyword";
       type union {
         type string {
           pattern "<.*>|$.*";
         }
         type int32 {
           range "0 .. 27";
         }
       }
     }
     uses apply-advanced;
     list channel-group {
       key name;
       junos:cli-feature "oneliner";
       description "Define channel group";
       leaf name {
         description "Channel group number";
         junos:cli-feature "nokeyword";
         type union {
           type string {
             pattern "<.*>|$.*";
           }
           type uint32 {
             range "0 .. 7";
           }
         }
       }
       leaf timeslots {
         description "DS0 timeslots (1..24); for example, 1-3,4,9,22-24 (no spaces)";
         type string;
       }
     }
   }
   grouping ip-monitoring-address-type {
     junos:cli-feature "nokeyword";
     junos:cli-feature "homogeneous";
     junos:cli-feature "oneliner-plus";
     description "Define IP address related parameters";
     leaf name {
       description "Define IPv4 address to be monitored";
       junos:cli-feature "nokeyword";
       type jt:ipv4addr;
     }
     uses apply-advanced;
     leaf weight {
       description "Define weight for this IP address";
       type union {
         type string {
           pattern "<.*>|$.*";
         }
         type uint16 {
           range "0 .. 255";
         }
       }
     }
     list interface {
       key name;
       ordered-by user;
       description "Logical interface through which to monitor this IP address";
       max-elements 1;
       leaf name {
         description "Logical interface name";
         junos:cli-feature "nokeyword";
         junos:must "(\"interfaces $$-IFL family inet\")";
         junos:must-message "Family inet must be defined on this logical interface";
         type union {
           type jt:interface-name;
           type string {
             pattern "<.*>|$.*";
           }
         }
       }
       uses apply-advanced;
       leaf secondary-ip-address {
         description "Define source address for monitoring packets on secondary link";
         type jt:ipv4addr;
       }
     }
   }
   grouping juniper-protected-system-domain {
     junos:cli-feature "homogeneous";
     description "Protected system domain configuration";
     leaf name {
       description "Name of protected system domain (psd[1-31], ex. psd2)";
       junos:cli-feature "nokeyword";
       type string {
         junos:posix-pattern "^psd([1-9]|[1-2][0-9]|[3][0-1])$";
         junos:pattern-message "Protected system domain name is a string consisting of \'psd\' follows by the PSD ID (1-31), ex. psd2";
       }
     }
     uses apply-advanced;
     leaf description {
       description "Description of protected system domain";
       type string;
     }
     list lcc {
       key name;
       junos:cli-feature "oneliner-plus";
       leaf name {
         description "Specific LCC";
         junos:cli-feature "nokeyword";
         type union {
           type string {
             pattern "<.*>|$.*";
           }
           type uint32;
         }
       }
       uses apply-advanced;
       leaf-list fpcs {
         description "FPC associated with protected system domain";
         type union {
           type string {
             pattern "<.*>|$.*";
           }
           type uint32;
         }
       }
     }
     leaf control-system-id {
       description "Control system identifier";
       type union {
         type string {
           pattern "<.*>|$.*";
         }
         type uint32 {
           range "1 .. 4";
         }
       }
     }
     leaf-list control-slot-numbers {
       ordered-by user;
       description "Slots associated with protected system domain";
       type union {
         type string {
           pattern "<.*>|$.*";
         }
         type uint32 {
           range "1 .. 12";
         }
       }
       max-elements 2;
     }
     leaf control-plane-bandwidth-percent {
       description "Percentage of control plane bandwidth";
       units "percent";
       type union {
         type string {
           pattern "<.*>|$.*";
         }
         type uint32 {
           range "0 .. 100";
         }
       }
     }
   }
   grouping juniper-protected-system-domain-traceoptions {
     description "Protected system domain traceoptions";
     uses apply-advanced;
     leaf no-remote-trace {
       description "Disable remote tracing";
       junos:must "(\"system tracing\")";
       junos:must-message "'no-remote-trace' is valid only when [system tracing] is configured";
       type empty;
     }
     container file {
       junos:cli-feature "oneliner";
       description "Trace file information";
       leaf filename {
         description "Name of file in which to write trace information";
         junos:cli-feature "nokeyword";
         type string {
           length "1 .. 1024";
           junos:posix-pattern "![/ %]";
           junos:pattern-message "Must not contain \'/\', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       junos:cli-feature "oneliner";
       description "Tracing parameters";
       leaf name {
         junos:cli-feature "nokeyword";
         type enumeration {
           enum "configuration" {
             description "Trace configuration events";
           }
           enum "rtsock" {
             description "Trace rtsock messages";
           }
           enum "ipc" {
             description "Trace IPC messages";
           }
           enum "init" {
             description "Trace intialization messages";
           }
           enum "psd" {
             description "Trace psd messages";
           }
           enum "all" {
             description "Trace everything";
           }
         }
       }
     }
   }
   grouping macro-data-type {
     junos:cli-feature "nokeyword";
     junos:cli-feature "homogeneous";
     junos:cli-feature "oneliner";
     leaf name {
       description "Keyword part of the keyword-value pair";
       junos:cli-feature "nokeyword";
       type string;
     }
     leaf value {
       description "Value part of the keyword-value pair";
       junos:cli-feature "nokeyword";
       type string;
     }
   }
 }
