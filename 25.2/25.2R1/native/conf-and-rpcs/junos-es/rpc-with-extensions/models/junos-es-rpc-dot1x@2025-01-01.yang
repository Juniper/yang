/*
 * Copyright (c) 2025 Juniper Networks, Inc.
 * All rights reserved.
 */
 module junos-es-rpc-dot1x {
   namespace "http://yang.juniper.net/junos-es/rpc/dot1x";

   prefix dot1x;

   import junos-common-ddl-extensions {
     prefix junos;
     revision-date 2025-01-01;
   }

   import junos-common-types {
     prefix jt;
     revision-date 2025-01-01;
   }

   organization "Juniper Networks, Inc.";

   contact "yang-support@juniper.net";

   description "Junos RPC YANG module for dot1x command(s)";

   revision 2025-01-01 {
     description "Junos: 25.2R1.9";
   }

   rpc get-dot1x-interface-information {
     description "Show 802.1X interface information";
     junos:command "show dot1x interface";
     input {
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf interface-name {
         description "Name of interface";
         junos:cli-feature "nokeyword";
         type union {
           type jt:interface-wildcard;
           type string {
             pattern "<.*>|$.*";
           }
         }
       }
     }
     output {
       container dot1x-interface-information {
         uses dot1x-interface-information-block;
       }
     }
   }
   rpc get-dot1x-supplicant {
     description "Show 802.1X supplicants";
     junos:command "show dot1x supplicant";
     output {
       container dot1x-interface-information {
         uses dot1x-interface-information-block;
       }
     }
   }
   rpc get-dot1x-interface-supplicant {
     description "Show 802.1X supplicant details on this interface";
     junos:command "show dot1x supplicant interface";
     input {
       leaf verbosity_level {
         junos:cli-feature "nokeyword";
         default "brief";
         type enumeration {
           enum "brief" {
             description "Display brief output (default)";
           }
           enum "detail" {
             description "Display detailed output";
           }
         }
       }
       leaf interface-name {
         junos:cli-feature "nokeyword";
         type union {
           type jt:interface-wildcard;
           type string {
             pattern "<.*>|$.*";
           }
         }
       }
     }
     output {
       container dot1x-interface-information {
         uses dot1x-interface-information-block;
       }
     }
   }
   rpc get-dot1x-static-mac-addresess {
     description "Show 802.1X static MAC addresses";
     junos:command "show dot1x static-mac-address";
     output {
       container dot1x-interface-information {
         uses dot1x-interface-information-block;
       }
     }
   }
   rpc get-dot1x-interface-mac-addresses {
     description "Show 802.1X static MAC addresses on this interface";
     junos:command "show dot1x static-mac-address interface";
     input {
       leaf interface-name {
         description "Show static MAC addresses of interface";
         junos:cli-feature "nokeyword";
         type union {
           type jt:interface-wildcard;
           type string {
             pattern "<.*>|$.*";
           }
         }
       }
     }
     output {
       container dot1x-interface-information {
         uses dot1x-interface-information-block;
       }
     }
   }
   rpc get-dot1x-accounting-attributes {
     description "Show 802.1x accounting attributes";
     junos:command "show dot1x accounting-attributes";
     output {
       container dot1x-interface-information {
         uses dot1x-interface-information-block;
       }
     }
   }
   rpc get-dot1x-interface-accounting-attributes {
     description "Show 802.1x accounting attributes on this interface";
     junos:command "show dot1x accounting-attributes interface";
     input {
       leaf interface-name {
         description "Show accounting attributes";
         junos:cli-feature "nokeyword";
         type union {
           type jt:interface-wildcard;
           type string {
             pattern "<.*>|$.*";
           }
         }
       }
     }
     output {
       container dot1x-interface-information {
         uses dot1x-interface-information-block;
       }
     }
   }
   rpc get-dot1x-authentication-failed-users {
     description "List users who have failed 802.1X authentication";
     junos:command "show dot1x authentication-failed-users";
     output {
       container dot1x-interface-information {
         uses dot1x-interface-information-block;
       }
     }
   }
   rpc get-dot1x-context-history {
     description "Print dot1xd context-history";
     junos:command "show dot1x context-history";
     output {
       container dot1xd-ctxt-history {
         uses dot1xd-ctxt-history-block;
       }
     }
   }
   rpc get-dot1x-context-history-mac {
     description "Dot1x clients mac context-history";
     junos:command "show dot1x context-history mac";
     input {
       leaf mac-address {
         description "MAC address for which context-history to be fetched";
         junos:cli-feature "nokeyword";
         default "all";
         type jt:mac-addr;
       }
     }
     output {
       container dot1xd-ctxt-history {
         uses dot1xd-ctxt-history-block;
       }
     }
   }
   rpc dot1x-sync-pending-sessions {
     description "Print dot1x sync pending session during restart or issu";
     junos:command "show dot1x sync-pending-sessions";
     output {
       container dot1xd-sync-pending-sessions {
         uses dot1xd-sync-pending-sessions-block;
       }
     }
   }
   rpc get-static-mac-bypassed-users {
     description "List users who have bypassed 802.1X authentication";
     junos:command "show dot1x authentication-bypassed-users";
     output {
       container dot1x-interface-information {
         uses dot1x-interface-information-block;
       }
     }
   }
   rpc get-dot1x-statistics {
     description "Show 802.1X statistics";
     junos:command "show dot1x statistics";
     input {
       leaf verbosity_level {
         junos:cli-feature "nokeyword";
         default "brief";
         type enumeration {
           enum "brief" {
             description "Display brief output (default)";
           }
           enum "detail" {
             description "Display detailed output";
           }
         }
       }
     }
     output {
       container dot1x-interface-information {
         uses dot1x-interface-information-block;
       }
     }
   }
   rpc get-dot1x-statistics-interface {
     description "Show 802.1X statistics on this interface";
     junos:command "show dot1x statistics interface";
     input {
       leaf verbosity_level {
         junos:cli-feature "nokeyword";
         default "brief";
         type enumeration {
           enum "brief" {
             description "Display brief output (default)";
           }
           enum "detail" {
             description "Display detailed output";
           }
         }
       }
       leaf interface-name {
         description "Show statistics for this interface";
         junos:cli-feature "nokeyword";
         default "all";
         type union {
           type jt:interface-wildcard;
           type string {
             pattern "<.*>|$.*";
           }
         }
       }
     }
     output {
       container dot1x-interface-information {
         uses dot1x-interface-information-block;
       }
     }
   }
   rpc get-dot1x-firewall-interface {
     description "Show dot1x firewall statistics for an interface";
     junos:command "show dot1x firewall";
     input {
       leaf interface-name {
         description "Show firewall statistics for this interface";
         junos:cli-feature "nokeyword";
         type union {
           type jt:interface-wildcard;
           type string {
             pattern "<.*>|$.*";
           }
         }
       }
     }
     output {
       container dot1x-interface-information {
         uses dot1x-interface-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping dot1x-interface-information-block {
     list interface {
       leaf interface-name {
         type string;
       }
       leaf state {
         type string;
         description "Current state of interface";
       }
       leaf user-mac-address {
         type jt:mac-addr;
         description "MAC address of client";
       }
       leaf authenticated-method {
         type string;
         description "Authentication Method used to authenticate a supplicant";
       }
       leaf authenticated-vlan {
         type uint32;
         description "VLAN ID on which supplicant is authenticated";
       }
       leaf authenticated-voip-vlan {
         type string;
         description "Voip VLAN ID on which supplicant is authenticated";
       }
       leaf user-name {
         type string;
         description "User name as sent by client for authentication";
       }
       leaf ignore-port-bounce {
         type string;
         description "Ignore port-bounce request from RADIUS server";
       }
       list supplicant-list {
         container supplicant {
           leaf supplicant-name {
             type string;
             description "User name as sent by the supplicant for authentication";
           }
           leaf supplicant-mac-address {
             type jt:mac-addr;
             description "MAC address of the supplicant";
           }
           leaf radius-supplicant-name {
             type string;
             description "User name as sent by the radius for authentication";
           }
           leaf supplicant-state {
             type string;
             description "Current state of the supplicant";
           }
           leaf supplicant-held-reason {
             type string;
             description "Held state reason of the supplicant";
           }
           leaf backend-administrative-state {
             type string;
             description "Backend Authentication state of port";
           }
           leaf authentication-method {
             type string;
             description "Authentication Method used to authenticate a supplicant";
           }
           leaf authentication-mode {
             type string;
             description "Authentication Mode(EAP/Mac-Radius) used to authenticate a supplicant";
           }
           leaf vlan {
             type string;
             description "VLAN on which supplicant is authenticated";
           }
           leaf secondary-vlan {
             type string;
             description "Secondary VLAN on which supplicant is authenticated";
           }
           leaf voip-vlan {
             type string;
             description "Voip VLAN on which supplicant is authenticated";
           }
           leaf dynamic-filter {
             type string;
             description "Dynamic firewall filter applied for this supplicant";
           }
           leaf group-based-policy-id {
             type uint32;
             description "GBP filter applied for this supplicant";
           }
           leaf vlan-grp-name {
             type string;
             description "Vlan group name for this supplicant";
           }
           leaf session-reauthentication-interval {
             type uint32;
             description "Session reauthentication timer";
           }
           leaf reauthentication-due {
             type uint32;
             description "How long before reauthenticating supplicant";
           }
           leaf no-mac-binding-reauth-vsa {
             type string;
             description "No mac binding reauth VSA status";
           }
           leaf ip-mac-session-binding-vsa {
             type string;
             description "Ip mac session binding VSA status";
           }
           leaf egress-vlan-list {
             type string;
             description "Egress vlan list";
           }
           leaf radius-supplicant-mode {
             type string;
             description "Supplicant authorization mode";
           }
           leaf retain-mac-aged-session-vsa {
             type string;
             description "Retain mac aged session vsa";
           }
           leaf session-acct-interim-interval {
             type uint32;
             description "Session Acct-Interim-Interval timer";
           }
           leaf acct-interim-due {
             type uint32;
             description "How long before updating accounting information";
           }
           leaf cwa-redirect-url {
             type string;
             description "URL to be used for CWA authentication for this client";
           }
           leaf cwa-fallback {
             type string;
             description "Session Fallback from CWA";
           }
           leaf server-fail-voip-action {
             type string;
             description "Server fail action applicable for VoIP clients";
           }
           leaf eapol-block {
             type string;
             description "Eapol-block is in effect or not";
           }
           leaf tenant-id {
             type uint32;
             description "Tenant Id";
           }
           leaf domain {
             type string;
             description "Session Domain";
           }
         }
       }
       leaf role {
         type string;
         description "Role of interface";
       }
       leaf administrative-state {
         type string;
         description "Administrative state of port";
       }
       leaf administrative-mode {
         type string;
         description "Supplicant authorization mode";
       }
       leaf number-of-retries {
         type uint32;
         description "Number of retries after which port is placed into wait state";
       }
       leaf quiet-period {
         type uint32;
         description "Time to wait after authentication failure";
       }
       leaf transmit-period {
         type uint32;
         description "Interval before retransmitting initial EAPOL PDUs";
       }
       leaf mac-radius {
         type string;
         description "MAC-RADIUS status";
       }
       leaf mac-radius-strict {
         type string;
         description "MAC-RADIUS-STRICT status";
       }
       leaf mac-radius-protocol {
         type string;
         description "MAC-RADIUS-PROTOCOL status";
       }
       leaf mac-radius-ignore-port-bounce {
         type string;
         description "Ignore mac-radius port-bounce request from RADIUS server";
       }
       leaf reauthentication {
         type string;
         description "Reauthentication status";
       }
       leaf reauthentication-interval {
         type uint32;
         description "Reauthentication interval";
       }
       leaf supplicant-timeout {
         type uint32;
         description "Time to wait for response from supplicant before resending request";
       }
       leaf server-timeout {
         type uint32;
         description "Time to wait before invoking server-fail action";
       }
       leaf max-eapol-request {
         type uint32;
         description "Maximum number of EAPOL request IDs to client";
       }
       leaf frame-control {
         type string;
         description "Block only ingress traffic before authentication";
       }
       leaf guest-vlan {
         type string;
         description "VLAN members for unauthenticated or non-responsive hosts";
       }
       leaf max-data-session-count {
         type uint32;
         description "Multi domain data session count";
       }
       leaf multi-domain-recovery-timeout {
         type string;
         description "Multi domain error disable recovery timeout";
       }
       leaf no-mac-table-binding {
         type string;
         description "No mac table binding status";
       }
       leaf ip-mac-session-binding {
         type string;
         description "Ip mac session binding status";
       }
       leaf retain-mac-aged-session {
         type string;
         description "Retain mac aged session status";
       }
       leaf last-mac-learn-req {
         type jt:mac-addr;
         description "Last Mac learn request received on the interface.";
       }
       leaf last-mac-learn-time {
         type string;
         description "Timestamp for last Mac learn request received on the interface";
       }
       leaf number-of-connected-supplicants {
         type uint32;
         description "Number of connected supplicants";
       }
       leaf number-of-authentication-bypassed-clients {
         type uint32;
         description "Number of clients bypassed because of authentication";
       }
       leaf static-mac-bypass {
         type jt:mac-addr;
         description "MAC address of bypassed client";
       }
       leaf reauthentication-due {
         type uint32;
         description "How long before reauthenticating supplicant";
       }
     }
     container dot1x-static-mac-address {
       description "Information about configured static MAC addresses";
       leaf static-mac-address {
         type jt:mac-addr;
         description "MAC address configured for bypass";
       }
       leaf static-mac-prefix {
         type int32;
         description "MAC prefix configured for bypass clients";
       }
       leaf static-mac-vlan-assignment {
         type string;
         description "VLAN assigned to the client with this MAC address";
       }
       leaf static-mac-interface {
         type string;
         description "Interface on which client MAC was learned";
       }
     }
     container dot1x-accounting-attribute {
       description "Information about dot1x session accounting attributes";
       leaf dot1x-accounting-attribute-user {
         type string;
         description "User name as sent by the supplicant for authentication";
       }
       leaf dot1x-accounting-attribute-mac-address {
         type string;
         description "MAC address of the supplicant";
       }
       leaf dot1x-accounting-attribute-nas-port {
         type int32;
         description "NAS Port AVP(5)";
       }
       leaf dot1x-accounting-attribute-nas-port-id {
         type string;
         description "NAS Port ID AVP(87)";
       }
       leaf dot1x-accounting-attribute-called-station-id {
         type string;
         description "Called Station Id AVP(30)";
       }
       leaf dot1x-accounting-attribute-calling-station-id {
         type string;
         description "Calling Station Id AVP(31)";
       }
       leaf dot1x-accounting-attribute-framed-ip-address {
         type string;
         description "Framed IP Address AVP(8)";
       }
       leaf dot1x-accounting-attribute-framed-ipv6-address {
         type string;
         description "Framed IPV6 Address AVP(168)";
       }
       leaf dot1x-accounting-attribute-filter-id {
         type string;
         description "Filter ID AVP(11)";
       }
       leaf dot1x-accounting-attribute-framed-mtu {
         type int32;
         description "Framed MTU AVP(12)";
       }
       leaf dot1x-accounting-attribute-client-system-name {
         type string;
         description "Client System Name AVP(26)";
       }
       leaf dot1x-accounting-attribute-session-timeout {
         type int32;
         description "Session Timeout AVP(27)";
       }
       leaf dot1x-accounting-attribute-acct-authentic {
         type string;
         description "Acct Authentic Cause(45)";
       }
       leaf dot1x-accounting-attribute-nas-identifier {
         type string;
         description "NAS Identifier(32)";
       }
       leaf dot1x-accounting-attribute-acct-status {
         type string;
         description "Acct Status Type(40)";
       }
       leaf dot1x-accounting-attribute-acct-session {
         type int32;
         description "Acct Session Id(44)";
       }
       leaf dot1x-accounting-attribute-service-type {
         type string;
         description "Service Type(6)";
       }
     }
     container dot1x-authentication-failed-users {
       description "List of users who failed authentication";
       leaf authentication-failed-interface {
         type string;
         description "Interface used in failed authentication";
       }
       leaf authentication-failed-mac-addr {
         type jt:mac-addr;
         description "MAC address used by user who failed authentication";
       }
       leaf authentication-failed-user {
         type string;
         description "Users who failed authentication";
       }
       leaf authentication-failed-count {
         type int32;
         description "Number of failed authentication attempts";
       }
     }
     container dot1x-interface-statistics {
       description "Display interface statistics";
       leaf eapol-interface-name {
         type string;
         description "Interface name";
       }
       leaf eapol-request-id-frames {
         type int32;
         description "Number of EAPOL Request ID packets transmitted";
       }
       leaf eapol-request-frames {
         type int32;
         description "Number of EAPOL Request packets transmitted";
       }
       leaf eapol-total-transmitted-packets {
         type int32;
         description "Total Number of EAPOL packets transmitted";
       }
       leaf eapol-start-frames {
         type int32;
         description "Number of EAPOL START packets received";
       }
       leaf eapol-logoff-frames {
         type int32;
         description "Number of EAPOL LOGOFF packets received";
       }
       leaf eapol-response-id-frames {
         type int32;
         description "Number of EAPOL Response ID packets received";
       }
       leaf eapol-response-frames {
         type int32;
         description "Number of EAPOL Response packets received";
       }
       leaf coa-request-frames {
         type int32;
         description "Number of CoA Request packets received";
       }
       leaf coa-ack-frames {
         type int32;
         description "Number of EAPOL Request packets transmitted";
       }
       leaf coa-nak-frames {
         type int32;
         description "Number of EAPOL Request packets transmitted";
       }
       leaf eapol-invalid-frames {
         type int32;
         description "Number of Invalid EAPOL packets received";
       }
       leaf eapol-length-error-frames {
         type int32;
         description "Number of invalid length EAPOL packets received";
       }
       leaf eapol-total-received-frames {
         type int32;
         description "Total Number of EAPOL packets received";
       }
       leaf eapol-lastframe-version {
         type int32;
         description "Version of the last EAPOL packet received";
       }
       leaf eapol-lastframe-macaddress {
         type string;
         description "Source Mac Address of last frame received";
       }
       leaf coa-port-bounce-request-frames {
         type int32;
         description "Number of Port Bounce Requests received";
       }
       list session-list {
         container session {
           leaf session-macaddress {
             type string;
             description "Source Mac Address for this session";
           }
           leaf session-eapol-request-id-frames {
             type int32;
             description "Number of EAPOL Request ID packets transmitted for this session";
           }
           leaf session-eapol-request-frames {
             type int32;
             description "Number of EAPOL Request packets transmitted for this session";
           }
           leaf session-eapol-total-transmitted-packets {
             type int32;
             description "Total Number of EAPOL packets transmitted for this session";
           }
           leaf session-eapol-start-frames {
             type int32;
             description "Number of EAPOL START packets received for this session";
           }
           leaf session-eapol-response-id-frames {
             type int32;
             description "Number of EAPOL Response ID packets received for this session";
           }
           leaf session-eapol-response-frames {
             type int32;
             description "Number of EAPOL Response packets received for this session";
           }
           leaf session-coa-request-frames {
             type int32;
             description "Number of CoA Request packets received for this session";
           }
           leaf session-coa-ack-frames {
             type int32;
             description "Number of COA-Ack packets transmitted for this session";
           }
           leaf session-coa-nak-frames {
             type int32;
             description "Number of COA-NAK packets transmitted for this session";
           }
           leaf session-eapol-invalid-frames {
             type int32;
             description "Number of Invalid EAPOL packets received for this session";
           }
           leaf session-eapol-length-error-frames {
             type int32;
             description "Number of invalid length EAPOL packets received for this session";
           }
           leaf session-eapol-total-received-frames {
             type int32;
             description "Total Number of EAPOL packets received for this session";
           }
           leaf session-eapol-lastframe-version {
             type int32;
             description "Version of the last EAPOL packet received for this session";
           }
         }
       }
     }
     container dot1x-staticmac-bypassed-users {
       description "List of users who bypassed authentication";
       list static-mac-info {
         leaf static-mac-bypass {
           type jt:mac-addr;
           description "MAC address of bypassed client";
         }
         leaf static-mac-bypass-interface {
           type string;
           description "Interface on which MAC address is bypassed";
         }
         leaf static-mac-bypass-vlan {
           type string;
           description "VLAN of bypassed client";
         }
       }
     }
     container dot1x-firewall-interface {
       leaf filter-name {
         type string;
         description "Filter name";
       }
       leaf counter-name {
         type string;
         description "Counter name";
       }
       leaf bytes {
         type uint32;
         description "Number of bytes";
       }
       leaf packets {
         type uint32;
         description "Number of Packets";
       }
       leaf policer-name {
         type string;
         description "Policer name";
       }
       leaf packet-count {
         type uint32;
         description "Number of Packets";
       }
     }
   }
   grouping dot1xd-ctxt-history-block {
     list dot1xd-ctxt-history-entry {
       leaf ctxt-current {
         type uint32;
         description "Current context count";
       }
       leaf ctxt-entry {
         type string;
         description "Context-history values as a string";
       }
     }
   }
   grouping dot1xd-sync-pending-sessions-block {
     list dot1xd-sync-pending-session {
       leaf dot1x-sync-pending-interface {
         type string;
         description "Interface which is used for authentication";
       }
       leaf dot1x-sync-pending-interface-snmp-index {
         type int32;
         description "Snmp index for the interface which is used for authentication ";
       }
       leaf dot1x-sync-pending-state {
         type string;
         description "Sync state for the supplicant during restart or issu";
       }
       leaf dot1x-sync-pending-mac {
         type jt:mac-addr;
         description "MAC address of the supplicant";
       }
       leaf dot1x-sync-pending-data-vlan {
         type string;
         description "Data Vlan on which supplicant is authenticated";
       }
       leaf dot1x-sync-pending-voip-vlan {
         type string;
         description "Voip VLAN on which supplicant is authenticated";
       }
       leaf dot1x-sync-pending-mode {
         type string;
         description "Authentication mode used for this user";
       }
       leaf dot1x-sync-pending-user-name {
         type string;
         description "User name as sent by client for authentication";
       }
     }
   }
 }
