/*
 * Copyright (c) 2025 Juniper Networks, Inc.
 * All rights reserved.
 */
 module junos-es-conf-services {
   namespace "http://yang.juniper.net/junos-es/conf/services";

   prefix jc-services;

   import junos-common-types {
     prefix jt;
     revision-date 2025-01-01;
   }

   import junos-es-conf-root {
     prefix jc;
     revision-date 2025-01-01;
   }

   organization "Juniper Networks, Inc.";

   contact "yang-support@juniper.net";

   description "Junos services configuration module";

   revision 2025-01-01 {
     description "Junos: 25.2R1.9";
   }

   augment /jc:configuration {
     uses services-group;
   }
   augment /jc:configuration/jc:groups {
     uses services-group;
   }
   grouping services-group {
     container services {
       description "System services";
       uses apply-advanced;
       container jinsightd {
         presence "enable jinsightd";
         description "Health Monitoring services";
         uses apply-advanced;
         container traceoptions {
           description "Jinsight trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             description "Tracing parameters";
             leaf name {
               type enumeration {
                 enum "all" {
                   description "Trace all events";
                 }
                 enum "rule-engine" {
                   description "Log configuration rule engine";
                 }
                 enum "core" {
                   description "Trace core message events";
                 }
                 enum "database" {
                   description "Trace database events";
                 }
                 enum "timer" {
                   description "Trace timer events";
                 }
               }
             }
           }
         }
         container subscribe {
           presence "enable subscribe";
           description "Subscription";
           uses apply-advanced;
           leaf health-monitor {
             description "Health-monitor parameters";
             type empty;
           }
         }
       }
       container flow-tap {
         description "Configure flow-tap parameters";
         uses apply-advanced;
         container family {
           description "Address family of packets to tap";
           uses apply-advanced;
           leaf inet {
             description "IPv4 family";
             type empty;
           }
           leaf inet6 {
             description "IPv4 family";
             type empty;
           }
           leaf ccc {
             description "CCC family";
             type empty;
           }
         }
         leaf interface {
           description "Service interface on which to configure flow-tap service";
           type union {
             type jt:interface-name;
             type string {
               pattern "<.*>|$.*";
             }
           }
         }
         leaf tunnel-interface {
           description "Tunnel interface through which flow-tap would communicate with MD";
           type union {
             type jt:interface-name;
             type string {
               pattern "<.*>|$.*";
             }
           }
         }
       }
       container radius-flow-tap {
         description "Configure radius triggered flow-tap parameters";
         uses apply-advanced;
         leaf forwarding-class {
           description "Forwarding class assigned to intercepted packets";
           type string {
           }
         }
         leaf source-ipv4-address {
           description "IP Address to use as source address in IPv4 header appended to intercepted packets";
           type jt:ipv4addr;
         }
         leaf multicast-interception {
           description "Enable Multicast Tapping";
           type empty;
         }
         container interfaces {
           description "Tunnel Interfaces";
           uses apply-advanced;
           list tunnel-interface {
             key name;
             uses tunnel_interface_type;
           }
         }
         choice ri_or_ls {
           case case_1 {
             leaf routing-instance {
               description "Routing instance to be used for radius flow tap";
               type string;
             }
           }
           case case_2 {
             list logical-system {
               key name;
               ordered-by user;
               description "Logical system to be used for radius flow tap";
               max-elements 1;
               leaf name {
                 description "Logical system name";
                 type string;
               }
               uses apply-advanced;
               leaf routing-instance {
                 description "Routing instance to be used for radius flow tap";
                 type string;
               }
             }
           }
         }
         list policy {
           key name;
           ordered-by user;
           description "Policy";
           leaf name {
             description "Policy Name";
             type string {
             }
           }
           uses apply-advanced;
           container inet {
             description "Protocol family IPv4 drop policy terms";
             uses apply-advanced;
             list drop-policy {
               key name;
               ordered-by user;
               description "Define an IPv4 drop policy";
               uses drop-policy-term;
             }
           }
           container inet6 {
             description "Protocol family IPv6 drop policy terms";
             uses apply-advanced;
             list drop-policy {
               key name;
               ordered-by user;
               description "Define an IPv6 drop policy";
               uses drop-policy6-term;
             }
           }
         }
         container snmp {
           description "SNMP options for radius flow tap";
           uses apply-advanced;
           list notify-targets {
             key name;
             ordered-by user;
             description "Target list for packet mirror SNMP notifications";
             leaf name {
               description "Target IP address";
               type jt:ipaddr;
             }
             uses apply-advanced;
           }
         }
       }
       container mobile-flow-tap {
         description "Configure mobile triggered flow-tap parameters";
         uses apply-advanced;
         container source-interface {
           presence "enable source-interface";
           description "Source interface from which IRI packets will be sent";
           leaf interface-name {
             description "Interface name";
             type union {
               type jt:interface-name;
               type string {
                 pattern "<.*>|$.*";
               }
             }
           }
           leaf ipv4-address {
             description "Source IPv4 address to be used";
             type jt:ipv4addr;
           }
         }
       }
       container flow-monitoring {
         presence "enable flow-monitoring";
         description "Configure flow monitoring";
         uses apply-advanced;
         container version9 {
           description "Version 9 configuration";
           uses apply-advanced;
           list template {
             key name;
             ordered-by user;
             description "One or more version 9 templates";
             max-elements 10;
             uses version9-template;
           }
         }
         container version-ipfix {
           description "Version IP-Fix configuration";
           uses apply-advanced;
           list template {
             key name;
             ordered-by user;
             description "One or more version ip-fix templates";
             max-elements 10;
             uses version-ipfix-template;
           }
         }
       }
       container jdaf {
         description "Juniper distributed application framework (JDAF)";
         uses apply-advanced;
         leaf-list routing-instances {
           ordered-by user;
           description "List of routing-instance name for JDAF clients";
           type string {
             length "1 .. 128";
           }
         }
       }
       container app-engine {
         description "App-engine";
         uses apply-advanced;
         container security {
           presence "enable security";
           description "Enable app-engine security";
         }
         container monitor-cpu {
           description "Monitor node CPU usage";
           uses monitor-threshold;
         }
         container monitor-memory {
           description "Monitor node memory usage";
           uses monitor-threshold;
         }
         container monitor-storage {
           description "Monitor storage usage";
           uses monitor-threshold;
         }
         leaf default-compute-node-package {
           description "Default JunosV App Engine package for appliance";
           type string;
         }
         list compute-cluster {
           key name;
           ordered-by user;
           description "Configure compute cluster";
           leaf name {
             description "Compute cluster name";
             type string {
               length "1 .. 15";
             }
           }
           uses apply-advanced;
           container local-management {
             description "Management address connected to compute cluster";
             uses apply-advanced;
             list routing-instance {
               key routing-instance-name;
               ordered-by user;
               description "Packets are restriction to specified routing instance";
               max-elements 1;
               leaf routing-instance-name {
                 description "Name of routing instance";
                 type string {
                 }
               }
               uses apply-advanced;
               container family {
                 description "Protocol family";
                 container inet {
                   description "IPv4 parameters";
                   uses apply-advanced;
                   leaf address {
                     description "Interface address";
                     type jt:ipv4addr;
                   }
                 }
               }
             }
             container family {
               description "Protocol family";
               container inet {
                 description "IPv4 parameters";
                 uses apply-advanced;
                 leaf address {
                   description "Interface address";
                   type jt:ipv4addr;
                 }
               }
             }
           }
           container monitor-cpu {
             description "Monitor node CPU usage";
             uses monitor-threshold;
           }
           container monitor-memory {
             description "Monitor node memory usage";
             uses monitor-threshold;
           }
           container monitor-storage {
             description "Monitor storage usage";
             uses monitor-threshold;
           }
           list compute-node {
             key name;
             ordered-by user;
             description "Compute node name";
             max-elements 1;
             leaf name {
               description "Compute node name";
               type string {
                 length "1 .. 15";
               }
             }
             uses apply-advanced;
             container monitor-cpu {
               description "Monitor node CPU usage";
               uses monitor-threshold;
             }
             container monitor-memory {
               description "Monitor node memory usage";
               uses monitor-threshold;
             }
             container monitor-storage {
               description "Monitor storage usage";
               uses monitor-threshold;
             }
             choice compute-node-identifier {
               case case_1 {
                 leaf mac-address {
                   description "MAC address of the network boot interface";
                   type jt:mac-addr;
                 }
               }
               case case_2 {
               }
               case case_3 {
               }
             }
             leaf package {
               description "JunosV App Engine package";
               type string;
             }
             container routing-options {
               description "Route configuration for compute node";
               uses apply-advanced;
               container static {
                 description "Static routes";
                 uses apply-advanced;
                 list route {
                   key name;
                   ordered-by user;
                   description "Static route";
                   leaf name {
                     description "Destination IP address or prefix";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                   }
                 }
                 uses apply-advanced;
                 container static {
                   description "Static routes";
                   uses apply-advanced;
                   list route {
                     key name;
                     ordered-by user;
                     description "Static route";
                     leaf name {
                       description "Destination IP address or prefix";
                       type jt:ipv4prefix;
                     }
                     uses apply-advanced;
                     leaf next-hop {
                       description "Next hop to destination";
                       type jt:ipv4addr;
                     }
                   }
                 }
               }
             }
             container interfaces {
               description "Network interfaces configuration";
               uses apply-advanced;
               list ethernet {
                 key name;
                 ordered-by user;
                 description "Interface configuration";
                 leaf name {
                   description "Interface name";
                   type string {
                     length "1 .. 15";
                   }
                 }
                 uses apply-advanced;
                 leaf management {
                   description "Use this as management interface";
                   type empty;
                 }
                 container family {
                   description "Protocol family";
                   uses family;
                 }
                 leaf enable-passthrough {
                   description "Enable passthrough on this interface";
                   type empty;
                 }
                 leaf mtu {
                   description "Maximum transmit packet size";
                   type union {
                     type string {
                       pattern "<.*>|$.*";
                     }
                     type uint16 {
                       range "256 .. 9192";
                     }
                   }
                 }
                 container ether-options {
                   uses apply-advanced;
                   choice agg-intf {
                     case case_1 {
                       leaf ieee-802-3ad {
                         description "Aggregated interface name";
                         type string {
                           length "1 .. 15";
                         }
                       }
                     }
                   }
                 }
               }
               list bridge {
                 key name;
                 ordered-by user;
                 description "Bridge configuration";
                 leaf name {
                   description "Bridge name";
                   type string {
                     length "1 .. 15";
                   }
                 }
                 uses apply-advanced;
                 leaf management {
                   description "Use this as management bridge";
                   type empty;
                 }
                 container family {
                   description "Protocol family";
                   uses family;
                 }
                 leaf-list interface {
                   ordered-by user;
                   description "Bridge interface list";
                   type string {
                     length "1 .. 15";
                   }
                   max-elements 4;
                 }
                 leaf mtu {
                   description "Maximum transmit packet size";
                   type union {
                     type string {
                       pattern "<.*>|$.*";
                     }
                     type uint16 {
                       range "256 .. 9192";
                     }
                   }
                 }
               }
               list aggregate {
                 key name;
                 ordered-by user;
                 description "Aggregate interface configuration";
                 leaf name {
                   description "Aggregated interface name";
                   type string {
                     length "1 .. 15";
                   }
                 }
                 uses apply-advanced;
                 leaf management {
                   description "Use this as management aggregate";
                   type empty;
                 }
                 container family {
                   description "Protocol family";
                   uses family;
                 }
                 leaf mtu {
                   description "Maximum transmit packet size";
                   type union {
                     type string {
                       pattern "<.*>|$.*";
                     }
                     type uint16 {
                       range "256 .. 9192";
                     }
                   }
                 }
                 container aggregated-ether-options {
                   presence "enable aggregated-ether-options";
                   description "Link aggregation parameters";
                   uses apply-advanced;
                   leaf hash-policy {
                     default "layer-3-and-4";
                     type enumeration {
                       enum "layer-2" {
                         description "Uses mac address of both source and destination for hashing";
                       }
                       enum "layer-3-and-4" {
                         description "Uses port number and IP address of both source and destination for hashing";
                       }
                       enum "layer-2-and-3" {
                         description "Uses mac and IP address of both source and destination for hashing";
                       }
                     }
                   }
                   leaf miimon {
                     description "Link monitoring interval in milli-second";
                     type union {
                       type uint32;
                       type string {
                         pattern "<.*>|$.*";
                       }
                     }
                   }
                 }
               }
             }
             list syslog {
               key name;
               ordered-by user;
               description "System logging facility";
               leaf name {
                 description "Facility type";
                 type enumeration {
                   enum "any" {
                     description "All facilities";
                   }
                   enum "authorization" {
                     description "Authorization system";
                   }
                   enum "privileged" {
                     description "Privileged authorization events";
                   }
                   enum "cron" {
                     description "Cron daemon";
                   }
                   enum "daemon" {
                     description "Various system processes";
                   }
                   enum "kernel" {
                     description "Kernel";
                   }
                   enum "syslog" {
                     description "Syslog messages";
                   }
                   enum "user" {
                     description "User processes";
                   }
                   enum "uucp" {
                     description "UUCP system";
                   }
                   enum "local0" {
                     description "Local 0 messages";
                   }
                   enum "local1" {
                     description "Local 1 messages";
                   }
                   enum "local2" {
                     description "Local 2 messages";
                   }
                   enum "local3" {
                     description "Local 3 messages";
                   }
                   enum "local4" {
                     description "Local 4 messages";
                   }
                   enum "local5" {
                     description "Local 5 messages";
                   }
                   enum "local6" {
                     description "Local 6 messages";
                   }
                   enum "local7" {
                     description "Local 7 messages";
                   }
                 }
               }
               choice level {
                 case case_1 {
                   leaf any {
                     description "All levels";
                     type empty;
                   }
                 }
                 case case_2 {
                   leaf emergency {
                     description "Panic conditions";
                     type empty;
                   }
                 }
                 case case_3 {
                   leaf alert {
                     description "Conditions that should be corrected immediately";
                     type empty;
                   }
                 }
                 case case_4 {
                   leaf critical {
                     description "Critical conditions";
                     type empty;
                   }
                 }
                 case case_5 {
                   leaf error {
                     description "Error conditions";
                     type empty;
                   }
                 }
                 case case_6 {
                   leaf warning {
                     description "Warning messages";
                     type empty;
                   }
                 }
                 case case_7 {
                   leaf notice {
                     description "Conditions that should be handled specially";
                     type empty;
                   }
                 }
                 case case_8 {
                   leaf info {
                     description "Informational messages";
                     type empty;
                   }
                 }
                 case case_9 {
                   leaf debug {
                     description "Debug messages";
                     type empty;
                   }
                 }
               }
             }
           }
         }
         container virtual-machines {
           description "Virtual-machine management";
           uses apply-advanced;
           list instance {
             key name;
             ordered-by user;
             description "Virtual-machine instance";
             leaf name {
               description "Virtual-machine instance identifier";
               type string {
                 length "1 .. 39";
               }
             }
             uses apply-advanced;
             leaf cpu {
               description "Units of CPUs (default 1 cpu)";
               default "1";
               type union {
                 type string {
                   pattern "<.*>|$.*";
                 }
                 type uint32 {
                   range "1 .. 16";
                 }
               }
             }
             leaf memory {
               description "Memory for the virtual-machine (default 1 gigabytes)";
               default "1";
               units "gigabytes";
               type union {
                 type string {
                   pattern "<.*>|$.*";
                 }
                 type uint32 {
                   range "1 .. 32";
                 }
               }
             }
             leaf package {
               description "Virtual-machine package";
               type string {
                 length "1 .. 120";
               }
             }
             container local-management {
               description "Management address connected to virtual machine";
               uses apply-advanced;
               list routing-instance {
                 key routing-instance-name;
                 ordered-by user;
                 description "Packets are restriction to specified routing instance";
                 max-elements 1;
                 leaf routing-instance-name {
                   description "Name of routing instance";
                   type string {
                   }
                 }
                 uses apply-advanced;
                 container family {
                   description "Protocol family";
                   container inet {
                     description "IPv4 parameters";
                     uses apply-advanced;
                     leaf address {
                       description "Interface address";
                       type jt:ipv4addr;
                     }
                   }
                 }
               }
               container family {
                 description "Protocol family";
                 container inet {
                   description "IPv4 parameters";
                   uses apply-advanced;
                   leaf address {
                     description "Interface address";
                     type jt:ipv4addr;
                   }
                 }
               }
             }
             list compute-cluster {
               key name;
               ordered-by user;
               description "Compute cluster on which the virtual-machine runs";
               max-elements 1;
               leaf name {
                 description "Compute cluster name";
                 type string {
                   length "1 .. 15";
                 }
               }
               uses apply-advanced;
               leaf compute-node {
                 description "Compute node on which the virtual-machine runs";
                 type string {
                   length "1 .. 15";
                 }
               }
             }
             list interface {
               key name;
               ordered-by user;
               description "Virtual-machine interface configuration";
               leaf name {
                 description "Virtual-machine interface name";
                 type string {
                   length "1 .. 31";
                 }
               }
               uses apply-advanced;
               leaf hw-model {
                 description "Interface hardware model";
                 default "e1000g";
                 type enumeration {
                   enum "e1000g" {
                     description "Gigabit Ethernet e1000g driver";
                   }
                   enum "virtio" {
                     description "Para-virtualizing the interface";
                   }
                 }
               }
               leaf host-interface {
                 description "Passthrough host interface for virtual-machine";
                 type string {
                   length "1 .. 15";
                 }
               }
               leaf bridge {
                 description "Bridge that the interface connected to";
                 type string {
                   length "1 .. 15";
                 }
               }
               leaf mtu {
                 description "Maximum transmit packet size";
                 type union {
                   type string {
                     pattern "<.*>|$.*";
                   }
                   type uint16 {
                     range "256 .. 9192";
                   }
                 }
               }
               container family {
                 description "Interface address family";
                 container inet {
                   presence "enable inet";
                   description "IPv4 parameters";
                   uses apply-advanced;
                   list address {
                     key name;
                     ordered-by user;
                     description "Interface address/destination prefix";
                     leaf name {
                       description "Interface address/destination prefix";
                       type jt:ipv4prefix;
                     }
                     uses apply-advanced;
                     leaf primary {
                       description "Primary address on the interface";
                       type empty;
                     }
                   }
                 }
               }
             }
             container routing-options {
               description "Route configuration for virutal machine";
               uses apply-advanced;
               container static {
                 description "Static routes";
                 uses apply-advanced;
                 list route {
                   key name;
                   ordered-by user;
                   description "Static route";
                   leaf name {
                     description "Destination IP address or prefix";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                   }
                 }
                 uses apply-advanced;
                 container static {
                   description "Static routes";
                   uses apply-advanced;
                   list route {
                     key name;
                     ordered-by user;
                     description "Static route";
                     leaf name {
                       description "Destination IP address or prefix";
                       type jt:ipv4prefix;
                     }
                     uses apply-advanced;
                     leaf next-hop {
                       description "Next hop to destination";
                       type jt:ipv4addr;
                     }
                   }
                 }
               }
             }
             list secondary-disk {
               key name;
               ordered-by user;
               description "Virtual-machine disk";
               leaf name {
                 description "Virtual-machine disk name";
                 type enumeration {
                   enum "hdb" {
                     description "Disk name is hdb";
                   }
                   enum "hdc" {
                     description "Disk name is hdc";
                   }
                   enum "hdd" {
                     description "Disk name is hdd";
                   }
                 }
               }
               leaf size {
                 description "Virtual-machine secondary disk size";
                 units "gigabytes";
                 type union {
                   type string {
                     pattern "<.*>|$.*";
                   }
                   type uint32 {
                     range "1 .. 160";
                   }
                 }
               }
             }
           }
         }
       }
       container unified-access-control {
         description "Configure Unified Access Control";
         uses apply-advanced;
         list infranet-controller {
           key name;
           ordered-by user;
           description "Configure infranet controller";
           leaf name {
             description "Infranet controller name";
             type string {
               length "1 .. 31";
             }
           }
           uses apply-advanced;
           leaf address {
             description "Infranet controller IP address";
             type jt:ipv4addr;
           }
           leaf port {
             description "Infranet controller port";
             default "11123";
             type union {
               type string {
                 pattern "<.*>|$.*";
               }
               type uint32 {
                 range "1 .. 65535";
               }
             }
           }
           leaf interface {
             description "Outgoing interface";
             type union {
               type jt:interface-name;
               type string {
                 pattern "<.*>|$.*";
               }
             }
           }
           leaf password {
             description "Infranet controller server password";
             type string {
               length "1 .. 255";
             }
           }
           leaf-list ca-profile {
             ordered-by user;
             description "Define a list of certificate authority";
             type string;
           }
           leaf server-certificate-subject {
             description "Subject name of infranet controller certificate to match";
             type string {
               length "1 .. 255";
             }
           }
         }
         leaf certificate-verification {
           description "Specify certificate verification requirement";
           default "warning";
           type enumeration {
             enum "warning" {
               description "Warn if certificate is not being verified";
             }
             enum "required" {
               description "Require certificate verification. Most secure";
             }
             enum "optional" {
               description "Make verification optional, no warnings. Least secure";
             }
           }
         }
         leaf timeout {
           description "Timeout for idle infranet controller link in seconds";
           default "300";
           type union {
             type string {
               pattern "<.*>|$.*";
             }
             type uint32 {
               range "2 .. 10000";
             }
           }
         }
         leaf interval {
           description "Heartbeat interval from infranet controller in seconds";
           default "30";
           type union {
             type string {
               pattern "<.*>|$.*";
             }
             type uint32 {
               range "1 .. 9999";
             }
           }
         }
         leaf timeout-action {
           description "Specify action when infranet controller timeout occurs";
           default "close";
           type enumeration {
             enum "close" {
               description "Remove existing sessions and block further traffic";
             }
             enum "no-change" {
               description "Preserve existing connections; block new sessions";
             }
             enum "open" {
               description "Allow traffic for new and existing sessions to go through";
             }
           }
         }
         leaf test-only-mode {
           description "Allow all traffic and only log enforcement result";
           type empty;
         }
         leaf event-entry-lifetime {
           description "Interval between successive NO-AUTH msgs for same src ip in seconds";
           default "60";
           type union {
             type string {
               pattern "<.*>|$.*";
             }
             type uint32 {
               range "1 .. 60";
             }
           }
         }
         container traceoptions {
           description "UAC trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "all" {
                   description "Trace with all flags enabled";
                 }
                 enum "ipc" {
                   description "IPC tracing";
                 }
                 enum "config" {
                   description "Configuration tracing";
                 }
                 enum "connect" {
                   description "Communication with infranet controller tracing";
                 }
               }
             }
           }
         }
         list captive-portal {
           key name;
           ordered-by user;
           description "Unauthenticated HTTP redirect";
           leaf name {
             description "Redirect policy name";
             type string {
               length "1 .. 128";
             }
           }
           uses apply-advanced;
           leaf redirect-traffic {
             description "Traffic to redirect";
             type enumeration {
               enum "unauthenticated" {
                 description "Redirect unauthenticated traffic";
               }
               enum "all" {
                 description "Redirect all traffic";
               }
             }
           }
           leaf redirect-url {
             description "Redirect URL for unauthenticated users";
             type string {
               length "1 .. 512";
             }
           }
         }
       }
       container inband-flow-telemetry {
         presence "enable inband-flow-telemetry";
         description "Inband telemetry services";
         uses apply-advanced;
         container traceoptions {
           presence "enable traceoptions";
           description "Inband telemetry trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         container device-id {
           description "Inband telemetry global unique identifier";
           uses apply-advanced;
           choice device_id_choice {
             case case_1 {
               leaf auto {
                 description "Device router-id will be considered";
                 type empty;
               }
             }
             case case_2 {
               leaf id {
                 description "Specify unique device identifier";
                 type union {
                   type string {
                     pattern "<.*>|$.*";
                   }
                   type uint32 {
                     range "1 .. 1048575";
                   }
                 }
               }
             }
           }
         }
         leaf meta-data-stack-length {
           description "Maximum length for meta data";
           default "240";
           type union {
             type string {
               pattern "<.*>|$.*";
             }
             type uint32 {
               range "8 .. 255";
             }
           }
         }
         leaf hop-limit {
           description "Maximum hop limits allowed";
           default "250";
           type union {
             type string {
               pattern "<.*>|$.*";
             }
             type uint32 {
               range "1 .. 250";
             }
           }
         }
         leaf mode {
           description "Configure IFA initiator mode type";
           type enumeration {
             enum "live" {
               description "IFA Metadata insertion in the live or inband packet";
             }
             enum "probe" {
               description "IFA Metadata insertion in the probe or clone packet";
             }
           }
         }
         leaf flow-type {
           description "Configure IFA traffic type";
           type enumeration {
             enum "l3" {
               description "L3 traffic type";
             }
             enum "vxlan" {
               description "Vxlan traffic type";
             }
           }
         }
         leaf no-ipv6-address-match {
           description "Configure if no ipv6 address match is used";
           type empty;
         }
         leaf clock-source {
           description "Configure clock source for timestamping";
           type enumeration {
             enum "ntp" {
               description "Use Network Time Protocol";
             }
             enum "ptp" {
               description "Use Precision Time Protocol";
             }
           }
         }
         list profile {
           key name;
           description "Profile options";
           max-elements 32;
           uses inband-telemetry-profile-type;
         }
       }
       container pfe {
         presence "enable pfe";
         uses apply-advanced;
         container traffic {
           presence "enable traffic";
           description "PFE traffic monitor services";
           uses apply-advanced;
           container traceoptions {
             presence "enable traceoptions";
             description "PFE Monitor trace options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
           }
           container monitor-timer {
             presence "enable monitor-timer";
             description "PFE monitor timer to uninstall the filter";
             uses apply-advanced;
             leaf time {
               description "Default is 5 mins, max configurable time is 60 mins";
               default "300";
               units "seconds";
               type union {
                 type string {
                   pattern "<.*>|$.*";
                 }
                 type uint32 {
                   range "300 .. 3600";
                 }
               }
             }
           }
         }
       }
       container captive-portal {
         description "Captive Portal options";
         uses juniper-services-captive-portal;
       }
       container advanced-anti-malware {
         uses apply-advanced;
         container dynamic-filter {
           description "Dynamic Filtering configuration";
           uses apply-advanced;
           container traceoptions {
             description "Dynamic Filtering traceoptions";
             uses dyn-filterd-traceoptions;
           }
         }
         container connection {
           presence "enable connection";
           description "Cloud service RE connection, only for master logical domain";
           uses apply-advanced;
           leaf url {
             description "The url of the cloud server [https://<ip or hostname>:<port>]";
             type string;
           }
           container authentication {
             description "The authentication profile for using cloud services";
             uses apply-advanced;
             leaf tls-profile {
               description "TLS profile";
               type string;
             }
           }
           leaf proxy-profile {
             description "Proxy profile";
             type string {
               length "1 .. 63";
             }
           }
           leaf source-address {
             description "The source ip for connecting to the cloud server.";
             type jt:ipaddr;
           }
           leaf source-interface {
             description "The source interface for connecting to the cloud server";
             type union {
               type jt:interface-name;
               type string {
                 pattern "<.*>|$.*";
               }
             }
           }
         }
         container default-policy {
           presence "enable default-policy";
           description "Advanced Anti-malware default policy";
           uses apply-advanced;
           container http {
             description "Configure HTTP options";
             uses apply-advanced;
             leaf inspection-profile {
               description "Advanced Anti-malware inspection-profile name (default:default_profile)";
               type string {
                 length "1 .. 63";
               }
             }
             leaf file-verdict-unknown {
               description "Action taken for contents with verdict unknown";
               type enumeration {
                 enum "permit" {
                   description "Allow contents";
                 }
                 enum "block" {
                   description "Disallow contents";
                 }
               }
             }
             leaf action {
               description "Action taken for contents with verdict meet threshold";
               type enumeration {
                 enum "permit" {
                   description "Allow contents";
                 }
                 enum "block" {
                   description "Disallow contents";
                 }
               }
             }
             container client-notify {
               description "Notification action taken for contents with verdict meet threshold";
               uses apply-advanced;
               choice http-choice {
                 case case_1 {
                   leaf file {
                     description "File name for http response to client";
                     type string {
                       length "1 .. 255";
                     }
                   }
                 }
                 case case_2 {
                   leaf message {
                     description "Block message to client";
                     type string {
                       length "1 .. 1023";
                     }
                   }
                 }
                 case case_3 {
                   leaf redirect-url {
                     description "Redirect url to client";
                     type string {
                       length "1 .. 1023";
                     }
                   }
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container smb {
             description "Configure SMB options";
             uses apply-advanced;
             leaf inspection-profile {
               description "Advanced Anti-malware inspection-profile name (default:default_profile)";
               type string {
                 length "1 .. 63";
               }
             }
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
             container service-not-ready {
               description "Service not ready yet";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container invalid-content-size {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container out-of-resources {
               description "Service out of resources";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container verdict-timeout {
               description "Verdict timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container submission-timeout {
               description "Submission timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container unknown-file {
               description "File type unknown";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         list policy {
           key name;
           description "Advanced Anti-malware policy";
           leaf name {
             description "Policy name, default policy must name (default-policy)";
             type string {
               length "1 .. 63";
             }
           }
           uses apply-advanced;
           container match {
             description "Policy match conditions";
             status deprecated;
             uses apply-advanced;
             leaf application {
               description "Application";
               type enumeration {
                 enum "HTTP" {
                   description "HTTP Traffic";
                 }
               }
             }
             leaf verdict-threshold {
               description "Verdict threshold";
               type enumeration {
                 enum "1" {
                   description "Verdict-threshold level 1";
                 }
                 enum "2" {
                   description "Verdict-threshold level 2";
                 }
                 enum "3" {
                   description "Verdict-threshold level 3";
                 }
                 enum "4" {
                   description "Verdict-threshold level 4";
                 }
                 enum "5" {
                   description "Verdict-threshold level 5";
                 }
                 enum "6" {
                   description "Verdict-threshold level 6";
                 }
                 enum "7" {
                   description "Verdict-threshold level 7";
                 }
                 enum "8" {
                   description "Verdict-threshold level 8";
                 }
                 enum "9" {
                   description "Verdict-threshold level 9";
                 }
                 enum "10" {
                   description "Verdict-threshold level 10";
                 }
                 enum "recommended" {
                   description "Recommended verdict-threshold";
                 }
               }
             }
           }
           container then {
             status deprecated;
             uses apply-advanced;
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container http {
             description "Configure HTTP options";
             uses apply-advanced;
             leaf inspection-profile {
               description "Advanced Anti-malware inspection-profile name (default:default_profile)";
               type string {
                 length "1 .. 63";
               }
             }
             leaf file-verdict-unknown {
               description "Action taken for contents with verdict unknown";
               type enumeration {
                 enum "permit" {
                   description "Allow contents";
                 }
                 enum "block" {
                   description "Disallow contents";
                 }
               }
             }
             leaf action {
               description "Action taken for contents with verdict meet threshold";
               type enumeration {
                 enum "permit" {
                   description "Allow contents";
                 }
                 enum "block" {
                   description "Disallow contents";
                 }
               }
             }
             container client-notify {
               description "Notification action taken for contents with verdict meet threshold";
               uses apply-advanced;
               choice http-choice {
                 case case_1 {
                   leaf file {
                     description "File name for http response to client";
                     type string {
                       length "1 .. 255";
                     }
                   }
                 }
                 case case_2 {
                   leaf message {
                     description "Block message to client";
                     type string {
                       length "1 .. 1023";
                     }
                   }
                 }
                 case case_3 {
                   leaf redirect-url {
                     description "Redirect url to client";
                     type string {
                       length "1 .. 1023";
                     }
                   }
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container smb {
             description "Configure SMB options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
             leaf action {
               description "Action taken for contents with verdict meet threshold";
               type enumeration {
                 enum "permit" {
                   description "Allow contents";
                 }
                 enum "block" {
                   description "Disallow contents";
                 }
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
             container service-not-ready {
               description "Service not ready yet";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container invalid-content-size {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container out-of-resources {
               description "Service out of resources";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container verdict-timeout {
               description "Verdict timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container submission-timeout {
               description "Submission timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container unknown-file {
               description "File type unknown";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         container traceoptions {
           description "Advanced Anti-malware trace options";
           uses aamwd-traceoptions;
         }
       }
       container application-identification {
         presence "enable application-identification";
         description "Application identification configuration";
         uses apply-advanced;
         leaf enable-heuristics {
           description "Enable heuristic application identification";
           status deprecated;
           type empty;
         }
         container enable-performance-mode {
           presence "enable enable-performance-mode";
           description "Enable performance mode knobs for best DPI performance";
           status deprecated;
           uses apply-advanced;
           leaf max-packet-threshold {
             description "Max packet inspection threshold including both c2s ans s2c direction packets. Default value is 2 if not configured";
             status deprecated;
             default "2";
             type union {
               type string {
                 pattern "<.*>|$.*";
               }
               type uint32 {
                 range "1 .. 100";
               }
             }
           }
         }
         leaf imap-cache-timeout {
           description "IMAP cache entry timeout in seconds";
           type union {
             type string {
               pattern "<.*>|$.*";
             }
             type uint32 {
               range "1 .. 86400";
             }
           }
         }
         leaf imap-cache-size {
           description "IMAP cache size, it will be effective only after next appid sigpack install";
           type union {
             type string {
               pattern "<.*>|$.*";
             }
             type uint32 {
               range "60 .. 512000";
             }
           }
         }
         container download {
           uses apply-advanced;
           leaf url {
             description "URL for application package download";
             type string {
             }
           }
           leaf ignore-server-validation {
             description "Disable server authentication for Applicaton Signature download";
             type empty;
           }
           container automatic {
             description "Scheduled download and update";
             uses apply-advanced;
             leaf start-time {
               description "Start time(MM-DD.hh:mm / YYYY-MM-DD.hh:mm:ss)";
               type string {
               }
             }
             leaf interval {
               description "Attempt to download new application package";
               default "24";
               units "hours";
               type union {
                 type string {
                   pattern "<.*>|$.*";
                 }
                 type uint32 {
                   range "6 .. 720";
                 }
               }
             }
             leaf minor-only {
               description "Download only the minor application package";
               type empty;
             }
           }
           leaf proxy-profile {
             description "Configure web proxy for Application signature download";
             type string {
               length "1 .. 128";
             }
           }
         }
         container statistics {
           description "Configure application statistics information";
           leaf interval {
             description "Application statistics collection interval";
             default "1";
             units "minutes";
             type union {
               type string {
                 pattern "<.*>|$.*";
               }
               type uint32 {
                 range "1 .. 1440";
               }
             }
           }
         }
         container nested-application-settings {
           presence "enable nested-application-settings";
           description "Nested application settings";
           status deprecated;
           uses apply-advanced;
           leaf no-nested-application {
             description "Disable nested application identification";
             type empty;
           }
           leaf no-application-system-cache {
             description "Not to save nested AI match in application system cache";
             type empty;
           }
         }
         leaf no-application-identification {
           description "Disable all application identification methods";
           status deprecated;
           type empty;
         }
         leaf no-application-system-cache {
           description "Disable storing AI result in application system cache";
           type empty;
         }
         leaf no-application-statistics {
           description "Disable application statistics";
           type empty;
         }
         leaf max-sessions {
           description "Max sessions that can run AI at the same time";
           status deprecated;
           type union {
             type string {
               pattern "<.*>|$.*";
             }
             type uint32 {
               range "0 .. 500000";
             }
           }
         }
         leaf application-system-cache-timeout {
           description "Application system cache entry lifetime";
           type union {
             type string {
               pattern "<.*>|$.*";
             }
             type uint32 {
               range "0 .. 1000000";
             }
           }
         }
         container application-system-cache {
           presence "enable application-system-cache";
           description "Enable or Disable application system cache";
           uses apply-advanced;
           leaf security-services {
             description "Enable ASC for security services (appfw, appqos, idp, skyatp..)";
             type empty;
           }
           leaf no-miscellaneous-services {
             description "Disable ASC for miscellaneous services APBR,...";
             type empty;
           }
         }
         leaf micro-apps {
           description "Enable Micro Apps identifcation";
           type empty;
         }
         leaf max-transactions {
           description "Number of transaction finals to terminate application classification";
           type union {
             type string {
               pattern "<.*>|$.*";
             }
             type uint16 {
               range "0 .. 25";
             }
           }
         }
         leaf micro-app-max-transactions {
           description "Number of micro-app transaction finals to terminate application classification";
           type union {
             type string {
               pattern "<.*>|$.*";
             }
             type uint16 {
               range "1 .. 25";
             }
           }
         }
         leaf custom-application-byte-limit {
           description "Max bytes to be scanned for identification of custom application";
           type union {
             type string {
               pattern "<.*>|$.*";
             }
             type uint32 {
               range "1 .. 100000";
             }
           }
         }
         leaf max-memory {
           description "Maximum amount of object cache memory JDPI can use (in MB)";
           type union {
             type string {
               pattern "<.*>|$.*";
             }
             type uint32 {
               range "1 .. 200000";
             }
           }
         }
         leaf max-checked-bytes {
           description "Inspect the maximal number of bytes";
           status deprecated;
           type union {
             type string {
               pattern "<.*>|$.*";
             }
             type uint32 {
               range "0 .. 100000";
             }
           }
         }
         list application {
           key name;
           description "Configure application definition";
           leaf name {
             description "A unique application identifier";
             type string {
               length "1 .. 63";
             }
           }
           uses apply-advanced;
           leaf index {
             description "Custom index (32768..65534). Application index";
             status deprecated;
             type union {
               type string {
                 pattern "<.*>|$.*";
               }
               type uint16 {
                 range "1 .. 65534";
               }
             }
           }
           leaf disable {
             description "Disable this application definition in AI";
             status deprecated;
             type empty;
           }
           leaf cacheable {
             description "Cacheable";
             type empty;
           }
           leaf risk {
             description "Risk/Hotness of application";
             type union {
               type string {
                 pattern "<.*>|$.*";
               }
               type uint32 {
                 range "1 .. 5";
               }
             }
           }
           leaf description {
             description "Text description of application";
             type string {
             }
           }
           leaf priority {
             description "Application matching priority";
             default "low";
             type enumeration {
               enum "high" {
                 description "Highest priority over all other signatures";
               }
               enum "low" {
                 description "Lowest priority over all other signatures";
               }
             }
           }
           leaf order {
             description "The order value, lower the value higher the priority";
             type union {
               type string {
                 pattern "<.*>|$.*";
               }
               type uint16 {
                 range "1 .. 50000";
               }
             }
           }
           leaf maximum-transactions {
             description "Maximum number of transactions matched by AI";
             status deprecated;
             type union {
               type uint16;
               type string {
                 pattern "<.*>|$.*";
               }
             }
           }
           container icmp-mapping {
             description "Match ICMP message";
             uses apply-advanced;
             leaf type {
               description "Numeric type value";
               type union {
                 type string {
                   pattern "<.*>|$.*";
                 }
                 type uint16 {
                   range "0 .. 254";
                 }
               }
             }
             leaf code {
               description "Numeric code value";
               type union {
                 type string {
                   pattern "<.*>|$.*";
                 }
                 type uint16 {
                   range "0 .. 254";
                 }
               }
             }
           }
           container ip-protocol-mapping {
             description "Match IP protocol";
             uses apply-advanced;
             leaf protocol {
               description "Numeric protocol value";
               type union {
                 type string {
                   pattern "<.*>|$.*";
                 }
                 type uint16 {
                   range "0 .. 254";
                 }
               }
             }
           }
           list address-mapping {
             key name;
             ordered-by user;
             description "Match IP address";
             leaf name {
               description "Address name";
               type string {
                 length "1 .. 63";
               }
             }
             uses apply-advanced;
             container filter {
               description "Match IP/port";
               uses apply-advanced;
               leaf ip {
                 description "IP address and prefix-length";
                 type jt:ipprefix;
               }
               container port-range {
                 description "Port ranges";
                 uses apply-advanced;
                 leaf-list tcp {
                   ordered-by user;
                   description "TCP port range";
                   type string;
                   max-elements 20;
                 }
                 leaf-list udp {
                   ordered-by user;
                   description "UDP port range";
                   type string;
                   max-elements 20;
                 }
               }
             }
           }
           list over {
             key name;
             description "Set of L4/L7 application that carries given application";
             max-elements 8;
             leaf name {
               description "A unique application and protocol identifier";
               type string {
                 length "1 .. 63";
               }
             }
             uses apply-advanced;
             list signature {
               key name;
               description "Application signature for pattern matching";
               leaf name {
                 description "A unique application signature identifier";
                 type string {
                   length "1 .. 63";
                 }
               }
               uses apply-advanced;
               leaf-list port-range {
                 ordered-by user;
                 description "Port range";
                 type string;
                 max-elements 64;
               }
               list member {
                 key name;
                 description "Application signature member";
                 leaf name {
                   description "Application signature member identifier in range m01 - m15";
                   type string {
                     length "1 .. 63";
                   }
                 }
                 uses apply-advanced;
                 leaf depth {
                   description "Maximum number of bytes to check for context match";
                   type union {
                     type string {
                       pattern "<.*>|$.*";
                     }
                     type uint32 {
                       range "1 .. 8000";
                     }
                   }
                 }
                 leaf context {
                   description "Context to be matched on";
                   type string;
                 }
                 leaf pattern {
                   description "DFA pattern matched on context";
                   type string {
                   }
                 }
                 leaf direction {
                   description "Connection direction of the packets to apply pattern matching";
                   type enumeration {
                     enum "client-to-server" {
                       description "Client to server";
                     }
                     enum "server-to-client" {
                       description "Server to client";
                     }
                     enum "any" {
                       description "Any direction";
                     }
                   }
                 }
               }
             }
           }
         }
         list nested-application {
           key name;
           description "Configure nested application definition";
           status deprecated;
           leaf name {
             description "A unique application identifier";
             type string {
               length "1 .. 63";
             }
           }
           uses apply-advanced;
           leaf type {
             description "Well-known application such as FACEBOOK and KAZZA";
             type string {
               length "1 .. 63";
             }
           }
           leaf index {
             description "Custom index (32768..65534). Application index";
             status deprecated;
             type union {
               type string {
                 pattern "<.*>|$.*";
               }
               type uint16 {
                 range "1 .. 65534";
               }
             }
           }
           leaf protocol {
             description "Name of layer 7 application that carries nested application";
             type string {
               length "1 .. 63";
             }
           }
           list signature {
             key name;
             description "Nested application signature for pattern matching";
             leaf name {
               description "A unique nested application signature identifier";
               type string {
                 length "1 .. 63";
               }
             }
             uses apply-advanced;
             list member {
               key name;
               description "Pattern matched on client-to-server packets";
               leaf name {
                 description "A unique nested application signature member identifier";
                 type string {
                   length "1 .. 63";
                 }
               }
               uses apply-advanced;
               leaf context {
                 description "Context to be matched on";
                 type string;
               }
               leaf pattern {
                 description "Pattern matched on context";
                 type string;
               }
               leaf direction {
                 description "Connection direction of the packets to apply pattern matching";
                 type enumeration {
                   enum "client-to-server" {
                     description "Client to server";
                   }
                   enum "server-to-client" {
                     description "Server to client";
                   }
                   enum "any" {
                     description "Any direction";
                   }
                 }
               }
               leaf check-bytes {
                 description "Maximum number of bytes to check for stream context ";
                 default "1000";
                 type union {
                   type string {
                     pattern "<.*>|$.*";
                   }
                   type uint32 {
                     range "1 .. 5000";
                   }
                 }
               }
             }
             leaf chain-order {
               description "The order of members is used to match the pattern";
               type empty;
             }
             leaf maximum-transactions {
               description "Maximum number of transactions matched by AI";
               type union {
                 type uint16;
                 type string {
                   pattern "<.*>|$.*";
                 }
               }
             }
             leaf order {
               description "Application matching priority";
               status deprecated;
               type union {
                 type string {
                   pattern "<.*>|$.*";
                 }
                 type uint16 {
                   range "1 .. 65535";
                 }
               }
             }
             container insert-before {
               description "Insert before another signature";
               uses apply-advanced;
               leaf insert-before-name {
                 description "An application name";
                 type string;
               }
             }
           }
         }
         list application-group {
           key name;
           description "Define application group";
           leaf name {
             description "A unique application group identifier";
             type string {
               length "1 .. 63";
             }
           }
           uses apply-advanced;
           list tag-group {
             key name;
             description "Configure application tag group that belong to this application group";
             leaf name {
               description "A unique tag group identifier";
               type string {
                 length "1 .. 63";
               }
             }
             uses apply-advanced;
             leaf-list application-tags {
               ordered-by user;
               description "Name of application tag to configure";
               type string;
               max-elements 128;
             }
           }
           list application-groups {
             key name;
             description "Configure child application group(s)";
             leaf name {
               description "Name of the child application group";
               type string {
                 length "1 .. 63";
               }
             }
             uses apply-advanced;
           }
           list applications {
             key name;
             description "Configure applications that belong to this application group";
             leaf name {
               description "Configure application name";
               type string {
                 length "1 .. 63";
               }
             }
             uses apply-advanced;
           }
           leaf disable {
             description "Disable this application group definition in AI";
             status deprecated;
             type empty;
           }
         }
         container traceoptions {
           description "Trace options for application identification";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Events and other information to include in trace output";
             leaf name {
               description "Flag name to include in trace output";
               type enumeration {
                 enum "all" {
                   description "All events";
                 }
               }
             }
           }
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
         }
         container inspection-limit {
           description "Bytes and packets limit for AppID inspection.";
           uses apply-advanced;
           container tcp {
             presence "enable tcp";
             description "TCP byte/packet inspection limit.";
             uses apply-advanced;
             leaf byte-limit {
               description "TCP byte inspection limit. (Default 6000)";
               default "6000";
               type union {
                 type uint32;
                 type string {
                   pattern "<.*>|$.*";
                 }
               }
             }
             leaf packet-limit {
               description "TCP packet inspection limit.";
               type union {
                 type uint32;
                 type string {
                   pattern "<.*>|$.*";
                 }
               }
             }
           }
           container udp {
             presence "enable udp";
             description "UDP byte/packet inspection limit.";
             uses apply-advanced;
             leaf byte-limit {
               description "UDP byte inspection limit.";
               type union {
                 type uint32;
                 type string {
                   pattern "<.*>|$.*";
                 }
               }
             }
             leaf packet-limit {
               description "UDP packet inspection limit. (Default 10)";
               default "10";
               type union {
                 type uint32;
                 type string {
                   pattern "<.*>|$.*";
                 }
               }
             }
           }
         }
         leaf global-offload-byte-limit {
           description "Global byte limit to offload AppID inspection. (Default 10000)";
           default "10000";
           type union {
             type uint32;
             type string {
               pattern "<.*>|$.*";
             }
           }
         }
         container packet-capture {
           description "To capture the unknown application traffic";
           uses apply-advanced;
           leaf global {
             description "Enable global capturing of application traffic";
             type empty;
           }
           leaf aggressive-mode {
             description "This mode captures all traffic prior to AppID classification";
             type empty;
           }
           leaf max-packets {
             description "Maximum number of UDP packets per session";
             type union {
               type string {
                 pattern "<.*>|$.*";
               }
               type uint32 {
                 range "1 .. 1000";
               }
             }
           }
           leaf max-bytes {
             description "Maximum number of TCP bytes per session";
             units "bytes";
             type union {
               type string {
                 pattern "<.*>|$.*";
               }
               type uint32 {
                 range "40 .. 1073741824";
               }
             }
           }
           leaf max-files {
             description "Maximum number of unique pcap files";
             type union {
               type string {
                 pattern "<.*>|$.*";
               }
               type uint32 {
                 range "1 .. 2500";
               }
             }
           }
           leaf no-inconclusive {
             description "Disable capturing of inconclusive traffic";
             type empty;
           }
           leaf storage-limit {
             description "Maximum disk space";
             units "bytes";
             type string;
           }
           leaf buffer-packets-limit {
             description "Maximum memory to buffer packets";
             units "bytes";
             type union {
               type uint64;
               type string {
                 pattern "<.*>|$.*";
               }
             }
           }
           leaf capture-interval {
             description "Timeout to avoid repetitive capture of same traffic (minutes)";
             type union {
               type string {
                 pattern "<.*>|$.*";
               }
               type uint32 {
                 range "1 .. 525600";
               }
             }
           }
           leaf capture-limit {
             description "Number of repetitive captures of same traffic";
             type union {
               type string {
                 pattern "<.*>|$.*";
               }
               type uint32 {
                 range "1 .. 1000";
               }
             }
           }
           leaf ssl-unknown {
             description "This mode captures all SSL unknown traffic";
             type empty;
           }
         }
         leaf l3l4-app-reclassification {
           description "Enable l3l4 custom app to be reclassified by jdpi ignoring results from other plugins";
           type empty;
         }
         leaf nb-flows-limit {
           description "Maximum number of nb flows";
           type union {
             type uint32;
             type string {
               pattern "<.*>|$.*";
             }
           }
         }
       }
       container ssl {
         description "Configuration for Secure Socket Layer support service";
         uses apply-advanced;
         container traceoptions {
           description "Trace options for Secure Socket Layer support service";
           uses ssl-traceoptions;
         }
         container termination {
           description "Configuration for Secure Socket Layer termination support service";
           uses ssl-termination-config;
         }
         container initiation {
           description "Configuration for Secure Socket Layer initiation support service";
           uses ssl-initiation-config;
         }
         container proxy {
           description "Configuration for Secure Socket Layer proxy support service";
           uses ssl-proxy-config;
         }
       }
       container dns-snooping {
         presence "enable dns-snooping";
         description "Enable DNS-Snooping, mandatory with policy context config";
         uses apply-advanced;
         leaf global-enable {
           description "Enable DNS-Snooping globally, policy config not required";
           type empty;
         }
         leaf-list trusted-dns-server {
           description "Trusted dns server address";
           type jt:ipaddr;
           max-elements 32;
         }
         leaf report-interval {
           description "Configure interval for report generation";
           default "5";
           type union {
             type string {
               pattern "<.*>|$.*";
             }
             type int32 {
               range "1 .. 10";
             }
           }
         }
       }
       container softwires {
         description "Configure softwire feature";
         uses softwires-object;
       }
       container rpm {
         presence "enable rpm";
         description "Real-time performance monitoring";
         uses apply-advanced;
         container probe-server {
           description "ICMP/TCP/UDP probe server";
           uses apply-advanced;
           container icmp {
             description "ICMP probe server";
             uses apply-advanced;
           }
           container tcp {
             description "TCP probe server";
             uses apply-advanced;
             leaf port {
               description "Port number 7 through 65535";
               type union {
                 type uint16;
                 type string {
                   pattern "<.*>|$.*";
                 }
               }
             }
           }
           container udp {
             description "UDP probe server";
             uses apply-advanced;
             leaf port {
               description "Port number 7 through 65535";
               type union {
                 type uint16;
                 type string {
                   pattern "<.*>|$.*";
                 }
               }
             }
           }
         }
         container traceoptions {
           description "RMOPD trace options";
           uses rmopd-traceoptions;
         }
         container bgp {
           description "BGP options for real-time performance monitoring";
           uses apply-advanced;
           leaf probe-type {
             description "RPM-BGP probe request type";
             default "icmp-ping";
             type enumeration {
               enum "icmp-ping" {
                 description "Send ICMP echo request to target address";
               }
               enum "icmp-ping-timestamp" {
                 description "Send ICMP timestamp request to target address";
               }
               enum "icmp6-ping" {
                 description "Send ICMP6 echo request to target address";
               }
               enum "tcp-ping" {
                 description "Send TCP packets to target";
               }
               enum "udp-ping" {
                 description "Send UDP packets to target";
               }
               enum "udp-ping-timestamp" {
                 description "Send UDP packets with timestamp to target";
               }
             }
           }
           leaf probe-count {
             description "Total number of probes per test";
             default "1";
             type union {
               type string {
                 pattern "<.*>|$.*";
               }
               type uint32 {
                 range "1 .. 15";
               }
             }
           }
           leaf probe-interval {
             description "Delay between probes";
             default "3";
             units "seconds";
             type union {
               type string {
                 pattern "<.*>|$.*";
               }
               type uint32 {
                 range "1 .. 255";
               }
             }
           }
           leaf test-interval {
             description "Delay between tests";
             default "1";
             units "seconds";
             type union {
               type string {
                 pattern "<.*>|$.*";
               }
               type uint32 {
                 range "0 .. 86400";
               }
             }
           }
           leaf destination-port {
             description "TCP/UDP port number";
             type union {
               type string {
                 pattern "<.*>|$.*";
               }
               type uint16 {
                 range "7 .. 65535";
               }
             }
           }
           leaf history-size {
             description "Number of stored history entries";
             default "50";
             type union {
               type string {
                 pattern "<.*>|$.*";
               }
               type uint32 {
                 range "0 .. 512";
               }
             }
           }
           leaf moving-average-size {
             description "Number of samples used for moving average";
             default "0";
             type union {
               type string {
                 pattern "<.*>|$.*";
               }
               type uint32 {
                 range "0 .. 512";
               }
             }
           }
           leaf data-size {
             description "Size of the data portion of the probes";
             default "0";
             type union {
               type string {
                 pattern "<.*>|$.*";
               }
               type uint32 {
                 range "0 .. 65400";
               }
             }
           }
           leaf data-fill {
             description "Define contents of the data portion of the probes";
             type string {
               length "1 .. 2048";
             }
           }
           leaf ttl {
             description "Time to Live (hop-limit) value for an RPM IPv4(IPv6) packet";
             default "64";
             type union {
               type string {
                 pattern "<.*>|$.*";
               }
               type uint32 {
                 range "1 .. 254";
               }
             }
           }
           list logical-system {
             key name;
             description "Logical systems";
             uses bgp-logical-system;
           }
           list routing-instances {
             key name;
             description "Routing instances";
             uses bgp-routing-instances;
           }
         }
         list probe {
           key name;
           ordered-by user;
           description "TCP/UDP/ICMP ping";
           leaf name {
             description "Name of owner";
             type string {
               length "1 .. 32";
             }
           }
           uses apply-advanced;
           leaf delegate-probes {
             description "Offload real-time performance monitoring probes to MS-MIC/MS-MPC card";
             type empty;
           }
           list test {
             key name;
             ordered-by user;
             description "TCP/UDP/ICMP/ICMP6 ping test";
             leaf name {
               description "Name of test";
               type string {
                 length "1 .. 32";
               }
             }
             uses apply-advanced;
             container rpm-scale {
               presence "enable rpm-scale";
               description "Configuring real-time performance monitoring scale tests";
               uses apply-advanced;
               leaf tests-count {
                 description "Number of probe-tests generated using scale config";
                 type union {
                   type string {
                     pattern "<.*>|$.*";
                   }
                   type uint32 {
                     range "1 .. 500000";
                   }
                 }
               }
               choice target-type {
                 case case_1 {
                   container target {
                     presence "enable target";
                     description "Target address generation for scale test config";
                     uses apply-advanced;
                     leaf address-base {
                       description "Base address of target host in a.b.c.d format";
                       type jt:ipv4addr;
                     }
                     leaf step {
                       description "Steps to increment target address in a.b.c.d format";
                       type jt:ipv4addr;
                     }
                     leaf count {
                       description "Target address count";
                       type union {
                         type string {
                           pattern "<.*>|$.*";
                         }
                         type uint32 {
                           range "1 .. 500000";
                         }
                       }
                     }
                   }
                 }
                 case case_2 {
                   container target-inet6 {
                     presence "enable target-inet6";
                     description "IPv6 target address generation for scale test config";
                     uses apply-advanced;
                     leaf address-base {
                       description "Base address of target host in a:b:c:d:e:f:g:h format";
                       type jt:ipv6addr;
                     }
                     leaf step {
                       description "Steps to increment target address in a:b:c:d:e:f:g:h format";
                       type jt:ipv6addr;
                     }
                     leaf count {
                       description "Target address count";
                       type union {
                         type string {
                           pattern "<.*>|$.*";
                         }
                         type uint32 {
                           range "1 .. 500000";
                         }
                       }
                     }
                   }
                 }
               }
               choice source-type {
                 case case_1 {
                   container source {
                     presence "enable source";
                     description "Source address generation in scale tests";
                     uses apply-advanced;
                     leaf address-base {
                       description "Base address of host in a.b.c.d format";
                       type jt:ipv4addr;
                     }
                     leaf step {
                       description "Steps to increment src address in a.b.c.d format";
                       type jt:ipv4addr;
                     }
                     leaf count {
                       description "Source-address count";
                       type union {
                         type string {
                           pattern "<.*>|$.*";
                         }
                         type uint32 {
                           range "1 .. 500000";
                         }
                       }
                     }
                   }
                 }
                 case case_2 {
                   container source-inet6 {
                     presence "enable source-inet6";
                     description "IPv6 source address generation in scale tests";
                     uses apply-advanced;
                     leaf address-base {
                       description "Base address of host in a:b:c:d:e:f:g:h format";
                       type jt:ipv6addr;
                     }
                     leaf step {
                       description "Steps to increment src address in a:b:c:d:e:f:g:h format";
                       type jt:ipv6addr;
                     }
                     leaf count {
                       description "Source-address count";
                       type union {
                         type string {
                           pattern "<.*>|$.*";
                         }
                         type uint32 {
                           range "1 .. 500000";
                         }
                       }
                     }
                   }
                 }
               }
               container destination {
                 presence "enable destination";
                 description "Name of output interface for probes";
                 uses apply-advanced;
                 leaf interface {
                   description "Base destination interface for scale test";
                   type union {
                     type jt:interface-name;
                     type string {
                       pattern "<.*>|$.*";
                     }
                   }
                 }
                 leaf subunit-cnt {
                   description "Subunit count for destination interface for scale test";
                   type union {
                     type string {
                       pattern "<.*>|$.*";
                     }
                     type uint32 {
                       range "1 .. 500000";
                     }
                   }
                 }
               }
             }
             leaf probe-type {
               description "Probe request type";
               default "icmp-ping";
               type enumeration {
                 enum "http-get" {
                   description "Perform HTTP Get request at target URL";
                 }
                 enum "http-metadata-get" {
                   description "Perform HTTP Get request of metadata at target URL";
                 }
                 enum "icmp-ping" {
                   description "Send ICMP echo request to target address";
                 }
                 enum "icmp-ping-timestamp" {
                   description "Send ICMP timestamp request to target address";
                 }
                 enum "icmp6-ping" {
                   description "Send ICMP6 echo request to target address";
                 }
                 enum "tcp-ping" {
                   description "Send TCP packets to target";
                 }
                 enum "udp-ping" {
                   description "Send UDP packets to target";
                 }
                 enum "udp-ping-timestamp" {
                   description "Send UDP packets with timestamp to target";
                 }
               }
             }
             container target {
               presence "enable target";
               description "Target destination for probe";
               choice target-type {
                 case case_1 {
                   leaf address {
                     description "Address of target host";
                     type jt:ipv4addr;
                   }
                 }
                 case case_2 {
                   leaf inet6-address {
                     description "Inet6 Address of target host";
                     type jt:ipv6addr;
                   }
                 }
                 case case_3 {
                   leaf url {
                     description "Fully formed target URL";
                     type string;
                   }
                 }
                 case case_4 {
                   leaf inet6-url {
                     description "Fully formed target IPV6 URL";
                     type string;
                   }
                 }
               }
             }
             container inet6-options {
               presence "enable inet6-options";
               description "IPV6 related options";
               uses apply-advanced;
               leaf source-address {
                 description "Inet6 Source Address of the probe";
                 type jt:ipv6addr;
               }
             }
             leaf probe-count {
               description "Total number of probes per test";
               default "1";
               type union {
                 type string {
                   pattern "<.*>|$.*";
                 }
                 type uint32 {
                   range "1 .. 15";
                 }
               }
             }
             leaf probe-interval {
               description "Delay between probes";
               default "3";
               units "seconds";
               type union {
                 type string {
                   pattern "<.*>|$.*";
                 }
                 type uint32 {
                   range "1 .. 255";
                 }
               }
             }
             leaf test-interval {
               description "Delay between tests";
               default "1";
               units "seconds";
               type union {
                 type string {
                   pattern "<.*>|$.*";
                 }
                 type uint32 {
                   range "0 .. 86400";
                 }
               }
             }
             leaf destination-port {
               description "TCP/UDP port number";
               type union {
                 type string {
                   pattern "<.*>|$.*";
                 }
                 type uint16 {
                   range "7 .. 65535";
                 }
               }
             }
             leaf source-address {
               description "Source address for probe";
               type jt:ipv4addr;
             }
             leaf routing-instance {
               description "Routing instance used by probes";
               type string {
               }
             }
             leaf history-size {
               description "Number of stored history entries";
               default "50";
               type union {
                 type string {
                   pattern "<.*>|$.*";
                 }
                 type uint32 {
                   range "0 .. 512";
                 }
               }
             }
             leaf moving-average-size {
               description "Number of samples used for moving average";
               default "0";
               type union {
                 type string {
                   pattern "<.*>|$.*";
                 }
                 type uint32 {
                   range "0 .. 512";
                 }
               }
             }
             leaf dscp-code-points {
               description "Differentiated Services code point bits or alias";
               default "000000";
               type string {
               }
             }
             leaf data-size {
               description "Size of the data portion of the probes";
               default "0";
               type union {
                 type string {
                   pattern "<.*>|$.*";
                 }
                 type uint32 {
                   range "0 .. 65400";
                 }
               }
             }
             leaf data-fill {
               description "Define contents of the data portion of the probes";
               type string {
                 length "1 .. 2048";
               }
             }
             leaf ttl {
               description "Time to Live (hop-limit) value for an RPM IPv4(IPv6) packet";
               default "64";
               type union {
                 type string {
                   pattern "<.*>|$.*";
                 }
                 type uint32 {
                   range "1 .. 254";
                 }
               }
             }
             container thresholds {
               presence "enable thresholds";
               description "Probe and test threshold values. Set 0 to disable respective threshold";
               uses apply-advanced;
               leaf successive-loss {
                 description "Successive probe loss count indicating probe failure";
                 default "1";
                 type union {
                   type string {
                     pattern "<.*>|$.*";
                   }
                   type uint32 {
                     range "0 .. 15";
                   }
                 }
               }
               leaf total-loss {
                 description "Total probe loss count indicating test failure";
                 default "1";
                 type union {
                   type string {
                     pattern "<.*>|$.*";
                   }
                   type uint32 {
                     range "0 .. 15";
                   }
                 }
               }
               leaf rtt {
                 description "Maximum round trip time per probe";
                 default "0";
                 units "microseconds";
                 type union {
                   type string {
                     pattern "<.*>|$.*";
                   }
                   type uint32 {
                     range "0 .. 60000000";
                   }
                 }
               }
               leaf jitter-rtt {
                 description "Maximum jitter per test";
                 default "0";
                 units "microseconds";
                 type union {
                   type string {
                     pattern "<.*>|$.*";
                   }
                   type uint32 {
                     range "0 .. 60000000";
                   }
                 }
               }
               leaf std-dev-rtt {
                 description "Maximum standard deviation per test";
                 default "0";
                 units "microseconds";
                 type union {
                   type string {
                     pattern "<.*>|$.*";
                   }
                   type uint32 {
                     range "0 .. 60000000";
                   }
                 }
               }
               leaf egress-time {
                 description "Maximum source to destination time per probe";
                 default "0";
                 units "microseconds";
                 type union {
                   type string {
                     pattern "<.*>|$.*";
                   }
                   type uint32 {
                     range "0 .. 60000000";
                   }
                 }
               }
               leaf ingress-time {
                 description "Maximum destination to source time per probe";
                 default "0";
                 units "microseconds";
                 type union {
                   type string {
                     pattern "<.*>|$.*";
                   }
                   type uint32 {
                     range "0 .. 60000000";
                   }
                 }
               }
               leaf jitter-ingress {
                 description "Maximum destination to source jitter per test";
                 default "0";
                 units "microseconds";
                 type union {
                   type string {
                     pattern "<.*>|$.*";
                   }
                   type uint32 {
                     range "0 .. 60000000";
                   }
                 }
               }
               leaf jitter-egress {
                 description "Maximum source to destination jitter per test";
                 default "0";
                 units "microseconds";
                 type union {
                   type string {
                     pattern "<.*>|$.*";
                   }
                   type uint32 {
                     range "0 .. 60000000";
                   }
                 }
               }
               leaf std-dev-ingress {
                 description "Maximum destination to source standard deviation per test";
                 default "0";
                 units "microseconds";
                 type union {
                   type string {
                     pattern "<.*>|$.*";
                   }
                   type uint32 {
                     range "0 .. 60000000";
                   }
                 }
               }
               leaf std-dev-egress {
                 description "Maximum source to destination standard deviation per test";
                 default "0";
                 units "microseconds";
                 type union {
                   type string {
                     pattern "<.*>|$.*";
                   }
                   type uint32 {
                     range "0 .. 60000000";
                   }
                 }
               }
             }
             leaf-list traps {
               ordered-by user;
               description "Trap to send if threshold is met or exceeded";
               type enumeration {
                 enum "probe-failure" {
                   description "Successive probe loss threshold reached";
                 }
                 enum "test-failure" {
                   description "Total probe loss threshold reached";
                 }
                 enum "test-completion" {
                   description "Test completed";
                 }
                 enum "rtt-exceeded" {
                   description "Exceeded maximum round trip time threshold";
                 }
                 enum "std-dev-exceeded" {
                   description "Exceeded round trip time standard deviation threshold";
                 }
                 enum "jitter-exceeded" {
                   description "Exceeded jitter in round trip time threshold";
                 }
                 enum "ingress-time-exceeded" {
                   description "Exceeded maximum ingress time threshold";
                 }
                 enum "ingress-std-dev-exceeded" {
                   description "Exceeded ingress time standard deviation threshold";
                 }
                 enum "ingress-jitter-exceeded" {
                   description "Exceeded jitter in ingress time threshold";
                 }
                 enum "egress-time-exceeded" {
                   description "Exceeded maximum egress time threshold";
                 }
                 enum "egress-std-dev-exceeded" {
                   description "Exceeded egress time standard deviation threshold";
                 }
                 enum "egress-jitter-exceeded" {
                   description "Exceeded jitter in egress time threshold";
                 }
               }
             }
             leaf destination-interface {
               description "Name of output interface for probes";
               type union {
                 type jt:interface-name;
                 type string {
                   pattern "<.*>|$.*";
                 }
               }
             }
             leaf hardware-timestamp {
               description "Packet Forwarding Engine updates timestamps";
               type empty;
             }
             leaf one-way-hardware-timestamp {
               description "Enable hardware timestamps for one-way measurements";
               type empty;
             }
             leaf next-hop {
               description "Next-hop to which probe should be sent";
               type jt:ipv4addr;
             }
           }
         }
         leaf probe-limit {
           description "Maximum number of concurrent probes allowed";
           default "100";
           type union {
             type string {
               pattern "<.*>|$.*";
             }
             type uint32 {
               range "1 .. 2000";
             }
           }
         }
         container rfc2544-benchmarking {
           presence "enable rfc2544-benchmarking";
           description "Rfc2544 benchmarking tests";
           uses apply-advanced;
           container profiles {
             description "Rfc2544 test profiles";
             uses apply-advanced;
             list test-profile {
               key name;
               ordered-by user;
               description "Test-profile definition";
               leaf name {
                 description "Test name";
                 type string {
                   length "1 .. 32";
                 }
               }
               uses apply-advanced;
               leaf test-type {
                 description "Rfc2544 test type";
                 default "throughput";
                 type enumeration {
                   enum "throughput" {
                     description "Rfc2544 throughput test";
                   }
                   enum "latency" {
                     description "Rfc2544 latency test";
                   }
                   enum "frame-loss" {
                     description "Rfc2544 frame-loss test";
                   }
                   enum "back-back-frames" {
                     description "Rfc2544 back to back frames test";
                   }
                 }
               }
               leaf-list packet-size {
                 ordered-by user;
                 description "Size of the test packet";
                 type union {
                   type string {
                     pattern "<.*>|$.*";
                   }
                   type uint32 {
                     range "64 .. 9216";
                   }
                 }
               }
               leaf bandwidth-kbps {
                 description "Theoretical max service bandwidth in kbps";
                 default "10000";
                 type union {
                   type string {
                     pattern "<.*>|$.*";
                   }
                   type uint32;
                 }
               }
               leaf step-percent {
                 description "Step percent for test";
                 default "10";
                 type union {
                   type string {
                     pattern "<.*>|$.*";
                   }
                   type uint32 {
                     range "1 .. 100";
                   }
                 }
               }
             }
           }
           container tests {
             presence "enable tests";
             description "Rfc2544 test configuration";
             uses apply-advanced;
             list test-name {
               key name;
               ordered-by user;
               description "Test definition";
               leaf name {
                 description "Test name";
                 type string {
                   length "1 .. 32";
                 }
               }
               uses apply-advanced;
               leaf test-profile {
                 description "Name of the test profile";
                 type string;
               }
               leaf source-mac-address {
                 description "MAC address of source host in xx:xx:xx:xx:xx:xx format -Generator MAC";
                 type jt:mac-unicast;
               }
               leaf destination-mac-address {
                 description "MAC address of destination host in xx:xx:xx:xx:xx:xx format -Reflector MAC";
                 type jt:mac-unicast;
               }
               leaf ovlan-id {
                 description "Outer vlan id";
                 type union {
                   type string {
                     pattern "<.*>|$.*";
                   }
                   type int32 {
                     range "0 .. 4094";
                   }
                 }
               }
               leaf ovlan-priority {
                 description "Outer vlan priority";
                 type union {
                   type string {
                     pattern "<.*>|$.*";
                   }
                   type int32 {
                     range "0 .. 7";
                   }
                 }
               }
               leaf ovlan-cfi {
                 description "Outer vlan CFI bit";
                 type union {
                   type string {
                     pattern "<.*>|$.*";
                   }
                   type int32 {
                     range "0 .. 1";
                   }
                 }
               }
               leaf outer-tag-protocol-id {
                 description "Outer tag protocol id";
                 default "0x8100";
                 type string {
                 }
               }
               leaf ivlan-id {
                 description "Inner vlan id";
                 type union {
                   type string {
                     pattern "<.*>|$.*";
                   }
                   type int32 {
                     range "0 .. 4094";
                   }
                 }
               }
               leaf ivlan-priority {
                 description "Inner vlan priority";
                 type union {
                   type string {
                     pattern "<.*>|$.*";
                   }
                   type int32 {
                     range "0 .. 7";
                   }
                 }
               }
               leaf ivlan-cfi {
                 description "Inner vlan CFI bit";
                 type union {
                   type string {
                     pattern "<.*>|$.*";
                   }
                   type int32 {
                     range "0 .. 1";
                   }
                 }
               }
               leaf service-type {
                 description "Service type";
                 type enumeration {
                   enum "eline" {
                     description "Eline service";
                   }
                   enum "elan" {
                     description "Elan service";
                   }
                 }
               }
               leaf in-service {
                 description "Test executed in-service mode";
                 type empty;
               }
               leaf ip-swap {
                 description "Swap IP in the test payload";
                 type empty;
               }
               leaf udp-tcp-port-swap {
                 description "Swap UDP/TCP port in the test payload";
                 type empty;
               }
               leaf disable-signature-check {
                 description "Signature check disable";
                 type empty;
               }
               leaf packet-loss-priority {
                 description "Packet loss priority assigned to the frames";
                 type enumeration {
                   enum "low" {
                     description "Packet loss priority is low";
                   }
                   enum "high" {
                     description "Packet loss priority is high";
                   }
                   enum "medium-high" {
                     description "Packet loss priority is medium-high";
                   }
                 }
               }
               leaf dscp-code-points {
                 description "Differentiated Services code point bits or alias";
                 default "000000";
                 type string {
                 }
               }
               leaf mode {
                 description "Test mode";
                 type enumeration {
                   enum "reflect" {
                     description "Reflector end";
                   }
                   enum "initiate-and-terminate" {
                     description "Initiate and terminator";
                   }
                   enum "ethernet-loopback" {
                     description "Ethernet loopback";
                   }
                 }
               }
               leaf reflect-mode {
                 description "Reflect mode";
                 type enumeration {
                   enum "mac-swap" {
                     description "Mac swap ";
                   }
                   enum "no-mac-swap" {
                     description "No mac-swap";
                   }
                   enum "mac-rewrite" {
                     description "Mac-rewrite";
                   }
                 }
               }
               leaf family {
                 description "Family type";
                 type enumeration {
                   enum "inet" {
                     description "Inet family";
                   }
                   enum "ccc" {
                     description "CCC family ";
                   }
                   enum "bridge" {
                     description "Bridge family ";
                   }
                   enum "vpls" {
                     description "VPLS family ";
                   }
                 }
               }
               leaf reflect-etype {
                 description "Etype to match for reflect mode";
                 type union {
                   type string {
                     pattern "<.*>|$.*";
                   }
                   type uint32 {
                     range "1 .. 65535";
                   }
                 }
               }
               leaf direction {
                 description "Direction of test";
                 type enumeration {
                   enum "ingress" {
                     description "Pseudo-wire/Bridge/Vpls Ingress direction";
                   }
                   enum "egress" {
                     description "Pseudo-wire/Bridge/Vpls Egress direction";
                   }
                 }
               }
               leaf timestamp-format {
                 description "Format of timestamp values";
                 type enumeration {
                   enum "microseconds" {
                     description "Timestamps in microseconds";
                   }
                   enum "nanoseconds" {
                     description "Timestamps in nanoseconds";
                   }
                 }
               }
               leaf source-udp-port {
                 description "Source udp port";
                 type union {
                   type string {
                     pattern "<.*>|$.*";
                   }
                   type uint32 {
                     range "1 .. 65535";
                   }
                 }
               }
               leaf destination-udp-port {
                 description "Destination udp port";
                 type union {
                   type string {
                     pattern "<.*>|$.*";
                   }
                   type uint32 {
                     range "1 .. 65535";
                   }
                 }
               }
               leaf test-duration {
                 description "Test duration in minutes";
                 status deprecated;
                 default "10";
                 type union {
                   type string {
                     pattern "<.*>|$.*";
                   }
                   type uint32 {
                     range "1 .. 5000";
                   }
                 }
               }
               leaf test-iterator-duration {
                 description "Duration of each iteration in seconds";
                 type union {
                   type string {
                     pattern "<.*>|$.*";
                   }
                   type uint32 {
                     range "10 .. 1728000";
                   }
                 }
               }
               leaf test-finish-wait-duration {
                 description "Number of seconds to wait after test completes before stopping the test";
                 default "1";
                 type union {
                   type string {
                     pattern "<.*>|$.*";
                   }
                   type uint32 {
                     range "1 .. 60";
                   }
                 }
               }
               leaf transmit-failure-threshold {
                 description "Transmit failure-threshold (default 0.5%)";
                 default "0.5";
                 type decimal64 {
                   fraction-digits 9;
                   range "0 .. 100";
                 }
               }
               leaf receive-failure-threshold {
                 description "Receive failure-threshold (default 0%)";
                 default "0";
                 type decimal64 {
                   fraction-digits 9;
                   range "0 .. 100";
                 }
               }
               leaf test-iterator-pass-threshold {
                 description "Test pass-threshold (default 0.5%)";
                 default "0.5";
                 type decimal64 {
                   fraction-digits 9;
                   range "0 .. 100";
                 }
               }
               leaf halt-on-prefix-down {
                 description "Halt test on prefix down";
                 type empty;
               }
               leaf skip-arp-iteration {
                 description "Skip arp iteration in tests";
                 type empty;
               }
               leaf test-interface {
                 description "Name of interface(ifl) for test";
                 type union {
                   type jt:interface-name;
                   type string {
                     pattern "<.*>|$.*";
                   }
                 }
               }
               leaf destination-ipv4-address {
                 description "Destination address for test";
                 type jt:ipv4addr;
               }
               leaf source-ipv4-address {
                 description "Source address for test";
                 type jt:ipv4addr;
               }
             }
           }
         }
         container twamp {
           description "Two-way Active Measurement Protocol configuration";
           uses apply-advanced;
           leaf post-cli-implicit-firewall {
             description "Enable post cli implicit firewall";
             type empty;
           }
           container client {
             description "TWAMP client configuration";
             uses apply-advanced;
             list control-connection {
               key name;
               ordered-by user;
               description "TWAMP control session configuration";
               leaf name {
                 description "Client name";
                 type string {
                   length "1 .. 32";
                 }
               }
               uses apply-advanced;
               container authentication-mode {
                 description "Authentication modes";
                 uses apply-advanced;
                 leaf none {
                   description "No authentication or encryption";
                   type empty;
                 }
               }
               leaf destination-interface {
                 description "Name of output interface for all test sessions";
                 type union {
                   type jt:interface-name;
                   type string {
                     pattern "<.*>|$.*";
                   }
                 }
               }
               leaf persistent-results {
                 description "Displays the old results along with present. Default disable";
                 type empty;
               }
               leaf control-type {
                 description "TWAMP control connection type";
                 default "managed";
                 type enumeration {
                   enum "light" {
                     description "No control connection to manage test sessions";
                   }
                   enum "managed" {
                     description "Control connection will negotiate test sessions";
                   }
                 }
               }
               leaf tcp-keepidle {
                 description "Time to start TCP KEEPALIVEs on control connection (default 120)";
                 default "120";
                 units "seconds";
                 type union {
                   type string {
                     pattern "<.*>|$.*";
                   }
                   type uint32 {
                     range "1 .. 600";
                   }
                 }
               }
               leaf tcp-keepintvl {
                 description "Delay between succesive TCP KEEPALIVEs (default 5)";
                 default "5";
                 units "seconds";
                 type union {
                   type string {
                     pattern "<.*>|$.*";
                   }
                   type uint32 {
                     range "1 .. 600";
                   }
                 }
               }
               leaf tcp-keepcnt {
                 description "Number of TCP KEEPALIVEs sent (default 6)";
                 default "6";
                 type union {
                   type string {
                     pattern "<.*>|$.*";
                   }
                   type uint32 {
                     range "1 .. 50";
                   }
                 }
               }
               leaf destination-port {
                 description "TCP TWAMP client listening port for the test sessions. Default 862";
                 default "862";
                 type union {
                   type string {
                     pattern "<.*>|$.*";
                   }
                   type uint16 {
                     range "862 .. 65535";
                   }
                 }
               }
               leaf history-size {
                 description "Number of stored history entries";
                 default "50";
                 type union {
                   type string {
                     pattern "<.*>|$.*";
                   }
                   type uint32 {
                     range "0 .. 512";
                   }
                 }
               }
               leaf moving-average-size {
                 description "Number of samples used for moving average";
                 default "0";
                 type union {
                   type string {
                     pattern "<.*>|$.*";
                   }
                   type uint32 {
                     range "0 .. 512";
                   }
                 }
               }
               leaf routing-instance {
                 description "Routing instance used by the test sessions";
                 type string {
                 }
               }
               leaf source-address {
                 description "Source address of TWAMP Control client";
                 type jt:ipv4addr;
               }
               leaf target-address {
                 description "Destination IPv4 address of TWAMP responder";
                 type jt:ipv4addr;
               }
               leaf test-count {
                 description "Total number of test session iterations";
                 default "0";
                 type union {
                   type string {
                     pattern "<.*>|$.*";
                   }
                   type uint32 {
                     range "0 .. 4294967290";
                   }
                 }
               }
               leaf test-interval {
                 description "Delay between test session iterations";
                 default "1";
                 units "seconds";
                 type union {
                   type string {
                     pattern "<.*>|$.*";
                   }
                   type uint16 {
                     range "1 .. 255";
                   }
                 }
               }
               container traps {
                 description "Trap to send if threshold is met or exceeded";
                 uses apply-advanced;
                 leaf test-iteration-done {
                   description "All test sessions configured under the control connection have completed an iteration";
                   type empty;
                 }
                 leaf control-connection-closed {
                   description "Control connection closed";
                   type empty;
                 }
               }
               list test-session {
                 key name;
                 ordered-by user;
                 description "Test session details";
                 leaf name {
                   description "Test session name";
                   type string {
                     length "1 .. 32";
                   }
                 }
                 uses apply-advanced;
                 leaf source-address {
                   description "Source address of TWAMP Probes";
                   type jt:ipaddr;
                 }
                 container target-address {
                   presence "enable target-address";
                   description "Destination IPv4 or IPv6 address of TWAMP responder";
                   leaf address {
                     description "Address of TWAMP session reflector";
                     type jt:ipaddr;
                   }
                   leaf local-link {
                     description "Link scope for IPv6 link-local address";
                     type union {
                       type jt:interface-name;
                       type string {
                         pattern "<.*>|$.*";
                       }
                     }
                   }
                 }
                 leaf destination-port {
                   description "Target port number for test";
                   default "862";
                   type union {
                     type string {
                       pattern "<.*>|$.*";
                     }
                     type uint16 {
                       range "862 .. 65535";
                     }
                   }
                 }
                 leaf data-fill-with-zeros {
                   description "Fill contents of test packet with zeros";
                   type empty;
                 }
                 leaf data-size {
                   description "Size of the data portion of the probes";
                   default "60";
                   type union {
                     type string {
                       pattern "<.*>|$.*";
                     }
                     type uint16 {
                       range "60 .. 1400";
                     }
                   }
                 }
                 leaf dscp-code-points {
                   description "Differentiated Services code point bits or alias used for TCP control and UDP TWAMP test packets";
                   default "000000";
                   type string {
                   }
                 }
                 leaf ttl {
                   description "Time to Live (hop-limit) value for an RPM IPv4(IPv6) packet";
                   default "64";
                   type union {
                     type string {
                       pattern "<.*>|$.*";
                     }
                     type uint32 {
                       range "1 .. 254";
                     }
                   }
                 }
                 leaf probe-count {
                   description "Total number of probes per test";
                   default "1";
                   type union {
                     type string {
                       pattern "<.*>|$.*";
                     }
                     type uint32 {
                       range "1 .. 4294967290";
                     }
                   }
                 }
                 leaf probe-interval {
                   description "Delay between two consecutive probes";
                   default "1";
                   units "seconds";
                   type union {
                     type string {
                       pattern "<.*>|$.*";
                     }
                     type uint32 {
                       range "1 .. 255";
                     }
                   }
                 }
                 container thresholds {
                   presence "enable thresholds";
                   description "TWAMP test threshold values. Set 0 to disable respective threshold";
                   uses apply-advanced;
                   leaf successive-loss {
                     description "Successive probe loss count indicating probe failure";
                     default "1";
                     type union {
                       type string {
                         pattern "<.*>|$.*";
                       }
                       type uint32 {
                         range "0 .. 15";
                       }
                     }
                   }
                   leaf total-loss {
                     description "Total probe loss count indicating test failure";
                     default "1";
                     type union {
                       type string {
                         pattern "<.*>|$.*";
                       }
                       type uint32 {
                         range "0 .. 4294967290";
                       }
                     }
                   }
                   leaf rtt {
                     description "Maximum round trip time per probe";
                     default "0";
                     units "microseconds";
                     type union {
                       type string {
                         pattern "<.*>|$.*";
                       }
                       type uint32 {
                         range "0 .. 60000000";
                       }
                     }
                   }
                   leaf max-rtt {
                     description "Maximum round trip time per test";
                     status deprecated;
                     default "0";
                     units "microseconds";
                     type union {
                       type string {
                         pattern "<.*>|$.*";
                       }
                       type uint32 {
                         range "0 .. 60000000";
                       }
                     }
                   }
                   leaf jitter-rtt {
                     description "Maximum jitter per test";
                     default "0";
                     units "microseconds";
                     type union {
                       type string {
                         pattern "<.*>|$.*";
                       }
                       type uint32 {
                         range "0 .. 60000000";
                       }
                     }
                   }
                   leaf std-dev-rtt {
                     description "Maximum standard deviation per test";
                     default "0";
                     units "microseconds";
                     type union {
                       type string {
                         pattern "<.*>|$.*";
                       }
                       type uint32 {
                         range "0 .. 60000000";
                       }
                     }
                   }
                   leaf egress-time {
                     description "Maximum source to destination time per probe";
                     default "0";
                     units "microseconds";
                     type union {
                       type string {
                         pattern "<.*>|$.*";
                       }
                       type uint32 {
                         range "0 .. 60000000";
                       }
                     }
                   }
                   leaf ingress-time {
                     description "Maximum destination to source time per probe";
                     default "0";
                     units "microseconds";
                     type union {
                       type string {
                         pattern "<.*>|$.*";
                       }
                       type uint32 {
                         range "0 .. 60000000";
                       }
                     }
                   }
                   leaf jitter-ingress {
                     description "Maximum destination to source jitter per test";
                     default "0";
                     units "microseconds";
                     type union {
                       type string {
                         pattern "<.*>|$.*";
                       }
                       type uint32 {
                         range "0 .. 60000000";
                       }
                     }
                   }
                   leaf jitter-egress {
                     description "Maximum source to destination jitter per test";
                     default "0";
                     units "microseconds";
                     type union {
                       type string {
                         pattern "<.*>|$.*";
                       }
                       type uint32 {
                         range "0 .. 60000000";
                       }
                     }
                   }
                   leaf std-dev-ingress {
                     description "Maximum destination to source standard deviation per test";
                     default "0";
                     units "microseconds";
                     type union {
                       type string {
                         pattern "<.*>|$.*";
                       }
                       type uint32 {
                         range "0 .. 60000000";
                       }
                     }
                   }
                   leaf std-dev-egress {
                     description "Maximum source to destination standard deviation per test";
                     default "0";
                     units "microseconds";
                     type union {
                       type string {
                         pattern "<.*>|$.*";
                       }
                       type uint32 {
                         range "0 .. 60000000";
                       }
                     }
                   }
                 }
                 container traps {
                   description "Trap to send if threshold is met or exceeded";
                   uses apply-advanced;
                   leaf probe-failure {
                     description "Successive probe loss threshold reached";
                     type empty;
                   }
                   leaf test-failure {
                     description "Total probe loss threshold reached";
                     type empty;
                   }
                   leaf test-completion {
                     description "Test completed";
                     type empty;
                   }
                   leaf rtt-exceeded {
                     description "Exceeded maximum round trip time threshold";
                     type empty;
                   }
                   leaf max-rtt-exceeded {
                     description "Exceeded maximum round trip time threshold at the end of per test";
                     type empty;
                   }
                   leaf std-dev-exceeded {
                     description "Exceeded round trip time standard deviation threshold";
                     type empty;
                   }
                   leaf jitter-exceeded {
                     description "Exceeded jitter in round trip time threshold";
                     type empty;
                   }
                   leaf ingress-time-exceeded {
                     description "Exceeded maximum ingress time threshold";
                     type empty;
                   }
                   leaf ingress-std-dev-exceeded {
                     description "Exceeded ingress time standard deviation threshold";
                     type empty;
                   }
                   leaf ingress-jitter-exceeded {
                     description "Exceeded jitter in ingress time threshold";
                     type empty;
                   }
                   leaf egress-time-exceeded {
                     description "Exceeded maximum egress time threshold";
                     type empty;
                   }
                   leaf egress-std-dev-exceeded {
                     description "Exceeded egress time standard deviation threshold";
                     type empty;
                   }
                   leaf egress-jitter-exceeded {
                     description "Exceeded jitter in egress time threshold";
                     type empty;
                   }
                 }
               }
             }
           }
           container server {
             description "TWAMP server configuration";
             uses apply-advanced;
             leaf tcp-keepidle {
               description "Time to start TCP KEEPALIVEs on control connection (default 120)";
               default "120";
               units "seconds";
               type union {
                 type string {
                   pattern "<.*>|$.*";
                 }
                 type uint32 {
                   range "1 .. 600";
                 }
               }
             }
             leaf tcp-keepintvl {
               description "Delay between succesive TCP KEEPALIVEs (default 5)";
               default "5";
               units "seconds";
               type union {
                 type string {
                   pattern "<.*>|$.*";
                 }
                 type uint32 {
                   range "1 .. 600";
                 }
               }
             }
             leaf tcp-keepcnt {
               description "Number of TCP KEEPALIVEs sent (default 6)";
               default "6";
               type union {
                 type string {
                   pattern "<.*>|$.*";
                 }
                 type uint32 {
                   range "1 .. 50";
                 }
               }
             }
             list routing-instance-list {
               key name;
               ordered-by user;
               description "List of allowed routing instances,not more than 100, along with ports";
               leaf name {
                 description "Name of the routing instance";
                 type string {
                 }
               }
               uses apply-advanced;
               leaf port {
                 description "Port to be used by the routing instance";
                 type union {
                   type string {
                     pattern "<.*>|$.*";
                   }
                   type uint32 {
                     range "1 .. 65535";
                   }
                 }
               }
             }
             container authentication-mode {
               description "Authentication modes";
               uses apply-advanced;
               leaf none {
                 description "No authentication or encryption";
                 type empty;
               }
               container authenticated {
                 presence "enable authenticated";
                 description "Authenticated mode";
                 leaf control-only {
                   description "Authentication mode only for TWAMP control protocol";
                   status deprecated;
                   type empty;
                 }
               }
               container encrypted {
                 presence "enable encrypted";
                 description "Encrypted mode";
                 leaf control-only {
                   description "Encryption mode only for TWAMP control protocol";
                   status deprecated;
                   type empty;
                 }
               }
               leaf control-only-encrypted {
                 description "Encrypted control and unauthenticated data mode";
                 type empty;
               }
             }
             list authentication-key-chain {
               key name;
               ordered-by user;
               description "Authentication key chain configuration";
               uses twamp-authentication-key-chain;
             }
             leaf server-inactivity-timeout {
               description "Control packet idle timeout value in minutes, 0 to disable";
               default "15";
               units "minutes";
               type union {
                 type string {
                   pattern "<.*>|$.*";
                 }
                 type uint32 {
                   range "0 .. 30";
                 }
               }
             }
             leaf max-connection-duration {
               description "Maximum Connection duration in hours, 0 to disable";
               default "0";
               units "hours";
               type union {
                 type string {
                   pattern "<.*>|$.*";
                 }
                 type uint32 {
                   range "0 .. 120";
                 }
               }
             }
             leaf maximum-sessions {
               description "Maximum number of test sessions for the server";
               default "64";
               type union {
                 type string {
                   pattern "<.*>|$.*";
                 }
                 type uint32 {
                   range "1 .. 2048";
                 }
               }
             }
             leaf maximum-sessions-per-connection {
               description "Maximum number of test sessions per client connection";
               type union {
                 type string {
                   pattern "<.*>|$.*";
                 }
                 type uint32 {
                   range "1 .. 1024";
                 }
               }
             }
             leaf maximum-connections {
               description "Maximum number of connections for the server";
               default "64";
               type union {
                 type string {
                   pattern "<.*>|$.*";
                 }
                 type uint32 {
                   range "1 .. 1000";
                 }
               }
             }
             leaf maximum-connections-per-client {
               description "Maximum number of server connections per client";
               type union {
                 type string {
                   pattern "<.*>|$.*";
                 }
                 type uint32 {
                   range "1 .. 500";
                 }
               }
             }
             leaf port {
               description "TWAMP server listening port";
               default "862";
               type union {
                 type string {
                   pattern "<.*>|$.*";
                 }
                 type uint32 {
                   range "1 .. 65535";
                 }
               }
             }
             list client-list {
               key name;
               ordered-by user;
               description "List of allowed clients";
               leaf name {
                 description "Name of client list";
                 type string {
                   length "1 .. 127";
                 }
               }
               uses apply-advanced;
               list address {
                 key name;
                 ordered-by user;
                 description "IPv4 prefix of TWAMP client";
                 leaf name {
                   description "IPv4 prefix of TWAMP client";
                   type jt:ipv4prefix;
                 }
                 uses apply-advanced;
               }
             }
             container light {
               presence "enable light";
               description "Enable TWAMP server for light control on the default port";
               uses apply-advanced;
               leaf-list port {
                 ordered-by user;
                 description "UDP ports reflecting TWAMP light test packets";
                 type union {
                   type uint16;
                   type string {
                     pattern "<.*>|$.*";
                   }
                 }
                 max-elements 1000;
               }
             }
           }
         }
       }
       container screen {
         description "Configure screen feature";
         uses apply-advanced;
         container trap {
           presence "enable trap";
           description "Configure trap interval";
           leaf interval {
             description "Trap interval";
             default "2";
             units "seconds";
             type union {
               type string {
                 pattern "<.*>|$.*";
               }
               type uint32 {
                 range "1 .. 3600";
               }
             }
           }
         }
         container cpu-throttle {
           presence "enable cpu-throttle";
           description "Configure cpu-throttle percentage";
           uses apply-advanced;
           leaf percentage {
             description "Percentage of cpu throttle";
             units "percentage";
             type union {
               type string {
                 pattern "<.*>|$.*";
               }
               type uint32 {
                 range "1 .. 100";
               }
             }
           }
         }
         list ids-option {
           key name;
           description "Configure ids-option";
           uses ids-option-type;
         }
         container traceoptions {
           description "Trace options for Network Security Screen";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
         list whitelist {
           key name;
           description "Set of IP addresses for white list";
           max-elements 32;
           uses ids-wlist-type;
         }
       }
       container icap-redirect {
         description "Configure ICAP redirection service";
         uses apply-advanced;
         list profile {
           key name;
           ordered-by user;
           description "Congifure ICAP service profile";
           uses icap-profile-object;
         }
         container traceoptions {
           description "ICAP redirect trace options";
           uses icap-redirect-traceoptions;
         }
       }
       container security-metadata-streaming {
         uses apply-advanced;
         list policy {
           key name;
           description "Security Metadata Streaming policy";
           leaf name {
             description "Policy name";
             type string {
               length "1 .. 63";
             }
           }
           uses apply-advanced;
           container dynamic-filter {
             presence "enable dynamic-filter";
             description "Configure dynamic filtering options";
           }
           container http {
             description "Configure HTTP options";
             uses apply-advanced;
             leaf action {
               description "Action for HTTP";
               status deprecated;
               type enumeration {
                 enum "permit" {
                   description "Allow traffic";
                   status deprecated;
                 }
               }
             }
             container notification {
               description "Notification action taken for traffic";
               status deprecated;
               uses apply-advanced;
               leaf log {
                 description "Logging option for Security Metadata Streaming actions";
                 type empty;
               }
             }
             container detections {
               description "Type of Detection Methods for DNS Request";
               uses apply-advanced;
               container encryptedc2 {
                 description "Detection on the HTTPS";
                 uses apply-advanced;
                 leaf action {
                   description " Action to take on the HTTPS packet";
                   type enumeration {
                     enum "permit" {
                       description "Allow traffic";
                     }
                   }
                 }
                 leaf notification {
                   description "Notification action taken for traffic";
                   type enumeration {
                     enum "log" {
                       description "Log Everything";
                     }
                     enum "log-detections" {
                       description "Log only Macilious HTTP detections";
                     }
                   }
                 }
                 container fallback-options {
                   description "Fallback options for encryptedc2 detection";
                   uses apply-advanced;
                   container notification {
                     description "Notification action taken for the packet";
                     uses apply-advanced;
                     leaf log {
                       description "Log HTTP Request";
                       type empty;
                     }
                   }
                 }
               }
               container all {
                 description "All Detections";
                 uses apply-advanced;
                 leaf action {
                   description "Action for HTTP";
                   type enumeration {
                     enum "permit" {
                       description "Allow traffic";
                     }
                   }
                 }
                 leaf notification {
                   description "Notification action taken for traffic";
                   type enumeration {
                     enum "log" {
                       description "Log Everything";
                     }
                     enum "log-detections" {
                       description "Log only Macilious HTTP detections";
                     }
                   }
                 }
                 container fallback-options {
                   description "Fallback options for the encryptedc2 detection";
                   uses apply-advanced;
                   container notification {
                     description "Notification action taken for the packet";
                     uses apply-advanced;
                     leaf log {
                       description "Log HTTP Request";
                       type empty;
                     }
                   }
                 }
               }
             }
           }
           container dns {
             description "Configure DNS options";
             uses apply-advanced;
             container cache {
               description "Storing DNS in Cache till TTL";
               uses apply-advanced;
               container ttl {
                 presence "enable ttl";
                 description "For setting TTL values";
                 uses apply-advanced;
                 leaf benign {
                   description "Set Benign TTL value";
                   default "86400";
                   units "seconds";
                   type union {
                     type string {
                       pattern "<.*>|$.*";
                     }
                     type uint32 {
                       range "60 .. 172800";
                     }
                   }
                 }
                 leaf c2 {
                   description "Set C2 TTL value";
                   default "86400";
                   units "seconds";
                   type union {
                     type string {
                       pattern "<.*>|$.*";
                     }
                     type uint32 {
                       range "60 .. 172800";
                     }
                   }
                 }
               }
             }
             container detections {
               description "Type of Detection Methods for DNS Request";
               uses apply-advanced;
               container dga {
                 description "Detecting DGA Algorithms on DNS Packets";
                 uses apply-advanced;
                 leaf action {
                   description "Action to take on the DNS tunneled packet";
                   type enumeration {
                     enum "permit" {
                       description "Allow the packet";
                     }
                     enum "deny" {
                       description "Drop the packet";
                     }
                     enum "sinkhole" {
                       description "Sinkhole the packet";
                     }
                   }
                 }
                 leaf verdict-timeout {
                   description "Time to wait for a verdict on DNS Packet";
                   default "100";
                   units "milliseconds";
                   type union {
                     type string {
                       pattern "<.*>|$.*";
                     }
                     type uint32 {
                       range "50 .. 500";
                     }
                   }
                 }
                 leaf notification {
                   description "Notification action taken for DNS DGA Detection";
                   type enumeration {
                     enum "log" {
                       description "Log Everything";
                     }
                     enum "log-detections" {
                       description "Only log malicious DNS activity";
                     }
                   }
                 }
                 container fallback-options {
                   description "Fallback options for DNS DGA detection";
                   uses apply-advanced;
                   container notification {
                     description "Notification action taken for the packet";
                     uses apply-advanced;
                     leaf log {
                       description "Log DNS Request";
                       type empty;
                     }
                   }
                 }
               }
               container tunneling {
                 description "Detecting DNS Tunneling";
                 uses apply-advanced;
                 leaf action {
                   description " Action to take on the DNS tunneled packet";
                   type enumeration {
                     enum "permit" {
                       description "Allow the packet";
                     }
                     enum "deny" {
                       description "Drop the packet";
                     }
                     enum "sinkhole" {
                       description "Sinkhole the packet";
                     }
                   }
                 }
                 leaf notification {
                   description "Notification action taken for DNS Tunneling Detection";
                   type enumeration {
                     enum "log" {
                       description "Log Everything";
                     }
                     enum "log-detections" {
                       description "Only log malicious DNS activity";
                     }
                   }
                 }
                 leaf inspection-depth {
                   description "Number of packets to be inspected for Tunnel Detection";
                   default "4";
                   type union {
                     type string {
                       pattern "<.*>|$.*";
                     }
                     type uint8 {
                       range "0 .. 10";
                     }
                   }
                 }
                 container fallback-options {
                   description "Fallback options for DNS Tunneling detection";
                   uses apply-advanced;
                   container notification {
                     description "Notification action taken for the packet";
                     uses apply-advanced;
                     leaf log {
                       description "Log DNS Request";
                       type empty;
                     }
                   }
                 }
               }
               container all {
                 description "All Detections";
                 uses apply-advanced;
                 leaf action {
                   description " Global Action to take on the DNS packet";
                   type enumeration {
                     enum "permit" {
                       description "Allow the packet";
                     }
                     enum "deny" {
                       description "Drop the packet";
                     }
                     enum "sinkhole" {
                       description "Sinkhole the packet";
                     }
                   }
                 }
                 leaf notification {
                   description "Global Notification action taken for DNS Detection Methods";
                   type enumeration {
                     enum "log" {
                       description "Log Everything";
                     }
                     enum "log-detections" {
                       description "Only log malicious DNS activity";
                     }
                   }
                 }
                 container fallback-options {
                   description "Fallback options for DNS detections";
                   uses apply-advanced;
                   container notification {
                     description "Notification action taken for the packet";
                     uses apply-advanced;
                     leaf log {
                       description "Log DNS Request";
                       type empty;
                     }
                   }
                 }
               }
             }
           }
         }
         container dns-cache {
           description "Storing DNS-Cache user configured lists";
           uses apply-advanced;
           container custom-list {
             description "For setting TTL values";
             uses apply-advanced;
             leaf-list benign {
               description "Set Benign Persistent domains";
               type string {
                 length "1 .. 255";
               }
               max-elements 500;
             }
             leaf-list c2 {
               description "Set C2 Persistent domains";
               type string {
                 length "1 .. 255";
               }
               max-elements 500;
             }
           }
         }
       }
       container anti-virus {
         uses apply-advanced;
         container update {
           description "Anti-virus package download and install options";
           uses apply-advanced;
           leaf url {
             description "HTTP/HTTPS URL of Anti-virus package download";
             type string;
           }
           leaf proxy-profile {
             description "Proxy profile";
             type string {
               length "1 .. 63";
             }
           }
           container automatic {
             description "Scheduled download and install";
             uses apply-advanced;
             leaf interval {
               description "Interval in minutes";
               default "5";
               type union {
                 type string {
                   pattern "<.*>|$.*";
                 }
                 type uint32 {
                   range "5 .. 60";
                 }
               }
             }
             container off {
               presence "enable off";
               description "Disable automatic Anti-virus download and install";
             }
           }
         }
         container machine-learning-scan {
           description "Machine learning scan engine settings";
           uses apply-advanced;
           leaf max-concurrent {
             description "Max files concurrent scanned by machine learning scan";
             type union {
               type string {
                 pattern "<.*>|$.*";
               }
               type uint32 {
                 range "10 .. 1000";
               }
             }
           }
         }
         list policy {
           key name;
           description "Anti-virus policy";
           leaf name {
             description "Policy name";
             type string {
               length "1 .. 63";
             }
           }
           uses apply-advanced;
           leaf action {
             description "Action taken when file meets verdict threshold";
             type enumeration {
               enum "permit" {
                 description "Allow contents";
               }
               enum "block" {
                 description "Disallow contents";
               }
             }
           }
           container default-notification {
             description "Notification log when file not meets verdict threshold";
             uses apply-advanced;
             leaf log {
               description "Logging option for anti-virus action";
               type empty;
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Anti-virus fallback action";
                 type empty;
               }
             }
             container invalid-content-size {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Anti-virus fallback action";
                   type empty;
                 }
               }
             }
             container out-of-resources {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Anti-virus fallback action";
                   type empty;
                 }
               }
             }
             container service-not-ready {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Anti-virus fallback action";
                   type empty;
                 }
               }
             }
           }
           container http-client-notify {
             description "Notification action taken for contents with verdict meet threshold";
             uses apply-advanced;
             choice http-choice {
               case case_1 {
                 leaf file {
                   description "File name for http response to client";
                   type string {
                     length "1 .. 255";
                   }
                 }
               }
               case case_2 {
                 leaf message {
                   description "Block message to client";
                   type string {
                     length "1 .. 1023";
                   }
                 }
               }
               case case_3 {
                 leaf redirect-url {
                   description "Redirect url to client";
                   type string {
                     length "1 .. 1023";
                   }
                 }
               }
             }
           }
           container notification {
             description "Notification action taken for contents with verdict meet threshold";
             uses apply-advanced;
             leaf log {
               description "Logging option for Anti-virus actions";
               type empty;
             }
           }
           container machine-learning-scan {
             description "Configure machine learning scan options";
             uses apply-advanced;
             leaf action {
               description "Action when malware is found by machine learning scan";
               type enumeration {
                 enum "permit" {
                   description "Allow contents";
                 }
                 enum "block" {
                   description "Disallow contents";
                 }
               }
             }
             container notification {
               description "Notification when malware is found by machine learning scan";
               uses apply-advanced;
               leaf log {
                 description "Logging option for machine learning malware scan actions";
                 type empty;
               }
             }
             container default-notification {
               description "Notification action taken for action";
               uses apply-advanced;
               leaf log {
                 description "Logging option for machine learning scan action";
                 type empty;
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
             }
           }
         }
         container default-policy {
           presence "enable default-policy";
           description "Anti-virus default policy";
           uses apply-advanced;
           leaf action {
             description "Action taken when file meets verdict threshold";
             type enumeration {
               enum "permit" {
                 description "Allow contents";
               }
               enum "block" {
                 description "Disallow contents";
               }
             }
           }
           container default-notification {
             description "Notification log when file not meets verdict threshold";
             uses apply-advanced;
             leaf log {
               description "Logging option for anti-virus action";
               type empty;
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Anti-virus fallback action";
                 type empty;
               }
             }
             container invalid-content-size {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Anti-virus fallback action";
                   type empty;
                 }
               }
             }
             container out-of-resources {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Anti-virus fallback action";
                   type empty;
                 }
               }
             }
             container service-not-ready {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Anti-virus fallback action";
                   type empty;
                 }
               }
             }
           }
           container http-client-notify {
             description "Notification action taken for contents with verdict meet threshold";
             uses apply-advanced;
             choice http-choice {
               case case_1 {
                 leaf file {
                   description "File name for http response to client";
                   type string {
                     length "1 .. 255";
                   }
                 }
               }
               case case_2 {
                 leaf message {
                   description "Block message to client";
                   type string {
                     length "1 .. 1023";
                   }
                 }
               }
               case case_3 {
                 leaf redirect-url {
                   description "Redirect url to client";
                   type string {
                     length "1 .. 1023";
                   }
                 }
               }
             }
           }
           container notification {
             description "Notification action taken for contents with verdict meet threshold";
             uses apply-advanced;
             leaf log {
               description "Logging option for Anti-virus actions";
               type empty;
             }
           }
           container machine-learning-scan {
             description "Configure machine learning scan options";
             uses apply-advanced;
             leaf action {
               description "Action when malware is found by machine learning scan";
               type enumeration {
                 enum "permit" {
                   description "Allow contents";
                 }
                 enum "block" {
                   description "Disallow contents";
                 }
               }
             }
             container notification {
               description "Notification when malware is found by machine learning scan";
               uses apply-advanced;
               leaf log {
                 description "Logging option for machine learning malware scan actions";
                 type empty;
               }
             }
             container default-notification {
               description "Notification action taken for action";
               uses apply-advanced;
               leaf log {
                 description "Logging option for machine learning scan action";
                 type empty;
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
             }
           }
         }
         container traceoptions {
           description "Anti-virus trace options";
           uses antivirus-traceoptions;
         }
       }
       container user-identification {
         description "Configure user-identification";
         uses apply-advanced;
         container fwauth {
           presence "enable fwauth";
           description "Configure userid fwauth interaction options";
           uses apply-advanced;
           container traceoptions {
             description "Userid fwauth interaction tracing options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "userid-fwauth-group" {
                     description "Trace userid fwauth group opertaions";
                   }
                   enum "userid-fwauth-db" {
                     description "Trace userid fwauth db opertaions";
                   }
                   enum "userid-fwauth-config" {
                     description "Trace userid fwauth config read opertaions";
                   }
                   enum "userid-fwauth-ut" {
                     description "Trace userid fwauth unit test opertaions";
                   }
                   enum "userid-fwauth-all" {
                     description "Trace userid fwauth all opertaions";
                   }
                 }
               }
             }
           }
         }
         container active-directory-access {
           presence "enable active-directory-access";
           description "Configure active directory access";
           uses apply-advanced;
           container traceoptions {
             description "Active-directory-access Tracing Options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "active-directory-authentication" {
                     description "Trace active directory auth";
                   }
                   enum "configuration" {
                     description "Trace configuration";
                   }
                   enum "db" {
                     description "Trace db";
                   }
                   enum "ip-user-mapping" {
                     description "Trace ip-user-mapping module";
                   }
                   enum "ip-user-probe" {
                     description "Trace ip-user-probe";
                   }
                   enum "ipc" {
                     description "Trace ipc";
                   }
                   enum "user-group-mapping" {
                     description "Trace user-group-mapping module";
                   }
                   enum "wmic" {
                     description "Trace wmic";
                   }
                   enum "memory" {
                     description "Trace memory";
                   }
                   enum "all" {
                     description "Trace everything";
                   }
                 }
               }
             }
           }
           list domain {
             key name;
             ordered-by user;
             description "Configure active-directory-access domain";
             max-elements 2;
             leaf name {
               description "Domain name";
               type string {
                 length "1 .. 64";
               }
             }
             uses apply-advanced;
             container user {
               description "User name";
               uses apply-advanced;
               leaf user-name {
                 description "User name";
                 type string {
                   length "1 .. 64";
                 }
               }
               leaf password {
                 description "Password string";
                 type string {
                   length "1 .. 128";
                 }
               }
             }
             list domain-controller {
               key name;
               ordered-by user;
               description "Domain controller";
               max-elements 10;
               leaf name {
                 description "Domain controller name";
                 type string {
                   length "1 .. 64";
                 }
               }
               uses apply-advanced;
               leaf address {
                 description "Address of domain controller";
                 type jt:ipaddr;
               }
             }
             container ip-user-mapping {
               description "Ip-user-mapping";
               uses apply-advanced;
               container discovery-method {
                 description "Discovery method";
                 uses apply-advanced;
                 container wmi {
                   presence "enable wmi";
                   description "WMI";
                   uses apply-advanced;
                   leaf event-log-scanning-interval {
                     description "Interval of event log scanning";
                     units "seconds";
                     type union {
                       type string {
                         pattern "<.*>|$.*";
                       }
                       type uint16 {
                         range "5 .. 60";
                       }
                     }
                   }
                   leaf initial-event-log-timespan {
                     description "Event log scanning timespan";
                     units "hours";
                     type union {
                       type string {
                         pattern "<.*>|$.*";
                       }
                       type uint16 {
                         range "1 .. 168";
                       }
                     }
                   }
                 }
               }
             }
             container user-group-mapping {
               description "User-group-mapping";
               uses user-group-mapping-type;
             }
           }
           leaf no-on-demand-probe {
             description "Disable on-demand probe";
             type empty;
           }
           leaf authentication-entry-timeout {
             description "Authentication entry timeout number (0, 10-1440)";
             units "minutes";
             type union {
               type uint16;
               type string {
                 pattern "<.*>|$.*";
               }
             }
           }
           leaf invalid-authentication-entry-timeout {
             description "Invalid authentication entry timeout number (0, 10-1440)";
             units "minutes";
             type union {
               type uint16;
               type string {
                 pattern "<.*>|$.*";
               }
             }
           }
           leaf firewall-authentication-forced-timeout {
             description "Firewallauth fallback authentication entry forced timeout number (10-1440)";
             units "minutes";
             type union {
               type uint16;
               type string {
                 pattern "<.*>|$.*";
               }
             }
           }
           leaf wmi-timeout {
             description "Wmi timeout number";
             units "seconds";
             type union {
               type string {
                 pattern "<.*>|$.*";
               }
               type uint32 {
                 range "3 .. 120";
               }
             }
           }
           leaf thread {
             description "Thread to do PC probe";
             type union {
               type string {
                 pattern "<.*>|$.*";
               }
               type uint16 {
                 range "1 .. 100";
               }
             }
           }
           leaf probe-rate {
             description "PC probe rate per minute";
             type union {
               type string {
                 pattern "<.*>|$.*";
               }
               type uint32 {
                 range "100 .. 1500";
               }
             }
           }
           leaf-list event-log-identifier {
             ordered-by user;
             description "Event log identifier";
             type union {
               type uint16;
               type string {
                 pattern "<.*>|$.*";
               }
             }
           }
           leaf-list logon-type {
             ordered-by user;
             description "Logon type";
             type union {
               type uint16;
               type string {
                 pattern "<.*>|$.*";
               }
             }
           }
           container filter {
             description "Configure filter address or prefix";
             uses apply-advanced;
             list include {
               key name;
               ordered-by user;
               description "Include address";
               max-elements 20;
               leaf name {
                 description "Address or prefix";
                 type jt:ipprefix;
               }
             }
             list exclude {
               key name;
               ordered-by user;
               description "Exclude address";
               max-elements 20;
               leaf name {
                 description "Address or prefix";
                 type jt:ipprefix;
               }
             }
           }
         }
         list authentication-source {
           key name;
           ordered-by user;
           description "Configure authentication-source";
           max-elements 2;
           leaf name {
             description "Authenticaton source name";
             type enumeration {
               enum "aruba-clearpass" {
                 description "Authentication source from Aruba ClearPass";
               }
             }
           }
           uses apply-advanced;
           leaf authentication-entry-timeout {
             description "Aruba ClearPass authentication entry timeout number (0, 10-1440)";
             units "minutes";
             type union {
               type uint16;
               type string {
                 pattern "<.*>|$.*";
               }
             }
           }
           leaf invalid-authentication-entry-timeout {
             description "Invalid authentication entry timeout number (0, 10-1440)";
             units "minutes";
             type union {
               type uint16;
               type string {
                 pattern "<.*>|$.*";
               }
             }
           }
           container traceoptions {
             description "Aruba ClearPass authentication table Tracing Options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace Aruba ClearPass all modules";
                   }
                   enum "clearpass-authentication" {
                     description "Trace Aruba ClearPass auth table management module";
                   }
                   enum "configuration" {
                     description "Trace Aruba ClearPass configuration";
                   }
                   enum "dispatcher" {
                     description "Trace dispatcher module";
                   }
                   enum "ipc" {
                     description "Trace ipc";
                   }
                   enum "user-query" {
                     description "Trace user-query module";
                   }
                   enum "memory" {
                     description "Trace memory";
                   }
                 }
               }
             }
           }
           container user-query {
             description "ClearPass individual user query";
             uses apply-advanced;
             container web-server {
               description "Web server for user query";
               uses apply-advanced;
               leaf server-name {
                 description "Web server name";
                 type string {
                   length "1 .. 64";
                 }
               }
               leaf connect-method {
                 description "Method of connecting to web server";
                 type enumeration {
                   enum "https" {
                     description "HTTPS connection to web server";
                   }
                   enum "http" {
                     description "HTTP connection to web server";
                   }
                 }
               }
               leaf address {
                 description "IP address or hostname of web server";
                 type string {
                   length "1 .. 128";
                 }
               }
               leaf port {
                 description "Web server port";
                 default "443";
                 type union {
                   type string {
                     pattern "<.*>|$.*";
                   }
                   type uint32 {
                     range "1 .. 65535";
                   }
                 }
               }
             }
             leaf ca-certificate {
               description "Ca-certificate file name";
               type string {
                 length "1 .. 256";
               }
             }
             leaf client-id {
               description "Client ID for OAuth2 grant";
               type string {
                 length "1 .. 64";
               }
             }
             leaf client-secret {
               description "Client secret for OAuth2 grant";
               type string {
                 length "1 .. 128";
               }
             }
             leaf token-api {
               description "API of acquiring token for OAuth2 authentication";
               type string {
                 length "1 .. 128";
               }
             }
             leaf query-api {
               description "User query API";
               type string {
                 length "4 .. 128";
               }
             }
             leaf delay-query-time {
               description "Delay time to send user query (0~60sec)";
               default "15";
               units "seconds";
               type union {
                 type string {
                   pattern "<.*>|$.*";
                 }
                 type uint8 {
                   range "0 .. 60";
                 }
               }
             }
           }
           container no-user-query {
             presence "enable no-user-query";
             description "Disable user query from ClearPass";
           }
         }
         container device-information {
           description "Device information configuration";
           uses apply-advanced;
           container authentication-source {
             description "Configure authentication-source";
             uses apply-advanced;
             leaf authentication-source-name {
               default "no-configured";
               type enumeration {
                 enum "active-directory" {
                   description "From windows active directory";
                 }
                 enum "network-access-controller" {
                   description "From network access controller such as Aruba ClearPass or JIMS";
                 }
                 enum "no-configured" {
                   description "No configuring authentication source for device entry";
                 }
               }
             }
           }
           container end-user-profile {
             description "End-user-profile configuration";
             uses apply-advanced;
             list profile-name {
               key name;
               ordered-by user;
               description "End-user-profile profile-name configuration";
               leaf name {
                 description "End-user-profile profile-name";
                 type string {
                   length "1 .. 64";
                 }
               }
               uses apply-advanced;
               leaf domain-name {
                 description "Domain name";
                 type string {
                   length "1 .. 64";
                 }
               }
               list attribute {
                 key name;
                 ordered-by user;
                 description "Attribute";
                 leaf name {
                   description "Attribute name";
                   type string;
                 }
                 uses apply-advanced;
                 choice attribute-value {
                   case case_1 {
                     leaf-list string {
                       ordered-by user;
                       description "Value type is strings";
                       type string;
                       max-elements 20;
                     }
                   }
                   case case_2 {
                     container digital {
                       presence "enable digital";
                       description "Value type is digital";
                       uses apply-advanced;
                       leaf-list value {
                         ordered-by user;
                         description "Digital value";
                         type union {
                           type uint32;
                           type string {
                             pattern "<.*>|$.*";
                           }
                         }
                       }
                       list from {
                         key name;
                         ordered-by user;
                         description "Range of digital value";
                         leaf name {
                           description "Digit range's start value";
                           type union {
                             type uint32;
                             type string {
                               pattern "<.*>|$.*";
                             }
                           }
                         }
                         uses apply-advanced;
                         leaf to {
                           description "Digit range's end value";
                           type union {
                             type uint32;
                             type string {
                               pattern "<.*>|$.*";
                             }
                           }
                         }
                       }
                     }
                   }
                 }
               }
             }
           }
           container identity-context-profile {
             description "Identity-context-profile configuration";
             uses apply-advanced;
             list profile-name {
               key name;
               ordered-by user;
               description "Identity-context-profile profile-name configuration";
               leaf name {
                 description "Identity-context-profile profile-name";
                 type string {
                   length "1 .. 64";
                 }
               }
               uses apply-advanced;
               leaf domain-name {
                 description "Domain name";
                 type string {
                   length "1 .. 64";
                 }
               }
               list attribute {
                 key name;
                 ordered-by user;
                 description "Attribute";
                 leaf name {
                   description "Attribute name";
                   type string;
                 }
                 uses apply-advanced;
                 choice attribute-value {
                   case case_1 {
                     leaf-list string {
                       ordered-by user;
                       description "Value type is strings";
                       type string;
                       max-elements 20;
                     }
                   }
                   case case_2 {
                     container digital {
                       presence "enable digital";
                       description "Value type is digital";
                       uses apply-advanced;
                       leaf-list value {
                         ordered-by user;
                         description "Digital value";
                         type union {
                           type uint32;
                           type string {
                             pattern "<.*>|$.*";
                           }
                         }
                       }
                       list from {
                         key name;
                         ordered-by user;
                         description "Range of digital value";
                         leaf name {
                           description "Digit range's start value";
                           type union {
                             type uint32;
                             type string {
                               pattern "<.*>|$.*";
                             }
                           }
                         }
                         uses apply-advanced;
                         leaf to {
                           description "Digit range's end value";
                           type union {
                             type uint32;
                             type string {
                               pattern "<.*>|$.*";
                             }
                           }
                         }
                       }
                     }
                   }
                 }
               }
             }
           }
           container traceoptions {
             description "Device info related Tracing Options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace device info all modules";
                   }
                   enum "auth-source" {
                     description "Trace Auth source module";
                   }
                   enum "configuration" {
                     description "Trace Device info configuration";
                   }
                   enum "device-table" {
                     description "Trace device table management module";
                   }
                   enum "ipid-all" {
                     description "Trace IPID all functions";
                   }
                   enum "ipid-db" {
                     description "Trace IPID Database function";
                   }
                   enum "ipid-entry" {
                     description "Trace IPID entry management function";
                   }
                   enum "ipid-ipc" {
                     description "Trace IPID communication processing function";
                   }
                   enum "ipid-message" {
                     description "Trace IPID message processing function";
                   }
                   enum "ipid-others" {
                     description "Trace IPID other function";
                   }
                   enum "ipid-server" {
                     description "Trace IPID server handling function";
                   }
                   enum "ipid-statistics" {
                     description "Trace IPID statistics handling function";
                   }
                   enum "ipid-task" {
                     description "Trace IPID task handling function";
                   }
                   enum "profile-lookup" {
                     description "Trace End-user-profile lookup function";
                   }
                   enum "memory" {
                     description "Trace memory";
                   }
                 }
               }
             }
           }
         }
         container identity-management {
           description "Identity management configuration";
           uses apply-advanced;
           leaf authentication-entry-timeout {
             description "Authentication entry timeout number (0, 10-1440)";
             default "60";
             units "minutes";
             type union {
               type uint16;
               type string {
                 pattern "<.*>|$.*";
               }
             }
           }
           leaf invalid-authentication-entry-timeout {
             description "Invalid authentication entry timeout number (0, 10-1440)";
             default "30";
             units "minutes";
             type union {
               type uint16;
               type string {
                 pattern "<.*>|$.*";
               }
             }
           }
           leaf preserve-valid-user {
             description "Null user will not overwrite valid user for the same ip";
             type empty;
           }
           container connection {
             description "Connection to identity management";
             uses identity-management-connection-type;
           }
           container jims-validator {
             description "Web server from JIMS for Validate or group query request";
             uses jims-validator-type;
           }
           container batch-query {
             description "Batch query parameters";
             uses batch-query-type;
           }
           container ip-query {
             description "IP query parameters";
             uses apply-advanced;
             leaf query-delay-time {
               description "Delay time to send IP query (0~60sec)";
               default "15";
               units "seconds";
               type union {
                 type string {
                   pattern "<.*>|$.*";
                 }
                 type uint8 {
                   range "0 .. 60";
                 }
               }
             }
             container no-ip-query {
               presence "enable no-ip-query";
               description "Disable IP query";
             }
             leaf max-connections {
               description "Max connection number";
               type union {
                 type string {
                   pattern "<.*>|$.*";
                 }
                 type uint32 {
                   range "1 .. 20";
                 }
               }
             }
           }
           container filter {
             description "Filter for query";
             uses apply-advanced;
             list domain {
               key name;
               ordered-by user;
               description "Domain filter";
               max-elements 20;
               leaf name {
                 description "Domain name";
                 type string {
                   length "1 .. 64";
                 }
               }
             }
             container include-ip {
               description "Include IP filter";
               uses address-filter-type;
             }
             container exclude-ip {
               description "Exclude IP filter";
               uses address-filter-type;
             }
           }
           container traceoptions {
             description "Tracing Options";
             uses ims-traceoptions-type;
           }
           container session-batch-query {
             description "Session batch query parameters";
             uses apply-advanced;
             leaf items-per-batch {
               description "Items number per batch query";
               default "200";
               type union {
                 type string {
                   pattern "<.*>|$.*";
                 }
                 type uint32 {
                   range "100 .. 1000";
                 }
               }
             }
             leaf query-interval {
               description "Query interval";
               default "5";
               units "seconds";
               type union {
                 type string {
                   pattern "<.*>|$.*";
                 }
                 type uint32 {
                   range "1 .. 60";
                 }
               }
             }
           }
           container session-query {
             description "Session query parameters";
             uses apply-advanced;
             leaf query-delay-time {
               description "Delay time to send session query (0~60sec)";
               default "15";
               units "seconds";
               type union {
                 type string {
                   pattern "<.*>|$.*";
                 }
                 type uint8 {
                   range "0 .. 60";
                 }
               }
             }
             container no-session-query {
               presence "enable no-session-query";
               description "Disable session query";
             }
             leaf max-connections {
               description "Session query configuration";
               type union {
                 type string {
                   pattern "<.*>|$.*";
                 }
                 type uint32 {
                   range "1 .. 20";
                 }
               }
             }
           }
         }
         container logical-domain-identity-management {
           description "Logical domain identity management configuration";
           uses apply-advanced;
           container active {
             description "Actve mode for logical domain identity management moudule";
             uses apply-advanced;
             leaf authentication-entry-timeout {
               description "Authentication entry timeout number (0, 10-1440)";
               default "60";
               units "minutes";
               type union {
                 type uint16;
                 type string {
                   pattern "<.*>|$.*";
                 }
               }
             }
             leaf invalid-authentication-entry-timeout {
               description "Invalid authentication entry timeout number (0, 10-1440)";
               default "30";
               units "minutes";
               type union {
                 type uint16;
                 type string {
                   pattern "<.*>|$.*";
                 }
               }
             }
             container ip-query {
               description "IP query parameters";
               uses apply-advanced;
               leaf query-delay-time {
                 description "Delay time to send IP query (0~60sec)";
                 default "15";
                 units "seconds";
                 type union {
                   type string {
                     pattern "<.*>|$.*";
                   }
                   type uint8 {
                     range "0 .. 60";
                   }
                 }
               }
             }
             container filter {
               description "Filter for query";
               uses apply-advanced;
               list domain {
                 key name;
                 ordered-by user;
                 description "Domain filter";
                 max-elements 20;
                 leaf name {
                   description "Domain name";
                   type string {
                     length "1 .. 64";
                   }
                 }
               }
               container include-ip {
                 description "Include IP filter";
                 uses address-filter-type;
               }
               container exclude-ip {
                 description "Exclude IP filter";
                 uses address-filter-type;
               }
             }
             list query-server {
               key name;
               ordered-by user;
               description "Query server";
               max-elements 1;
               leaf name {
                 description "Query server name";
                 type string {
                   length "1 .. 64";
                 }
               }
               uses apply-advanced;
               container connection {
                 description "Connection to identity management";
                 uses ims-connection-type;
               }
               container batch-query {
                 description "Batch query parameters";
                 uses batch-query-type;
               }
             }
           }
           container traceoptions {
             description "Tracing Options";
             uses ims-traceoptions-type;
           }
         }
         leaf lookup-inline {
           description "Configure First session lookup";
           type empty;
         }
         container captive-portal {
           description "Captive Portal configuration";
           uses apply-advanced;
           list profile {
             key name;
             ordered-by user;
             description "Captive portal profile";
             leaf name {
               description "Captive portal profile name";
               type string {
                 length "1 .. 64";
               }
             }
             uses apply-advanced;
             leaf redirect-url {
               description "Captive portal redirect url";
               type string {
                 length "1 .. 256";
               }
             }
             leaf default-profile {
               description "Enable captive portal default profile";
               type empty;
             }
           }
           container connection {
             description "Captive Portal connection";
             uses apply-advanced;
             leaf cloud-certificate-profile {
               description "Cloud certificate profile to use with this connection";
               type string;
             }
           }
         }
       }
       container ip-monitoring {
         description "IP monitoring for route action";
         uses apply-advanced;
         list policy {
           key name;
           ordered-by user;
           description "Policy for route action";
           leaf name {
             description "Policy name";
             type string {
               length "1 .. 64";
             }
           }
           uses apply-advanced;
           leaf no-preempt {
             description "No automatic failback preemption once policy failover";
             type empty;
           }
           container match {
             description "Matching probing condition";
             uses apply-advanced;
             leaf-list rpm-probe {
               ordered-by user;
               description "RPM probe name";
               type string;
             }
           }
           container then {
             description "Action to be taken";
             uses action-object-type;
           }
         }
         container traceoptions {
           description "IP-Monitoring trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "debug" {
                   description "Trace debug";
                 }
                 enum "configuration" {
                   description "Trace configuration events";
                 }
                 enum "errors" {
                   description "Trace errors";
                 }
                 enum "memory" {
                   description "Trace memory allocation or deallocation messages";
                 }
                 enum "event" {
                   description "Trace events";
                 }
                 enum "all" {
                   description "Trace events";
                 }
               }
             }
           }
         }
       }
       container wireless-wan {
         description "Wireless WAN configuration";
         uses apply-advanced;
         list adapter {
           key name;
           ordered-by user;
           description "Wireless adapter name configuration";
           leaf name {
             description "Wireless adapter name";
             type string {
               length "1 .. 16";
             }
           }
           uses apply-advanced;
           leaf ip-address {
             description "Adapter management IP address";
             type jt:ipaddr;
           }
           leaf adapter-type {
             description "Select adapter type";
             type enumeration {
               enum "cx-bridge" {
                 description "Adapter type - CX-bridge";
               }
             }
           }
           container modem {
             description "Adapter modem settings";
             uses apply-advanced;
             container usb1 {
               presence "enable usb1";
               description "Adapter USB1 modem name";
               uses apply-advanced;
               leaf description {
                 description "Text description for modem";
                 type string;
               }
             }
             container usb2 {
               presence "enable usb2";
               description "Adapter USB2 modem name";
               uses apply-advanced;
               leaf description {
                 description "Text description for modem";
                 type string;
               }
             }
             container usb3 {
               presence "enable usb3";
               description "Adapter USB3 modem name";
               uses apply-advanced;
               leaf description {
                 description "Text description for modem";
                 type string;
               }
             }
             container expresscard {
               presence "enable expresscard";
               description "Adapter Expresscard modem name";
               uses apply-advanced;
               leaf description {
                 description "Text description for modem";
                 type string;
               }
             }
           }
         }
       }
       container proxy {
         description "Proxy setting for services";
         uses apply-advanced;
         list profile {
           key name;
           ordered-by user;
           description "Proxy profile";
           uses proxy-profile-setting;
         }
       }
       container web-proxy {
         description "Configuration for Web Proxy service";
         uses apply-advanced;
         container traceoptions {
           description "Trace options for Web Proxy service";
           uses web-proxy-traceoptions;
         }
         container transparent-proxy {
           description "Configuration for transparent proxy profile ";
           uses web-config;
         }
         container explicit-proxy {
           description "Configuration for explicit proxy profile ";
           uses explicit-config;
         }
       }
       container security-intelligence {
         uses apply-advanced;
         container category {
           description "Category to be disabled";
           uses apply-advanced;
           container all {
             presence "enable all";
             description "All categories";
             uses apply-advanced;
             container disable {
               presence "enable disable";
               description "To disable all categories";
             }
           }
           list category-name {
             key name;
             ordered-by user;
             uses secintel-category-disable;
           }
         }
         leaf url {
           description "Configure the url of feed server [https://<ip or hostname>:<port>/<uri>]";
           type string;
         }
         leaf url-parameter {
           description "Configure the parameter of url";
           type jt:unreadable;
         }
         leaf proxy-profile {
           description "The proxy profile name";
           type string {
             length "1 .. 64";
           }
         }
         container authentication {
           description "Authenticate to use feed update services";
           uses apply-advanced;
           leaf auth-token {
             description "Token string for authentication";
             type string {
             }
           }
           leaf tls-profile {
             description "TLS profile";
             type string;
           }
         }
         leaf http-persist {
           description "Inspect all HTTP requests in a connection";
           type empty;
         }
         container traceoptions {
           description "Security intelligence trace options";
           uses secintel-traceoptions;
         }
         list profile {
           key name;
           ordered-by user;
           description "Configure security intelligence profile";
           uses secintel-profile-setting;
         }
         container default-policy {
           description "Configure security intelligence default policy";
           uses apply-advanced;
           list category-profiles {
             key name;
             ordered-by user;
             description "Security intelligence category profiles";
             leaf name {
               description "Name of security intelligence category";
               type enumeration {
                 enum "IPFilter" {
                   description "IPFilter";
                 }
                 enum "GeoIP" {
                   description "GeoIP";
                 }
                 enum "CC" {
                   description "Command and control";
                 }
                 enum "Infected-Hosts" {
                   description "Infected-Hosts";
                 }
                 enum "DNS" {
                   description "DNS";
                 }
               }
             }
             uses apply-advanced;
             leaf profile-name {
               description "Name of profile";
               type string;
             }
           }
         }
         list policy {
           key name;
           ordered-by user;
           description "Configure security intelligence policy";
           uses secintel-policy-setting;
         }
         container global-disable-feed {
           presence "enable global-disable-feed";
           description "Security intelligence global feed disabling setting";
           uses apply-advanced;
           list feed-name {
             key name;
             ordered-by user;
             max-elements 32;
             leaf name {
               description "Name of security intelligence global Command and control feed";
               type string {
                 length "1 .. 63";
               }
             }
             uses apply-advanced;
           }
           container all {
             presence "enable all";
             description "All of security intelligence global Command and control feed";
           }
         }
       }
       container dns-filtering {
         presence "enable dns-filtering";
         uses apply-advanced;
         container traceoptions {
           description "Security intelligence trace options";
           uses dnsf-traceoptions-object;
         }
         container sinkhole {
           presence "enable sinkhole";
           description "DNS Sinkhole Configuration";
           uses apply-advanced;
           leaf ipv4-address {
             description "Sinkhole IPv4 address";
             type jt:ipv4addr;
           }
           leaf ipv6-address {
             description "Sinkhole IPv6 address";
             type jt:ipv6addr;
           }
           leaf fqdn {
             description "FQDN sent as response to MX qeries";
             type string {
               length "1 .. 80";
             }
           }
           leaf dns-resp-ttl {
             description "TTL to be used in DNS response";
             default "1800";
             units "seconds";
             type union {
               type string {
                 pattern "<.*>|$.*";
               }
               type uint32 {
                 range "0 .. 3600";
               }
             }
           }
           leaf wildcarding-level {
             description "Wildcarding level for exact match";
             default "2";
             type union {
               type string {
                 pattern "<.*>|$.*";
               }
               type uint32 {
                 range "0 .. 10";
               }
             }
           }
           leaf txt-resp-err-code {
             description "Text response error code";
             default "Refused";
             type enumeration {
               enum "Noerror" {
                 description "No error response";
               }
               enum "Refused" {
                 description "Refuse the DNS Query";
               }
             }
           }
           leaf srv-resp-err-code {
             description "Server response error code";
             default "Refused";
             type enumeration {
               enum "Noerror" {
                 description "No error response";
               }
               enum "Refused" {
                 description "Refuse the DNS Query";
               }
             }
           }
         }
       }
       container trace {
         presence "enable trace";
         description "Enable tracing";
         uses apply-advanced;
         leaf evpn-vxlan {
           description "Enable evpn-vxlan tracing";
           type empty;
         }
       }
       container evpn {
         description "Auto-configuration for various layer2 features";
         uses apply-advanced;
         container traceoptions {
           description "Trace options for evpn services";
           uses apply-advanced;
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           container flag {
             description "Type of operation to be traced";
             uses apply-advanced;
             leaf input-configuration {
               description "Trace input configuration";
               type empty;
             }
             leaf chassis {
               description "Trace chassis configuration";
               type empty;
             }
             leaf interfaces {
               description "Trace interfaces configuration";
               type empty;
             }
             leaf routing-instance {
               description "Trace routing-instance configuration";
               type empty;
             }
             leaf routing-options {
               description "Trace routing-options configuration";
               type empty;
             }
             leaf policy-options {
               description "Trace policy-options configuration";
               type empty;
             }
             leaf protocols {
               description "Trace protocols configuration";
               type empty;
             }
             leaf forwarding-options {
               description "Trace forwarding-options configuration";
               type empty;
             }
             leaf all {
               description "Trace all generated configuration";
               type empty;
             }
           }
         }
         container defaults-override {
           description "Select configuration generation override";
           uses apply-advanced;
           leaf no-platform-defaults-config {
             description "Do not auto-derive platform specific configurations";
             type empty;
           }
           leaf no-aggregate-device-count-config {
             description "Do not auto-derive aggregated device count configurations";
             type empty;
           }
           leaf no-policy-and-routing-options-config {
             description "Do not auto-derive routing-options and policy-options configurations";
             type empty;
           }
           leaf no-loop-detect-config {
             description "Do not auto-derive loop-detect configurations";
             type empty;
           }
           leaf no-storm-control-config {
             description "Do not auto-derive loop-detect configurations";
             type empty;
           }
           leaf no-underlay-config {
             description "Do not auto-derive underlay configurations";
             type empty;
           }
           leaf no-overlay-bgp-config {
             description "Do not auto-derive BGP overlay configurations";
             type empty;
           }
         }
         container global-parameters {
           description "Global parameters";
           uses apply-advanced;
           leaf start-aggregate-ethernet-index {
             description "Start index for aggregate interfaces";
             type union {
               type string {
                 pattern "<.*>|$.*";
               }
               type uint32 {
                 range "1 .. 255";
               }
             }
           }
           leaf default-vlan-id {
             description "Vlan-id to be used as a default vlan-id";
             type string;
           }
           leaf anycast-mac {
             description "Configure anycast MAC address";
             type jt:mac-unicast;
           }
           container virtual-gateway {
             description "Configure virtual gateway MAC address";
             leaf v4-mac {
               description "Configure virtual gateway IPV4 virtual MAC address";
               type jt:mac-unicast;
             }
             leaf v6-mac {
               description "Configure virtual gateway IPV6 virtual MAC address";
               type jt:mac-unicast;
             }
           }
           leaf virtual-gateway-mac {
             description "Configure virtual gateway IPV4 virtual MAC address";
             type jt:mac-unicast;
           }
           leaf no-irb-address-auto-derive {
             description "Do not auto-dervie address and use the subnet address as is";
             type empty;
           }
           container mtu {
             description "Configure maximum transmission unit";
             leaf underlay {
               description "Configure maximum transmission unit for underlay interfaces";
               type union {
                 type uint32;
                 type string {
                   pattern "<.*>|$.*";
                 }
               }
             }
             leaf overlay {
               description "Configure maximum transmission unit for overlay interfaces";
               type union {
                 type uint32;
                 type string {
                   pattern "<.*>|$.*";
                 }
               }
             }
           }
         }
         container device-attribute {
           description "Device specific attributes";
           uses apply-advanced;
           leaf peer-id {
             description "Assign an id for each PEER device";
             type union {
               type string {
                 pattern "<.*>|$.*";
               }
               type uint32 {
                 range "1 .. 2";
               }
             }
           }
           choice loopback-choice {
             case case_1 {
               leaf loopback-subnet {
                 description "Ipv4 address prefix for loopback subnet";
                 status deprecated;
                 type jt:ipv4prefix;
               }
             }
             case case_2 {
               container loopback {
                 description "Ipv4 address prefix for loopback subnet";
                 uses apply-advanced;
                 choice peer1-subnet-choice {
                   case case_1 {
                     leaf peer1-subnet {
                       description "Ipv4 address prefix for peer1 loopback subnet";
                       type jt:ipv4prefix;
                     }
                   }
                 }
                 choice peer2-subnet-choice {
                   case case_1 {
                     leaf peer2-subnet {
                       description "Ipv4 address prefix for peer2 loopback subnet";
                       type jt:ipv4prefix;
                     }
                   }
                 }
               }
             }
           }
           leaf remote-peer-as {
             description " Autonomous system number in plain number or 'higher 16bits'.'Lower 16 bits' format";
             type string {
             }
           }
           leaf system-id {
             description "Node's System ID, encoded as a MAC address";
             type jt:mac-unicast;
           }
           container peer-to-peer {
             description "Interface between PEER to PEER";
             uses apply-advanced;
             container peer-subnet {
               description "PEER to PEER subnet";
               leaf inet {
                 description "IPv4 address prefix for aggregated-ethernet interface bundle";
                 type jt:ipv4prefix;
               }
               leaf inet6 {
                 description "IPv6 address prefix for aggregated-ethernet interface bundle";
                 type jt:ipv6prefix;
               }
               leaf-list interface-name {
                 description "Interface or list of peer to peer interfaces";
                 type union {
                   type jt:interface-device;
                   type string {
                     pattern "<.*>|$.*";
                   }
                 }
               }
             }
             container overlay-connectivity {
               uses apply-advanced;
               leaf ibgp {
                 description "Setup IBGP as OVERLAY";
                 type empty;
               }
             }
             container underlay-connectivity {
               uses apply-advanced;
               leaf ospf {
                 description "Setup OSPF as UNDERLAY";
                 type empty;
               }
             }
           }
         }
         container evpn-vxlan {
           description "EVPN VXLAN configurations";
           uses apply-advanced;
           list dhcp-relay {
             key name;
             description "Dynamic Host Configuration Protocol relay configuration";
             leaf name {
               description "Group name to identify a Server/Relay group";
               type string;
             }
             uses apply-advanced;
             leaf relay-source {
               description "Interface for relay source";
               type union {
                 type jt:interface-name;
                 type string {
                   pattern "<.*>|$.*";
                 }
               }
             }
             list dhcp-server-address {
               key name;
               description "IP Address of one or more DHCP servers";
               max-elements 32;
               leaf name {
                 description "IP Address of DHCP server";
                 type jt:ipaddr;
               }
               uses apply-advanced;
             }
             leaf vrf-instance {
               description "Identifier for VRF instance";
               type union {
                 type string {
                   pattern "<.*>|$.*";
                 }
                 type uint32 {
                   range "1 .. 255";
                 }
               }
             }
             leaf routing-instance {
               description "Name of the routing-instance from where server-group is reachable";
               type string {
               }
             }
           }
           list irb {
             key name;
             description "IRB settings";
             leaf name {
               description "IRB instance";
               type string {
               }
             }
             uses apply-advanced;
             leaf use-anycast-address {
               description "Use anycast address";
               type empty;
             }
             leaf no-dhcp-relay {
               description "Exclude this irb from dhcp-relay";
               type empty;
             }
             leaf vlan-id {
               description "IEEE 802.1q VLAN identifier for VLAN";
               type string;
             }
             container subnet-address {
               description "Subnet address";
               leaf-list inet {
                 description "Ipv4 subnet address";
                 type jt:ipv4prefix;
               }
               leaf virtual-gateway-v4-address {
                 description "Virtual Gateway IPv4 address";
                 type jt:ipv4addr;
               }
               leaf-list inet6 {
                 description "Ipv6 subnet address";
                 type jt:ipv6prefix;
               }
               leaf virtual-gateway-v6-address {
                 description "Virtual Gateway IPv6 address";
                 type jt:ipv6addr;
               }
               leaf no-irb-address-auto-derive {
                 description "Do not auto-dervie address and use the subnet address as is";
                 type empty;
               }
             }
             container instance {
               description "Specify mac-vrf-instance or vrf-instance instance";
               leaf vrf-instance {
                 description "VRF instance identifier";
                 type union {
                   type string {
                     pattern "<.*>|$.*";
                   }
                   type uint32 {
                     range "1 .. 255";
                   }
                 }
               }
               leaf mac-vrf-instance {
                 description "MAC-VRF instance identifier";
                 type union {
                   type string {
                     pattern "<.*>|$.*";
                   }
                   type uint32 {
                     range "1 .. 255";
                   }
                 }
               }
             }
             leaf apply-config-groups {
               description "Apply groups to the generated irb configuration";
               type string;
             }
           }
           list server {
             key name;
             description "Server configuration";
             leaf name {
               description "SERVER name";
               type string {
               }
             }
             uses apply-advanced;
             choice esi-lag-id-choice {
               case case_1 {
                 leaf esi-lag-id {
                   description "Assign an identifier for each server";
                   type union {
                     type string {
                       pattern "<.*>|$.*";
                     }
                     type uint32 {
                       range "1 .. 1024";
                     }
                   }
                 }
               }
               case case_2 {
                 leaf single-home-id {
                   description "Assign an identifier for a single home server";
                   type union {
                     type string {
                       pattern "<.*>|$.*";
                     }
                     type uint32 {
                       range "1 .. 1024";
                     }
                   }
                 }
               }
             }
             leaf-list vlan-id-list {
               description "Create VLAN for each of the vlan-id specified in the vlan-id-list";
               type jt:vlan-range;
             }
             list mac-vrf-instance {
               key name;
               description "MAC-VRF instance identifier";
               leaf name {
                 description "Instance identifier";
                 type union {
                   type string {
                     pattern "<.*>|$.*";
                   }
                   type uint32 {
                     range "1 .. 255";
                   }
                 }
               }
               uses apply-advanced;
               leaf-list vlan-id-list {
                 description "Create VLAN for each of the vlan-id specified in the vlan-id-list";
                 type jt:vlan-range;
               }
             }
             leaf-list interface {
               description "Interface or list of peer to server interfaces";
               type union {
                 type jt:interface-device;
                 type string {
                   pattern "<.*>|$.*";
                 }
               }
             }
             leaf enable-pxe-boot {
               description "Enable PXE boot";
               type empty;
             }
             leaf apply-config-groups {
               description "Apply groups to the generated interface configuration";
               type string;
             }
             leaf no-lacp {
               description "Do not configure LACP for this server";
               type empty;
             }
           }
         }
       }
       container inline-napt {
         presence "enable inline-napt";
         description "Inline-NAPT configuration";
         uses apply-advanced;
         container nat44 {
           presence "enable nat44";
           uses apply-advanced;
           choice enable-disable {
             case case_1 {
               leaf disable {
                 description "Disable NAT44 on this interface";
                 type empty;
               }
             }
           }
         }
         container nat64 {
           presence "enable nat64";
           uses apply-advanced;
           choice enable-disable {
             case case_1 {
               leaf disable {
                 description "Disable NAT64 on this interface";
                 type empty;
               }
             }
           }
         }
       }
       container pcp {
         description "Configure Port Control Protocol";
         uses pcp-object;
       }
       container rtlog {
         presence "enable rtlog";
         description "Secure log daemon options";
         uses apply-advanced;
         container traceoptions {
           description "Security log daemon trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "List of things to include in trace";
             leaf name {
               type enumeration {
                 enum "source" {
                   description "Communication with security log forwarder";
                 }
                 enum "configuration" {
                   description "Reading of configuration";
                 }
                 enum "all" {
                   description "Everything";
                 }
                 enum "report" {
                   description "Trace report";
                 }
                 enum "hpl" {
                   description "Trace HPL logging";
                 }
               }
             }
           }
         }
       }
       container service-interface-pools {
         description "Configure service interface pools";
         uses apply-advanced;
         list pool {
           key name;
           ordered-by user;
           description "Define service interface pool";
           uses service_interface_pool_object;
         }
       }
       container hosted-services {
         description "Configuration for services performed in the remote server";
         uses apply-advanced;
         list client-profile {
           key name;
           ordered-by user;
           description "Configure client profile";
           leaf name {
             description "Client profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf client-address {
             description "Client address";
             type jt:ipv4addr;
           }
           leaf hosted-service-identifier {
             description "Identifier for the service performed on the remote server";
             type union {
               type string {
                 pattern "<.*>|$.*";
               }
               type int32 {
                 range "1 .. 63";
               }
             }
           }
         }
         list server-profile {
           key name;
           ordered-by user;
           description "Configure server profile";
           leaf name {
             description "Server profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf server-address {
             description "Server address";
             type jt:ipv4addr;
           }
           leaf client-address {
             description "Client address";
             type jt:ipv4addr;
           }
           leaf hosted-service-identifier {
             description "Identifier for the service performed in the remote server";
             type union {
               type string {
                 pattern "<.*>|$.*";
               }
               type int32 {
                 range "1 .. 63";
               }
             }
           }
         }
       }
       container jflow-log {
         presence "enable jflow-log";
         description "Configure jflow-logging parameters for services";
         uses apply-advanced;
         list collector {
           key name;
           ordered-by user;
           description "Collector attributes";
           leaf name {
             description "Profile name";
             type string {
               length "1 .. 63";
             }
           }
           uses apply-advanced;
           leaf destination-address {
             description "IPv4 Address or hostname of the collector";
             type string {
             }
           }
           leaf destination-port {
             description "Destination port of the collector";
             type union {
               type string {
                 pattern "<.*>|$.*";
               }
               type uint16 {
                 range "1 .. 65535";
               }
             }
           }
           leaf source-ip {
             description "Source IPv4 Address from which logging is to be done";
             type jt:ipv4addr;
           }
         }
         list collector-group {
           key name;
           ordered-by user;
           leaf name {
             description "Name of collector-group";
             type string {
               length "1 .. 63";
             }
           }
           uses apply-advanced;
           leaf-list collector {
             ordered-by user;
             description "List of Collector profiles";
             type string {
               length "1 .. 63";
             }
             max-elements 8;
           }
         }
         list template-profile {
           key name;
           ordered-by user;
           leaf name {
             description "Specify name of the template";
             type string {
               length "1 .. 63";
             }
           }
           uses apply-advanced;
           leaf collector {
             description "Specify a collector name";
             type string {
               length "1 .. 63";
             }
           }
           leaf-list collector-group {
             ordered-by user;
             description "Specify a collector-group name";
             type string {
               length "1 .. 63";
             }
             max-elements 1;
           }
           leaf template-type {
             description "Allow jflow-log for applications";
             type enumeration {
               enum "nat" {
                 description "Enable jflow-logs for NAT events";
               }
             }
           }
           leaf version {
             description "Version of jflow-logging";
             type enumeration {
               enum "v9" {
                 description "Version 9";
               }
               enum "ipfix" {
                 description "Ipfix";
               }
             }
           }
           container refresh-rate {
             presence "enable refresh-rate";
             uses apply-advanced;
             leaf packets {
               description "Specify number of packets after which templates are sent to collector";
               default "4800";
               type union {
                 type string {
                   pattern "<.*>|$.*";
                 }
                 type uint32 {
                   range "1 .. 48000";
                 }
               }
             }
             leaf seconds {
               description "Specify number of seconds after which templates are sent to collector";
               default "1800";
               type union {
                 type string {
                   pattern "<.*>|$.*";
                 }
                 type uint32 {
                   range "10 .. 1800";
                 }
               }
             }
           }
           leaf session-end-reason {
             description "Session end reason";
             type enumeration {
               enum "custom-reason" {
                 description "Custom specific session end reason";
               }
               enum "default-reason" {
                 description "Default session end reason";
               }
             }
           }
         }
       }
       container service-device-pools {
         description "Configure service device pools";
         uses apply-advanced;
         list pool {
           key name;
           ordered-by user;
           description "Define service device pool";
           uses service_device_pool_object;
         }
       }
       container network-slicing {
         description "Configure network wide slicing parameters";
         uses apply-advanced;
         list slice {
           key name;
           description "Configure network wide slice name";
           max-elements 8000;
           leaf name {
             description "Name of the network wide slice";
             type string {
               length "1 .. 64";
             }
           }
         }
       }
       container redundancy-set {
         description "Redundancy-set settings";
         uses apply-advanced;
         container traceoptions {
           description "Services redundancy trace options";
           uses srd-traceoptions-object;
         }
         list rs-id-object {
           key name;
           ordered-by user;
           description "Definition of redundancy-set";
           uses srd-rs-id-object;
         }
       }
       container analytics {
         presence "enable analytics";
         description "Traffic analytics configuration options";
         uses apply-advanced;
         container na-grpc-server {
           presence "enable na-grpc-server";
           description "Configuration for na-grpcd";
           uses apply-advanced;
           container traceoptions {
             description "Traceoptions for na-grpcd";
             uses apply-advanced;
             container file {
               presence "enable file";
               description "Trace file information";
               uses apply-advanced;
               leaf size {
                 description "Maximum trace file size";
                 type string;
               }
               leaf files {
                 description "Maximum number of trace files";
                 default "5";
                 type union {
                   type string {
                     pattern "<.*>|$.*";
                   }
                   type uint32 {
                     range "2 .. 1000";
                   }
                 }
               }
             }
           }
         }
         container zero-suppression {
           description "Configure suppression of zeros for GRPC sensors";
           uses apply-advanced;
           leaf no-zero-suppression {
             description "Disable zero suppression";
             type empty;
           }
         }
         list streaming-server {
           key name;
           ordered-by user;
           description "Define Telemetry data servers";
           leaf name {
             description "Telemetry App server Name";
             type string {
               length "1 .. 128";
             }
           }
           uses apply-advanced;
           leaf remote-address {
             description "Telemetry server IP address";
             type jt:host;
           }
           leaf remote-port {
             description "Telemetry server Port";
             type union {
               type uint16;
               type string {
                 pattern "<.*>|$.*";
               }
             }
           }
           leaf transport {
             description "Telemetry export transport protocol";
             type enumeration {
               enum "udp" {
                 description "Use UDP transport protocol";
               }
               enum "grpc" {
                 description "Use grpc transport";
               }
             }
           }
           leaf dialout {
             description "Supports dynamic dialout subscriptions";
             type empty;
           }
         }
         list export-profile {
           key name;
           ordered-by user;
           description "Telemetry export profile name";
           leaf name {
             description "Telemetry export profile name";
             type string {
               length "1 .. 128";
             }
           }
           uses apply-advanced;
           leaf local-address {
             description "Source address for exported packets";
             type jt:ipaddr;
           }
           leaf local-port {
             description "Source port for exported packets";
             type union {
               type uint16;
               type string {
                 pattern "<.*>|$.*";
               }
             }
           }
           leaf dscp {
             description "DSCP value for exported packets";
             type union {
               type string {
                 pattern "<.*>|$.*";
               }
               type uint8 {
                 range "0 .. 63";
               }
             }
           }
           leaf forwarding-class {
             description "Forwarding-class for exported packets, applicable only for PFE sensors";
             type string {
               length "1 .. 64";
             }
           }
           leaf reporting-rate {
             description "Telemetry interval in seconds, max 24 hours";
             units "seconds";
             type union {
               type string {
                 pattern "<.*>|$.*";
               }
               type uint32 {
                 range "0 .. 86400";
               }
             }
           }
           leaf payload-size {
             description "Telemetry payload size";
             default "5000";
             units "bytes";
             type union {
               type string {
                 pattern "<.*>|$.*";
               }
               type uint32 {
                 range "1400 .. 9192";
               }
             }
           }
           leaf format {
             description "Telemetry export record format";
             type enumeration {
               enum "gpb" {
                 description "Use gpb format";
               }
               enum "gpb-gnmi" {
                 description "Use gnmi format for gpb messages";
               }
               enum "json-gnmi" {
                 description "Use gnmi format for json messages";
               }
             }
           }
           leaf transport {
             description "Telemetry export transport protocol";
             type enumeration {
               enum "udp" {
                 description "Use UDP transport protocol";
               }
               enum "grpc" {
                 description "Use grpc transport";
               }
             }
           }
           leaf routing-instance {
             description "Routing instance to be used for grpc transport";
             type string;
           }
         }
         list sensor {
           key name;
           ordered-by user;
           description "Define Telemetry sensors";
           leaf name {
             description "Name of the sensor";
             type string {
               length "1 .. 128";
             }
           }
           uses apply-advanced;
           leaf-list server-name {
             ordered-by user;
             description "Define Telemetry server ";
             type string {
               length "1 .. 128";
             }
           }
           leaf export-name {
             description "Define Telemetry export profiles";
             type string {
               length "1 .. 128";
             }
           }
           leaf polling-interval {
             description "Define sensor polling interval in nano secs (1 .. 4294967295)";
             status deprecated;
             units "nanoseconds";
             type union {
               type string {
                 pattern "<.*>|$.*";
               }
               type uint32 {
                 range "1 .. 4294967295";
               }
             }
           }
           leaf resource {
             description "System resource identifier string";
             type string {
               length "1 .. 1024";
             }
           }
           leaf resource-filter {
             description "Regexp for filtering resource instances (1 .. 1024)";
             type string {
               length "1 .. 1024";
             }
           }
           leaf subscription-id {
             description "Subscription ID (Used internally to group sensors)";
             type union {
               type uint64;
               type string {
                 pattern "<.*>|$.*";
               }
             }
           }
           leaf suppress-zeros {
             description "Supress zeros while data export";
             type empty;
           }
           leaf reporting-rate {
             description "Telemetry interval in seconds, max 24 hours";
             units "seconds";
             type union {
               type string {
                 pattern "<.*>|$.*";
               }
               type uint32 {
                 range "0 .. 86400";
               }
             }
           }
           leaf-list end-of-sync-identifiers {
             ordered-by user;
             description "Set of end-of-syncs for this sensor";
             type union {
               type string {
                 pattern "<.*>|$.*";
               }
               type uint32 {
                 range "1 .. 64";
               }
             }
             max-elements 30;
           }
           leaf target-defined {
             description "Allow target to decide periodic, on-change or mix";
             type empty;
           }
           leaf life-time {
             description "Denotes sensor life-time";
             type enumeration {
               enum "long-lived" {
                 description "A long-lived subscription";
               }
               enum "one-off" {
                 description "An one-off subscription";
               }
             }
           }
         }
         container agent {
           description "Configure analytics agent";
           uses apply-advanced;
           list service-agents {
             key name;
             ordered-by user;
             description "Analytics service agent configuration";
             leaf name {
               description "Analytics service agent name";
               type string;
             }
             uses apply-advanced;
             container inputs {
               description "List of input plugins";
               uses apply-advanced;
               container input-jti-ipfix {
                 presence "enable input-jti-ipfix";
                 description "Junos grpc IPFIX group plugin";
                 uses apply-advanced;
                 container parameters {
                   presence "enable parameters";
                   uses apply-advanced;
                   list record-group {
                     key name;
                     ordered-by user;
                     description "Group sensors";
                     max-elements 10;
                     leaf name {
                       description "Group sensors";
                       type string;
                     }
                     uses apply-advanced;
                     leaf reporting-interval {
                       description "Reporting-interval";
                       default "900";
                       type union {
                         type string {
                           pattern "<.*>|$.*";
                         }
                         type uint32 {
                           range "60 .. 86400";
                         }
                       }
                     }
                     leaf-list record {
                       ordered-by user;
                       description "Ipfix record name";
                       type enumeration {
                         enum "port-statistics" {
                           description "Port statistics";
                         }
                         enum "address-pool-utilization" {
                           description "Address pool utilization";
                         }
                         enum "dhcpv4-server-stats" {
                           description "Dhcpv4 server statistics";
                         }
                         enum "thermal" {
                           description "Thermal statistics";
                         }
                         enum "chassis-inventory" {
                           description "Chassis inventory details";
                         }
                         enum "chassis-power" {
                           description "Chassis power details";
                         }
                         enum "resource-utilization" {
                           description "Resource utilization details";
                         }
                         enum "uptime" {
                           description "Uptime value";
                         }
                         enum "subscriber-statistics" {
                           description "Subscriber statistics";
                         }
                         enum "interface-metadata" {
                           description "Interface metadata details";
                         }
                         enum "interface-queue-statistics" {
                           description "Interface Queue statistics";
                         }
                       }
                     }
                   }
                 }
               }
               container input-ipfix {
                 presence "enable input-ipfix";
                 description "Junos IPFIX Mediator input plugin";
                 uses apply-advanced;
                 container parameters {
                   presence "enable parameters";
                   description "List of IPFIX parameters";
                   uses apply-advanced;
                   leaf tcp-port {
                     description "Listening TCP Port for IPFIX Mediator";
                     type union {
                       type uint16;
                       type string {
                         pattern "<.*>|$.*";
                       }
                     }
                   }
                   leaf maximum-connections {
                     description "Maximum TCP Connections 1..500";
                     type union {
                       type string {
                         pattern "<.*>|$.*";
                       }
                       type uint32 {
                         range "1 .. 500";
                       }
                     }
                   }
                   leaf vrf-name {
                     description "VRF name on which IPFIX packets are accepted";
                     type string;
                   }
                 }
               }
               container analytics {
                 presence "enable analytics";
                 description "Junos Telemetry plugin";
                 uses apply-advanced;
                 container parameters {
                   presence "enable parameters";
                   description "List of key:value parameters";
                   uses apply-advanced;
                   leaf sample-frequency {
                     description "Interval for sensor data in seconds, max 24 hours";
                     default "5";
                     units "seconds";
                     type union {
                       type string {
                         pattern "<.*>|$.*";
                       }
                       type uint32 {
                         range "0 .. 86400";
                       }
                     }
                   }
                   leaf sensors {
                     description "Space separated list of sensor paths";
                     type string {
                       length "1 .. 2048";
                     }
                   }
                   leaf generate-tags {
                     description "Enable generation of tags";
                     type empty;
                   }
                 }
               }
             }
             list outputs {
               key name;
               ordered-by user;
               description "List of output plugins";
               max-elements 1;
               uses output-plugin;
             }
           }
           container traceoptions {
             presence "enable traceoptions";
             uses apply-advanced;
             leaf flag {
               description "Set log level for tracing";
               type enumeration {
                 enum "trace" {
                   description "Log level TRACE, will trace everything";
                 }
                 enum "debug" {
                   description "Log level DEBUG, will trace debug messages";
                 }
                 enum "info" {
                   description "Log level INFO";
                 }
                 enum "error" {
                   description "Log level ERROR, will trace all error messages";
                 }
               }
             }
             leaf filename {
               description "Configure filename for trace messages";
               default "ntf-agent.log";
               type string;
             }
           }
         }
         container traceoptions {
           description "Traffic analytics trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             description "Tracing parameters";
             leaf name {
               type enumeration {
                 enum "all" {
                   description "Trace configuration events";
                 }
                 enum "configuration" {
                   description "Log configuration events";
                 }
                 enum "rtsock" {
                   description "Trace rtsock message events";
                 }
                 enum "client-server" {
                   description "Trace client-server events";
                 }
                 enum "interface" {
                   description "Trace interface update events";
                 }
                 enum "xmlproxy" {
                   description "Trace xmlproxy events";
                 }
               }
             }
             leaf disable {
               description "Disable this trace flag";
               type empty;
             }
           }
         }
         list export-profiles {
           key name;
           ordered-by user;
           description "Mapping of export-profiles to collectors";
           leaf name {
             description "Export profile name";
             type string {
               length "1 .. 64";
             }
           }
           uses apply-advanced;
           leaf stream-format {
             description "Streaming data format";
             default "gpb";
             type enumeration {
               enum "gpb" {
                 description "Google protocol buffer format";
               }
               enum "json" {
                 description "Java script object notation format";
               }
               enum "csv" {
                 description "Comma separated value";
               }
               enum "tsv" {
                 description "Tab separated value";
               }
             }
           }
           container interface {
             presence "enable interface";
             description "Interface specific information";
             uses apply-advanced;
             leaf information {
               description "Enable streaming of interface information";
               type empty;
             }
             container statistics {
               description "Type of statistics to stream";
               uses apply-advanced;
               leaf traffic {
                 description "Enable streaming of interface traffic statistics";
                 type empty;
               }
               leaf queue {
                 description "Enable streaming of interface queue statistics";
                 type empty;
               }
             }
             container status {
               description "Type of statistics to stream";
               uses apply-advanced;
               leaf link {
                 description "Enable streaming of interface link status";
                 type empty;
               }
               leaf traffic {
                 description "Enable streaming of interface traffic status";
                 type empty;
               }
               leaf queue {
                 description "Enable streaming of interface queue status";
                 type empty;
               }
             }
           }
           container system {
             presence "enable system";
             description "Interface specific information";
             uses apply-advanced;
             leaf information {
               description "Enable streaming of system information";
               type empty;
             }
             container status {
               description "Type of statistics to stream";
               uses apply-advanced;
               leaf traffic {
                 description "Enable streaming of system traffic status";
                 type empty;
               }
               leaf queue {
                 description "Enable streaming of system queue status";
                 type empty;
               }
             }
           }
         }
         list resource-profiles {
           key name;
           ordered-by user;
           description "Mapping of resource profiles to interfaces/queues/system";
           leaf name {
             description "Export profile name";
             type string {
               length "1 .. 64";
             }
           }
           uses apply-advanced;
           choice queue-monitoring-choice {
             leaf queue-monitoring {
               description "Enable queue statistics monitoring";
               type empty;
             }
             leaf no-queue-monitoring {
               description "Don't enable queue statistics monitoring";
               type empty;
             }
           }
           choice traffic-monitoring-choice {
             leaf traffic-monitoring {
               description "Enable traffic statistics monitoring";
               type empty;
             }
             leaf no-traffic-monitoring {
               description "Don't enable traffic statistics monitoring";
               type empty;
             }
           }
           container depth-threshold {
             description "Depth threshold configuration";
             leaf high {
               description "High queue depth threshold";
               units "bytes";
               type union {
                 type string {
                   pattern "<.*>|$.*";
                 }
                 type uint32 {
                   range "1 .. 1250000000";
                 }
               }
             }
             leaf low {
               description "Low queue depth threshold";
               units "bytes";
               type union {
                 type string {
                   pattern "<.*>|$.*";
                 }
                 type uint32 {
                   range "1 .. 1250000000";
                 }
               }
             }
           }
           container latency-threshold {
             description "Latency threshold configuration";
             leaf high {
               description "High latency threshold";
               units "nanoseconds";
               type union {
                 type string {
                   pattern "<.*>|$.*";
                 }
                 type uint32 {
                   range "1 .. 100000000";
                 }
               }
             }
             leaf low {
               description "Low latency threshold";
               units "nanoseconds";
               type union {
                 type string {
                   pattern "<.*>|$.*";
                 }
                 type uint32 {
                   range "1 .. 100000000";
                 }
               }
             }
           }
         }
         container resource {
           presence "enable resource";
           uses apply-advanced;
           container system {
             description "System configuration options";
             uses apply-advanced;
             leaf resource-profile {
               description "Resouce profile name";
               type string {
                 length "1 .. 64";
               }
             }
             container polling-interval {
               description "Polling interval";
               uses apply-advanced;
               leaf traffic-monitoring {
                 description "Traffic statistics polling interval";
                 units "seconds";
                 type union {
                   type string {
                     pattern "<.*>|$.*";
                   }
                   type uint32 {
                     range "1 .. 300";
                   }
                 }
               }
               leaf queue-monitoring {
                 description "Queue statistics polling interval";
                 units "milliseconds";
                 type union {
                   type string {
                     pattern "<.*>|$.*";
                   }
                   type uint32 {
                     range "1 .. 1000";
                   }
                 }
               }
             }
           }
           container interfaces {
             description "Interface configuration options";
             uses apply-advanced;
             list interface {
               key name;
               uses interface_type;
             }
           }
         }
         container collector {
           description "Remote streaming servers configuration options";
           uses apply-advanced;
           container local {
             description "Remote streaming servers configuration options";
             uses apply-advanced;
             container file {
               description "Log file information";
               leaf filename {
                 description "Name of file in which to write log information";
                 type jt:filename;
               }
               leaf size {
                 description "Maximum log file size";
                 type string;
               }
               leaf files {
                 description "Maximum number of trace files";
                 default "10";
                 type union {
                   type string {
                     pattern "<.*>|$.*";
                   }
                   type uint32 {
                     range "2 .. 1000";
                   }
                 }
               }
             }
           }
           list address {
             key name;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               list transport {
                 key name;
                 description "Transport protocol";
                 leaf name {
                   type enumeration {
                     enum "tcp" {
                       description "Transmission control protocol";
                     }
                     enum "udp" {
                       description "User datagram protocol";
                     }
                   }
                 }
                 uses apply-advanced;
                 leaf export-profile {
                   description "Export profile name";
                   type string {
                     length "1 .. 64";
                   }
                 }
               }
             }
           }
         }
         container traffic-statistics {
           description "Traffic statistics configuration options";
           status deprecated;
           uses apply-advanced;
           container file {
             description "Log file information";
             leaf filename {
               description "Name of file in which to write log information";
               type jt:filename;
             }
             leaf size {
               description "Maximum log file size";
               type string;
             }
             leaf files {
               description "Maximum number of trace files";
               default "10";
               type union {
                 type string {
                   pattern "<.*>|$.*";
                 }
                 type uint32 {
                   range "2 .. 1000";
                 }
               }
             }
           }
           leaf interval {
             description "Traffic statistics polling interval";
             units "seconds";
             type union {
               type string {
                 pattern "<.*>|$.*";
               }
               type uint32 {
                 range "1 .. 300";
               }
             }
           }
         }
         container queue-statistics {
           description "Microburst statistics configuration options";
           status deprecated;
           uses apply-advanced;
           container file {
             description "Log file information";
             leaf filename {
               description "Name of file in which to write log information";
               type jt:filename;
             }
             leaf size {
               description "Maximum log file size";
               type string;
             }
             leaf files {
               description "Maximum number of trace files";
               default "10";
               type union {
                 type string {
                   pattern "<.*>|$.*";
                 }
                 type uint32 {
                   range "2 .. 1000";
                 }
               }
             }
           }
           leaf interval {
             description "Queue statistics polling interval";
             units "milliseconds";
             type union {
               type string {
                 pattern "<.*>|$.*";
               }
               type uint32 {
                 range "1 .. 1000";
               }
             }
           }
         }
         container interfaces {
           description "Interface configuration options";
           status deprecated;
           uses apply-advanced;
           list interface {
             key name;
             uses interface_type;
           }
         }
         container streaming-servers {
           description "Remote streaming servers configuration options";
           status deprecated;
           uses apply-advanced;
           list address {
             key name;
             ordered-by user;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               leaf stream-format {
                 description "Streaming data format";
                 type enumeration {
                   enum "json" {
                     description "Javascript object notation";
                   }
                   enum "csv" {
                     description "Comma separated value";
                   }
                   enum "tsv" {
                     description "Tab separated value";
                   }
                 }
               }
               list stream-type {
                 key name;
                 description "Type of statistics to stream";
                 leaf name {
                   type enumeration {
                     enum "traffic-statistics" {
                       description "Enable streaming of traffic statistics";
                     }
                     enum "queue-statistics" {
                       description "Enable streaming of queue statistics";
                     }
                   }
                 }
                 uses apply-advanced;
               }
             }
           }
         }
       }
     }
   }
   grouping aamwd-traceoptions {
     description "Advanced anti-malware trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "connection" {
             description "Trace the connection to server";
           }
           enum "content" {
             description "Trace the content buffer management";
           }
           enum "daemon" {
             description "Trace advanced-anti-malware daemon";
           }
           enum "http" {
             description "Trace http protocol operations";
           }
           enum "identification" {
             description "Trace file identification";
           }
           enum "imap" {
             description "Trace imap protocol operations";
           }
           enum "parser" {
             description "Trace protocol context parser";
           }
           enum "plugin" {
             description "Trace advanced-anti-malware plugin";
           }
           enum "policy" {
             description "Trace advanced-anti-malware policy";
           }
           enum "smb" {
             description "Trace smb protocol operations";
           }
           enum "smtp" {
             description "Trace smtp protocol operations";
           }
         }
       }
     }
   }
   grouping action-object-type {
     uses apply-advanced;
     container preferred-route {
       description "Preferred route action";
       uses apply-advanced;
       leaf withdraw {
         description "Withdraw the preferred route";
         type empty;
       }
       list routing-instances {
         key name;
         ordered-by user;
         description "Routing-instance";
         leaf name {
           type string;
         }
         uses apply-advanced;
         list route {
           key name;
           ordered-by user;
           description "Route";
           leaf name {
             type jt:ipprefix;
           }
           uses apply-advanced;
           choice next_hop {
             case case_1 {
               leaf-list next-hop {
                 ordered-by user;
                 description "Next hop to destination of route-action";
                 type union {
                   type jt:ipaddr-or-interface;
                   type string {
                     pattern "<.*>|$.*";
                   }
                 }
               }
             }
             case case_2 {
               leaf discard {
                 description "Drop packets to destination; send no ICMP unreachables";
                 type empty;
               }
             }
           }
           leaf direct-next-hop {
             description "Accept only direct nexthop";
             type empty;
           }
           leaf preferred-metric {
             description "Preferred metric value assigned to route action";
             type union {
               type string {
                 pattern "<.*>|$.*";
               }
               type uint32 {
                 range "1 .. 255";
               }
             }
           }
         }
       }
       list route {
         key name;
         ordered-by user;
         description "Route";
         leaf name {
           type jt:ipprefix;
         }
         uses apply-advanced;
         choice next_hop {
           case case_1 {
             leaf-list next-hop {
               ordered-by user;
               description "Next hop to destination of route-action";
               type union {
                 type jt:ipaddr-or-interface;
                 type string {
                   pattern "<.*>|$.*";
                 }
               }
             }
           }
           case case_2 {
             leaf discard {
               description "Drop packets to destination; send no ICMP unreachables";
               type empty;
             }
           }
         }
         leaf direct-next-hop {
           description "Accept only direct nexthop";
           type empty;
         }
         leaf preferred-metric {
           description "Preferred metric value assigned to route action";
           type union {
             type string {
               pattern "<.*>|$.*";
             }
             type uint32 {
               range "1 .. 255";
             }
           }
         }
       }
     }
     list interface {
       key name;
       ordered-by user;
       description "Interface enabling/disabling action";
       leaf name {
         type union {
           type jt:interface-wildcard;
           type string {
             pattern "<.*>|$.*";
           }
         }
       }
       uses apply-advanced;
       choice action {
         case case_1 {
           leaf enable {
             description "Enable interface";
             type empty;
           }
         }
         case case_2 {
           leaf disable {
             description "Disable interface";
             type empty;
           }
         }
       }
     }
   }
   grouping address-filter-type {
     description "IP address filter";
     uses apply-advanced;
     leaf address-book {
       description "Referenced address book";
       type string;
     }
     leaf address-set {
       description "Referenced address set";
       type string {
         length "1 .. 63";
       }
     }
   }
   grouping antivirus-traceoptions {
     description "Anti-virus trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "content" {
             description "Trace the content buffer management";
           }
           enum "daemon" {
             description "Trace advanced-anti-malware daemon";
           }
           enum "http" {
             description "Trace http protocol operations";
           }
           enum "identification" {
             description "Trace file identification";
           }
           enum "imap" {
             description "Trace imap protocol operations";
           }
           enum "parser" {
             description "Trace protocol context parser";
           }
           enum "plugin" {
             description "Trace advanced-anti-malware plugin";
           }
           enum "policy" {
             description "Trace anti-virus policy";
           }
           enum "smb" {
             description "Trace smb protocol operations";
           }
           enum "smtp" {
             description "Trace smtp protocol operations";
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping batch-query-type {
     description "Batch query configuration";
     uses apply-advanced;
     leaf items-per-batch {
       description "Items number per batch query";
       default "200";
       type union {
         type string {
           pattern "<.*>|$.*";
         }
         type uint32 {
           range "100 .. 1000";
         }
       }
     }
     leaf query-interval {
       description "Query interval";
       default "5";
       units "seconds";
       type union {
         type string {
           pattern "<.*>|$.*";
         }
         type uint32 {
           range "1 .. 60";
         }
       }
     }
   }
   grouping bgp-logical-system {
     description "Logical systems configuration for rpm";
     leaf name {
       description "Logical system name";
       type string {
       }
     }
     uses apply-advanced;
     list routing-instances {
       key name;
       description "Routing instances";
       uses bgp-routing-instances;
     }
   }
   grouping bgp-routing-instances {
     description "Routing-instance configuration for rpm";
     leaf name {
       description "Routing instance name";
       type string;
     }
     uses apply-advanced;
   }
   grouping dnsf-traceoptions-object {
     description "URL filtering trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "normal" {
             description "Trace normal events";
           }
           enum "config" {
             description "Trace dns filtering config events";
           }
           enum "dns" {
             description "Trace url filtering DNS crawler events";
           }
           enum "timer" {
             description "Trace url filtering timer events";
           }
           enum "connect" {
             description "Trace url filtering ipc events";
           }
           enum "parse" {
             description "Trace url filtering parse events";
           }
           enum "statistics" {
             description "Trace url filtering statistics events";
           }
           enum "system" {
             description "Trace url filtering system events";
           }
           enum "operational-commands" {
             description "Trace url filtering show events";
           }
           enum "filter" {
             description "Trace url filtering filter programming events";
           }
           enum "gencfg" {
             description "Trace url filtering gencfg events";
           }
           enum "routing" {
             description "Trace url filtering route programming events";
           }
           enum "snmp" {
             description "Trace url filtering snmp events";
           }
           enum "all" {
             description "Trace everything";
           }
         }
       }
     }
   }
   grouping drop-policy-term {
     description "One or more drop terms";
     leaf name {
       description "Term name";
       type string {
       }
     }
     uses apply-advanced;
     container from {
       description "Define match criteria";
       uses apply-advanced;
       container source-address {
         description "Source IP Address";
         presence "enable source-address";
         uses li_policy_addr_simple_object;
       }
       container destination-address {
         description "Destination IP Address";
         presence "enable destination-address";
         uses li_policy_addr_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping drop-policy6-term {
     description "One or more drop terms";
     leaf name {
       description "Term name";
       type string {
       }
     }
     uses apply-advanced;
     container from {
       description "Define match criteria";
       uses apply-advanced;
       container source-address {
         description "Source IPv6 Address or Prefix";
         presence "enable source-address";
         uses li_policy_addr6_simple_object;
       }
       container destination-address {
         description "Destination IPv6 Address or Prefix";
         presence "enable destination-address";
         uses li_policy_addr6_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping dyn-filterd-traceoptions {
     description "Dynamic Filtering trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "config" {
             description "Trace config handling events";
           }
           enum "connection" {
             description "Trace the connection to server";
           }
           enum "daemon" {
             description "Trace generic daemon handling events";
           }
           enum "filters" {
             description "Trace filter related events";
           }
           enum "pki" {
             description "Trace Public Key Encryption events";
           }
           enum "policy" {
             description "Trace policy events from RE to PFE";
           }
         }
       }
     }
   }
   grouping explicit-config {
     uses apply-advanced;
     list profile {
       key name;
       ordered-by user;
       description "Configure explicit proxy profile";
       leaf name {
         description "Explicit proxy profile name";
         type string {
           length "1 .. 63";
         }
       }
       uses apply-advanced;
       leaf-list listening-port {
         description "Listening ports for explicit proxy traffic";
         type union {
           type string {
             pattern "<.*>|$.*";
           }
           type uint16 {
             range "1025 .. 65535";
           }
         }
       }
       leaf preferred-egress-source-ip {
         description "Specify preferred egress source IP";
         default "default-egress-ip";
         type enumeration {
           enum "default-egress-ip" {
             description "Egress source IP will be the IP address associated with outgoing interface";
           }
           enum "explicit-proxy-ip" {
             description "Egress source IP will be the explicit proxy IP address on which the proxy request was made";
           }
         }
       }
       leaf proxy-mode {
         description "Supported modes for explict proxy";
         default "hop-by-hop";
         type enumeration {
           enum "hop-by-hop" {
             description "Modify hop-by-hop headers";
           }
           enum "opaque" {
             description "Relay messages directly without altering any content";
           }
         }
       }
       container ssl-proxy {
         presence "enable ssl-proxy";
         description "SSL Proxy profile";
         uses apply-advanced;
         leaf profile-name {
           description "Specify SSL proxy service profile name";
           type string;
         }
       }
       container captive-portal {
         presence "enable captive-portal";
         description "Authentication captive portal profile";
         uses apply-advanced;
         leaf profile-name {
           description "Specify Captive portal service profile name";
           type string;
         }
       }
       container add-forwarded-header {
         description "Adds the forwarded header in the request messages";
         uses apply-advanced;
         leaf obfuscated-forwarded-for-info {
           description "Adds the forwarded header with obfuscated identifiers for client information";
           type string {
             length "1 .. 63";
           }
         }
         leaf obfuscated-forwarded-by-info {
           description "Adds the forwarded header with obfuscated identifiers for proxy information";
           type string {
             length "1 .. 63";
           }
         }
         leaf add-client-ipaddr-in-forwarded-for-info {
           description "Adds the IP address of the client in the forwarded header";
           type empty;
         }
         leaf add-proxy-ipaddr-in-forwarded-by-info {
           description "Adds the explicit proxy IP address in the forwarded header";
           type empty;
         }
         leaf add-forwarded-proto-info {
           description "Adds the http protocol information in the forwarded header";
           type empty;
         }
       }
       container security-metadata-streaming-policy {
         description "Specify security-metadata-streaming-policy";
         uses apply-advanced;
         leaf policy-name {
           type string {
             length "1 .. 63";
           }
         }
       }
       leaf session-rate-limiter {
         description "Number of sessions per second";
         default "2500";
         type union {
           type string {
             pattern "<.*>|$.*";
           }
           type uint32 {
             range "1 .. 32000";
           }
         }
       }
     }
   }
   grouping family {
     container inet {
       description "IPv4 parameters";
       uses apply-advanced;
       choice if-addr {
         case case_1 {
           leaf dhcp {
             description "Enable DHCP on ethernet interface";
             type empty;
           }
         }
         case case_2 {
           leaf address {
             description "Interface address/destination prefix";
             type jt:ipv4prefix;
           }
         }
       }
     }
   }
   grouping icap-profile-object {
     leaf name {
       description "ICAP service profile name";
       type string {
         length "1 .. 63";
       }
     }
     uses apply-advanced;
     list server {
       key name;
       ordered-by user;
       description "Configure service redirection server";
       max-elements 16;
       uses icap-redir-server;
     }
     container http {
       description "ICAP methods switch";
       uses http-redirect-object;
     }
     container fallback-option {
       description "Failure event actions";
       uses icap-redirect-fallback;
     }
     leaf timeout {
       description "Server response timeout in milliseconds";
       default "500";
       type union {
         type string {
           pattern "<.*>|$.*";
         }
         type uint16 {
           range "100 .. 50000";
         }
       }
     }
   }
   grouping http-redirect-object {
     uses apply-advanced;
     leaf redirect-request {
       description "Enable redirect service on HTTP request";
       type empty;
     }
     leaf redirect-response {
       description "Enable redirect service on HTTP response";
       type empty;
     }
   }
   grouping icap-redir-server {
     leaf name {
       description "Server name";
       type string {
         length "1 .. 63";
       }
     }
     uses apply-advanced;
     container authorization {
       description "User authentication";
       uses apply-advanced;
       leaf authorization-type {
         description "Authentication type. 'Basic' by default";
         type string {
           length "1 .. 127";
         }
       }
       container credentials {
         description "Credentials text";
         choice credentials-choice {
           case case_1 {
             leaf ascii {
               description "ASCII string";
               type string {
                 length "1 .. 511";
               }
             }
           }
           case case_2 {
             leaf base64 {
               description "Base64 string";
               type string {
                 length "1 .. 511";
               }
             }
           }
         }
       }
     }
     leaf host {
       description "Host name/IP address";
       type string {
         length "1 .. 255";
       }
     }
     leaf port {
       description "Server listening port";
       default "1344";
       type union {
         type string {
           pattern "<.*>|$.*";
         }
         type uint16 {
           range "1025 .. 65535";
         }
       }
     }
     leaf reqmod-uri {
       description "REQMOD option resource identifier";
       type string {
         length "0 .. 1023";
       }
     }
     leaf respmod-uri {
       description "RESPMOD option resource identifier";
       type string {
         length "0 .. 1023";
       }
     }
     container routing-instance {
       description "Routing instance";
       leaf ri-name {
         description "Routing instance name";
         type string {
           length "1 .. 127";
         }
       }
     }
     leaf sockets {
       description "Number of connections to create";
       default "8";
       type union {
         type string {
           pattern "<.*>|$.*";
         }
         type uint8 {
           range "1 .. 64";
         }
       }
     }
     leaf tls-profile {
       description "TLS profile";
       type string {
         length "1 .. 63";
       }
     }
   }
   grouping icap-redirect-fallback {
     uses apply-advanced;
     leaf timeout {
       description "Request timeout action";
       default "permit";
       type enumeration {
         enum "permit" {
           description "Direct permit action";
         }
         enum "log-permit" {
           description "Log then permit action";
         }
         enum "block" {
           description "Block action";
         }
       }
     }
     leaf connectivity {
       description "Connection-related failure action";
       default "permit";
       type enumeration {
         enum "permit" {
           description "Direct permit action";
         }
         enum "log-permit" {
           description "Log then permit action";
         }
         enum "block" {
           description "Block action";
         }
       }
     }
     leaf default-action {
       description "Default failure action";
       default "permit";
       type enumeration {
         enum "permit" {
           description "Direct permit action";
         }
         enum "log-permit" {
           description "Log then permit action";
         }
         enum "block" {
           description "Block action";
         }
       }
     }
   }
   grouping icap-redirect-traceoptions {
     description "ICAP redirect traceoptions";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Trace flags";
       leaf name {
         type enumeration {
           enum "all" {
             description "Trace everything";
           }
           enum "icap-redirect-re" {
             description "Trace events on RE side";
           }
           enum "icap-redirect-control" {
             description "Trace events on PFE-ukernel side";
           }
           enum "icap-redirect-connection" {
             description "Trace ICAP server connection events";
           }
           enum "icap-redirect-protocol" {
             description "Trace redirect packet events";
           }
         }
       }
     }
   }
   grouping identity-management-connection-type {
     description "Identity management connection";
     uses apply-advanced;
     leaf connect-method {
       description "Method of connection";
       type enumeration {
         enum "https" {
           description "HTTPS connection";
         }
         enum "http" {
           description "HTTP connection";
         }
       }
     }
     leaf port {
       description "Server port";
       default "443";
       type union {
         type string {
           pattern "<.*>|$.*";
         }
         type uint32 {
           range "1 .. 65535";
         }
       }
     }
     container primary {
       description "Primary server";
       uses identity-server-connection-type;
     }
     container secondary {
       description "Secondary server";
       uses identity-server-connection-type;
     }
     leaf token-api {
       description "API of acquiring token for OAuth2 authentication";
       type string {
         length "1 .. 128";
       }
     }
     leaf query-api {
       description "Query API";
       type string {
         length "4 .. 128";
       }
     }
     leaf server-validity-check-interval {
       description "Interval to check server certificate revocation status";
       units "minutes";
       type union {
         type uint32;
         type string {
           pattern "<.*>|$.*";
         }
       }
     }
   }
   grouping identity-server-connection-type {
     description "Connection parameters per server";
     uses apply-advanced;
     leaf address {
       description "Server address as fqdn or ip address";
       type string;
     }
     leaf ca-profile {
       description "CA profile name";
       type string {
         length "1 .. 256";
       }
     }
     leaf client-id {
       description "Client ID for OAuth2 grant";
       type string {
         length "1 .. 64";
       }
     }
     leaf client-secret {
       description "Client secret for OAuth2 grant";
       type string {
         length "1 .. 128";
       }
     }
     leaf source {
       description "Client address";
       type jt:ipaddr;
     }
     leaf interface {
       description "Interface name";
       type union {
         type jt:interface-name;
         type string {
           pattern "<.*>|$.*";
         }
       }
     }
     leaf routing-instance {
       description "Routing instance name";
       type string;
     }
   }
   grouping ids-option-type {
     description "Configure screen object";
     leaf name {
       description "Screen object name";
       type string {
         length "1 .. 64";
       }
     }
     uses apply-advanced;
     leaf description {
       description "Text description of screen";
       type string {
         length "1 .. 900";
       }
     }
     leaf alarm-without-drop {
       description "Do not drop packet, only generate alarm";
       type empty;
     }
     leaf match-direction {
       description "Match direction";
       type enumeration {
         enum "input" {
           description "Match on input to interface";
         }
         enum "output" {
           description "Match on output from interface";
         }
         enum "input-output" {
           description "Match on input to or output from interface";
         }
       }
     }
     container aggregation {
       presence "enable aggregation";
       description "Configure the source and Destination prefix for a ids-option";
       uses apply-advanced;
       leaf source-prefix-mask {
         description "Source IPV4 prefix";
         type union {
           type string {
             pattern "<.*>|$.*";
           }
           type uint32 {
             range "1 .. 32";
           }
         }
       }
       leaf destination-prefix-mask {
         description "Destination IPV4 prefix";
         type union {
           type string {
             pattern "<.*>|$.*";
           }
           type uint32 {
             range "1 .. 32";
           }
         }
       }
       leaf source-prefix-v6-mask {
         description "Source IPV6 prefix";
         type union {
           type string {
             pattern "<.*>|$.*";
           }
           type uint32 {
             range "1 .. 128";
           }
         }
       }
       leaf destination-prefix-v6-mask {
         description "Destination IPV6 prefix";
         type union {
           type string {
             pattern "<.*>|$.*";
           }
           type uint32 {
             range "1 .. 128";
           }
         }
       }
     }
     container icmp {
       description "Configure ICMP ids options";
       uses apply-advanced;
       container ip-sweep {
         presence "enable ip-sweep";
         description "Configure ip sweep ids option";
         leaf threshold {
           description "Threshold";
           default "5000";
           units "microseconds in which 10 ICMP packets are detected";
           type union {
             type string {
               pattern "<.*>|$.*";
             }
             type uint32 {
               range "1000 .. 1000000";
             }
           }
         }
       }
       leaf fragment {
         description "Enable ICMP fragment ids option";
         type empty;
       }
       leaf large {
         description "Enable large ICMP packet (size > 1024) ids option";
         type empty;
       }
       container flood {
         presence "enable flood";
         description "Configure icmp flood ids option";
         leaf threshold {
           description "Threshold";
           default "1000";
           units "ICMP packets per second";
           type union {
             type string {
               pattern "<.*>|$.*";
             }
             type uint32;
           }
         }
       }
       leaf ping-death {
         description "Enable ping of death ids option";
         type empty;
       }
       leaf icmpv6-malformed {
         description "Enable icmpv6 malformed ids option";
         type empty;
       }
     }
     container ip {
       description "Configure IP layer ids options";
       uses apply-advanced;
       leaf bad-option {
         description "Enable ip with bad option ids option";
         type empty;
       }
       leaf record-route-option {
         description "Enable ip with record route option ids option";
         type empty;
       }
       leaf timestamp-option {
         description "Enable ip with timestamp option ids option";
         type empty;
       }
       leaf security-option {
         description "Enable ip with security option ids option";
         type empty;
       }
       leaf stream-option {
         description "Enable ip with stream option ids option";
         type empty;
       }
       leaf spoofing {
         description "Enable IP address spoofing ids option";
         type empty;
       }
       leaf source-route-option {
         description "Enable ip source route ids option";
         type empty;
       }
       leaf loose-source-route-option {
         description "Enable ip with loose source route ids option";
         type empty;
       }
       leaf strict-source-route-option {
         description "Enable ip with strict source route ids option";
         type empty;
       }
       leaf unknown-protocol {
         description "Enable ip unknown protocol ids option";
         type empty;
       }
       container block-frag {
         presence "enable block-frag";
         description "Enable ip fragment blocking ids option";
         uses apply-advanced;
         leaf-list white-list {
           ordered-by user;
           description "Configure ip block fragmentation white list group name";
           type string;
           max-elements 2;
         }
       }
       leaf tear-drop {
         description "Enable tear drop ids option";
         type empty;
       }
       container ipv6-extension-header {
         description "Configure ipv6 extension header ids option";
         uses apply-advanced;
         container hop-by-hop-header {
           presence "enable hop-by-hop-header";
           description "Enable ipv6 hop by hop option header ids option";
           uses apply-advanced;
           leaf jumbo-payload-option {
             description "Enable jumbo payload option ids option";
             type empty;
           }
           leaf router-alert-option {
             description "Enable router alert option ids option";
             type empty;
           }
           leaf quick-start-option {
             description "Enable quick start option ids option";
             type empty;
           }
           leaf CALIPSO-option {
             description "Enable Common Architecture Label ipv6 Security Option ids option";
             type empty;
           }
           leaf SMF-DPD-option {
             description "Enable Simplified Multicast Forwarding ipv6 Duplicate Packet Detection option ids option";
             type empty;
           }
           leaf RPL-option {
             description "Enable Routing Protocol for Low-power and Lossy networks option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf routing-header {
           description "Enable ipv6 routing header ids option";
           type empty;
         }
         leaf fragment-header {
           description "Enable ipv6 fragment header ids option";
           type empty;
         }
         leaf ESP-header {
           description "Enable ipv6 Encapsulating Security Payload header ids option";
           type empty;
         }
         leaf AH-header {
           description "Enable ipv6 Authentication Header ids option";
           type empty;
         }
         leaf no-next-header {
           description "Enable ipv6 no next header ids option";
           type empty;
         }
         container destination-header {
           presence "enable destination-header";
           description "Enable ipv6 destination option header ids option";
           uses apply-advanced;
           leaf tunnel-encapsulation-limit-option {
             description "Enable tunnel encapsulation limit option ids option";
             type empty;
           }
           leaf home-address-option {
             description "Enable home address option ids option";
             type empty;
           }
           leaf ILNP-nonce-option {
             description "Enable Identifier-Locator Network Protocol Nonce option ids option";
             type empty;
           }
           leaf line-identification-option {
             description "Enable line identification option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf shim6-header {
           description "Enable ipv6 shim header ids option";
           type empty;
         }
         leaf mobility-header {
           description "Enable ipv6 mobility header ids option";
           type empty;
         }
         leaf HIP-header {
           description "Enable ipv6 Host Identify Protocol header ids option";
           type empty;
         }
         list user-defined-header-type {
           key name;
           ordered-by user;
           description "User-defined header type range";
           max-elements 256;
           leaf name {
             description "User-defined header type low value";
             type union {
               type string {
                 pattern "<.*>|$.*";
               }
               type uint32 {
                 range "0 .. 255";
               }
             }
           }
           container to {
             description "Upper limit of header type range";
             uses apply-advanced;
             leaf type-high {
               description "User-defined header type high value";
               type union {
                 type string {
                   pattern "<.*>|$.*";
                 }
                 type uint32 {
                   range "0 .. 255";
                 }
               }
             }
           }
         }
       }
       leaf ipv6-extension-header-limit {
         description "Enable ipv6 extension header limit ids option";
         type union {
           type string {
             pattern "<.*>|$.*";
           }
           type uint32 {
             range "0 .. 32";
           }
         }
       }
       leaf ipv6-malformed-header {
         description "Enable ipv6 malformed header ids option";
         type empty;
       }
       container tunnel {
         description "Configure IP tunnel ids options";
         uses apply-advanced;
         leaf bad-inner-header {
           description "Enable IP tunnel bad inner header ids option";
           type empty;
         }
         container gre {
           description "Configure IP tunnel GRE ids option";
           uses apply-advanced;
           leaf gre-6in4 {
             description "Enable IP tunnel GRE 6in4 ids option";
             type empty;
           }
           leaf gre-4in6 {
             description "Enable IP tunnel GRE 4in6 ids option";
             type empty;
           }
           leaf gre-6in6 {
             description "Enable IP tunnel GRE 6in6 ids option";
             type empty;
           }
           leaf gre-4in4 {
             description "Enable IP tunnel GRE 4in4 ids option";
             type empty;
           }
         }
         container ip-in-udp {
           description "Configure IP tunnel IPinUDP ids option";
           uses apply-advanced;
           leaf teredo {
             description "Enable IP tunnel IPinUDP Teredo ids option";
             type empty;
           }
         }
         container ipip {
           description "Configure IP tunnel IPIP ids option";
           uses apply-advanced;
           leaf ipip-6to4relay {
             description "Enable IP tunnel IPIP 6to4 Relay ids option";
             type empty;
           }
           leaf ipip-6in4 {
             description "Enable IP tunnel IPIP 6in4 ids option";
             type empty;
           }
           leaf ipip-4in6 {
             description "Enable IP tunnel IPIP 4in6 ids option";
             type empty;
           }
           leaf ipip-4in4 {
             description "Enable IP tunnel IPIP 4in4 ids option";
             type empty;
           }
           leaf ipip-6in6 {
             description "Enable IP tunnel IPIP 6in6 ids option";
             type empty;
           }
           leaf ipip-6over4 {
             description "Enable IP tunnel IPIP 6over4 ids option";
             type empty;
           }
           leaf isatap {
             description "Enable IP tunnel IPIP ISATAP ids option";
             type empty;
           }
           leaf dslite {
             description "Enable IP tunnel IPIP DS-Lite ids option";
             type empty;
           }
         }
       }
     }
     container tcp {
       description "Configure TCP Layer ids options";
       uses apply-advanced;
       leaf syn-fin {
         description "Enable SYN and FIN bits set attack ids option";
         type empty;
       }
       leaf fin-no-ack {
         description "Enable Fin bit with no ACK bit ids option";
         type empty;
       }
       leaf tcp-no-flag {
         description "Enable TCP packet without flag ids option";
         type empty;
       }
       leaf syn-frag {
         description "Enable SYN fragment ids option";
         type empty;
       }
       leaf syn-defense {
         description "Enable tcp syn-defense";
         type empty;
       }
       container port-scan {
         presence "enable port-scan";
         description "Configure TCP port scan ids option";
         leaf threshold {
           description "Threshold";
           default "5000";
           units "microseconds in which 10 attack packets are detected";
           type union {
             type string {
               pattern "<.*>|$.*";
             }
             type uint32 {
               range "1000 .. 1000000";
             }
           }
         }
       }
       container syn-ack-ack-proxy {
         presence "enable syn-ack-ack-proxy";
         description "Configure syn-ack-ack proxy ids option";
         leaf threshold {
           description "Threshold";
           default "512";
           units "un-authenticated connections";
           type union {
             type string {
               pattern "<.*>|$.*";
             }
             type uint32 {
               range "1 .. 250000";
             }
           }
         }
       }
       container syn-flood {
         presence "enable syn-flood";
         description "Configure SYN flood ids option";
         uses apply-advanced;
         leaf alarm-threshold {
           description "Alarm threshold";
           default "512";
           units "requests per second";
           type union {
             type string {
               pattern "<.*>|$.*";
             }
             type uint32;
           }
         }
         leaf attack-threshold {
           description "Attack threshold";
           default "200";
           units "proxied requests per second";
           type union {
             type string {
               pattern "<.*>|$.*";
             }
             type uint32;
           }
         }
         leaf source-threshold {
           description "Source threshold";
           default "4000";
           units "SYN pps";
           type union {
             type string {
               pattern "<.*>|$.*";
             }
             type uint32;
           }
         }
         leaf destination-threshold {
           description "Destination threshold";
           default "4000";
           units "SYN pps";
           type union {
             type string {
               pattern "<.*>|$.*";
             }
             type uint32;
           }
         }
         leaf queue-size {
           description "Queue size";
           status deprecated;
           default "1024";
           units "proxied requests in queue";
           type union {
             type string {
               pattern "<.*>|$.*";
             }
             type uint32 {
               range "200 .. 20000";
             }
           }
         }
         leaf timeout {
           description "SYN flood ager timeout";
           default "20";
           units "seconds";
           type union {
             type string {
               pattern "<.*>|$.*";
             }
             type uint32 {
               range "1 .. 50";
             }
           }
         }
         list white-list {
           key name;
           description "Set of IP addresses that will not trigger a screen";
           max-elements 2;
           leaf name {
             description "White-list name";
             type string {
               length "1 .. 32";
             }
           }
           uses apply-advanced;
           leaf-list source-address {
             ordered-by user;
             description "Source address";
             type jt:ipprefix;
             max-elements 32;
           }
           leaf-list destination-address {
             ordered-by user;
             description "Destination address";
             type jt:ipprefix;
             max-elements 32;
           }
         }
       }
       leaf land {
         description "Enable land attack ids option";
         type empty;
       }
       leaf winnuke {
         description "Enable winnuke attack ids option";
         type empty;
       }
       container tcp-sweep {
         presence "enable tcp-sweep";
         description "Configure TCP sweep ids option";
         leaf threshold {
           description "Threshold";
           default "5000";
           units "microseconds in which 10 TCP packets are detected";
           type union {
             type string {
               pattern "<.*>|$.*";
             }
             type uint32 {
               range "1000 .. 1000000";
             }
           }
         }
       }
     }
     container udp {
       description "Configure UDP layer ids options";
       uses apply-advanced;
       container flood {
         presence "enable flood";
         description "Configure UDP flood ids option";
         uses apply-advanced;
         leaf threshold {
           description "Threshold";
           default "1000";
           units "UDP packets per second";
           type union {
             type string {
               pattern "<.*>|$.*";
             }
             type uint32;
           }
         }
         leaf-list white-list {
           ordered-by user;
           description "Configure UDP flood white list group name";
           type string;
           max-elements 2;
         }
       }
       container udp-sweep {
         presence "enable udp-sweep";
         description "Configure UDP sweep ids option";
         leaf threshold {
           description "Threshold";
           default "5000";
           units "microseconds in which 10 UDP packets are detected";
           type union {
             type string {
               pattern "<.*>|$.*";
             }
             type uint32 {
               range "1000 .. 1000000";
             }
           }
         }
       }
       container port-scan {
         presence "enable port-scan";
         description "Configure UDP port scan ids option";
         leaf threshold {
           description "Threshold";
           default "5000";
           units "microseconds in which 10 attack packets are detected";
           type union {
             type string {
               pattern "<.*>|$.*";
             }
             type uint32 {
               range "1000 .. 1000000";
             }
           }
         }
       }
     }
     container limit-session {
       description "Limit sessions";
       uses apply-advanced;
       leaf source-ip-based {
         description "Limit sessions from the same source IP";
         type union {
           type string {
             pattern "<.*>|$.*";
           }
           type uint32;
         }
       }
       leaf destination-ip-based {
         description "Limit sessions to the same destination IP";
         type union {
           type string {
             pattern "<.*>|$.*";
           }
           type uint32;
         }
       }
       container by-source {
         presence "enable by-source";
         description "Limit sessions from the same source IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           presence "enable by-protocol";
           uses by-protocol-object-type;
         }
         leaf-list whitelist {
           ordered-by user;
           description "Configure white list group name";
           type string;
           max-elements 10;
         }
       }
       container by-destination {
         presence "enable by-destination";
         description "Limit sessions to the same destination IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           presence "enable by-protocol";
           uses by-protocol-object-type;
         }
         leaf-list whitelist {
           ordered-by user;
           description "Configure white list group name";
           type string;
           max-elements 10;
         }
       }
     }
   }
   grouping by-protocol-object-type {
     description "Configure limit-session on the basis of protocol";
     uses apply-advanced;
     container tcp {
       description "Configure limit-session on the basis of TCP";
       presence "enable tcp";
       uses by-protocol-object-limit-tcp-type;
     }
     container udp {
       description "Configure limit-session on the basis of UDP";
       presence "enable udp";
       uses by-protocol-object-limit-type;
     }
     container icmp {
       description "Configure limit-session on the basis of ICMP";
       presence "enable icmp";
       uses by-protocol-object-limit-type;
     }
   }
   grouping by-protocol-object-limit-tcp-type {
     description "Configure the limit-session for tcp protocol";
     uses apply-advanced;
     leaf maximum-sessions {
       description "Limit sessions on the basis of maximum concurrent sessions";
       type union {
         type string {
           pattern "<.*>|$.*";
         }
         type uint32;
       }
     }
     leaf packet-rate {
       description "Limit sessions on the basis of packet rate";
       type union {
         type string {
           pattern "<.*>|$.*";
         }
         type uint32 {
           range "1 .. 4294967295";
         }
       }
     }
     leaf session-rate {
       description "Limit sessions on the basis of session rate";
       type union {
         type string {
           pattern "<.*>|$.*";
         }
         type uint32 {
           range "1 .. 4294967295";
         }
       }
     }
     leaf-list whitelist {
       ordered-by user;
       description "Configure white list group name";
       type string;
       max-elements 10;
     }
     container syn-cookie {
       presence "enable syn-cookie";
       description "Configure syn-cookie parameters";
       uses apply-advanced;
       leaf mss {
         description "TCP maximum segment size";
         type union {
           type string {
             pattern "<.*>|$.*";
           }
           type uint32 {
             range "64 .. 65535";
           }
         }
       }
       leaf threshold-rate {
         description "TCP-SYN cps rate to trigger SYN-COOKIE";
         type union {
           type string {
             pattern "<.*>|$.*";
           }
           type uint32 {
             range "1 .. 4294967295";
           }
         }
       }
       leaf threshold-num {
         description "Number of sessions to trigger SYN-COOKIE";
         type union {
           type string {
             pattern "<.*>|$.*";
           }
           type uint32;
         }
       }
     }
   }
   grouping by-protocol-object-limit-type {
     description "Configure the limit-session for each protocol";
     uses apply-advanced;
     leaf maximum-sessions {
       description "Limit sessions on the basis of maximum concurrent sessions";
       type union {
         type string {
           pattern "<.*>|$.*";
         }
         type uint32;
       }
     }
     leaf packet-rate {
       description "Limit sessions on the basis of packet rate";
       type union {
         type string {
           pattern "<.*>|$.*";
         }
         type uint32 {
           range "1 .. 4294967295";
         }
       }
     }
     leaf session-rate {
       description "Limit sessions on the basis of session rate";
       type union {
         type string {
           pattern "<.*>|$.*";
         }
         type uint32 {
           range "1 .. 4294967295";
         }
       }
     }
     leaf-list whitelist {
       ordered-by user;
       description "Configure white list group name";
       type string;
       max-elements 10;
     }
   }
   grouping ids-wlist-type {
     leaf name {
       description "White-list name";
       type string {
         length "1 .. 32";
       }
     }
     uses apply-advanced;
     leaf-list address {
       ordered-by user;
       description "Address";
       type jt:ipprefix;
       max-elements 32;
     }
   }
   grouping ims-connection-type {
     description "Identity management connection";
     uses apply-advanced;
     leaf connect-method {
       description "Method of connection";
       type enumeration {
         enum "https" {
           description "HTTPS connection";
         }
         enum "http" {
           description "HTTP connection";
         }
       }
     }
     leaf port {
       description "Server port";
       default "443";
       type union {
         type string {
           pattern "<.*>|$.*";
         }
         type uint32 {
           range "1 .. 65535";
         }
       }
     }
     container primary {
       description "Primary server";
       uses server-connection-type;
     }
     container secondary {
       description "Secondary server";
       uses server-connection-type;
     }
     leaf token-api {
       description "API of acquiring token for OAuth2 authentication";
       type string {
         length "1 .. 128";
       }
     }
     leaf query-api {
       description "Query API";
       type string {
         length "4 .. 128";
       }
     }
   }
   grouping ims-traceoptions-type {
     description "Identity management tracing Options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "all" {
             description "Trace identity management all modules";
           }
           enum "authentication-management" {
             description "Trace advanced-query auth table management module";
           }
           enum "configuration" {
             description "Trace identity management configuration";
           }
           enum "dispatcher" {
             description "Trace dispatcher module";
           }
           enum "query" {
             description "Trace query process";
           }
           enum "jims-validator-query" {
             description "Trace jims validator query process";
           }
           enum "memory" {
             description "Trace memory";
           }
         }
       }
     }
   }
   grouping inband-telemetry-profile-type {
     description "Inband Telemetry Profile";
     leaf name {
       description "Profile Name";
       type string {
         length "1 .. 32";
       }
     }
     uses apply-advanced;
     leaf sample-rate {
       description "Ratio of packets to be sampled (1 out of N)";
       type union {
         type string {
           pattern "<.*>|$.*";
         }
         type uint32 {
           range "1 .. 16777215";
         }
       }
     }
     container collector {
       description "Profile options";
       uses apply-advanced;
       leaf source-address {
         description "Source IP Address";
         type jt:ipv4addr;
       }
       leaf destination-address {
         description "Destination IP Address";
         type jt:ipv4addr;
       }
       leaf destination-port {
         description "Destionation Port";
         type union {
           type string {
             pattern "<.*>|$.*";
           }
           type uint32 {
             range "1 .. 65535";
           }
         }
       }
       leaf maximum-clip-length {
         description "Maximum data packet length for export";
         default "256";
         type union {
           type string {
             pattern "<.*>|$.*";
           }
           type uint32 {
             range "64 .. 9000";
           }
         }
       }
       leaf mtu {
         description "Maximum size of export packet";
         default "9000";
         type union {
           type string {
             pattern "<.*>|$.*";
           }
           type uint32 {
             range "256 .. 9000";
           }
         }
       }
     }
   }
   grouping interface_type {
     description "Physical interface";
     leaf name {
       type string;
     }
     uses apply-advanced;
     choice queue-statistics-choice {
       leaf queue-statistics {
         description "Enable queue statistics collection";
         status deprecated;
         type empty;
       }
       leaf no-queue-statistics {
         description "Don't enable queue statistics collection";
         status deprecated;
         type empty;
       }
     }
     choice traffic-statistics-choice {
       leaf traffic-statistics {
         description "Enable traffic statistics collection";
         status deprecated;
         type empty;
       }
       leaf no-traffic-statistics {
         description "Don't enable traffic statistics collection";
         status deprecated;
         type empty;
       }
     }
     leaf resource-profile {
       description "Resouce profile name";
       type string {
         length "1 .. 64";
       }
     }
   }
   grouping jims-validator-type {
     description "Web server from JIMS for Validate or group query request";
     uses apply-advanced;
     leaf address {
       description "IP address or hostname of web server";
       type string {
         length "1 .. 128";
       }
     }
     leaf client-id {
       description "Client ID for OAuth2 grant";
       type string {
         length "1 .. 64";
       }
     }
     leaf client-secret {
       description "Client secret for OAuth2 grant";
       type string {
         length "1 .. 128";
       }
     }
     leaf port {
       description "Web server port";
       default "591";
       type union {
         type string {
           pattern "<.*>|$.*";
         }
         type uint32 {
           range "1 .. 65535";
         }
       }
     }
   }
   grouping juniper-services-captive-portal {
     uses apply-advanced;
     leaf authentication-profile-name {
       description "Access profile name to use for authentication";
       type string {
         length "1 .. 63";
       }
     }
     container traceoptions {
       description "Trace options for CAPTIVE PORTAL";
       status deprecated;
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "dot1x-debug" {
               description "Trace dot1x events";
             }
             enum "parse" {
               description "Trace configuration parsing";
             }
             enum "esw-if" {
               description "Trace ESW Interactions";
             }
             enum "config-internal" {
               description "Trace configuration internals";
             }
             enum "normal" {
               description "Trace normal events";
             }
             enum "general" {
               description "Trace general events";
             }
             enum "state" {
               description "Trace state transitions";
             }
             enum "task" {
               description "Trace task processing";
             }
             enum "timer" {
               description "Trace task timer processing";
             }
             enum "all" {
               description "Trace everything";
             }
             enum "dot1x-ipc" {
               description "Trace dot1x IPC interactions";
             }
             enum "dot1x-event" {
               description "Trace dot1x events";
             }
           }
         }
         leaf disable {
           description "Disable this trace flag";
           type empty;
         }
       }
     }
     list interface {
       key name;
       description "Captive Portal interface specific options";
       leaf name {
         type string;
       }
       uses apply-advanced;
       leaf supplicant {
         description "Set supplicant mode for this interface";
         type enumeration {
           enum "single" {
             description "Allow multiple clients; authenticate first client only";
           }
           enum "single-secure" {
             description "Allow and authenticate only a single client";
           }
           enum "multiple" {
             description "Allow multiple clients; authenticate each individually";
           }
         }
       }
       leaf retries {
         description "Number of retries after which port is placed into wait state";
         type union {
           type string {
             pattern "<.*>|$.*";
           }
           type uint32 {
             range "1 .. 10";
           }
         }
       }
       leaf quiet-period {
         description "Time to wait after an authentication failure";
         units "seconds";
         type union {
           type string {
             pattern "<.*>|$.*";
           }
           type uint32 {
             range "0 .. 65535";
           }
         }
       }
       leaf server-timeout {
         description "Authentication server timeout interval";
         units "seconds";
         type union {
           type string {
             pattern "<.*>|$.*";
           }
           type uint32 {
             range "1 .. 60";
           }
         }
       }
       leaf session-expiry {
         description "Session Expiry Timeout";
         units "seconds";
         type union {
           type string {
             pattern "<.*>|$.*";
           }
           type uint32 {
             range "1 .. 65535";
           }
         }
       }
       leaf user-keepalive {
         description "Session keepalive after mac-flush";
         units "minutes";
         type union {
           type string {
             pattern "<.*>|$.*";
           }
           type uint32 {
             range "7 .. 65535";
           }
         }
       }
     }
     leaf secure-authentication {
       description "Set secure authentication using encrypted HTTPS or insecure authentication using plain-text HTTP";
       default "http";
       type enumeration {
         enum "http" {
           description "Insecure plain-text HTTP will be used for Captive Portal authentication, username and password can be sniffed";
         }
         enum "https" {
           description "Encrypted HTTPS will be used for Captive Portal authentication";
         }
       }
     }
     container custom-options {
       presence "enable custom-options";
       description "Captive Portal html user interface customization options";
       uses apply-advanced;
       leaf header-logo {
         description "Path to logo image file";
         type string {
           length "1 .. 255";
         }
       }
       leaf header-bgcolor {
         description "Background color of the html header in hex html format";
         type string {
           length 7;
         }
       }
       leaf header-text-color {
         description "Text color of the html header in hex html format";
         type string {
           length 7;
         }
       }
       leaf header-message {
         description "Message to be displayed in the html header";
         type string {
           length "1 .. 2047";
         }
       }
       leaf banner-message {
         description "Terms and Conditions of usage message";
         type string {
           length "1 .. 2047";
         }
       }
       leaf form-header-message {
         description "Message to be displayed in the login form header";
         type string {
           length "1 .. 255";
         }
       }
       leaf form-header-bgcolor {
         description "Background color of the login form header in hex html format";
         type string {
           length 7;
         }
       }
       leaf form-header-text-color {
         description "Text color of the login form header in hex html format";
         type string {
           length 7;
         }
       }
       leaf form-submit-label {
         description "Label to be displayed for the login form submit button";
         type string {
           length "1 .. 255";
         }
       }
       leaf form-reset-label {
         description "Label to be displayed for the login form reset button";
         type string {
           length "1 .. 255";
         }
       }
       leaf footer-message {
         description "Message to be displayed in the html footer";
         type string {
           length "1 .. 2047";
         }
       }
       leaf footer-bgcolor {
         description "Background color of the html footer in hex html format";
         type string {
           length 7;
         }
       }
       leaf footer-text-color {
         description "Text color of the footer in hex html format";
         type string {
           length 7;
         }
       }
       leaf post-authentication-url {
         description "Post authentication redirection URL";
         type string {
           length "1 .. 255";
         }
       }
     }
   }
   grouping li_policy_addr6_simple_object {
     uses apply-advanced;
     leaf address {
       description "Prefix to match";
       type jt:ipv6prefix;
     }
   }
   grouping li_policy_addr_simple_object {
     uses apply-advanced;
     leaf address {
       description "Prefix to match";
       type jt:ipv4prefix;
     }
   }
   grouping macro-data-type {
     leaf name {
       description "Keyword part of the keyword-value pair";
       type string;
     }
     leaf value {
       description "Value part of the keyword-value pair";
       type string;
     }
   }
   grouping match_li_simple_dscp_value {
     uses apply-advanced;
     leaf value_keyword {
       type string;
     }
   }
   grouping match_li_simple_port_value {
     uses apply-advanced;
     leaf value_keyword {
       type string;
     }
   }
   grouping match_li_simple_protocol_value {
     uses apply-advanced;
     leaf value_keyword {
       type string;
     }
   }
   grouping monitor-threshold {
     leaf normal {
       description "Usage under normal conditions";
       type union {
         type string {
           pattern "<.*>|$.*";
         }
         type uint8 {
           range "1 .. 100";
         }
       }
     }
     leaf threshold {
       description "Threshold upon which alarm is raised";
       type union {
         type string {
           pattern "<.*>|$.*";
         }
         type uint8 {
           range "1 .. 100";
         }
       }
     }
   }
   grouping output-plugin {
     leaf name {
       description "Plugin name";
       type string;
     }
     uses apply-advanced;
     list parameters {
       key name;
       ordered-by user;
       description "List of key:value parameters for plugin";
       uses parameter-pair;
     }
   }
   grouping parameter-pair {
     leaf name {
       description "Parameter key";
       type string;
     }
     uses apply-advanced;
     leaf value {
       description "Parameter value";
       type string;
     }
   }
   grouping pcp-object {
     description "Configure Port Control Protocol";
     uses apply-advanced;
     container traceoptions {
       description "Trace options for PCP-LOG";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "all" {
               description "Trace everything";
             }
           }
         }
       }
     }
     list rule-set {
       key name;
       ordered-by user;
       description "Defines a set of PCP rules";
       max-elements 16960;
       leaf name {
         description "Name of the rule set";
         type string {
           length "1 .. 63";
         }
       }
       uses apply-advanced;
       list rule {
         key name;
         ordered-by user;
         description "Rule to be included in this rule set";
         max-elements 16960;
         leaf name {
           description "Rule name";
           type string {
           }
         }
         uses apply-advanced;
       }
     }
   }
   grouping proxy-profile-setting {
     description "Proxy profile settings";
     leaf name {
       description "Proxy profile name";
       type string {
         length "1 .. 64";
       }
     }
     uses apply-advanced;
     container protocol {
       description "Protocol level proxy setting";
       uses apply-advanced;
       container http {
         description "HTTP proxy setting";
         uses apply-advanced;
         leaf host {
           description "Proxy server name or IP address";
           type string {
             length "1 .. 256";
           }
         }
         leaf port {
           description "Proxy server port";
           default "3128";
           type union {
             type string {
               pattern "<.*>|$.*";
             }
             type uint16 {
               range "0 .. 65535";
             }
           }
         }
       }
     }
   }
   grouping rmopd-traceoptions {
     description "Trace options for remote-monitoring";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "ipc" {
             description "Trace ipc messages";
           }
           enum "ppm" {
             description "Trace ppm";
           }
           enum "rpd" {
             description "Trace rpd events";
           }
           enum "info" {
             description "Trace info events";
           }
           enum "statistics" {
             description "Trace statistics";
           }
           enum "error" {
             description "Trace events related to catastrophic errors in daemon";
           }
           enum "all" {
             description "Trace everything";
           }
         }
       }
     }
   }
   grouping secintel-category-disable {
     description "Security intelligence category";
     leaf name {
       description "Name of security intelligence category";
       type enumeration {
         enum "IPFilter" {
           description "IPFilter";
         }
         enum "GeoIP" {
           description "GeoIP";
         }
         enum "CC" {
           description "Command and control";
         }
         enum "Blacklist" {
           description "Blacklist";
         }
         enum "Whitelist" {
           description "Whitelist";
         }
         enum "Infected-Hosts" {
           description "Infected-Hosts";
         }
         enum "SecProfiling" {
           description "SecProfiling";
         }
         enum "DNS" {
           description "DNS";
         }
       }
     }
     uses apply-advanced;
     container disable {
       presence "enable disable";
       description "To disable category for feed update";
     }
   }
   grouping secintel-policy-setting {
     description "Security intelligence policy setting";
     leaf name {
       description "Security intelligence policy name";
       type string {
         length "1 .. 63";
       }
     }
     uses apply-advanced;
     leaf description {
       description "Text description of policy";
       type string {
         length "1 .. 900";
       }
     }
     list category-profiles {
       key name;
       ordered-by user;
       description "Security intelligence category profiles";
       leaf name {
         description "Name of security intelligence category";
         type enumeration {
           enum "IPFilter" {
             description "IPFilter";
           }
           enum "GeoIP" {
             description "GeoIP";
           }
           enum "CC" {
             description "Command and control";
           }
           enum "Infected-Hosts" {
             description "Infected-Hosts";
           }
           enum "DNS" {
             description "DNS";
           }
           enum "Reverse-Shell" {
             description "Reverse-Shell";
           }
         }
       }
       uses apply-advanced;
       leaf profile-name {
         description "Name of profile";
         type string;
       }
     }
   }
   grouping secintel-profile-setting {
     description "Security intelligence profile settings";
     leaf name {
       description "Security intelligence profile name";
       type string {
         length "1 .. 63";
       }
     }
     uses apply-advanced;
     leaf description {
       description "Text description of profile";
       type string {
         length "1 .. 900";
       }
     }
     leaf category {
       description "Profile category name";
       type string;
     }
     list rule {
       key name;
       ordered-by user;
       description "Profile rule name";
       uses secintel-profile-rule;
     }
     container default-rule {
       presence "enable default-rule";
       description "Profile default rule";
       uses apply-advanced;
       container then {
         presence "enable then";
         description "Profile default rule action";
         uses apply-advanced;
         container action {
           description "Security intelligence profile action";
           uses apply-advanced;
           choice action {
             case case_1 {
               leaf permit {
                 description "Permit action";
                 type empty;
               }
             }
             case case_2 {
               container block {
                 description "Block action";
                 uses apply-advanced;
                 choice action {
                   case case_1 {
                     container drop {
                       presence "enable drop";
                       description "Drop packet";
                     }
                   }
                   case case_2 {
                     container close {
                       presence "enable close";
                       description "Close session";
                       uses apply-advanced;
                       container http {
                         description "Http content for block action";
                         uses apply-advanced;
                         choice http-choice {
                           case case_1 {
                             leaf file {
                               description "File name for http response to client";
                               type string;
                             }
                           }
                           case case_2 {
                             leaf message {
                               description "Block message to client";
                               type string;
                             }
                           }
                           case case_3 {
                             leaf redirect-url {
                               description "Redirect url to client";
                               type string {
                                 length "1 .. 1023";
                               }
                             }
                           }
                         }
                       }
                     }
                   }
                 }
               }
             }
             case case_3 {
               container recommended {
                 presence "enable recommended";
                 description "Recommended action from feed server";
               }
             }
             case case_4 {
               leaf sinkhole {
                 description "DNS sinkhole for DNS profile";
                 type empty;
               }
             }
           }
         }
         choice log-choice {
           leaf log {
             description "Log security intelligence block action";
             type empty;
           }
           leaf no-log {
             description "Don't log security intelligence block action";
             type empty;
           }
         }
       }
     }
   }
   grouping secintel-profile-rule {
     description "Security intelligence profile rule";
     leaf name {
       description "Profile rule name";
       type string {
         length "1 .. 63";
       }
     }
     uses apply-advanced;
     container match {
       description "Profile matching feed name and threat levels";
       uses apply-advanced;
       list feed-name {
         key name;
         ordered-by user;
         description "Profile matching feed name";
         max-elements 32;
         leaf name {
           type string {
             length "1 .. 63";
           }
         }
         uses apply-advanced;
       }
       leaf-list threat-level {
         ordered-by user;
         description "Profile matching threat levels, higher number is more severe";
         type union {
           type uint32;
           type string {
             pattern "<.*>|$.*";
           }
         }
       }
     }
     container then {
       description "Profile action and log";
       uses apply-advanced;
       container action {
         description "Security intelligence profile action";
         uses apply-advanced;
         choice action {
           case case_1 {
             leaf permit {
               description "Permit action";
               type empty;
             }
           }
           case case_2 {
             container block {
               description "Block action";
               uses apply-advanced;
               choice action {
                 case case_1 {
                   container drop {
                     presence "enable drop";
                     description "Drop packet";
                   }
                 }
                 case case_2 {
                   container close {
                     presence "enable close";
                     description "Close session";
                     uses apply-advanced;
                     container http {
                       description "Http content for block action";
                       uses apply-advanced;
                       choice http-choice {
                         case case_1 {
                           leaf file {
                             description "File name for http response to client";
                             type string;
                           }
                         }
                         case case_2 {
                           leaf message {
                             description "Block message to client";
                             type string;
                           }
                         }
                         case case_3 {
                           leaf redirect-url {
                             description "Redirect url to client";
                             type string {
                               length "1 .. 1023";
                             }
                           }
                         }
                       }
                     }
                   }
                 }
               }
             }
           }
           case case_3 {
             container recommended {
               presence "enable recommended";
               description "Recommended action from feed server";
             }
           }
           case case_4 {
             leaf sinkhole {
               description "DNS sinkhole for DNS profile";
               type empty;
             }
           }
         }
       }
       container log {
         presence "enable log";
         description "Log security intelligence block action";
       }
     }
   }
   grouping secintel-traceoptions {
     description "Security intelligence trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "blacklist" {
             description "Trace security intelligence Blacklist category";
           }
           enum "cc" {
             description "Trace security intelligence CC category";
           }
           enum "infected-hosts" {
             description "Trace security intelligence Infected-Hosts category";
           }
           enum "control" {
             description "Trace control plane";
           }
           enum "feed" {
             description "Trace feed operation";
           }
           enum "ipc" {
             description "Trace ipc module";
           }
           enum "infrastucture" {
             description "Trace infrastucture functions";
           }
           enum "jwas" {
             description "Trace security intelligence JWAS category";
           }
           enum "plugin" {
             description "Trace security intelligence plugin services";
           }
           enum "whitelist" {
             description "Trace security intelligence Whitelist category";
           }
           enum "secprofiling" {
             description "Trace security intelligence Secprofiling category";
           }
           enum "reverse-shell" {
             description "Trace security intelligence reverse-shell category";
           }
         }
       }
     }
   }
   grouping server-connection-type {
     description "Connection parameters per server";
     uses apply-advanced;
     leaf address {
       description "IP address";
       type string;
     }
     leaf ca-certificate {
       description "Ca-certificate file name";
       type string {
         length "1 .. 256";
       }
     }
     leaf client-id {
       description "Client ID for OAuth2 grant";
       type string {
         length "1 .. 64";
       }
     }
     leaf client-secret {
       description "Client secret for OAuth2 grant";
       type string {
         length "1 .. 128";
       }
     }
   }
   grouping service_device_pool_object {
     leaf name {
       description "Service device pool name";
       type string {
         length "1 .. 63";
       }
     }
     uses apply-advanced;
     list interface {
       key name;
       ordered-by user;
       description "Service device name";
       leaf name {
         type string;
       }
       uses apply-advanced;
     }
   }
   grouping service_interface_pool_object {
     leaf name {
       description "Service interface pool name";
       type string {
         length "1 .. 63";
       }
     }
     uses apply-advanced;
     list interface {
       key name;
       ordered-by user;
       description "Service interface name";
       leaf name {
         type union {
           type jt:interface-unit;
           type string {
             pattern "<.*>|$.*";
           }
         }
       }
       uses apply-advanced;
     }
   }
   grouping softwires-object {
     description "Configure softwire feature";
     uses apply-advanced;
     list softwire-name {
       key name;
       description "Configure softwire object";
       uses softwire-option-type;
     }
     container softwire-types {
       description "Configure softwire objects";
       uses apply-advanced;
       list v6rd {
         key name;
         description "Configure v6rd object";
         uses softwire-option-type;
       }
       list ds-lite {
         key name;
         description "Configure ds-lite object";
         uses softwire-option-type;
       }
       list map-e {
         key name;
         ordered-by user;
         description "Configure Map-e object";
         uses map-e-domain;
       }
       list map-t {
         key name;
         ordered-by user;
         description "Configure Map-t object";
         uses map-t-domain;
       }
     }
     list map-e {
       key name;
       ordered-by user;
       description "Configure a MAP-E domain and domain rules";
       max-elements 1;
       uses map-e-domain;
     }
     container traceoptions {
       description "Trace options for Network Security DS-Lite";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "all" {
               description "Trace everything";
             }
           }
         }
       }
     }
     list rule-set {
       key name;
       ordered-by user;
       description "Define a softwire rule set";
       uses sw-rule-set-object;
     }
   }
   grouping map-e-domain {
     description "Configure a MAP-E domain";
     leaf name {
       description "MAP-E domain name";
       type string {
         length "1 .. 11";
       }
     }
     uses apply-advanced;
     leaf confidentiality {
       description "Configure JUNOS MAP-E confidentiality";
       type empty;
     }
     leaf br-address {
       description "Ipv6 address of BR";
       type jt:unreadable;
     }
     container end-user-prefix {
       description "Configure end-user-prefix value or source interface for obtaining end-user-prefix";
       uses apply-advanced;
       leaf prefix-value {
         description "End user prefix";
         type jt:ipv6prefix;
       }
     }
     list rule {
       key name;
       ordered-by user;
       description "Configure a BMR or FMR rule for map-e ";
       max-elements 101;
       uses map-e-rule;
     }
     leaf role {
       description "Define a role of the MAP-E";
       type enumeration {
         enum "CE" {
           description "CE deployment";
         }
       }
     }
     leaf version {
       description "Define version of the MAP-E";
       type enumeration {
         enum "3" {
           description "Version 3: draft-ietf-softwire-map-03";
         }
       }
     }
   }
   grouping map-e-rule {
     description "Configure a MAP-E rule";
     leaf name {
       description "MAP-E rule name";
       type string {
         length "1 .. 11";
       }
     }
     uses apply-advanced;
     leaf rule-type {
       description "Define a rule type of MAP-E";
       type enumeration {
         enum "BMR" {
           description "Define BMR rule type";
         }
         enum "FMR" {
           description "Define FMR rule type";
         }
       }
     }
     leaf ipv4-prefix {
       description "Ipv4 prefix";
       type jt:unreadable;
     }
     leaf ipv6-prefix {
       description "Ipv6 prefix";
       type jt:unreadable;
     }
     leaf ea-bits-length {
       description "EA bits length";
       type string {
         length "1 .. 2";
       }
     }
     leaf psid-offset {
       description "PSID offset";
       type jt:unreadable;
     }
     leaf psid-len {
       description "PSID length";
       type union {
         type string {
           pattern "<.*>|$.*";
         }
         type uint32 {
           range "0 .. 16";
         }
       }
     }
     leaf mtu-v6 {
       description "MTU for the softwire tunnel";
       default "9192";
       type union {
         type string {
           pattern "<.*>|$.*";
         }
         type uint32 {
           range "1280 .. 9192";
         }
       }
     }
     leaf v4-reassembly {
       description "MAP-E IPv4 reassembly support";
       type empty;
     }
     leaf v6-reassembly {
       description "MAP-E IPv6 reassembly support";
       type empty;
     }
     leaf disable-auto-route {
       description "MAP-E Disable Auto Route";
       type empty;
     }
     leaf v4-partial-reassembly {
       description "For higher number of fragments/reassembled packet size";
       type empty;
     }
   }
   grouping map-t-domain {
     description "Configure a MAP-T domain";
     leaf name {
       description "MAP-T domain name";
       type string {
         length "1 .. 11";
       }
     }
     uses apply-advanced;
     leaf dmr-address {
       description "Ipv6 address of DMR";
       type jt:ipv6prefix;
     }
     list rule {
       key name;
       ordered-by user;
       description "Configure a BMR rule for map-t ";
       max-elements 1;
       uses map-t-rule;
     }
   }
   grouping map-t-rule {
     description "Configure a MAP-T rule";
     leaf name {
       description "MAP-T rule name";
       type string {
         length "1 .. 11";
       }
     }
     uses apply-advanced;
     leaf ipv4-prefix {
       description "Ipv4 prefix";
       type jt:ipv4prefix;
     }
     leaf ipv6-prefix {
       description "Ipv6 prefix";
       type jt:ipv6prefix;
     }
     leaf ea-bits-length {
       description "EA bits length";
       type union {
         type string {
           pattern "<.*>|$.*";
         }
         type uint32 {
           range "0 .. 48";
         }
       }
     }
     leaf psid-offset {
       description "PSID offset";
       type union {
         type string {
           pattern "<.*>|$.*";
         }
         type uint32 {
           range "0 .. 16";
         }
       }
     }
     leaf psid-len {
       description "PSID length";
       type union {
         type string {
           pattern "<.*>|$.*";
         }
         type uint32 {
           range "0 .. 16";
         }
       }
     }
     leaf v4-reassembly {
       description "MAP-T IPv4 reassembly support";
       type empty;
     }
     leaf v6-reassembly {
       description "MAP-T IPv6 reassembly support";
       type empty;
     }
     leaf mtu-v6 {
       description "MTU for the softwire tunnel";
       default "9192";
       type union {
         type string {
           pattern "<.*>|$.*";
         }
         type uint32 {
           range "1280 .. 9192";
         }
       }
     }
   }
   grouping softwire-option-type {
     description "Configure softwire object";
     leaf name {
       description "DS-Lite/Softwire object name";
       type string {
         length "1 .. 23";
       }
     }
     uses apply-advanced;
     leaf softwire-concentrator {
       description "Concentrator address";
       type jt:ipaddr;
     }
     leaf softwire-type {
       description "Softwire-type";
       default "IPv4-in-IPv6";
       type enumeration {
         enum "IPv4-in-IPv6" {
           description "Ipv4-in-IPv6";
         }
         enum "v6rd" {
           description "V6rd";
         }
       }
     }
     leaf ipv4-prefix {
       description "6rd customer edge IPV4 prefix";
       type jt:ipv4prefix;
     }
     leaf v6rd-prefix {
       description "6rd domain's IPV6 prefix";
       type jt:ipv6prefix;
     }
     leaf mtu-v4 {
       description "MTU for the softwire tunnel";
       type union {
         type string {
           pattern "<.*>|$.*";
         }
         type uint32 {
           range "576 .. 9192";
         }
       }
     }
     leaf mtu-v6 {
       description "MTU for the softwire tunnel";
       type union {
         type string {
           pattern "<.*>|$.*";
         }
         type uint32 {
           range "1280 .. 9192";
         }
       }
     }
     leaf auto-update-mtu {
       description "Auto update MTU from received ICMPv6 messages";
       type empty;
     }
     leaf copy-dscp {
       description "Copy DSCP (type of service) from IPv6 to IPv4 header";
       type empty;
     }
     leaf flow-limit {
       description "Max Number of IPv4 flows per Softwire";
       default "0";
       type union {
         type string {
           pattern "<.*>|$.*";
         }
         type uint32 {
           range "0 .. 16384";
         }
       }
     }
     leaf session-limit-per-prefix {
       description "Max number of sessions allowed per Softwire prefix";
       default "0";
       type union {
         type string {
           pattern "<.*>|$.*";
         }
         type uint32 {
           range "0 .. 16384";
         }
       }
     }
     leaf pre-fragmentation {
       description "Ip fragmentation options for the softwire tunnel";
       default "on";
       type enumeration {
         enum "on" {
           description "Enable pre-fragmentation for the softwire tunnel";
         }
         enum "clear-df-bit" {
           description "Clear df bit of inner v4 packet";
         }
         enum "off" {
           description "Disable pre-fragmentation for the softwire tunnel";
         }
       }
     }
     leaf post-fragmentation {
       description "Post fragmentation options for the softwire tunnel";
       default "off";
       type enumeration {
         enum "off" {
           description "Disable post-fragmentation for the softwire tunnel";
         }
         enum "on" {
           description "Enable post-fragmentation for the softwire tunnel";
         }
       }
     }
     leaf services-offload-off {
       description "Disable services offload at softwire concentrator level";
       type empty;
     }
     leaf power-mode-disable {
       description "Power mode disabled for the softwire tunnel";
       type empty;
     }
   }
   grouping srd-rs-id-object {
     description "Definition of redundancy-set";
     leaf name {
       description "Redundancy set identifier";
       type union {
         type string {
           pattern "<.*>|$.*";
         }
         type uint32 {
           range "1 .. 100";
         }
       }
     }
     uses apply-advanced;
     leaf redundancy-group {
       description "Name of redundancy-group";
       type union {
         type string {
           pattern "<.*>|$.*";
         }
         type uint32 {
           range "1 .. 16";
         }
       }
     }
     leaf-list redundancy-policy {
       description "Redundancy-policy list";
       type string;
     }
     leaf keepalive {
       description "Frequency of SRD hello messages";
       default "10";
       units "seconds";
       type union {
         type string {
           pattern "<.*>|$.*";
         }
         type uint32 {
           range "1 .. 60";
         }
       }
     }
     leaf hold-time {
       description "Time before SRD peer is declared down";
       default "30";
       units "seconds";
       type union {
         type string {
           pattern "<.*>|$.*";
         }
         type uint32 {
           range "0 .. 3600";
         }
       }
     }
     leaf healthcheck-timer-interval {
       description "Healthcheck timer interval";
       default "5";
       units "seconds";
       type union {
         type string {
           pattern "<.*>|$.*";
         }
         type uint32 {
           range "1 .. 3600";
         }
       }
     }
   }
   grouping srd-traceoptions-object {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "config" {
             description "Trace parse events";
           }
           enum "connect" {
             description "Trace ipc events";
           }
           enum "route" {
             description "Trace route events";
           }
           enum "ssd" {
             description "Trace SDK Service events";
           }
           enum "snmp" {
             description "Trace snmp events";
           }
           enum "system" {
             description "Trace services redundancy system events";
           }
           enum "opcmd" {
             description "Trace operational command events";
           }
           enum "state-machine" {
             description "Trace finite-state-machine events";
           }
           enum "kcom" {
             description "Trace KCOM events";
           }
           enum "database" {
             description "Trace database events";
           }
           enum "swithover" {
             description "Trace switchover events";
           }
           enum "stateful-sync" {
             description "Trace stateful-sync related events";
           }
           enum "redundancy-group" {
             description "Trace redundancy-group related events";
           }
           enum "all" {
             description "Trace everything";
           }
         }
       }
     }
   }
   grouping ssl-initiation-config {
     uses apply-advanced;
     list profile {
       key name;
       ordered-by user;
       description "SSL client profile";
       leaf name {
         description "Profile identifier";
         type string {
           length "1 .. 63";
         }
       }
       uses apply-advanced;
       leaf enable-flow-tracing {
         description "Enable flow tracing for the profile";
         type empty;
       }
       leaf supported-ec-groups {
         description "Supported electic curve groups";
         type enumeration {
           enum "P-256" {
             description "P-256 group";
           }
           enum "P-384" {
             description "P-384 group";
           }
           enum "P-521" {
             description "P-521 group";
           }
         }
       }
       leaf protocol-version {
         description "Protocol SSL version accepted";
         default "all";
         type enumeration {
           enum "all" {
             description "TLS version 1.0 or TLS version 1.1 or TLS version 1.2 or TLS version 1.3";
           }
           enum "ssl3" {
             description "SSL version 3";
           }
           enum "tls1" {
             description "TLS version 1";
           }
           enum "tls11" {
             description "TLS version 1.1";
           }
           enum "tls12" {
             description "TLS version 1.2";
           }
           enum "tls13" {
             description "TLS version 1.3";
           }
           enum "tls12-and-lower" {
             description "Dont support TLS 1.3 (downgrade all the connections to TLS 1.2 or below)";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
           }
         }
       }
       leaf-list custom-ciphers {
         ordered-by user;
         description "Custom cipher list";
         type enumeration {
           enum "tls12-rsa-aes-128-cbc-sha" {
             description "RSA, 128 bit aes/cbc, sha hash";
           }
           enum "tls12-rsa-aes-256-cbc-sha" {
             description "RSA, 256 bit aes/cbc, sha hash";
           }
           enum "tls12-rsa-aes-256-gcm-sha384" {
             description "RSA, 256 bit aes/gcm, sha384 hash ";
           }
           enum "tls12-rsa-aes-256-cbc-sha256" {
             description "RSA, 256 bit aes/cbc, sha256 hash";
           }
           enum "tls12-rsa-aes-128-gcm-sha256" {
             description "RSA, 128 bit aes/gcm, sha256 hash";
           }
           enum "tls12-rsa-aes-128-cbc-sha256" {
             description "RSA, 128 bit aes/cbc, sha256 hash";
           }
           enum "tls12-ecdhe-rsa-aes-256-gcm-sha384" {
             description "ECDHE/rsa, 256 bit aes/gcm, sha384 hash";
           }
           enum "tls12-ecdhe-rsa-aes-256-cbc-sha" {
             description "ECDHE/rsa, 256 bit aes/cbc, sha hash";
           }
           enum "tls12-ecdhe-rsa-aes-256-cbc-sha384" {
             description "ECDHE/rsa, 256 bit aes/cbc, sha384 hash";
           }
           enum "tls12-ecdhe-rsa-3des-ede-cbc-sha" {
             description "ECDHE/rsa, 3des ede/cbc, sha hash";
           }
           enum "tls12-ecdhe-rsa-aes-128-gcm-sha256" {
             description "ECDHE/rsa, 128 bit aes/gcm, sha256 hash";
           }
           enum "tls12-ecdhe-rsa-aes-128-cbc-sha" {
             description "ECDHE/rsa, 128 bit aes/cbc, sha hash";
           }
           enum "tls12-ecdhe-rsa-aes-128-cbc-sha256" {
             description "ECDHE/rsa, 128 bit aes/cbc, sha256 hash";
           }
           enum "tls12-rsa-aes-128-ccm-sha256" {
             description "RSA, 128 bit aes/ccm, sha256 hash";
           }
           enum "tls12-rsa-aes-128-ccm8-sha256" {
             description "RSA, 128 bit aes/ccm8, sha256 hash";
           }
           enum "tls12-rsa-aes-256-ccm-sha256" {
             description "RSA, 256 bit aes/ccm, sha256 hash";
           }
           enum "tls12-rsa-aes-256-ccm8-sha256" {
             description "RSA, 128 bit aes/ccm8, sha256 hash";
           }
           enum "tls12-ecdhe-ecdsa-aes-128-ccm-sha256" {
             description "ECDHE,ECDSA, 128 bit aes/ccm, sha256 hash";
           }
           enum "tls12-ecdhe-ecdsa-aes-256-ccm-sha256" {
             description "ECDHE,ECDSA, 256 bit aes/ccm, sha256 hash";
           }
           enum "tls12-ecdhe-ecdsa-aes-128-ccm8-sha256" {
             description "ECDHE,ECDSA, 128 bit aes/ccm8, sha256 hash";
           }
           enum "tls12-ecdhe-ecdsa-aes-256-ccm8-sha256" {
             description "ECDHE,ECDSA, 256 bit aes/ccm8, sha256 hash";
           }
           enum "tls12-ecdhe-rsa-chacha20-poly1305-sha256" {
             description "ECDHE/rsa, chacha_poly , sha256 hash";
           }
           enum "tls12-ecdhe-ecdsa-aes-256-gcm-sha384" {
             description "ECDHE,ECDSA, 256 bit aes/gcm, sha384 hash";
           }
           enum "tls12-ecdhe-ecdsa-aes-256-cbc-sha" {
             description "ECDHE,ECDSA, 256 bit aes/cbc, sha hash";
           }
           enum "tls12-ecdhe-ecdsa-aes-256-cbc-sha384" {
             description "ECDHE,ECDSA, 256 bit aes/cbc, sha384 hash";
           }
           enum "tls12-ecdhe-ecdsa-aes-128-gcm-sha256" {
             description "ECDHE,ECDSA, 128 bit aes/gcm, sha256 hash";
           }
           enum "tls12-ecdhe-ecdsa-aes-128-cbc-sha" {
             description "ECDHE,ECDSA, 128 bit aes/cbc, sha hash";
           }
           enum "tls12-ecdhe-ecdsa-aes-128-cbc-sha256" {
             description "ECDHE,ECDSA, 128 bit aes/cbc, sha256 hash";
           }
           enum "tls12-ecdhe-ecdsa-3des-ede-cbc-sha" {
             description "ECDHE,ECDSA, 3des ede/cbc, sha hash";
           }
           enum "dhe-rsa-with-aes-128-ccm8-sha256" {
             description "DHE/rsa, 128 bit aes/ccm8, sha256 hash";
           }
           enum "dhe-rsa-with-aes-256-ccm8-sha256" {
             description "DHE/rsa, 256 bit aes/ccm8, sha256 hash";
           }
           enum "dhe-rsa-with-aes-256-ccm-sha256" {
             description "DHE/rsa, 256 bit aes/ccm, sha256 hash";
           }
           enum "dhe-rsa-with-aes-128-ccm-sha256" {
             description "DHE/rsa, 128 bit aes/ccm, sha256 hash";
           }
           enum "tls12-ecdhe-ecdsa-chacha20-poly1305-sha256" {
             description "ECDHE,ECDSA, chacha_poly, sha256 hash";
           }
           enum "tls13-with-aes-256-gcm-sha384" {
             description "Any key-exchange, Any authentication,256bit aes, sha384 hash";
           }
           enum "tls13-with-aes-128-gcm-sha256" {
             description "Any key-exchange, Any authentication,128bit aes, sha256 hash";
           }
           enum "tls13-with-chacha20-poly1305-sha256" {
             description "Any key-exchange, Any authentication,chacha, sha256 hash";
           }
           enum "tls13-with-aes-128-ccm-sha256" {
             description "Any key-exchange, Any authentication,128bit aes, sha256 hash";
           }
           enum "tls13-with-aes-128-ccm8-sha256" {
             description "Any key-exchange, Any authentication,128bit aes, sha256 hash";
           }
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
           }
           enum "rsa-with-aes-256-cbc-sha" {
             description "RSA, 256 bit aes/cbc, sha hash";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
           enum "dhe-rsa-with-aes-256-gcm-sha384" {
             description "DHE/rsa, 256 bit aes/gcm, sha384 hash";
           }
           enum "dhe-rsa-with-aes-256-cbc-sha" {
             description "DHE/rsa, 256 bit aes/cbc, sha hash";
           }
           enum "dhe-rsa-with-aes-256-cbc-sha256" {
             description "DHE/rsa, 256 bit aes/cbc, sha256 hash";
           }
           enum "dhe-rsa-with-3des-ede-cbc-sha" {
             description "DHE/rsa, 3des ede/cbc, sha hash";
           }
           enum "dhe-rsa-with-aes-128-gcm-sha256" {
             description "DHE/rsa, 128 bit aes/gcm, sha256 hash";
           }
           enum "dhe-rsa-with-aes-128-cbc-sha" {
             description "DHE/rsa, 128 bit aes/cbc, sha hash";
           }
           enum "dhe-rsa-with-aes-128-cbc-sha256" {
             description "DHE/rsa, 128 bit aes/cbc, sha256 hash";
           }
         }
         max-elements 64;
       }
       leaf enable-session-cache {
         description "Enable SSL session cache";
         type empty;
       }
       leaf-list trusted-ca {
         ordered-by user;
         description "List of trusted certificate authority profiles";
         type string;
         max-elements 400;
       }
       container crypto-hardware-offload {
         presence "enable crypto-hardware-offload";
         description "Config related to crypto hardware offload";
         uses apply-advanced;
         leaf tpm {
           description "Enable TPM hardware offload";
           type empty;
         }
       }
       leaf client-certificate {
         description "Local certificate identifier";
         type string {
         }
       }
       container actions {
         description "Traffic related actions";
         uses apply-advanced;
         leaf ignore-server-auth-failure {
           description "Ignore server authentication failure";
           type empty;
         }
         container crl {
           description "Certificate Revocation actions.";
           leaf disable {
             description "Disable CRL validation.";
             type empty;
           }
           leaf if-not-present {
             description "Action if CRL information is not present.";
             default "allow";
             type enumeration {
               enum "allow" {
                 description "Allow session if CRL information is not present.";
               }
               enum "drop" {
                 description "Drop session if CRL information is not present.";
               }
             }
           }
           leaf ignore-hold-instruction-code {
             description "Ignore 'Hold Instruction Code' present in the CRL entry.";
             type empty;
           }
         }
         leaf unsupported-cipher-on-hw {
           description "Unsupported cipher processing on hardware mode";
           default "drop";
           type enumeration {
             enum "drop" {
               description "Drop session if cipher isn't supported on hardware mode";
             }
             enum "software-inspection" {
               description "Allow session in software mode";
             }
           }
         }
       }
     }
   }
   grouping ssl-proxy-config {
     uses apply-advanced;
     container global-config {
       description "Global proxy configuration";
       uses apply-advanced;
       leaf session-cache-timeout {
         description "Session cache timeout";
         units "seconds";
         type union {
           type string {
             pattern "<.*>|$.*";
           }
           type uint32 {
             range "300 .. 86400";
           }
         }
       }
       leaf disable-cert-cache {
         description "Disable proxy mode certificate cache";
         type empty;
       }
       leaf certificate-cache-timeout {
         description "Certificate cache timeout";
         units "seconds";
         type union {
           type string {
             pattern "<.*>|$.*";
           }
           type uint32 {
             range "300 .. 3600";
           }
         }
       }
       leaf invalidate-cache-on-crl-update {
         description "Invalidate certificate cache on crl update";
         type empty;
       }
       leaf cache-usage-enforcement-threshold {
         description "Percentage of total cache size after which per lsys limits will be enforced";
         type union {
           type string {
             pattern "<.*>|$.*";
           }
           type uint32 {
             range "1 .. 100";
           }
         }
       }
       leaf disable-deferred-profile-selection {
         description "Disable the deferred profile selection mechanism";
         type empty;
       }
       container non-ssl-detection-threshold {
         presence "enable non-ssl-detection-threshold";
         description "Thresholds that allow user to decide how long to wait for STARTTLS/AUTHTLS (EMAIL,FTP)";
         uses apply-advanced;
         leaf packet-threshold {
           description "Number of plain packets in C2S direction after which session will be ignored";
           default "5";
           type union {
             type string {
               pattern "<.*>|$.*";
             }
             type uint32 {
               range "1 .. 15";
             }
           }
         }
         leaf byte-threshold {
           description "Minimum bytes required to ignore the session";
           default "200";
           type union {
             type string {
               pattern "<.*>|$.*";
             }
             type uint32 {
               range "1 .. 600";
             }
           }
         }
       }
       container actions {
         description "Define global ssl proxy actions";
         uses apply-advanced;
       }
     }
     list profile {
       key name;
       ordered-by user;
       description "SSL Proxy profile";
       leaf name {
         description "Profile identifier";
         type string {
           length "1 .. 63";
         }
       }
       uses apply-advanced;
       leaf enable-flow-tracing {
         description "Enable flow tracing for the profile";
         type empty;
       }
       leaf supported-ec-groups {
         description "Supported electic curve groups";
         type enumeration {
           enum "P-256" {
             description "P-256 group";
           }
           enum "P-384" {
             description "P-384 group";
           }
           enum "P-521" {
             description "P-521 group";
           }
         }
       }
       leaf protocol-version {
         description "Protocol SSL version accepted";
         default "all";
         type enumeration {
           enum "all" {
             description "TLS version 1.0 or TLS version 1.1 or TLS version 1.2 or TLS version 1.3";
           }
           enum "ssl3" {
             description "SSL version 3";
           }
           enum "tls1" {
             description "TLS version 1";
           }
           enum "tls11" {
             description "TLS version 1.1";
           }
           enum "tls12" {
             description "TLS version 1.2";
           }
           enum "tls13" {
             description "TLS version 1.3";
           }
           enum "tls12-and-lower" {
             description "Dont support TLS 1.3 (downgrade all the connections to TLS 1.2 or below)";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
           }
         }
       }
       leaf-list custom-ciphers {
         ordered-by user;
         description "Custom cipher list";
         type enumeration {
           enum "tls12-rsa-aes-128-cbc-sha" {
             description "RSA, 128 bit aes/cbc, sha hash";
           }
           enum "tls12-rsa-aes-256-cbc-sha" {
             description "RSA, 256 bit aes/cbc, sha hash";
           }
           enum "tls12-rsa-aes-256-gcm-sha384" {
             description "RSA, 256 bit aes/gcm, sha384 hash ";
           }
           enum "tls12-rsa-aes-256-cbc-sha256" {
             description "RSA, 256 bit aes/cbc, sha256 hash";
           }
           enum "tls12-rsa-aes-128-gcm-sha256" {
             description "RSA, 128 bit aes/gcm, sha256 hash";
           }
           enum "tls12-rsa-aes-128-cbc-sha256" {
             description "RSA, 128 bit aes/cbc, sha256 hash";
           }
           enum "tls12-ecdhe-rsa-aes-256-gcm-sha384" {
             description "ECDHE/rsa, 256 bit aes/gcm, sha384 hash";
           }
           enum "tls12-ecdhe-rsa-aes-256-cbc-sha" {
             description "ECDHE/rsa, 256 bit aes/cbc, sha hash";
           }
           enum "tls12-ecdhe-rsa-aes-256-cbc-sha384" {
             description "ECDHE/rsa, 256 bit aes/cbc, sha384 hash";
           }
           enum "tls12-ecdhe-rsa-3des-ede-cbc-sha" {
             description "ECDHE/rsa, 3des ede/cbc, sha hash";
           }
           enum "tls12-ecdhe-rsa-aes-128-gcm-sha256" {
             description "ECDHE/rsa, 128 bit aes/gcm, sha256 hash";
           }
           enum "tls12-ecdhe-rsa-aes-128-cbc-sha" {
             description "ECDHE/rsa, 128 bit aes/cbc, sha hash";
           }
           enum "tls12-ecdhe-rsa-aes-128-cbc-sha256" {
             description "ECDHE/rsa, 128 bit aes/cbc, sha256 hash";
           }
           enum "tls12-rsa-aes-128-ccm-sha256" {
             description "RSA, 128 bit aes/ccm, sha256 hash";
           }
           enum "tls12-rsa-aes-128-ccm8-sha256" {
             description "RSA, 128 bit aes/ccm8, sha256 hash";
           }
           enum "tls12-rsa-aes-256-ccm-sha256" {
             description "RSA, 256 bit aes/ccm, sha256 hash";
           }
           enum "tls12-rsa-aes-256-ccm8-sha256" {
             description "RSA, 128 bit aes/ccm8, sha256 hash";
           }
           enum "tls12-ecdhe-ecdsa-aes-128-ccm-sha256" {
             description "ECDHE,ECDSA, 128 bit aes/ccm, sha256 hash";
           }
           enum "tls12-ecdhe-ecdsa-aes-256-ccm-sha256" {
             description "ECDHE,ECDSA, 256 bit aes/ccm, sha256 hash";
           }
           enum "tls12-ecdhe-ecdsa-aes-128-ccm8-sha256" {
             description "ECDHE,ECDSA, 128 bit aes/ccm8, sha256 hash";
           }
           enum "tls12-ecdhe-ecdsa-aes-256-ccm8-sha256" {
             description "ECDHE,ECDSA, 256 bit aes/ccm8, sha256 hash";
           }
           enum "tls12-ecdhe-rsa-chacha20-poly1305-sha256" {
             description "ECDHE/rsa, chacha_poly , sha256 hash";
           }
           enum "tls12-ecdhe-ecdsa-aes-256-gcm-sha384" {
             description "ECDHE,ECDSA, 256 bit aes/gcm, sha384 hash";
           }
           enum "tls12-ecdhe-ecdsa-aes-256-cbc-sha" {
             description "ECDHE,ECDSA, 256 bit aes/cbc, sha hash";
           }
           enum "tls12-ecdhe-ecdsa-aes-256-cbc-sha384" {
             description "ECDHE,ECDSA, 256 bit aes/cbc, sha384 hash";
           }
           enum "tls12-ecdhe-ecdsa-aes-128-gcm-sha256" {
             description "ECDHE,ECDSA, 128 bit aes/gcm, sha256 hash";
           }
           enum "tls12-ecdhe-ecdsa-aes-128-cbc-sha" {
             description "ECDHE,ECDSA, 128 bit aes/cbc, sha hash";
           }
           enum "tls12-ecdhe-ecdsa-aes-128-cbc-sha256" {
             description "ECDHE,ECDSA, 128 bit aes/cbc, sha256 hash";
           }
           enum "tls12-ecdhe-ecdsa-3des-ede-cbc-sha" {
             description "ECDHE,ECDSA, 3des ede/cbc, sha hash";
           }
           enum "dhe-rsa-with-aes-128-ccm8-sha256" {
             description "DHE/rsa, 128 bit aes/ccm8, sha256 hash";
           }
           enum "dhe-rsa-with-aes-256-ccm8-sha256" {
             description "DHE/rsa, 256 bit aes/ccm8, sha256 hash";
           }
           enum "dhe-rsa-with-aes-256-ccm-sha256" {
             description "DHE/rsa, 256 bit aes/ccm, sha256 hash";
           }
           enum "dhe-rsa-with-aes-128-ccm-sha256" {
             description "DHE/rsa, 128 bit aes/ccm, sha256 hash";
           }
           enum "tls12-ecdhe-ecdsa-chacha20-poly1305-sha256" {
             description "ECDHE,ECDSA, chacha_poly, sha256 hash";
           }
           enum "tls13-with-aes-256-gcm-sha384" {
             description "Any key-exchange, Any authentication,256bit aes, sha384 hash";
           }
           enum "tls13-with-aes-128-gcm-sha256" {
             description "Any key-exchange, Any authentication,128bit aes, sha256 hash";
           }
           enum "tls13-with-chacha20-poly1305-sha256" {
             description "Any key-exchange, Any authentication,chacha, sha256 hash";
           }
           enum "tls13-with-aes-128-ccm-sha256" {
             description "Any key-exchange, Any authentication,128bit aes, sha256 hash";
           }
           enum "tls13-with-aes-128-ccm8-sha256" {
             description "Any key-exchange, Any authentication,128bit aes, sha256 hash";
           }
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
           }
           enum "rsa-with-aes-256-cbc-sha" {
             description "RSA, 256 bit aes/cbc, sha hash";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
           enum "dhe-rsa-with-aes-256-gcm-sha384" {
             description "DHE/rsa, 256 bit aes/gcm, sha384 hash";
           }
           enum "dhe-rsa-with-aes-256-cbc-sha" {
             description "DHE/rsa, 256 bit aes/cbc, sha hash";
           }
           enum "dhe-rsa-with-aes-256-cbc-sha256" {
             description "DHE/rsa, 256 bit aes/cbc, sha256 hash";
           }
           enum "dhe-rsa-with-3des-ede-cbc-sha" {
             description "DHE/rsa, 3des ede/cbc, sha hash";
           }
           enum "dhe-rsa-with-aes-128-gcm-sha256" {
             description "DHE/rsa, 128 bit aes/gcm, sha256 hash";
           }
           enum "dhe-rsa-with-aes-128-cbc-sha" {
             description "DHE/rsa, 128 bit aes/cbc, sha hash";
           }
           enum "dhe-rsa-with-aes-128-cbc-sha256" {
             description "DHE/rsa, 128 bit aes/cbc, sha256 hash";
           }
         }
         max-elements 64;
       }
       leaf-list trusted-ca {
         ordered-by user;
         description "List of trusted certificate authority profiles";
         type string;
         max-elements 400;
       }
       choice certificate {
         case case_1 {
           leaf-list root-ca {
             ordered-by user;
             description "Root certificate for interdicting server certificates in proxy mode";
             type string;
             max-elements 2;
           }
         }
         case case_2 {
           leaf-list server-certificate {
             ordered-by user;
             description "Local certificate identifier";
             type string;
             max-elements 400;
           }
         }
       }
       container mirror-decrypt-traffic {
         description "Configure mirror interface and Destination MAC address";
         uses apply-advanced;
         leaf interface {
           description "Interface on which SSL decrypted traffic is mirrored";
           type union {
             type jt:interface-name;
             type string {
               pattern "<.*>|$.*";
             }
           }
         }
         leaf destination-mac-address {
           description "Mac address of host/server to which decrypted traffic is mirrored";
           type jt:mac-addr;
         }
         leaf only-after-security-policies-enforcement {
           description "Enables decrypted Traffic mirroring after policy enforcement";
           type empty;
         }
       }
       leaf-list whitelist {
         ordered-by user;
         description "Addresses exempted from SSL Proxy ";
         type string;
       }
       leaf-list whitelist-url-categories {
         ordered-by user;
         type string;
       }
       container actions {
         description "Logging and traffic related actions";
         uses apply-advanced;
         leaf ignore-server-auth-failure {
           description "Ignore server authentication failure";
           type empty;
         }
         container log {
           presence "enable log";
           description "Logging actions";
           leaf all {
             description "Log all events";
             type empty;
           }
           leaf sessions-dropped {
             description "Log only ssl session drop events";
             type empty;
           }
           leaf sessions-allowed {
             description "Log ssl session allow events after an error";
             type empty;
           }
           leaf sessions-ignored {
             description "Log  session ignore events ";
             type empty;
           }
           leaf sessions-whitelisted {
             description "Log ssl session whitelist events ";
             type empty;
           }
           leaf errors {
             description "Log all error events ";
             type empty;
           }
           leaf warning {
             description "Log all warning events ";
             type empty;
           }
           leaf info {
             description "Log all information events ";
             type empty;
           }
         }
         container crl {
           description "Certificate Revocation actions.";
           leaf disable {
             description "Disable CRL validation.";
             type empty;
           }
           leaf if-not-present {
             description "Action if CRL information is not present.";
             default "allow";
             type enumeration {
               enum "allow" {
                 description "Allow session if CRL information is not present.";
               }
               enum "drop" {
                 description "Drop session if CRL information is not present.";
               }
             }
           }
           leaf ignore-hold-instruction-code {
             description "Ignore 'Hold Instruction Code' present in the CRL entry.";
             type empty;
           }
         }
         leaf renegotiation {
           description "Renegotiation options";
           default "allow-secure";
           type enumeration {
             enum "allow" {
               description "Allow secure as well as non secure renegotiation";
             }
             enum "allow-secure" {
               description "Allow secure negotiation only (RFC 5746)";
             }
             enum "drop" {
               description "Drop session on renegotiation request";
             }
           }
         }
         leaf disable-session-resumption {
           description "Disable session resumption";
           type empty;
         }
         leaf unsupported-cipher-on-hw {
           description "Unsupported cipher processing on hardware mode";
           default "drop";
           type enumeration {
             enum "drop" {
               description "Drop session if cipher isn't supported on hardware mode";
             }
             enum "software-inspection" {
               description "Allow session in software mode";
             }
           }
         }
         leaf allow-strong-certificate {
           description "Certificate till 4K key-size processing on standalone SRX300/SRX320 platform";
           type empty;
         }
       }
       leaf disable-deferred-profile-selection {
         description "Disable the deferred profile selection mechanism at profile level";
         type empty;
       }
     }
   }
   grouping ssl-termination-config {
     uses apply-advanced;
     list profile {
       key name;
       ordered-by user;
       description "SSL server profile";
       leaf name {
         description "Profile identifier";
         type string {
           length "1 .. 63";
         }
       }
       uses apply-advanced;
       leaf enable-flow-tracing {
         description "Enable flow tracing for the profile";
         type empty;
       }
       leaf supported-ec-groups {
         description "Supported electic curve groups";
         type enumeration {
           enum "P-256" {
             description "P-256 group";
           }
           enum "P-384" {
             description "P-384 group";
           }
           enum "P-521" {
             description "P-521 group";
           }
         }
       }
       leaf protocol-version {
         description "Protocol SSL version accepted";
         default "all";
         type enumeration {
           enum "all" {
             description "TLS version 1.0 or TLS version 1.1 or TLS version 1.2 or TLS version 1.3";
           }
           enum "ssl3" {
             description "SSL version 3";
           }
           enum "tls1" {
             description "TLS version 1";
           }
           enum "tls11" {
             description "TLS version 1.1";
           }
           enum "tls12" {
             description "TLS version 1.2";
           }
           enum "tls13" {
             description "TLS version 1.3";
           }
           enum "tls12-and-lower" {
             description "Dont support TLS 1.3 (downgrade all the connections to TLS 1.2 or below)";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
           }
         }
       }
       leaf-list custom-ciphers {
         ordered-by user;
         description "Custom cipher list";
         type enumeration {
           enum "tls12-rsa-aes-128-cbc-sha" {
             description "RSA, 128 bit aes/cbc, sha hash";
           }
           enum "tls12-rsa-aes-256-cbc-sha" {
             description "RSA, 256 bit aes/cbc, sha hash";
           }
           enum "tls12-rsa-aes-256-gcm-sha384" {
             description "RSA, 256 bit aes/gcm, sha384 hash ";
           }
           enum "tls12-rsa-aes-256-cbc-sha256" {
             description "RSA, 256 bit aes/cbc, sha256 hash";
           }
           enum "tls12-rsa-aes-128-gcm-sha256" {
             description "RSA, 128 bit aes/gcm, sha256 hash";
           }
           enum "tls12-rsa-aes-128-cbc-sha256" {
             description "RSA, 128 bit aes/cbc, sha256 hash";
           }
           enum "tls12-ecdhe-rsa-aes-256-gcm-sha384" {
             description "ECDHE/rsa, 256 bit aes/gcm, sha384 hash";
           }
           enum "tls12-ecdhe-rsa-aes-256-cbc-sha" {
             description "ECDHE/rsa, 256 bit aes/cbc, sha hash";
           }
           enum "tls12-ecdhe-rsa-aes-256-cbc-sha384" {
             description "ECDHE/rsa, 256 bit aes/cbc, sha384 hash";
           }
           enum "tls12-ecdhe-rsa-3des-ede-cbc-sha" {
             description "ECDHE/rsa, 3des ede/cbc, sha hash";
           }
           enum "tls12-ecdhe-rsa-aes-128-gcm-sha256" {
             description "ECDHE/rsa, 128 bit aes/gcm, sha256 hash";
           }
           enum "tls12-ecdhe-rsa-aes-128-cbc-sha" {
             description "ECDHE/rsa, 128 bit aes/cbc, sha hash";
           }
           enum "tls12-ecdhe-rsa-aes-128-cbc-sha256" {
             description "ECDHE/rsa, 128 bit aes/cbc, sha256 hash";
           }
           enum "tls12-rsa-aes-128-ccm-sha256" {
             description "RSA, 128 bit aes/ccm, sha256 hash";
           }
           enum "tls12-rsa-aes-128-ccm8-sha256" {
             description "RSA, 128 bit aes/ccm8, sha256 hash";
           }
           enum "tls12-rsa-aes-256-ccm-sha256" {
             description "RSA, 256 bit aes/ccm, sha256 hash";
           }
           enum "tls12-rsa-aes-256-ccm8-sha256" {
             description "RSA, 128 bit aes/ccm8, sha256 hash";
           }
           enum "tls12-ecdhe-ecdsa-aes-128-ccm-sha256" {
             description "ECDHE,ECDSA, 128 bit aes/ccm, sha256 hash";
           }
           enum "tls12-ecdhe-ecdsa-aes-256-ccm-sha256" {
             description "ECDHE,ECDSA, 256 bit aes/ccm, sha256 hash";
           }
           enum "tls12-ecdhe-ecdsa-aes-128-ccm8-sha256" {
             description "ECDHE,ECDSA, 128 bit aes/ccm8, sha256 hash";
           }
           enum "tls12-ecdhe-ecdsa-aes-256-ccm8-sha256" {
             description "ECDHE,ECDSA, 256 bit aes/ccm8, sha256 hash";
           }
           enum "tls12-ecdhe-rsa-chacha20-poly1305-sha256" {
             description "ECDHE/rsa, chacha_poly , sha256 hash";
           }
           enum "tls12-ecdhe-ecdsa-aes-256-gcm-sha384" {
             description "ECDHE,ECDSA, 256 bit aes/gcm, sha384 hash";
           }
           enum "tls12-ecdhe-ecdsa-aes-256-cbc-sha" {
             description "ECDHE,ECDSA, 256 bit aes/cbc, sha hash";
           }
           enum "tls12-ecdhe-ecdsa-aes-256-cbc-sha384" {
             description "ECDHE,ECDSA, 256 bit aes/cbc, sha384 hash";
           }
           enum "tls12-ecdhe-ecdsa-aes-128-gcm-sha256" {
             description "ECDHE,ECDSA, 128 bit aes/gcm, sha256 hash";
           }
           enum "tls12-ecdhe-ecdsa-aes-128-cbc-sha" {
             description "ECDHE,ECDSA, 128 bit aes/cbc, sha hash";
           }
           enum "tls12-ecdhe-ecdsa-aes-128-cbc-sha256" {
             description "ECDHE,ECDSA, 128 bit aes/cbc, sha256 hash";
           }
           enum "tls12-ecdhe-ecdsa-3des-ede-cbc-sha" {
             description "ECDHE,ECDSA, 3des ede/cbc, sha hash";
           }
           enum "dhe-rsa-with-aes-128-ccm8-sha256" {
             description "DHE/rsa, 128 bit aes/ccm8, sha256 hash";
           }
           enum "dhe-rsa-with-aes-256-ccm8-sha256" {
             description "DHE/rsa, 256 bit aes/ccm8, sha256 hash";
           }
           enum "dhe-rsa-with-aes-256-ccm-sha256" {
             description "DHE/rsa, 256 bit aes/ccm, sha256 hash";
           }
           enum "dhe-rsa-with-aes-128-ccm-sha256" {
             description "DHE/rsa, 128 bit aes/ccm, sha256 hash";
           }
           enum "tls12-ecdhe-ecdsa-chacha20-poly1305-sha256" {
             description "ECDHE,ECDSA, chacha_poly, sha256 hash";
           }
           enum "tls13-with-aes-256-gcm-sha384" {
             description "Any key-exchange, Any authentication,256bit aes, sha384 hash";
           }
           enum "tls13-with-aes-128-gcm-sha256" {
             description "Any key-exchange, Any authentication,128bit aes, sha256 hash";
           }
           enum "tls13-with-chacha20-poly1305-sha256" {
             description "Any key-exchange, Any authentication,chacha, sha256 hash";
           }
           enum "tls13-with-aes-128-ccm-sha256" {
             description "Any key-exchange, Any authentication,128bit aes, sha256 hash";
           }
           enum "tls13-with-aes-128-ccm8-sha256" {
             description "Any key-exchange, Any authentication,128bit aes, sha256 hash";
           }
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
           }
           enum "rsa-with-aes-256-cbc-sha" {
             description "RSA, 256 bit aes/cbc, sha hash";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
           enum "dhe-rsa-with-aes-256-gcm-sha384" {
             description "DHE/rsa, 256 bit aes/gcm, sha384 hash";
           }
           enum "dhe-rsa-with-aes-256-cbc-sha" {
             description "DHE/rsa, 256 bit aes/cbc, sha hash";
           }
           enum "dhe-rsa-with-aes-256-cbc-sha256" {
             description "DHE/rsa, 256 bit aes/cbc, sha256 hash";
           }
           enum "dhe-rsa-with-3des-ede-cbc-sha" {
             description "DHE/rsa, 3des ede/cbc, sha hash";
           }
           enum "dhe-rsa-with-aes-128-gcm-sha256" {
             description "DHE/rsa, 128 bit aes/gcm, sha256 hash";
           }
           enum "dhe-rsa-with-aes-128-cbc-sha" {
             description "DHE/rsa, 128 bit aes/cbc, sha hash";
           }
           enum "dhe-rsa-with-aes-128-cbc-sha256" {
             description "DHE/rsa, 128 bit aes/cbc, sha256 hash";
           }
         }
         max-elements 64;
       }
       leaf enable-session-cache {
         description "Enable SSL session cache";
         type empty;
       }
       leaf server-certificate {
         description "Local certificate identifier";
         type string {
         }
       }
     }
   }
   grouping ssl-traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "cli-configuration" {
             description "Trace CLI configuration events";
           }
           enum "termination" {
             description "Trace termination service events";
           }
           enum "initiation" {
             description "Trace initiation service events";
           }
           enum "proxy" {
             description "Trace proxy service events";
           }
           enum "selected-profile" {
             description "Trace events for profiles with enable-flow-tracing set";
           }
           enum "all" {
             description "Trace everything";
           }
         }
       }
     }
     container packet-filter {
       description "SSL Packet filter";
       uses apply-advanced;
       leaf source-ip {
         description "Source IP address";
         type jt:ipaddr;
       }
       leaf destination-ip {
         description "Destination IP address";
         type jt:ipaddr;
       }
       leaf source-port {
         description "Source port";
         type union {
           type string {
             pattern "<.*>|$.*";
           }
           type uint16 {
             range "1 .. 65535";
           }
         }
       }
       leaf destination-port {
         description "Destination port";
         type union {
           type string {
             pattern "<.*>|$.*";
           }
           type uint16 {
             range "1 .. 65535";
           }
         }
       }
     }
   }
   grouping sw-rule-set-object {
     leaf name {
       description "Define Rule Set name";
       type string {
         length "1 .. 63";
       }
     }
     uses apply-advanced;
     list rule {
       key name;
       ordered-by user;
       description "Define a rule term";
       leaf name {
         description "Rule name";
         type string {
           length "1 .. 63";
         }
       }
       uses apply-advanced;
       container then {
         description "Action to take if the condition is matched";
         uses apply-advanced;
         choice designation {
           case case_1 {
             leaf ds-lite {
               description "Apply DS-Lite softwire";
               type string {
                 length "1 .. 63";
               }
             }
           }
           case case_2 {
             leaf v6rd {
               description "Apply 6rd softwire";
               type string {
                 length "1 .. 63";
               }
             }
           }
           case case_3 {
             leaf map-e {
               description "Apply MAP-E softwire";
               type string {
                 length "1 .. 63";
               }
             }
           }
           case case_4 {
             leaf map-t {
               description "Apply MAP-T softwire";
               type string {
                 length "1 .. 63";
               }
             }
           }
         }
       }
     }
     leaf match-direction {
       description "Match direction";
       type enumeration {
         enum "input" {
           description "Match on input to interface";
         }
         enum "output" {
           description "Match on output from interface";
         }
       }
     }
   }
   grouping tunnel_interface_type {
     description "One or more tunnel interfaces on which to configure flow-tap service";
     leaf name {
       description "Tunnel Interface name";
       type union {
         type jt:interface-unit;
         type string {
           pattern "<.*>|$.*";
         }
       }
     }
     uses apply-advanced;
   }
   grouping twamp-authentication-key-chain {
     leaf name {
       description "Name of authentication key chain";
       type string {
       }
     }
     uses apply-advanced;
     list key-id {
       key name;
       description "Authentication element configuration";
       leaf name {
         description "Authentication element identifier";
         type string {
           length "1 .. 80";
         }
       }
       uses apply-advanced;
       leaf secret {
         description "Authentication key";
         type string {
           length "1 .. 256";
         }
       }
     }
   }
   grouping user-group-mapping-type {
     uses apply-advanced;
     container ldap {
       description "LDAP";
       uses apply-advanced;
       leaf authentication-algorithm {
         description "Authentication-algorithm";
         type enumeration {
           enum "simple" {
             description "Simple authentication";
           }
         }
       }
       leaf ssl {
         description "SSL";
         type empty;
       }
       leaf base {
         description "Base distinguished name";
         type string {
           length "1 .. 128";
         }
       }
       container user {
         description "User name";
         uses apply-advanced;
         leaf user-name {
           description "User name";
           type string {
             length "1 .. 64";
           }
         }
         leaf password {
           description "Password string";
           type string {
             length "1 .. 128";
           }
         }
       }
       list address {
         key name;
         ordered-by user;
         description "Address of LDAP server";
         leaf name {
           description "Address";
           type jt:ipaddr;
         }
         uses apply-advanced;
         leaf port {
           description "LDAP port";
           type union {
             type string {
               pattern "<.*>|$.*";
             }
             type uint16 {
               range "1 .. 65535";
             }
           }
         }
       }
     }
   }
   grouping version-ipfix-template {
     description "One or more version-ipfix  templates for flow monitoring";
     leaf name {
       description "Name of template";
       type string;
     }
     uses apply-advanced;
     leaf flow-active-timeout {
       description "Interval after which active flow is exported";
       default "60";
       type union {
         type string {
           pattern "<.*>|$.*";
         }
         type uint32 {
           range "10 .. 600";
         }
       }
     }
     leaf flow-inactive-timeout {
       description "Period of inactivity that marks a flow inactive";
       default "60";
       type union {
         type string {
           pattern "<.*>|$.*";
         }
         type uint32 {
           range "10 .. 600";
         }
       }
     }
     leaf template-id {
       description "Template id";
       type union {
         type string {
           pattern "<.*>|$.*";
         }
         type uint32;
       }
     }
     leaf option-template-id {
       description "Options template id";
       type union {
         type string {
           pattern "<.*>|$.*";
         }
         type uint32;
       }
     }
     leaf observation-domain-id {
       description "Observation Domain Id";
       default "0";
       type union {
         type string {
           pattern "<.*>|$.*";
         }
         type uint32 {
           range "0 .. 255";
         }
       }
     }
     container nexthop-learning {
       presence "enable nexthop-learning";
       description "Nexthop learning parameter. Valid ONLY for INLINE-JFLOW";
       uses apply-advanced;
       choice enable-disable {
         case case_1 {
           leaf enable {
             description "Enable nexthop learning";
             type empty;
           }
         }
         case case_2 {
           leaf disable {
             description "Disable nexthop learning";
             type empty;
           }
         }
       }
     }
     container template-refresh-rate {
       presence "enable template-refresh-rate";
       description "Template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container option-refresh-rate {
       presence "enable option-refresh-rate";
       description "Option template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     choice template-types {
       case case_1 {
         container ipv4-template {
           presence "enable ipv4-template";
           description "IPv4 template configuration";
           uses apply-advanced;
           list export-extension {
             key name;
             ordered-by user;
             description "IPv4 template configuration with extra fields added to the template";
             leaf name {
               type enumeration {
                 enum "flow-dir" {
                   description "Flow-direction field type";
                 }
                 enum "app-id" {
                   description "Applicationid field type";
                 }
               }
             }
             uses apply-advanced;
           }
         }
       }
       case case_2 {
         container ipv6-template {
           presence "enable ipv6-template";
           description "IPv6 template configuration";
           uses apply-advanced;
           list export-extension {
             key name;
             ordered-by user;
             description "IPv6 template configuration with extra fields added to the template";
             leaf name {
               type enumeration {
                 enum "flow-dir" {
                   description "Flow-direction field type";
                 }
                 enum "app-id" {
                   description "Applicationid field type";
                 }
               }
             }
             uses apply-advanced;
           }
         }
       }
       case case_3 {
       }
       case case_4 {
       }
       case case_5 {
         container mpls-template {
           presence "enable mpls-template";
           description "MPLS template configuration";
           uses apply-advanced;
           leaf-list label-position {
             ordered-by user;
             description "One or more MPLS label positions";
             type union {
               type string {
                 pattern "<.*>|$.*";
               }
               type uint8 {
                 range "1 .. 8";
               }
             }
             max-elements 3;
           }
         }
       }
       case case_6 {
       }
     }
     container tunnel-observation {
       description "Tunnel observation";
       uses apply-advanced;
       leaf ipv4 {
         description "IPv4";
         type empty;
       }
       leaf ipv6 {
         description "IPv6";
         type empty;
       }
     }
     container flow-key {
       description "Flow key for the template. Valid ONLY for INLINE-JFLOW";
       uses apply-advanced;
       leaf flow-direction {
         description "Include flow direction";
         type empty;
       }
       leaf vlan-id {
         description "Include vlan ID";
         type empty;
       }
       leaf output-interface {
         description "Include output interface";
         type empty;
       }
     }
   }
   grouping version9-template {
     description "One or more version 9 templates for flow monitoring";
     leaf name {
       description "Name of template";
       type string;
     }
     uses apply-advanced;
     leaf flow-active-timeout {
       description "Interval after which active flow is exported";
       default "60";
       type union {
         type string {
           pattern "<.*>|$.*";
         }
         type uint32 {
           range "10 .. 600";
         }
       }
     }
     leaf flow-inactive-timeout {
       description "Period of inactivity that marks a flow inactive";
       default "60";
       type union {
         type string {
           pattern "<.*>|$.*";
         }
         type uint32 {
           range "10 .. 600";
         }
       }
     }
     leaf template-id {
       description "Template id";
       type union {
         type string {
           pattern "<.*>|$.*";
         }
         type uint32;
       }
     }
     leaf option-template-id {
       description "Options template id";
       type union {
         type string {
           pattern "<.*>|$.*";
         }
         type uint32;
       }
     }
     leaf source-id {
       description "Source Id";
       default "0";
       type union {
         type string {
           pattern "<.*>|$.*";
         }
         type uint32 {
           range "0 .. 255";
         }
       }
     }
     container nexthop-learning {
       description "Nexthop learning parameter. Valid ONLY for INLINE-JFLOW";
       uses apply-advanced;
       choice enable-disable {
         case case_1 {
           leaf enable {
             description "Enable nexthop learning";
             type empty;
           }
         }
         case case_2 {
           leaf disable {
             description "Disable nexthop learning";
             type empty;
           }
         }
       }
     }
     container template-refresh-rate {
       presence "enable template-refresh-rate";
       description "Template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container option-refresh-rate {
       presence "enable option-refresh-rate";
       description "Option template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container data-record-fields {
       description "Extended Data record fields";
       uses apply-advanced;
       leaf include-policy-map-name {
         description "Include first 4 letters of policymap name applied on packet";
         type empty;
       }
     }
     choice template-types {
       case case_1 {
       }
       case case_2 {
         container mpls-template {
           presence "enable mpls-template";
           description "MPLS template configuration";
           uses apply-advanced;
           leaf-list label-position {
             ordered-by user;
             description "One or more MPLS label positions";
             type union {
               type string {
                 pattern "<.*>|$.*";
               }
               type uint8 {
                 range "1 .. 8";
               }
             }
             max-elements 3;
           }
         }
       }
       case case_3 {
         container ipv6-template {
           presence "enable ipv6-template";
           description "IPv6 template configuration";
           uses apply-advanced;
           list export-extension {
             key name;
             ordered-by user;
             description "IPv6 template configuration with extra fields added to the template";
             leaf name {
               type enumeration {
                 enum "flow-dir" {
                   description "Applicationid field type";
                 }
                 enum "app-id" {
                   description "Applicationid field type";
                 }
               }
             }
             uses apply-advanced;
           }
           container nexthop-options {
             presence "enable nexthop-options";
             description "Additional information retrieved from nexthop";
             uses apply-advanced;
             choice nexthop-types {
               case case_1 {
                 container mpls {
                   presence "enable mpls";
                   description "MPLS information retrieved from nexthop";
                   uses apply-advanced;
                   leaf-list label-position {
                     ordered-by user;
                     description "One or more MPLS label positions";
                     type union {
                       type string {
                         pattern "<.*>|$.*";
                       }
                       type uint8 {
                         range "1 .. 3";
                       }
                     }
                     max-elements 3;
                   }
                 }
               }
             }
           }
         }
       }
       case case_4 {
         container peer-as-billing-template {
           presence "enable peer-as-billing-template";
           description "Peer AS billing template configuration";
         }
       }
       case case_5 {
         container ipv4-template {
           presence "enable ipv4-template";
           description "IPv4 template configuration";
           uses apply-advanced;
           list export-extension {
             key name;
             ordered-by user;
             description "IPv4 template configuration with extra fields added to the template";
             leaf name {
               type enumeration {
                 enum "flow-dir" {
                   description "Applicationid field type";
                 }
                 enum "app-id" {
                   description "Applicationid field type";
                 }
               }
             }
             uses apply-advanced;
           }
           container nexthop-options {
             presence "enable nexthop-options";
             description "Additional information retrieved from nexthop";
             uses apply-advanced;
             choice nexthop-types {
               case case_1 {
                 container mpls {
                   presence "enable mpls";
                   description "MPLS information retrieved from nexthop";
                   uses apply-advanced;
                   leaf-list label-position {
                     ordered-by user;
                     description "One or more MPLS label positions";
                     type union {
                       type string {
                         pattern "<.*>|$.*";
                       }
                       type uint8 {
                         range "1 .. 3";
                       }
                     }
                     max-elements 3;
                   }
                 }
               }
             }
           }
         }
       }
       case case_6 {
       }
       case case_7 {
       }
     }
     container tunnel-observation {
       description "Tunnel observation";
       uses apply-advanced;
       leaf ipv4 {
         description "IPv4";
         type empty;
       }
       leaf ipv6 {
         description "IPv6";
         type empty;
       }
     }
     container flow-key {
       description "Flow key for the template. Valid ONLY for INLINE-JFLOW";
       uses apply-advanced;
       leaf flow-direction {
         description "Include flow direction";
         type empty;
       }
       leaf vlan-id {
         description "Include vlan ID";
         type empty;
       }
       leaf output-interface {
         description "Include output interface";
         type empty;
       }
     }
   }
   grouping web-config {
     uses apply-advanced;
     list profile {
       key name;
       ordered-by user;
       description "Configure transparent proxy profile";
       leaf name {
         description "Transparent proxy profile name";
         type string {
           length "1 .. 63";
         }
       }
       uses apply-advanced;
       list proxy-address {
         key name;
         ordered-by user;
         description "Proxy server addresses";
         leaf name {
           description "Address name";
           type string {
             length "1 .. 63";
           }
         }
         uses apply-advanced;
         leaf ip {
           description "IP address and prefix-length";
           type jt:ipprefix;
         }
         leaf port {
           description "Port number";
           type union {
             type string {
               pattern "<.*>|$.*";
             }
             type uint16 {
               range "1 .. 65535";
             }
           }
         }
       }
       leaf-list dynamic-web-application {
         ordered-by user;
         type string;
       }
       leaf-list dynamic-web-application-group {
         ordered-by user;
         description "Specify dynamic application group name to match";
         type string;
       }
       leaf drop-on-dns-error {
         description "Drop Web Proxy Session on DNS error";
         type empty;
       }
     }
   }
   grouping web-proxy-traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "cli-configuration" {
             description "Trace CLI configuration events";
           }
           enum "ipc" {
             description "Trace Inter-process communication events";
           }
           enum "svc-config" {
             description "Trace service configuration events in DataPath";
           }
           enum "flow-session" {
             description "Trace flow-session events";
           }
           enum "all" {
             description "Trace everything";
           }
         }
       }
     }
   }
 }
