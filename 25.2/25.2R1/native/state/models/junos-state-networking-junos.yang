module junos-state-networking-junos {
  yang-version 1.1;
  namespace "http://yang.juniper.net/junos/state/networking/junos";
  prefix js-net-junos;

  import junos-extensions {
    prefix jx;
  }

  import ietf-yang-types {
    prefix yang;
  }

  import junos-state {
    prefix js;
  }

  import junos-state-chassis {
    prefix js-chas;
  }

  import junos-state-networking {
    prefix js-net;
  }

  organization
    "Juniper Networks, Inc.";

  contact
    "Juniper Networks, Inc.

     1133 Innovation Way
     Sunnyvale, CA 94089

     +1 888 314-5822

     E-mail: yang-support@juniper.net";

  description
    "This module contains a collection of top level nodes for
     JUNOS-only networking stack statistics data.

     Copyright (c) 2024 Juniper Networks, Inc.
     All rights reserved.";

  revision 2024-09-16 {
    description
      "Initial revision";
    reference "0.1.0";
  }

  jx:version "0.1.0";

  grouping ingress-ttp-counters {
    description
      "Grouping for ingress TTP counters";

    leaf clnp-pkts {
      type yang:counter64;
      description
        "TTP CLNP packets received";
    }

    leaf ipv4-mpls-pkts {
      type yang:counter64;
      description
        "TTP IPv4->MPLS packets received";
    }

    leaf mpls-ipv4-pkts {
      type yang:counter64;
      description
        "TTP MPLS->IPv4 packets received";
    }
  }

  augment "/js:state/js-chas:chassis/js-chas:modules/js-chas:module" +
          "/js-net:networking/js-net:jtd/js-net:ingress/js-net:ttp" +
          "/js-net:counters" {
    description
      "Augment the base model with JUNOS-only supported leaves";

    uses ingress-ttp-counters;
  }
}
