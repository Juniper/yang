module junos-genstate-mvrp-registration-information {
   yang-version 1;
   namespace "http://yang.juniper.net/junos/genstate/mvrp-registration-information";
   prefix jgmri;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for mvrp-registration-information";

   revision 2025-01-01 {
     description "Junos: 25.2R1.9-EVO";
   }

   grouping mvrp-registration-information-top {
     description "Top-level grouping";
     container mvrp-registration-information {
       description "Information about multicast MAC Registration state";
       list mvrp-registration-instance {
         leaf mvrp-routing-instance-name {
           type string;
           description "Name of routing instance";
         }
         list mvrp-registration-vlan-entry {
           description "Registration state information";
           leaf mvrp-vlan-id {
             type int32;
             description "VLAN ID";
           }
           list mvrp-registration-interface-entry {
             leaf mvrp-interface-name {
               type string;
               description "Name of interface";
             }
             leaf mvrp-registration-state {
               type string;
               description "Registration state";
             }
             leaf mvrp-registration-forced-state {
               type string;
               description "Forced state";
             }
             leaf mvrp-registration-manage-state {
               type string;
               description "Management state";
             }
             leaf mvrp-registration-stp-state {
               type string;
               description "STP state";
             }
           }
         }
       }
     }
   }
   augment "/jgs:genstate" {
     description "Adds mvrp-registration-information to top-level genstate";
     uses mvrp-registration-information-top;
   }
 }
