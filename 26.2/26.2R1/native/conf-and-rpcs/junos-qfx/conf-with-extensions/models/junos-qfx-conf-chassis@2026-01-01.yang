/*
 * Copyright (c) 2026 Juniper Networks, Inc.
 * All rights reserved.
 */
 module junos-qfx-conf-chassis {
   namespace "http://yang.juniper.net/junos-qfx/conf/chassis";

   prefix jc-chassis;

   import junos-common-ddl-extensions {
     prefix junos;
     revision-date 2026-01-01;
   }

   import junos-common-types {
     prefix jt;
     revision-date 2026-01-01;
   }

   import junos-qfx-conf-root {
     prefix jc;
     revision-date 2026-01-01;
   }

   organization "Juniper Networks, Inc.";

   contact "yang-support@juniper.net";

   description "Junos chassis configuration module";

   revision 2026-01-01 {
     description "Junos: 26.2R1.7";
   }

   augment /jc:configuration {
     uses chassis-group;
   }
   augment /jc:configuration/jc:groups {
     uses chassis-group;
   }
   grouping chassis-group {
     container chassis {
       description "Chassis configuration";
       uses chassis_type;
     }
   }
   grouping chassis_type {
     uses apply-advanced;
     container nssu {
       presence "enable nssu";
       description "Nonstop Software Upgrade settings";
       uses apply-advanced;
       list upgrade-group {
         key name;
         ordered-by user;
         description "Nonstop Software Upgrade group";
         leaf name {
           junos:cli-feature "nokeyword";
           type string {
             length "1 .. 254";
           }
         }
         uses apply-advanced;
         leaf-list fpcs {
           description "FPCs associated with update-group";
           type union {
             type string {
               pattern "<.*>|$.*";
             }
             type uint32;
           }
           max-elements 16;
         }
       }
       leaf rcp-count {
         description "Parallel rcp count";
         type union {
           type string {
             pattern "<.*>|$.*";
           }
           type int32 {
             range "1 .. 8";
           }
         }
       }
       leaf lc-reboot-delay {
         description "Delay between linecard reboot during NSSU";
         type union {
           type string {
             pattern "<.*>|$.*";
           }
           type int32 {
             range "0 .. 600";
           }
         }
       }
     }
     leaf no-psu-redundancy {
       description "Disable N+1 Redundancy for PSUs";
       type empty;
     }
     leaf no-power-budget {
       description "Disable Chassis Power Budget";
       type empty;
     }
     container psu {
       description "Power Supply Unit redundancy configuration";
       uses apply-advanced;
       container redundancy {
         description "PSU Redundancy settings";
         uses apply-advanced;
         leaf n-plus-n {
           description "PSU redundancy: N+N configuration";
           type empty;
         }
       }
     }
     leaf fpc-resync {
       description "Send and receive Nchip cells for newly onlined FPC";
       type empty;
     }
     container optics {
       presence "enable optics";
       description "Optics specific config";
       uses apply-advanced;
       leaf display-3po-pn {
         description "To display third party optics part number";
         type empty;
       }
       container pm {
         presence "enable pm";
         description "Optics Performance Monitoring";
         uses apply-advanced;
         leaf interval-length {
           description "Interval bin length";
           type enumeration {
             enum "10s" {
               description "10 seconds";
             }
             enum "30s" {
               description "30 seconds";
             }
             enum "1min" {
               description "1 minute";
             }
             enum "5min" {
               description "5 minutes";
             }
             enum "15min" {
               description "15 minutes";
             }
           }
         }
       }
       list logical-channel {
         key name;
         ordered-by user;
         description "Optics logical-channel specific config.";
         leaf name {
           description "Logical-channel-index";
           junos:cli-feature "nokeyword";
           type union {
             type uint32;
             type string {
               pattern "<.*>|$.*";
             }
           }
         }
         uses apply-advanced;
         list logical-channel-assignment {
           key name;
           ordered-by user;
           description "Logical-channel assignment configs";
           leaf name {
             description "Index of assignment";
             junos:cli-feature "nokeyword";
             type union {
               type uint32;
               type string {
                 pattern "<.*>|$.*";
               }
             }
           }
           uses apply-advanced;
           leaf description {
             description "Description of the logical-channel assignment";
             type string;
           }
           leaf allocation {
             description "Allocation of the logical-channel (Gbps)";
             type union {
               type uint32;
               type string {
                 pattern "<.*>|$.*";
               }
             }
           }
           leaf channel-assignment-type {
             description "Type of logical-channel (optical-channel or logical-channel)";
             type enumeration {
               enum "logical-channel" {
                 description "Channel is logical-channel";
               }
               enum "optical-channel" {
                 description "Channel is optical-channel";
               }
             }
           }
           leaf channel-assignment {
             description "Assignment of the logical-channel";
             junos:must "(\"chassis optics logical-channel $$\")";
             junos:must-message "logical-channel should be defined before assignment";
             type union {
               type uint32;
               type string {
                 pattern "<.*>|$.*";
               }
             }
           }
           leaf optical-channel-reference {
             description "Reference to optical-channel";
             type union {
               type jt:interface-device;
               type string {
                 pattern "<.*>|$.*";
               }
             }
           }
         }
         leaf admin-state {
           description "Logical-channel admin-state";
           default "enabled";
           type enumeration {
             enum "enabled" {
               description "Logical-channel is enabled";
             }
             enum "disabled" {
               description "Logical-channel is disabled";
             }
             enum "maint" {
               description "Logical-channel is set to maintainance mode";
             }
           }
         }
         leaf logical-channel-type {
           description "Type which determines the config/PM parameters";
           type enumeration {
             enum "ethernet" {
               description "Channel is logical-channel-type of Ethernet";
             }
             enum "otn" {
               description "Channel is logical-channel-type of OTN";
             }
           }
         }
         leaf trib-protocol {
           description "Protocol framing of the tributary signal";
           type enumeration {
             enum "1ge" {
               description "Protocol is 1G Ethernet";
             }
             enum "10ge-lan" {
               description "Protocol is 10G Ethernet LAN";
             }
             enum "10ge-wan" {
               description "Protocol is 10G Ethernet WAN";
             }
             enum "40ge" {
               description "Protocol is 400G Ethernet";
             }
             enum "100ge" {
               description "Protocol is 100G Ethernet";
             }
             enum "400ge" {
               description "Protocol is 400G Ethernet";
             }
             enum "800ge" {
               description "Protocol is 800G Ethernet";
             }
           }
         }
         leaf rate-class {
           description "Protocol framing of the tributary signal";
           type enumeration {
             enum "1g" {
               description "Tributary signal rate 1G";
             }
             enum "10g" {
               description "Tributary signal rate 10G";
             }
             enum "40g" {
               description "Tributary signal rate 40G";
             }
             enum "100g" {
               description "Tributary signal rate 100G";
             }
             enum "400g" {
               description "Tributary signal rate 400G";
             }
             enum "200g" {
               description "Tributary signal rate 200G";
             }
             enum "800g" {
               description "Tributary signal rate 800G";
             }
           }
         }
         leaf description {
           description "Description of the logical-channel";
           type string;
         }
         leaf ingress-channel-reference {
           description "Reference to ingress interface";
           type union {
             type jt:interface-device;
             type string {
               pattern "<.*>|$.*";
             }
           }
         }
       }
     }
     leaf craft-lockout {
       description "Disable craft interface input";
       type empty;
     }
     choice source-route-choice {
       leaf source-route {
         description "Enable IP source-route processing";
         status deprecated;
         type empty;
       }
       leaf no-source-route {
         description "Don't enable IP source-route processing";
         status deprecated;
         type empty;
       }
     }
     container icmp {
       description "ICMP protocol";
       uses apply-advanced;
     }
     container icmp6 {
       description "ICMP version 6 protocol";
       uses apply-advanced;
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
           junos:must "(!(\"system processes routing force-32-bit\"))";
           junos:must-message "32-bit rpd doesn't support ecmp greater than 128";
         }
         enum "192" {
           description "Maximum 192 ECMP routes";
           junos:must "(!(\"system processes routing force-32-bit\"))";
           junos:must-message "32-bit rpd doesn't support ecmp greater than 128";
         }
         enum "224" {
           description "Maximum 224 ECMP routes";
           junos:must "(!(\"system processes routing force-32-bit\"))";
           junos:must-message "32-bit rpd doesn't support ecmp greater than 128";
         }
         enum "256" {
           description "Maximum 256 ECMP routes";
           junos:must "(!(\"system processes routing force-32-bit\"))";
           junos:must-message "32-bit rpd doesn't support ecmp greater than 128";
         }
         enum "288" {
           description "Maximum 288 ECMP routes";
           junos:must "(!(\"system processes routing force-32-bit\"))";
           junos:must-message "32-bit rpd doesn't support ecmp greater than 128";
         }
         enum "320" {
           description "Maximum 320 ECMP routes";
           junos:must "(!(\"system processes routing force-32-bit\"))";
           junos:must-message "32-bit rpd doesn't support ecmp greater than 128";
         }
         enum "352" {
           description "Maximum 352 ECMP routes";
           junos:must "(!(\"system processes routing force-32-bit\"))";
           junos:must-message "32-bit rpd doesn't support ecmp greater than 128";
         }
         enum "384" {
           description "Maximum 384 ECMP routes";
           junos:must "(!(\"system processes routing force-32-bit\"))";
           junos:must-message "32-bit rpd doesn't support ecmp greater than 128";
         }
         enum "416" {
           description "Maximum 416 ECMP routes";
           junos:must "(!(\"system processes routing force-32-bit\"))";
           junos:must-message "32-bit rpd doesn't support ecmp greater than 128";
         }
         enum "448" {
           description "Maximum 448 ECMP routes";
           junos:must "(!(\"system processes routing force-32-bit\"))";
           junos:must-message "32-bit rpd doesn't support ecmp greater than 128";
         }
         enum "480" {
           description "Maximum 480 ECMP routes";
           junos:must "(!(\"system processes routing force-32-bit\"))";
           junos:must-message "32-bit rpd doesn't support ecmp greater than 128";
         }
         enum "512" {
           description "Maximum 512 ECMP routes";
           junos:must "(!(\"system processes routing force-32-bit\"))";
           junos:must-message "32-bit rpd doesn't support ecmp greater than 128";
         }
       }
     }
     container ecmp-alb {
       presence "enable ecmp-alb";
       junos:must "(((\"chassis network-services enhanced-ip\" || \"chassis network-services enhanced-mode\") && !(\"chassis interoperability advanced-forwarding\")))";
       junos:must-message "Enhanced-ip or Enhanced-mode must be enabled and advanced-forwarding must be disabled to set ecmp-alb";
       description "Enable adaptive load balancing for ECMP nexthops";
       uses apply-advanced;
       leaf tolerance {
         description "Adaptive tolerance in percentage (default 20%)";
         default "20";
         units "percent";
         type union {
           type string {
             pattern "<.*>|$.*";
           }
           type uint32 {
             range "1 .. 100";
           }
         }
       }
     }
     container redundancy {
       description "Redundancy settings";
       uses chassis_redundancy_type;
     }
     container routing-engine {
       description "Routing Engine settings";
       uses chassis_routing_engine_type;
     }
     container port-extender {
       presence "enable port-extender";
       description "Port extender settings";
       uses apply-advanced;
       list fpc-slot {
         key name;
         ordered-by user;
         description "Virtual FPC settings";
         leaf name {
           description "Virtual slot of the satellite device";
           junos:cli-feature "nokeyword";
           type union {
             type string {
               pattern "<.*>|$.*";
             }
             type uint8 {
               range "65 .. 254";
             }
           }
         }
         uses apply-advanced;
         leaf desc {
           description "Description of the satellite device";
           type string;
         }
         leaf device {
           description "Model of the satellite device";
           type enumeration {
             enum "ex4400-48p" {
               description "Select EX4400-48P as the satellite";
             }
             enum "ex4400-48t" {
               description "Select EX4400-48T as the satellite";
             }
             enum "qfx5120-48t-6c" {
               description "Select QFX5120-48T-CHAS as the satellite";
             }
             enum "qfx5120-48y-8c" {
               description "Select JNP48Y8C-CHAS as the satellite";
             }
           }
         }
         leaf satellite-mgmt-ip {
           description "Management IP of the satellite device";
           type jt:ipv4addr;
         }
         list cascade-port {
           key name;
           ordered-by user;
           description "List of cascade ports";
           leaf name {
             description "AE interface name";
             junos:cli-feature "nokeyword";
             junos:must "((\"interfaces $$ port-extender-cascade-port\" && \"chassis aggregated-devices ethernet device-count\"))";
             junos:must-message "Ensure that AE is configured as a 'port-extender-cascade-port' and 'chassis aggregated-devices ethernet device-count' is set to appropriate value.";
             type string {
               junos:posix-pattern "^ae[0-9]+$";
               junos:pattern-message "Cascade port must be an AE interface";
             }
           }
           uses apply-advanced;
         }
         leaf target-mode {
           description "Enable EP targeting";
           type empty;
         }
         list pic-slot {
           key name;
           ordered-by user;
           description "PIC slot";
           leaf name {
             description "PIC slot number";
             junos:cli-feature "nokeyword";
             type union {
               type string {
                 pattern "<.*>|$.*";
               }
               type uint8 {
                 range 0;
               }
             }
           }
           uses apply-advanced;
           list port {
             key name;
             ordered-by user;
             description "Port settings";
             leaf name {
               description "Port number";
               junos:cli-feature "nokeyword";
               type union {
                 type string {
                   pattern "<.*>|$.*";
                 }
                 type uint16 {
                   range "0 .. 47";
                 }
               }
             }
             uses apply-advanced;
             leaf speed {
               description "Port speed";
               type enumeration {
                 enum "speed-100mbps" {
                   description "Sets the interface speed to 100Mbps";
                 }
                 enum "speed-1gbps" {
                   description "Sets the interface speed to 1Gbps";
                 }
                 enum "speed-10gbps" {
                   description "Sets the interface speed to 10Gbps";
                 }
                 enum "speed-25gbps" {
                   description "Sets the interface speed to 25Gbps";
                 }
               }
             }
           }
         }
       }
     }
     container aggregated-devices {
       description "Aggregated devices configuration";
       uses chassis_agg_dev_type;
     }
     list disk-partition {
       key name;
       ordered-by user;
       description "Chassis disk monitor configuration";
       leaf name {
         description "Choose disk partition to monitor";
         junos:cli-feature "nokeyword";
         type enumeration {
           enum "/var" {
             description "Monitor /var partition";
           }
           enum "/config" {
             description "Monitor /config partition";
           }
         }
       }
       uses apply-advanced;
       list level {
         key name;
         ordered-by user;
         description "Threshold level";
         leaf name {
           junos:cli-feature "nokeyword";
           type enumeration {
             enum "high" {
               description "Set high level of threshold";
             }
             enum "full" {
               description "Set full level of threshold";
             }
           }
         }
         uses apply-advanced;
         container free-space {
           junos:cli-feature "oneliner";
           description "Enter threshold value & choose the metric";
           leaf thres-free {
             description "Enter free space threshold value";
             junos:cli-feature "nokeyword";
             type union {
               type string {
                 pattern "<.*>|$.*";
               }
               type uint32 {
                 range "0 .. 100";
               }
             }
           }
           choice thres-metric {
             case case_1 {
               leaf percent {
                 description "Free space threshold in %";
                 type empty;
               }
             }
             case case_2 {
               leaf mb {
                 description "Free space threshold in MB";
                 type empty;
               }
             }
           }
         }
       }
     }
     container container-devices {
       description "Container devices configuration";
       uses chassisd_agg_container_type;
     }
     container pseudowire-service {
       description "Pseudowire L3 termination device configuration";
       presence "enable pseudowire-service";
       uses chassis-pw-type;
     }
     container redundancy-group {
       description "Redundancy group configuration";
       uses chassisd-redundancy-group-type;
     }
     container fabric {
       description "Switch fabric settings";
       junos:cli-feature "oneliner-plus";
       uses chassis_fabric_type;
     }
     list fpc {
       key name;
       description "Flexible PIC Concentrator parameters";
       junos:must "((!(any \". <*> vpn-localization\") || !(\"virtual-chassis\")))";
       junos:must-message "vpn-localization cannot be configured on virtual-chassis";
       uses chassis_fpc_type;
     }
     leaf node-id {
       description "Chassis identifier";
       status deprecated;
       junos:must "(!(any \"chassis fpc <*> pfe <*> node $$\"))";
       junos:must-message "node-id needs to be unique across chassis fpc<> pfe<> node<>";
       type union {
         type string {
           pattern "<.*>|$.*";
         }
         type uint64 {
           range "1 .. 18446744073709551615";
         }
       }
     }
     container p4rt {
       presence "enable p4rt";
       description "Chassis p4rt";
       uses apply-advanced;
       leaf node-id {
         description "Chassis identifier";
         junos:must "(!(any \"chassis fpc <*> pfe <*> node $$\"))";
         junos:must-message "node-id needs to be unique across chassis fpc<> pfe<> node<>";
         type union {
           type string {
             pattern "<.*>|$.*";
           }
           type uint64 {
             range "1 .. 18446744073709551615";
           }
         }
       }
     }
     list cb {
       key name;
       description "Control Board parameters";
       uses chassis_cb_type;
     }
     leaf disable-fm {
       description "Disable Fabric Manager";
       type empty;
     }
     container pem {
       description "Power supply (PEM) parameters";
       uses chassis_pem_type;
     }
     container sib {
       description "Switch Interface Board parameters";
       uses chassis_sib_type;
     }
     container fabric-card {
       description "Fabric card parameters";
       presence "enable fabric-card";
       uses chassis_fabric_cards_type;
     }
     container feb {
       description "Forwarding Engine Board parameters";
       uses chassis_feb_type;
     }
     container alarm {
       description "Global alarm settings";
       uses chassis_alarm_type;
     }
     leaf slow-pfe-alarm {
       description "Enable slow (potential) PFE alarm";
       type empty;
     }
     leaf fpc-ifl-ae-statistics {
       description "Enable fpc ifl ae child statistics";
       type empty;
     }
     leaf ambient-temperature {
       description "Chassis ambient-temperature value in degree celsius";
       type enumeration {
         enum "55C" {
           description "55 degree celsius";
         }
         enum "40C" {
           description "40 degree celsius";
         }
         enum "25C" {
           description "25 degree celsius";
         }
         enum "32C" {
           description "32 degree celsius";
         }
       }
     }
     leaf network-services {
       description "Chassis network services configuration";
       type enumeration {
         enum "ip" {
           description "IP network services";
         }
         enum "ethernet" {
           description "Ethernet network services";
           junos:must "((!(any \"interfaces <*> unit <*> family inet accounting source-class-usage\") && (!(any \"interfaces <*> unit <*> family inet accounting destination-class-usage\") && (!(any \"interfaces <*> unit <*> family inet6 accounting source-class-usage\") && (!(any \"interfaces <*> unit <*> family inet6 accounting destination-class-usage\") && (!(any \"logical-systems <*> interfaces <*> unit <*> family inet accounting source-class-usage\") && (!(any \"logical-systems <*> interfaces <*> unit <*> family inet accounting destination-class-usage\") && (!(any \"logical-systems <*> interfaces <*> unit <*> family inet6 accounting source-class-usage\") && !(any \"logical-systems <*> interfaces <*> unit <*> family inet6 accounting destination-class-usage\")))))))))";
           junos:must-message "Cannot configure 'accounting source-class-usage or destination-class-usage' under network-services ethernet";
           junos:must "((!(\"routing-options forwarding-table unicast-reverse-path\") && (!(any \"routing-instances <*> routing-options forwarding-table unicast-reverse-path\") && (!(any \"logical-systems <*> routing-options forwarding-table unicast-reverse-path\") && !(any \"logical-systems <*> routing-instances <*> routing-options forwarding-table unicast-reverse-path\")))))";
           junos:must-message "Cannot configure 'unicast-reverse-path' under network-services ethernet";
           junos:must "((!(any \"interfaces <*> unit <*> family inet rpf-check\") && (!(any \"interfaces <*> unit <*> family inet6 rpf-check\") && (!(any \"logical-systems <*> interfaces <*> unit <*> family inet rpf-check\") && !(any \"logical-systems <*> interfaces <*> unit <*> family inet6 rpf-check\")))))";
           junos:must-message "Cannot configure 'rpf-check' under network-services ethernet";
           junos:must "((!(any \"policy-options policy-statement <*> then source-class\") && (!(any \"policy-options policy-statement <*> term <*> then source-class\") && (!(any \"policy-options policy-statement <*> then destination-class\") && (!(any \"policy-options policy-statement <*> term <*> then destination-class\") && (!(any \"policy-options policy-statement <*> from route-filter <*> <*>  source-class\") && (!(any \"policy-options policy-statement <*> term <*> from route-filter <*> <*>  source-class\") && (!(any \"policy-options policy-statement <*> from route-filter <*> <*> destination-class\") && (!(any \"policy-options policy-statement <*> term <*> from route-filter <*> <*>  destination-class\") && (!(any \"logical-systems <*> policy-options policy-statement <*> then source-class\") && (!(any \"logical-systems <*> policy-options policy-statement <*> term <*> then source-class\") && (!(any \"logical-systems <*> policy-options policy-statement <*> then destination-class\") && (!(any \"logical-systems <*> policy-options policy-statement <*> term <*> then destination-class\") && (!(any \"logical-systems <*> policy-options policy-statement <*> from route-filter <*> <*>  source-class\") && (!(any \"logical-systems <*> policy-options policy-statement <*> term <*> from route-filter <*> <*>  source-class\") && (!(any \"logical-systems <*> policy-options policy-statement <*> from route-filter <*> <*> destination-class\") && !(any \"logical-systems <*> policy-options policy-statement <*> term <*> from route-filter <*> <*>  destination-class\")))))))))))))))))";
           junos:must-message "Cannot configure 'destination-class|source-class' under network-services ethernet";
           junos:must "((!(\"protocols bgp family inet any\") && (!(\"protocols bgp family inet flow\") && (!(\"protocols bgp family inet multicast\") && (!(any \"protocols bgp group <*> family inet any\") && (!(any \"protocols bgp group <*> family inet flow\") && (!(any \"protocols bgp group <*> family inet multicast\") && (!(any \"protocols bgp group <*> neighbor <*> family inet any\") && (!(any \"protocols bgp group <*> neighbor <*> family inet flow\") && (!(any \"protocols bgp group <*> neighbor <*> family inet multicast\") && (!(\"protocols bgp family inet-vpn any\") && (!(\"protocols bgp family inet-vpn flow\") && (!(\"protocols bgp family inet-vpn multicast\") && (!(any \"protocols bgp group <*> family inet-vpn any\") && (!(any \"protocols bgp group <*> family inet-vpn flow\") && (!(any \"protocols bgp group <*> family inet-vpn multicast\") && (!(any \"protocols bgp group <*> neighbor <*> family inet-vpn any\") && (!(any \"protocols bgp group <*> neighbor <*> family inet-vpn flow\") && (!(any \"protocols bgp group <*> neighbor <*> family inet-vpn multicast\") && (!(\"protocols bgp family inet6\") && (!(any \"protocols bgp group <*> family inet6\") && (!(any \"protocols bgp group <*> neighbor <*> family inet6\") && (!(\"protocols bgp family inet6-vpn\") && (!(any \"protocols bgp group <*> family inet6-vpn\") && (!(any \"protocols bgp group <*> neighbor <*> family inet6-vpn\") && (!(\"protocols bgp family inet-mvpn\") && (!(any \"protocols bgp group <*> family inet-mvpn\") && (!(any \"protocols bgp group <*> neighbor <*> family inet-mvpn\") && (!(\"protocols bgp family inet6-mvpn\") && (!(any \"protocols bgp group <*> family inet6-mvpn\") && (!(any \"protocols bgp group <*> neighbor <*> family inet6-mvpn\") && (!(\"protocols bgp family iso\") && (!(any \"protocols bgp group <*> family iso\") && (!(any \"protocols bgp group <*> neighbor <*> family iso\") && (!(\"protocols bgp family iso-vpn\") && (!(any \"protocols bgp group <*> family iso-vpn\") && (!(any \"protocols bgp group <*> neighbor <*> family iso-vpn\") && (!(\"protocols bgp family atmvpn\") && (!(any \"protocols bgp group <*> family atmvpn\") && (!(any \"protocols bgp group <*> neighbor <*> family atmvpn\") && (!(any \"logical-systems <*> protocols bgp family inet any\") && (!(any \"logical-systems <*> protocols bgp family inet flow\") && (!(any \"logical-systems <*> protocols bgp family inet multicast\") && (!(any \"logical-systems <*> protocols bgp group <*> family inet any\") && (!(any \"logical-systems <*> protocols bgp group <*> family inet flow\") && (!(any \"logical-systems <*> protocols bgp group <*> family inet multicast\") && (!(any \"logical-systems <*> protocols bgp group <*> neighbor <*> family inet any\") && (!(any \"logical-systems <*> protocols bgp group <*> neighbor <*> family inet flow\") && (!(any \"logical-systems <*> protocols bgp group <*> neighbor <*> family inet multicast\") && (!(any \"logical-systems <*> protocols bgp family inet-vpn any\") && (!(any \"logical-systems <*> protocols bgp family inet-vpn flow\") && (!(any \"logical-systems <*> protocols bgp family inet-vpn multicast\") && (!(any \"logical-systems <*> protocols bgp group <*> family inet-vpn any\") && (!(any \"logical-systems <*> protocols bgp group <*> family inet-vpn flow\") && (!(any \"logical-systems <*> protocols bgp group <*> family inet-vpn multicast\") && (!(any \"logical-systems <*> protocols bgp group <*> neighbor <*> family inet-vpn any\") && (!(any \"logical-systems <*> protocols bgp group <*> neighbor <*> family inet-vpn flow\") && (!(any \"logical-systems <*> protocols bgp group <*> neighbor <*> family inet-vpn multicast\") && (!(any \"logical-systems <*> protocols bgp family inet6\") && (!(any \"logical-systems <*> protocols bgp group <*> family inet6\") && (!(any \"logical-systems <*> protocols bgp group <*> neighbor <*> family inet6\") && (!(any \"logical-systems <*> protocols bgp family inet6-vpn\") && (!(any \"logical-systems <*> protocols bgp group <*> family inet6-vpn\") && (!(any \"protocols bgp group <*> neighbor <*> family inet6-vpn\") && (!(any \"logical-systems <*> protocols bgp family inet-mvpn\") && (!(any \"logical-systems <*> protocols bgp group <*> family inet-mvpn\") && (!(any \"protocols bgp group <*> neighbor <*> family inet-mvpn\") && (!(any \"logical-systems <*> protocols bgp family inet6-mvpn\") && (!(any \"logical-systems <*> protocols bgp group <*> family inet6-mvpn\") && (!(any \"logical-systems <*> protocols bgp group <*> neighbor <*> family inet6-mvpn\") && (!(any \"logical-systems <*> protocols bgp family iso\") && (!(any \"logical-systems <*> protocols bgp group <*> family iso\") && (!(any \"protocols bgp group <*> neighbor <*> family iso\") && (!(any \"logical-systems <*> protocols bgp family iso-vpn\") && (!(any \"logical-systems <*> protocols bgp group <*> family iso-vpn\") && (!(any \"logical-systems <*> protocols bgp group <*> neighbor <*> family iso-vpn\") && (!(any \"logical-systems <*> protocols bgp family atmvpn\") && (!(any \"logical-systems <*> protocols bgp group <*> family atmvpn\") && !(any \"protocols bgp group <*> neighbor <*> family atmvpn\")))))))))))))))))))))))))))))))))))))))))))))))))))))))))))))))))))))))))))))))";
           junos:must-message "Only BGP groups with 'family inet unicast, inet labeled-unicast, inet-vpn unicast, l2vpn and route-target' are supported under network-services ethernet";
         }
         enum "enhanced-ip" {
           description "Enhanced IP network services";
         }
         enum "enhanced-ethernet" {
           description "Enhanced ethernet network services";
         }
         enum "enhanced-mode" {
           description "Enhanced network services";
         }
         enum "lan" {
           description "Ethernet LAN services";
         }
       }
     }
     container alarm-port {
       description "Craft-interface parameters";
       uses chassis_alarm_port_op_type;
     }
     container usb {
       description "USB control flags";
       uses apply-advanced;
       container storage {
         description "USB storage flags";
         uses apply-advanced;
         leaf disable {
           description "Disable USB storage";
           type empty;
         }
       }
     }
     container serdes {
       presence "enable serdes";
       description "Serdes test mode for link training";
       uses apply-advanced;
       leaf test-mode {
         description "Serdes test mode";
         type string;
       }
     }
     list lcc {
       key name;
       description "Line-card chassis configuration";
       leaf name {
         description "LCC number";
         junos:cli-feature "nokeyword";
         type union {
           type string {
             pattern "<.*>|$.*";
           }
           type uint32;
         }
       }
       uses apply-advanced;
       list fpc {
         key name;
         description "Flexible PIC Concentrator parameters";
         junos:must "((!(any \". <*> vpn-localization\") || !(\"virtual-chassis\")))";
         junos:must-message "vpn-localization cannot be configured on virtual-chassis";
         uses chassis_fpc_type;
       }
       container pem {
         description "Power supply (PEM) parameters";
         uses chassis_pem_type;
       }
       choice state {
         case case_1 {
           leaf online-expected {
             description "LCC is expected to be online";
             type empty;
           }
         }
         case case_2 {
           leaf offline {
             description "LCC is expected to be offline";
             type empty;
           }
         }
       }
     }
     container synchronization {
       description "Clock synchronization options";
       uses apply-advanced;
       leaf switchover-mode {
         description "Should system revert to higher priority valid source";
         default "revertive";
         type enumeration {
           enum "non-revertive" {
             description "System uses current source as long as it is valid";
           }
           enum "revertive" {
             description "Automatically switch to higher priority valid source";
           }
         }
       }
       leaf switching-mode {
         description "Should system revert to higher priority valid source";
         default "non-revertive";
         type enumeration {
           enum "non-revertive" {
             description "System uses current source as long as it is valid";
           }
           enum "revertive" {
             description "Automatically switch to higher priority valid source";
           }
         }
       }
       leaf network-option {
         description "EEC synchronization networking type";
         type enumeration {
           enum "option-1" {
             description "Option 1 (EEC1) synchronization networking";
           }
           enum "option-2" {
             description "Option 2 (EEC2) synchronization networking";
           }
         }
       }
       leaf selection-mode {
         description "Selection mode for incoming ESMC quality";
         default "configured-quality";
         type enumeration {
           enum "configured-quality" {
             description "Use source's configured ESMC quality";
           }
           enum "received-quality" {
             description "Use source's received ESMC quality";
             junos:must "(\"chassis synchronization quality-mode-enable\")";
             junos:must-message "Cannot configure received-quality without quality-mode-enable";
           }
         }
       }
       leaf clock-mode {
         description "Synchronous Ethernet Clock selection mode";
         type enumeration {
           enum "free-run" {
             description "Use the free-running local oscillator";
             junos:must "(!(\"protocols ptp\"))";
             junos:must-message "Cannot configure free-running clock when ptp is configured";
           }
           enum "auto-select" {
             description "Select best clock source";
           }
         }
       }
       leaf quality-mode-enable {
         description "Enable Synchronous Ethernet ESMC Quality mode";
         type empty;
       }
       leaf max-transmit-quality-level {
         description "Maximum transmit quality level";
         type enumeration {
           enum "ePRTC" {
             description "Time quality of enhanced primary reference time clock";
             junos:must "(\"chassis synchronization enable-extended-ql-tlv\")";
             junos:must-message "Must configure 'chassis synchronization enable-extended-ql-tlv'";
             junos:must "(\"chassis synchronization network-option\")";
             junos:must-message "Must configure 'chassis synchronization network-option'";
           }
           enum "PRTC" {
             description "Time quality of primary reference time clock";
             junos:must "(\"chassis synchronization enable-extended-ql-tlv\")";
             junos:must-message "Must configure 'chassis synchronization enable-extended-ql-tlv'";
             junos:must "(\"chassis synchronization network-option\")";
             junos:must-message "Must configure 'chassis synchronization network-option'";
           }
           enum "ePRC" {
             description "Time quality of enhanced primary reference clock";
             junos:must "(\"chassis synchronization enable-extended-ql-tlv\")";
             junos:must-message "Must configure 'chassis synchronization enable-extended-ql-tlv'";
             junos:must "(\"chassis synchronization network-option\")";
             junos:must-message "Must configure 'chassis synchronization network-option'";
           }
           enum "eEEC" {
             description "Time quality of enhanced ethernet equipment clock";
             junos:must "(\"chassis synchronization enable-extended-ql-tlv\")";
             junos:must-message "Must configure 'chassis synchronization enable-extended-ql-tlv'";
             junos:must "(\"chassis synchronization network-option\")";
             junos:must-message "Must configure 'chassis synchronization network-option'";
           }
           enum "prc" {
             description "Timing quality of a primary reference clock (option-1 only)";
             junos:must "(\"chassis synchronization network-option option-1\")";
             junos:must-message "Must configure 'chassis synchronization network-option option-1'";
           }
           enum "ssu-a" {
             description "Timing quality of a type I or IV slave clock (option-1 only)";
             junos:must "(\"chassis synchronization network-option option-1\")";
             junos:must-message "Must configure 'chassis synchronization network-option option-1'";
           }
           enum "ssu-b" {
             description "Timing quality of a type VI slave clock (option-1 only)";
             junos:must "(\"chassis synchronization network-option option-1\")";
             junos:must-message "Must configure 'chassis synchronization network-option option-1'";
           }
           enum "sec" {
             description "Timing quality of SDH equipment clock (option-1 only)";
             junos:must "(\"chassis synchronization network-option option-1\")";
             junos:must-message "Must configure 'chassis synchronization network-option option-1'";
           }
           enum "prs" {
             description "Clock traceable to primary reference source (option-2 only)";
             junos:must "(\"chassis synchronization network-option option-2\")";
             junos:must-message "Must configure 'chassis synchronization network-option option-2'";
           }
           enum "stu" {
             description "Clock traceable to unknown quality (option-2 only)";
             junos:must "(\"chassis synchronization network-option option-2\")";
             junos:must-message "Must configure 'chassis synchronization network-option option-2'";
           }
           enum "st2" {
             description "Clock traceable to stratum 2 (option-2 only)";
             junos:must "(\"chassis synchronization network-option option-2\")";
             junos:must-message "Must configure 'chassis synchronization network-option option-2'";
           }
           enum "tnc" {
             description "Clock traceable to transit node clock (option-2 only)";
             junos:must "(\"chassis synchronization network-option option-2\")";
             junos:must-message "Must configure 'chassis synchronization network-option option-2'";
           }
           enum "st3e" {
             description "Clock traceable to stratum 3E (option-2 only)";
             junos:must "(\"chassis synchronization network-option option-2\")";
             junos:must-message "Must configure 'chassis synchronization network-option option-2'";
           }
         }
       }
       leaf enable-extended-ql-tlv {
         description "Enable enhanced ESMC QL support";
         type empty;
       }
       leaf global-wait-to-restore {
         description "Global Port signal up state time before opening for ESMC";
         units "min";
         type union {
           type string {
             pattern "<.*>|$.*";
           }
           type uint32 {
             range "0 .. 12";
           }
         }
       }
       leaf minimum-quality {
         description "Minimum quality threshold";
         type enumeration {
           enum "prc" {
             description "Timing quality of a primary reference clock (option-1 only)";
             junos:must "(\"chassis synchronization network-option option-1\")";
             junos:must-message "Must configure 'chassis synchronization network-option option-1'";
           }
           enum "ssu-a" {
             description "Timing quality of a type I or IV slave clock (option-1 only)";
             junos:must "(\"chassis synchronization network-option option-1\")";
             junos:must-message "Must configure 'chassis synchronization network-option option-1'";
           }
           enum "ssu-b" {
             description "Timing quality of a type VI slave clock (option-1 only)";
             junos:must "(\"chassis synchronization network-option option-1\")";
             junos:must-message "Must configure 'chassis synchronization network-option option-1'";
           }
           enum "sec" {
             description "Timing quality of SDH equipment clock (option-1 only)";
             junos:must "(\"chassis synchronization network-option option-1\")";
             junos:must-message "Must configure 'chassis synchronization network-option option-1'";
           }
           enum "prs" {
             description "Clock traceable to primary reference source (option-2 only)";
             junos:must "(\"chassis synchronization network-option option-2\")";
             junos:must-message "Must configure 'chassis synchronization network-option option-2'";
           }
           enum "st2" {
             description "Clock traceable to stratum 2 (option-2 only)";
             junos:must "(\"chassis synchronization network-option option-2\")";
             junos:must-message "Must configure 'chassis synchronization network-option option-2'";
           }
           enum "tnc" {
             description "Clock traceable to transit node clock (option-2 only)";
             junos:must "(\"chassis synchronization network-option option-2\")";
             junos:must-message "Must configure 'chassis synchronization network-option option-2'";
           }
           enum "st3e" {
             description "Clock traceable to stratum 3E (option-2 only)";
             junos:must "(\"chassis synchronization network-option option-2\")";
             junos:must-message "Must configure 'chassis synchronization network-option option-2'";
           }
           enum "st3" {
             description "Clock traceable to stratum 3 (option-2 only)";
             junos:must "(\"chassis synchronization network-option option-2\")";
             junos:must-message "Must configure 'chassis synchronization network-option option-2'";
           }
           enum "st4" {
             description "Clock traceable to stratum 4 free-run (option-2 only)";
             junos:must "(\"chassis synchronization network-option option-2\")";
             junos:must-message "Must configure 'chassis synchronization network-option option-2'";
           }
           enum "smc" {
             description "Clock traceable to self-timed SONET (option-2 only)";
             junos:must "(\"chassis synchronization network-option option-2\")";
             junos:must-message "Must configure 'chassis synchronization network-option option-2'";
           }
           enum "stu" {
             description "Clock traceable to unknown quality (option-2 only)";
             junos:must "(\"chassis synchronization network-option option-2\")";
             junos:must-message "Must configure 'chassis synchronization network-option option-2'";
           }
         }
       }
       list port {
         key name;
         description "Clock synchronization ports";
         leaf name {
           junos:cli-feature "nokeyword";
           junos:cli-feature "homogeneous";
           type enumeration {
             enum "auxiliary" {
               description "Auxiliary port";
             }
             enum "gnss" {
               description "Global Navigation Satellite System - GPS or GLONASS port";
               junos:must "(!(\"chassis synchronization source\"))";
               junos:must-message "must not configure SYNCE source along with port gnss";
               junos:must "(\"protocols ptp\")";
               junos:must-message "must configure protocols ptp";
             }
             enum "time-of-day" {
               description "Time of Day(TOD) port";
             }
           }
         }
         uses apply-advanced;
         container client {
           presence "enable client";
           description "Port client receiving external signals";
           uses apply-advanced;
           container time-of-day-format {
             description "Time-of-day format as received on this port";
             uses apply-advanced;
             choice format {
               case case_1 {
                 leaf ascii {
                   description "ASCII Time-of-day message format string";
                   type string {
                     length "1 .. 80";
                   }
                 }
               }
               case case_2 {
               }
               case case_3 {
               }
             }
           }
           leaf cable-length-compensation {
             description "Antenna cable length compensation in nanoseconds";
             type union {
               type uint32;
               type string {
                 pattern "<.*>|$.*";
               }
             }
           }
           leaf antenna-voltage {
             description "Configure antenna voltage";
             type enumeration {
               enum "3.3" {
                 description "3.3 units";
               }
               enum "5" {
                 description "5 units";
               }
             }
           }
           leaf constellation {
             description "Configure constellation of satellites to use";
             type enumeration {
               enum "gps" {
                 description "Global Positioning Satellite(GPS) for clock recovery";
               }
               enum "glonass" {
                 description "Global Navigation Satellite System(GLONASS) constellation";
               }
               enum "gps-and-glonass" {
                 description "All constellations";
               }
               enum "beidou" {
                 description "BEIDOU for clock recovery constellations";
               }
               enum "gps-beidou" {
                 description "GPS and BEIDOU for clock recovery";
               }
               enum "gps-beidou-qzss" {
                 description "GPS ,BEIDOU and qzss for clock recovery";
               }
               enum "galileo" {
                 description "GALILEO for clock recovery";
               }
               enum "gps-galileo" {
                 description "GPS and GALILEO for clock recovery";
               }
               enum "gps-qzss" {
                 description "GPS and QZSS for clock recovery";
               }
               enum "gps-glonass-qzss" {
                 description "GPS,GLONASS and QZSS for clock recovery";
               }
               enum "gps-galileo-qzss" {
                 description "GPS , GALILEO and QZSS for clock recovery";
               }
             }
           }
           leaf anti-jamming {
             description "Enable anti-jamming feature";
             type empty;
           }
         }
       }
       list interfaces {
         key name;
         description "Interface(s) with upstream clock source";
         leaf name {
           junos:cli-feature "nokeyword";
           junos:cli-feature "homogeneous";
           type enumeration {
             enum "external" {
               description "External clock interface";
             }
             enum "external-0/0" {
               description "External clock interface on SCB-0";
               junos:must "(\"chassis synchronization interfaces external-0/0 signal-type\")";
               junos:must-message "Must configure 'chassis synchronization interfaces external-0/0 signal-type'";
             }
             enum "external-0/1" {
               description "External clock interface on SCB-0";
               junos:must "(\"chassis synchronization interfaces external-0/1 signal-type\")";
               junos:must-message "Must configure 'chassis synchronization interfaces external-0/1 signal-type'";
             }
             enum "external-1/0" {
               description "External clock interface on SCB-1";
               junos:must "(\"chassis synchronization interfaces external-1/0 signal-type\")";
               junos:must-message "Must configure 'chassis synchronization interfaces external-1/0 signal-type'";
             }
             enum "external-1/1" {
               description "External clock interface on SCB-1";
               junos:must "(\"chassis synchronization interfaces external-1/1 signal-type\")";
               junos:must-message "Must configure 'chassis synchronization interfaces external-1/1 signal-type'";
             }
             enum "external-a" {
               description "External-A clock interface";
             }
             enum "external-b" {
               description "External-B clock interface";
             }
             enum "external-0" {
               description "External-0 clock interface";
             }
             enum "external-1" {
               description "External-1 clock interface";
             }
             enum "external-2" {
               description "External-2 clock interface";
             }
             enum "bits" {
               description "External BITS interface configuration";
             }
             enum "bits-a" {
               description "External BITS interface A configuration";
             }
             enum "bits-b" {
               description "External BITS interface B configuration";
             }
             enum "gps-0" {
               description "External GPS interface A configuration";
             }
             enum "gps-1" {
               description "External GPS interface B configuration";
             }
           }
         }
         uses apply-advanced;
         leaf signal-type {
           description "Frequency for provided reference clocks";
           type enumeration {
             enum "1mhz" {
               description "1 MHz clock signal";
             }
             enum "5mhz" {
               description "5 MHz clock signal";
             }
             enum "10mhz" {
               description "10 MHz clock signal";
             }
             enum "2048khz" {
               description "E1 unframed 2048Khz G.703 signal";
               junos:must "(\"chassis synchronization network-option option-1\")";
               junos:must-message "Must configure 'chassis synchronization network-option option-1'";
             }
             enum "e1" {
               description "E1-coded 2048 KHz signal on 120 ohm balanced line";
               junos:must "(\"chassis synchronization network-option option-1\")";
               junos:must-message "Must configure 'chassis synchronization network-option option-1'";
             }
             enum "t1" {
               description "T1-coded 1.544 MHz signal on 100 ohm balanced line";
               junos:must "(\"chassis synchronization network-option option-2\")";
               junos:must-message "Must configure 'chassis synchronization network-option option-2'";
             }
             enum "cc-8k" {
               description "Composite Clock 64kHz+8kHz";
               junos:must "(\"chassis synchronization network-option option-2\")";
               junos:must-message "Must configure 'chassis synchronization network-option option-2'";
             }
             enum "cc-8k-400" {
               description "Composite Clock 64kHz+8kHz+400Hz";
               junos:must "(\"chassis synchronization network-option option-2\")";
               junos:must-message "Must configure 'chassis synchronization network-option option-2'";
             }
             enum "6312k" {
               description "Japanese Standard 6312kHz";
               junos:must "(\"chassis synchronization network-option option-2\")";
               junos:must-message "Must configure 'chassis synchronization network-option option-2'";
             }
           }
         }
         leaf pulse-per-second-enable {
           description "Enable pulse-per-second (PPS) receive on the interface";
           junos:must "((\".. signal-type $$={1mhz}\" || (\".. signal-type $$={5mhz}\" || \".. signal-type $$={10mhz}\")))";
           junos:must-message "Must configure signal-type to 1/5/10 MHz";
           type empty;
         }
         container e1-options {
           junos:must "(\"chassis synchronization network-option option-1\")";
           junos:must-message "Must configure 'chassis synchronization network-option option-1'";
           description "E1 interface-specific options";
           uses apply-advanced;
           leaf line-encoding {
             description "Line encoding";
             default "hdb3";
             type enumeration {
               enum "ami" {
                 description "Automatic mark inversion";
               }
               enum "hdb3" {
                 description "High-density bipolar 3 code";
               }
             }
           }
           leaf framing {
             description "Framing mode";
             default "g704";
             type enumeration {
               enum "g704" {
                 description "G.704 framing format for E1 interfaces";
               }
               enum "g704-no-crc4" {
                 description "G.704 framing without CRC4 for E1 interfaces";
               }
             }
           }
           leaf sabit {
             description "The sabit used for exchanging SSM quality";
             default "4";
             type union {
               type string {
                 pattern "<.*>|$.*";
               }
               type uint32 {
                 range "4 .. 8";
               }
             }
           }
         }
         container t1-options {
           junos:must "(\"chassis synchronization network-option option-2\")";
           junos:must-message "Must configure 'chassis synchronization network-option option-2'";
           description "T1 interface-specific options";
           uses apply-advanced;
           leaf line-encoding {
             description "Line encoding";
             default "b8zs";
             type enumeration {
               enum "ami" {
                 description "Automatic mark inversion";
               }
               enum "b8zs" {
                 description "8-bit zero suppression";
               }
             }
           }
           leaf framing {
             description "Framing mode";
             default "esf";
             type enumeration {
               enum "esf" {
                 description "Extended Super Frame";
               }
               enum "sf" {
                 description "Super Frame";
               }
             }
           }
         }
       }
       container source {
         junos:must "(\"chassis synchronization network-option\")";
         junos:must-message "Must configure 'chassis synchronization network-option'";
         junos:must "(!((\"chassis synchronization primary\" || \"chassis synchronization secondary\")))";
         junos:must-message "primary or secondary cannot be configured with source";
         description "ESMC source(s) related";
         uses apply-advanced;
         container gps-0 {
           presence "enable gps-0";
           description "Global Positioning System input A";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "PRTC" {
                 description "Time quality of primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "ePRC" {
                 description "Time quality of enhanced primary reference clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "eEEC" {
                 description "Time quality of enhanced ethernet equipment clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "prc" {
                 description "Timing quality of a primary reference clock (option-1 only)";
                 junos:must "(\"chassis synchronization network-option option-1\")";
                 junos:must-message "Must configure 'chassis synchronization network-option option-1'";
               }
               enum "ssu-a" {
                 description "Timing quality of a type I or IV slave clock (option-1 only)";
                 junos:must "(\"chassis synchronization network-option option-1\")";
                 junos:must-message "Must configure 'chassis synchronization network-option option-1'";
               }
               enum "ssu-b" {
                 description "Timing quality of a type VI slave clock (option-1 only)";
                 junos:must "(\"chassis synchronization network-option option-1\")";
                 junos:must-message "Must configure 'chassis synchronization network-option option-1'";
               }
               enum "sec" {
                 description "Timing quality of SDH equipment clock (option-1 only)";
                 junos:must "(\"chassis synchronization network-option option-1\")";
                 junos:must-message "Must configure 'chassis synchronization network-option option-1'";
               }
               enum "prs" {
                 description "Clock traceable to primary reference source (option-2 only)";
                 junos:must "(\"chassis synchronization network-option option-2\")";
                 junos:must-message "Must configure 'chassis synchronization network-option option-2'";
               }
               enum "st2" {
                 description "Clock traceable to stratum 2 (option-2 only)";
                 junos:must "(\"chassis synchronization network-option option-2\")";
                 junos:must-message "Must configure 'chassis synchronization network-option option-2'";
               }
               enum "tnc" {
                 description "Clock traceable to transit node clock (option-2 only)";
                 junos:must "(\"chassis synchronization network-option option-2\")";
                 junos:must-message "Must configure 'chassis synchronization network-option option-2'";
               }
               enum "st3e" {
                 description "Clock traceable to stratum 3E (option-2 only)";
                 junos:must "(\"chassis synchronization network-option option-2\")";
                 junos:must-message "Must configure 'chassis synchronization network-option option-2'";
               }
               enum "st3" {
                 description "Clock traceable to stratum 3 (option-2 only)";
                 junos:must "(\"chassis synchronization network-option option-2\")";
                 junos:must-message "Must configure 'chassis synchronization network-option option-2'";
               }
               enum "st4" {
                 description "Clock traceable to stratum 4 free-run (option-2 only)";
                 junos:must "(\"chassis synchronization network-option option-2\")";
                 junos:must-message "Must configure 'chassis synchronization network-option option-2'";
               }
               enum "smc" {
                 description "Clock traceable to self-timed SONET (option-2 only)";
                 junos:must "(\"chassis synchronization network-option option-2\")";
                 junos:must-message "Must configure 'chassis synchronization network-option option-2'";
               }
               enum "stu" {
                 description "Clock traceable to unknown quality (option-2 only)";
                 junos:must "(\"chassis synchronization network-option option-2\")";
                 junos:must-message "Must configure 'chassis synchronization network-option option-2'";
               }
             }
           }
         }
         container gps-1 {
           presence "enable gps-1";
           description "Global Positioning System input B";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "PRTC" {
                 description "Time quality of primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "ePRC" {
                 description "Time quality of enhanced primary reference clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "eEEC" {
                 description "Time quality of enhanced ethernet equipment clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "prc" {
                 description "Timing quality of a primary reference clock (option-1 only)";
                 junos:must "(\"chassis synchronization network-option option-1\")";
                 junos:must-message "Must configure 'chassis synchronization network-option option-1'";
               }
               enum "ssu-a" {
                 description "Timing quality of a type I or IV slave clock (option-1 only)";
                 junos:must "(\"chassis synchronization network-option option-1\")";
                 junos:must-message "Must configure 'chassis synchronization network-option option-1'";
               }
               enum "ssu-b" {
                 description "Timing quality of a type VI slave clock (option-1 only)";
                 junos:must "(\"chassis synchronization network-option option-1\")";
                 junos:must-message "Must configure 'chassis synchronization network-option option-1'";
               }
               enum "sec" {
                 description "Timing quality of SDH equipment clock (option-1 only)";
                 junos:must "(\"chassis synchronization network-option option-1\")";
                 junos:must-message "Must configure 'chassis synchronization network-option option-1'";
               }
               enum "prs" {
                 description "Clock traceable to primary reference source (option-2 only)";
                 junos:must "(\"chassis synchronization network-option option-2\")";
                 junos:must-message "Must configure 'chassis synchronization network-option option-2'";
               }
               enum "st2" {
                 description "Clock traceable to stratum 2 (option-2 only)";
                 junos:must "(\"chassis synchronization network-option option-2\")";
                 junos:must-message "Must configure 'chassis synchronization network-option option-2'";
               }
               enum "tnc" {
                 description "Clock traceable to transit node clock (option-2 only)";
                 junos:must "(\"chassis synchronization network-option option-2\")";
                 junos:must-message "Must configure 'chassis synchronization network-option option-2'";
               }
               enum "st3e" {
                 description "Clock traceable to stratum 3E (option-2 only)";
                 junos:must "(\"chassis synchronization network-option option-2\")";
                 junos:must-message "Must configure 'chassis synchronization network-option option-2'";
               }
               enum "st3" {
                 description "Clock traceable to stratum 3 (option-2 only)";
                 junos:must "(\"chassis synchronization network-option option-2\")";
                 junos:must-message "Must configure 'chassis synchronization network-option option-2'";
               }
               enum "st4" {
                 description "Clock traceable to stratum 4 free-run (option-2 only)";
                 junos:must "(\"chassis synchronization network-option option-2\")";
                 junos:must-message "Must configure 'chassis synchronization network-option option-2'";
               }
               enum "smc" {
                 description "Clock traceable to self-timed SONET (option-2 only)";
                 junos:must "(\"chassis synchronization network-option option-2\")";
                 junos:must-message "Must configure 'chassis synchronization network-option option-2'";
               }
               enum "stu" {
                 description "Clock traceable to unknown quality (option-2 only)";
                 junos:must "(\"chassis synchronization network-option option-2\")";
                 junos:must-message "Must configure 'chassis synchronization network-option option-2'";
               }
             }
           }
         }
         container bits-a {
           presence "enable bits-a";
           description "External Building Integrated Timing Supply input A";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "PRTC" {
                 description "Time quality of primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "ePRC" {
                 description "Time quality of enhanced primary reference clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "eEEC" {
                 description "Time quality of enhanced ethernet equipment clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "prc" {
                 description "Timing quality of a primary reference clock (option-1 only)";
                 junos:must "(\"chassis synchronization network-option option-1\")";
                 junos:must-message "Must configure 'chassis synchronization network-option option-1'";
               }
               enum "ssu-a" {
                 description "Timing quality of a type I or IV slave clock (option-1 only)";
                 junos:must "(\"chassis synchronization network-option option-1\")";
                 junos:must-message "Must configure 'chassis synchronization network-option option-1'";
               }
               enum "ssu-b" {
                 description "Timing quality of a type VI slave clock (option-1 only)";
                 junos:must "(\"chassis synchronization network-option option-1\")";
                 junos:must-message "Must configure 'chassis synchronization network-option option-1'";
               }
               enum "sec" {
                 description "Timing quality of SDH equipment clock (option-1 only)";
                 junos:must "(\"chassis synchronization network-option option-1\")";
                 junos:must-message "Must configure 'chassis synchronization network-option option-1'";
               }
               enum "prs" {
                 description "Clock traceable to primary reference source (option-2 only)";
                 junos:must "(\"chassis synchronization network-option option-2\")";
                 junos:must-message "Must configure 'chassis synchronization network-option option-2'";
               }
               enum "st2" {
                 description "Clock traceable to stratum 2 (option-2 only)";
                 junos:must "(\"chassis synchronization network-option option-2\")";
                 junos:must-message "Must configure 'chassis synchronization network-option option-2'";
               }
               enum "tnc" {
                 description "Clock traceable to transit node clock (option-2 only)";
                 junos:must "(\"chassis synchronization network-option option-2\")";
                 junos:must-message "Must configure 'chassis synchronization network-option option-2'";
               }
               enum "st3e" {
                 description "Clock traceable to stratum 3E (option-2 only)";
                 junos:must "(\"chassis synchronization network-option option-2\")";
                 junos:must-message "Must configure 'chassis synchronization network-option option-2'";
               }
               enum "st3" {
                 description "Clock traceable to stratum 3 (option-2 only)";
                 junos:must "(\"chassis synchronization network-option option-2\")";
                 junos:must-message "Must configure 'chassis synchronization network-option option-2'";
               }
               enum "st4" {
                 description "Clock traceable to stratum 4 free-run (option-2 only)";
                 junos:must "(\"chassis synchronization network-option option-2\")";
                 junos:must-message "Must configure 'chassis synchronization network-option option-2'";
               }
               enum "smc" {
                 description "Clock traceable to self-timed SONET (option-2 only)";
                 junos:must "(\"chassis synchronization network-option option-2\")";
                 junos:must-message "Must configure 'chassis synchronization network-option option-2'";
               }
               enum "stu" {
                 description "Clock traceable to unknown quality (option-2 only)";
                 junos:must "(\"chassis synchronization network-option option-2\")";
                 junos:must-message "Must configure 'chassis synchronization network-option option-2'";
               }
             }
           }
         }
         container bits-b {
           presence "enable bits-b";
           description "External Building Integrated Timing Supply input B";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "PRTC" {
                 description "Time quality of primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "ePRC" {
                 description "Time quality of enhanced primary reference clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "eEEC" {
                 description "Time quality of enhanced ethernet equipment clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "prc" {
                 description "Timing quality of a primary reference clock (option-1 only)";
                 junos:must "(\"chassis synchronization network-option option-1\")";
                 junos:must-message "Must configure 'chassis synchronization network-option option-1'";
               }
               enum "ssu-a" {
                 description "Timing quality of a type I or IV slave clock (option-1 only)";
                 junos:must "(\"chassis synchronization network-option option-1\")";
                 junos:must-message "Must configure 'chassis synchronization network-option option-1'";
               }
               enum "ssu-b" {
                 description "Timing quality of a type VI slave clock (option-1 only)";
                 junos:must "(\"chassis synchronization network-option option-1\")";
                 junos:must-message "Must configure 'chassis synchronization network-option option-1'";
               }
               enum "sec" {
                 description "Timing quality of SDH equipment clock (option-1 only)";
                 junos:must "(\"chassis synchronization network-option option-1\")";
                 junos:must-message "Must configure 'chassis synchronization network-option option-1'";
               }
               enum "prs" {
                 description "Clock traceable to primary reference source (option-2 only)";
                 junos:must "(\"chassis synchronization network-option option-2\")";
                 junos:must-message "Must configure 'chassis synchronization network-option option-2'";
               }
               enum "st2" {
                 description "Clock traceable to stratum 2 (option-2 only)";
                 junos:must "(\"chassis synchronization network-option option-2\")";
                 junos:must-message "Must configure 'chassis synchronization network-option option-2'";
               }
               enum "tnc" {
                 description "Clock traceable to transit node clock (option-2 only)";
                 junos:must "(\"chassis synchronization network-option option-2\")";
                 junos:must-message "Must configure 'chassis synchronization network-option option-2'";
               }
               enum "st3e" {
                 description "Clock traceable to stratum 3E (option-2 only)";
                 junos:must "(\"chassis synchronization network-option option-2\")";
                 junos:must-message "Must configure 'chassis synchronization network-option option-2'";
               }
               enum "st3" {
                 description "Clock traceable to stratum 3 (option-2 only)";
                 junos:must "(\"chassis synchronization network-option option-2\")";
                 junos:must-message "Must configure 'chassis synchronization network-option option-2'";
               }
               enum "st4" {
                 description "Clock traceable to stratum 4 free-run (option-2 only)";
                 junos:must "(\"chassis synchronization network-option option-2\")";
                 junos:must-message "Must configure 'chassis synchronization network-option option-2'";
               }
               enum "smc" {
                 description "Clock traceable to self-timed SONET (option-2 only)";
                 junos:must "(\"chassis synchronization network-option option-2\")";
                 junos:must-message "Must configure 'chassis synchronization network-option option-2'";
               }
               enum "stu" {
                 description "Clock traceable to unknown quality (option-2 only)";
                 junos:must "(\"chassis synchronization network-option option-2\")";
                 junos:must-message "Must configure 'chassis synchronization network-option option-2'";
               }
             }
           }
         }
         container virtual-port {
           presence "enable virtual-port";
           junos:must "(\"protocols ptp profile-type $$={g.8275.1}\")";
           junos:must-message "Must configure ptp profile type g.8275.1";
           junos:must "(\"protocols ptp virtual-port\")";
           junos:must-message "Must configure protocols ptp virtual-port";
           description "Virtual port";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "PRTC" {
                 description "Time quality of primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "ePRC" {
                 description "Time quality of enhanced primary reference clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "eEEC" {
                 description "Time quality of enhanced ethernet equipment clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "prc" {
                 description "Timing quality of a primary reference clock (option-1 only)";
                 junos:must "(\"chassis synchronization network-option option-1\")";
                 junos:must-message "Must configure 'chassis synchronization network-option option-1'";
               }
               enum "ssu-a" {
                 description "Timing quality of a type I or IV slave clock (option-1 only)";
                 junos:must "(\"chassis synchronization network-option option-1\")";
                 junos:must-message "Must configure 'chassis synchronization network-option option-1'";
               }
               enum "ssu-b" {
                 description "Timing quality of a type VI slave clock (option-1 only)";
                 junos:must "(\"chassis synchronization network-option option-1\")";
                 junos:must-message "Must configure 'chassis synchronization network-option option-1'";
               }
               enum "sec" {
                 description "Timing quality of SDH equipment clock (option-1 only)";
                 junos:must "(\"chassis synchronization network-option option-1\")";
                 junos:must-message "Must configure 'chassis synchronization network-option option-1'";
               }
               enum "prs" {
                 description "Clock traceable to primary reference source (option-2 only)";
                 junos:must "(\"chassis synchronization network-option option-2\")";
                 junos:must-message "Must configure 'chassis synchronization network-option option-2'";
               }
               enum "st2" {
                 description "Clock traceable to stratum 2 (option-2 only)";
                 junos:must "(\"chassis synchronization network-option option-2\")";
                 junos:must-message "Must configure 'chassis synchronization network-option option-2'";
               }
               enum "tnc" {
                 description "Clock traceable to transit node clock (option-2 only)";
                 junos:must "(\"chassis synchronization network-option option-2\")";
                 junos:must-message "Must configure 'chassis synchronization network-option option-2'";
               }
               enum "st3e" {
                 description "Clock traceable to stratum 3E (option-2 only)";
                 junos:must "(\"chassis synchronization network-option option-2\")";
                 junos:must-message "Must configure 'chassis synchronization network-option option-2'";
               }
               enum "st3" {
                 description "Clock traceable to stratum 3 (option-2 only)";
                 junos:must "(\"chassis synchronization network-option option-2\")";
                 junos:must-message "Must configure 'chassis synchronization network-option option-2'";
               }
               enum "st4" {
                 description "Clock traceable to stratum 4 free-run (option-2 only)";
                 junos:must "(\"chassis synchronization network-option option-2\")";
                 junos:must-message "Must configure 'chassis synchronization network-option option-2'";
               }
               enum "smc" {
                 description "Clock traceable to self-timed SONET (option-2 only)";
                 junos:must "(\"chassis synchronization network-option option-2\")";
                 junos:must-message "Must configure 'chassis synchronization network-option option-2'";
               }
               enum "stu" {
                 description "Clock traceable to unknown quality (option-2 only)";
                 junos:must "(\"chassis synchronization network-option option-2\")";
                 junos:must-message "Must configure 'chassis synchronization network-option option-2'";
               }
             }
           }
         }
         list interfaces {
           key name;
           description "Interface(s) with upstream clock source";
           leaf name {
             junos:cli-feature "nokeyword";
             junos:cli-feature "homogeneous";
             type string;
           }
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf no-ssm-support {
             description "No SSM support available for this interface";
             type empty;
           }
           leaf hold-off-time {
             description "Port signal down state time before closing for ESMC";
             units "milliseconds";
             type union {
               type string {
                 pattern "<.*>|$.*";
               }
               type uint32 {
                 range "300 .. 1800";
               }
             }
           }
           leaf aggregated-ether {
             description "Aggregated sources group name";
             junos:must "(\"interfaces $$-IFL\")";
             junos:must-message "System AE interface should be configured";
             type string;
           }
           leaf quality-level {
             description "ESMC Clock EEC level";
             type enumeration {
               enum "ePRTC" {
                 description "Time quality of enhanced primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "PRTC" {
                 description "Time quality of primary reference time clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "ePRC" {
                 description "Time quality of enhanced primary reference clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "eEEC" {
                 description "Time quality of enhanced ethernet equipment clock";
                 junos:must "(\"chassis synchronization enable-extended-ql-tlv\")";
                 junos:must-message "Must configure 'chassis synchronization enable-extended-ql-tlv'";
                 junos:must "(\"chassis synchronization network-option\")";
                 junos:must-message "Must configure 'chassis synchronization network-option'";
               }
               enum "prc" {
                 description "Timing quality of a primary reference clock (option-1 only)";
                 junos:must "(\"chassis synchronization network-option option-1\")";
                 junos:must-message "Must configure 'chassis synchronization network-option option-1'";
               }
               enum "ssu-a" {
                 description "Timing quality of a type I or IV slave clock (option-1 only)";
                 junos:must "(\"chassis synchronization network-option option-1\")";
                 junos:must-message "Must configure 'chassis synchronization network-option option-1'";
               }
               enum "ssu-b" {
                 description "Timing quality of a type VI slave clock (option-1 only)";
                 junos:must "(\"chassis synchronization network-option option-1\")";
                 junos:must-message "Must configure 'chassis synchronization network-option option-1'";
               }
               enum "sec" {
                 description "Timing quality of SDH equipment clock (option-1 only)";
                 junos:must "(\"chassis synchronization network-option option-1\")";
                 junos:must-message "Must configure 'chassis synchronization network-option option-1'";
               }
               enum "prs" {
                 description "Clock traceable to primary reference source (option-2 only)";
                 junos:must "(\"chassis synchronization network-option option-2\")";
                 junos:must-message "Must configure 'chassis synchronization network-option option-2'";
               }
               enum "st2" {
                 description "Clock traceable to stratum 2 (option-2 only)";
                 junos:must "(\"chassis synchronization network-option option-2\")";
                 junos:must-message "Must configure 'chassis synchronization network-option option-2'";
               }
               enum "tnc" {
                 description "Clock traceable to transit node clock (option-2 only)";
                 junos:must "(\"chassis synchronization network-option option-2\")";
                 junos:must-message "Must configure 'chassis synchronization network-option option-2'";
               }
               enum "st3e" {
                 description "Clock traceable to stratum 3E (option-2 only)";
                 junos:must "(\"chassis synchronization network-option option-2\")";
                 junos:must-message "Must configure 'chassis synchronization network-option option-2'";
               }
               enum "st3" {
                 description "Clock traceable to stratum 3 (option-2 only)";
                 junos:must "(\"chassis synchronization network-option option-2\")";
                 junos:must-message "Must configure 'chassis synchronization network-option option-2'";
               }
               enum "st4" {
                 description "Clock traceable to stratum 4 free-run (option-2 only)";
                 junos:must "(\"chassis synchronization network-option option-2\")";
                 junos:must-message "Must configure 'chassis synchronization network-option option-2'";
               }
               enum "smc" {
                 description "Clock traceable to self-timed SONET (option-2 only)";
                 junos:must "(\"chassis synchronization network-option option-2\")";
                 junos:must-message "Must configure 'chassis synchronization network-option option-2'";
               }
               enum "stu" {
                 description "Clock traceable to unknown quality (option-2 only)";
                 junos:must "(\"chassis synchronization network-option option-2\")";
                 junos:must-message "Must configure 'chassis synchronization network-option option-2'";
               }
             }
           }
         }
       }
       container esmc-transmit {
         junos:must "(\"chassis synchronization network-option\")";
         junos:must-message "Must configure 'chassis synchronization network-option'";
         junos:must "(!((\"chassis synchronization primary\" || \"chassis synchronization secondary\")))";
         junos:must-message "primary or secondary cannot be configured with esmc-transmit";
         description "ESMC transmit parameters";
         uses apply-advanced;
         list interfaces {
           key name;
           ordered-by user;
           description "Interface(s) on which to permit ESMC transmit messages";
           leaf name {
             junos:cli-feature "nokeyword";
             junos:cli-feature "homogeneous";
             type string;
           }
           uses apply-advanced;
           container squelch {
             presence "enable squelch";
             junos:must "(!((\"protocols ptp profile-type $$={g.8275.2}\" && !(\"protocols ptp slave hybrid\"))))";
             junos:must-message "Must not configure squelch when using PTS mode i.e. g.8275.2 profile in non-hybrid mode";
             description "Squelch a interface";
             uses apply-advanced;
             leaf method {
               description "Type of Squelch to be done";
               type enumeration {
                 enum "ais" {
                   description "Send AIS";
                 }
                 enum "ql-dnu" {
                   description "Send DNU Quality level out";
                 }
                 enum "rai" {
                   description "Method RAI";
                 }
                 enum "shut" {
                   description "Shutdown";
                 }
               }
             }
             leaf quality-level {
               description "ESMC Quality level below which output is squelched";
               type enumeration {
                 enum "ePRTC" {
                   description "Time quality of enhanced primary reference time clock";
                   junos:must "(\"chassis synchronization enable-extended-ql-tlv\")";
                   junos:must-message "Must configure 'chassis synchronization enable-extended-ql-tlv'";
                   junos:must "(\"chassis synchronization network-option\")";
                   junos:must-message "Must configure 'chassis synchronization network-option'";
                 }
                 enum "PRTC" {
                   description "Time quality of primary reference time clock";
                   junos:must "(\"chassis synchronization enable-extended-ql-tlv\")";
                   junos:must-message "Must configure 'chassis synchronization enable-extended-ql-tlv'";
                   junos:must "(\"chassis synchronization network-option\")";
                   junos:must-message "Must configure 'chassis synchronization network-option'";
                 }
                 enum "ePRC" {
                   description "Time quality of enhanced primary reference clock";
                   junos:must "(\"chassis synchronization enable-extended-ql-tlv\")";
                   junos:must-message "Must configure 'chassis synchronization enable-extended-ql-tlv'";
                   junos:must "(\"chassis synchronization network-option\")";
                   junos:must-message "Must configure 'chassis synchronization network-option'";
                 }
                 enum "eEEC" {
                   description "Time quality of enhanced ethernet equipment clock";
                   junos:must "(\"chassis synchronization enable-extended-ql-tlv\")";
                   junos:must-message "Must configure 'chassis synchronization enable-extended-ql-tlv'";
                   junos:must "(\"chassis synchronization network-option\")";
                   junos:must-message "Must configure 'chassis synchronization network-option'";
                 }
                 enum "prc" {
                   description "Timing quality of a primary reference clock (option-1 only)";
                   junos:must "(\"chassis synchronization network-option option-1\")";
                   junos:must-message "Must configure 'chassis synchronization network-option option-1'";
                 }
                 enum "ssu-a" {
                   description "Timing quality of a type I or IV slave clock (option-1 only)";
                   junos:must "(\"chassis synchronization network-option option-1\")";
                   junos:must-message "Must configure 'chassis synchronization network-option option-1'";
                 }
                 enum "ssu-b" {
                   description "Timing quality of a type VI slave clock (option-1 only)";
                   junos:must "(\"chassis synchronization network-option option-1\")";
                   junos:must-message "Must configure 'chassis synchronization network-option option-1'";
                 }
                 enum "sec" {
                   description "Timing quality of SDH equipment clock (option-1 only)";
                   junos:must "(\"chassis synchronization network-option option-1\")";
                   junos:must-message "Must configure 'chassis synchronization network-option option-1'";
                 }
                 enum "prs" {
                   description "Clock traceable to primary reference source (option-2 only)";
                   junos:must "(\"chassis synchronization network-option option-2\")";
                   junos:must-message "Must configure 'chassis synchronization network-option option-2'";
                 }
                 enum "st2" {
                   description "Clock traceable to stratum 2 (option-2 only)";
                   junos:must "(\"chassis synchronization network-option option-2\")";
                   junos:must-message "Must configure 'chassis synchronization network-option option-2'";
                 }
                 enum "tnc" {
                   description "Clock traceable to transit node clock (option-2 only)";
                   junos:must "(\"chassis synchronization network-option option-2\")";
                   junos:must-message "Must configure 'chassis synchronization network-option option-2'";
                 }
                 enum "st3e" {
                   description "Clock traceable to stratum 3E (option-2 only)";
                   junos:must "(\"chassis synchronization network-option option-2\")";
                   junos:must-message "Must configure 'chassis synchronization network-option option-2'";
                 }
                 enum "st3" {
                   description "Clock traceable to stratum 3 (option-2 only)";
                   junos:must "(\"chassis synchronization network-option option-2\")";
                   junos:must-message "Must configure 'chassis synchronization network-option option-2'";
                 }
                 enum "st4" {
                   description "Clock traceable to stratum 4 free-run (option-2 only)";
                   junos:must "(\"chassis synchronization network-option option-2\")";
                   junos:must-message "Must configure 'chassis synchronization network-option option-2'";
                 }
                 enum "smc" {
                   description "Clock traceable to self-timed SONET (option-2 only)";
                   junos:must "(\"chassis synchronization network-option option-2\")";
                   junos:must-message "Must configure 'chassis synchronization network-option option-2'";
                 }
                 enum "stu" {
                   description "Clock traceable to unknown quality (option-2 only)";
                   junos:must "(\"chassis synchronization network-option option-2\")";
                   junos:must-message "Must configure 'chassis synchronization network-option option-2'";
                 }
               }
             }
           }
         }
       }
       container hold-interval {
         description "Hold interval";
         uses apply-advanced;
         leaf switchover {
           description "Switchover wait time after clock recovery";
           default "30";
           units "sec";
           type union {
             type string {
               pattern "<.*>|$.*";
             }
             type uint32 {
               range "30 .. 60";
             }
           }
         }
         leaf configuration-change {
           description "Clock select wait time after change in config";
           default "15";
           units "sec";
           type union {
             type string {
               pattern "<.*>|$.*";
             }
             type uint32 {
               range "15 .. 60";
             }
           }
         }
         leaf restart {
           description "Clock select wait time after reboot";
           default "120";
           units "sec";
           type union {
             type string {
               pattern "<.*>|$.*";
             }
             type uint32 {
               range "60 .. 180";
             }
           }
         }
       }
       leaf signal-type {
         description "Frequency for provided reference clocks";
         default "t1";
         type enumeration {
           enum "e1" {
             description "E1-coded 2048 Khz signal on 120 ohm balanced line";
           }
           enum "t1" {
             description "T1-coded 1.544 Mhz signal on 100 ohm balanced line";
           }
           enum "cc-8k" {
             description "Composite Clock 64kHz+8kHz";
           }
           enum "cc-8k-400" {
             description "Composite Clock 64kHz+8kHz+400Hz";
           }
           enum "6312k" {
             description "Japanese Standard 6312kHz";
           }
         }
       }
       leaf primary {
         description "Best choice synchronization reference source list";
         junos:cli-feature "oneliner-plus";
         junos:must "((!(\"chassis synchronization source\") || \"chassis synchronization esmc-transmit\"))";
         junos:must-message "source or esmc-transmit cannot be configured with primary";
         type enumeration {
           enum "external-a" {
             description "Use external-a as a primary source";
           }
           enum "external-b" {
             description "Use external-b as a primary source";
           }
           enum "bits-a" {
             description "Use bits-a as a primary source";
           }
           enum "bits-b" {
             description "Use bits-b as a primary source";
           }
           enum "gps-0" {
             description "Use gps-0 as a primary source";
             junos:must "(!(\"chassis synchronization secondary gps-0\"))";
             junos:must-message "not allowed when gps-0 is already configured";
           }
           enum "gps-1" {
             description "Use gps-1 as a primary source";
             junos:must "(!(\"chassis synchronization secondary gps-1\"))";
             junos:must-message "not allowed when gps-1 is already configured";
           }
           enum "fpc-0" {
             description "Use fpc-0 as a primary source";
             junos:must "((\"chassis fpc 0 pic 0 recovered-clock\" || \"chassis fpc 0 pic 1 recovered-clock\"))";
             junos:must-message "Must configure recovered-clock for this fpc";
           }
           enum "fpc-1" {
             description "Use fpc-1 as a primary source";
             junos:must "((\"chassis fpc 1 pic 0 recovered-clock\" || \"chassis fpc 1 pic 1 recovered-clock\"))";
             junos:must-message "Must configure recovered-clock for this fpc";
           }
           enum "fpc-2" {
             description "Use fpc-2 as a primary source";
             junos:must "((\"chassis fpc 2 pic 0 recovered-clock\" || \"chassis fpc 2 pic 1 recovered-clock\"))";
             junos:must-message "Must configure recovered-clock for this fpc";
           }
           enum "fpc-3" {
             description "Use fpc-3 as a primary source";
             junos:must "((\"chassis fpc 3 pic 0 recovered-clock\" || \"chassis fpc 3 pic 1 recovered-clock\"))";
             junos:must-message "Must configure recovered-clock for this fpc";
           }
           enum "fpc-4" {
             description "Use fpc-4 as a primary source";
             junos:must "((\"chassis fpc 4 pic 0 recovered-clock\" || \"chassis fpc 4 pic 1 recovered-clock\"))";
             junos:must-message "Must configure recovered-clock for this fpc";
           }
           enum "fpc-5" {
             description "Use fpc-5 as a primary source";
             junos:must "((\"chassis fpc 5 pic 0 recovered-clock\" || \"chassis fpc 5 pic 1 recovered-clock\"))";
             junos:must-message "Must configure recovered-clock for this fpc";
           }
           enum "fpc-6" {
             description "Use fpc-6 as a primary source";
             junos:must "((\"chassis fpc 6 pic 0 recovered-clock\" || \"chassis fpc 6 pic 1 recovered-clock\"))";
             junos:must-message "Must configure recovered-clock for this fpc";
           }
           enum "fpc-7" {
             description "Use fpc-7 as a primary source";
             junos:must "((\"chassis fpc 7 pic 0 recovered-clock\" || \"chassis fpc 7 pic 1 recovered-clock\"))";
             junos:must-message "Must configure recovered-clock for this fpc";
           }
           enum "fpc-8" {
             description "Use fpc-8 as a primary source";
             junos:must "((\"chassis fpc 8 pic 0 recovered-clock\" || \"chassis fpc 8 pic 1 recovered-clock\"))";
             junos:must-message "Must configure recovered-clock for this fpc";
           }
           enum "fpc-9" {
             description "Use fpc-9 as a primary source";
             junos:must "((\"chassis fpc 9 pic 0 recovered-clock\" || \"chassis fpc 9 pic 1 recovered-clock\"))";
             junos:must-message "Must configure recovered-clock for this fpc";
           }
           enum "fpc-10" {
             description "Use fpc-10 as a primary source";
             junos:must "((\"chassis fpc 10 pic 0 recovered-clock\" || \"chassis fpc 10 pic 1 recovered-clock\"))";
             junos:must-message "Must configure recovered-clock for this fpc";
           }
           enum "fpc-11" {
             description "Use fpc-11 as a primary source";
             junos:must "((\"chassis fpc 11 pic 0 recovered-clock\" || \"chassis fpc 11 pic 1 recovered-clock\"))";
             junos:must-message "Must configure recovered-clock for this fpc";
           }
           enum "fpc-12" {
             description "Use fpc-12 as a primary source";
             junos:must "((\"chassis fpc 12 pic 0 recovered-clock\" || \"chassis fpc 12 pic 1 recovered-clock\"))";
             junos:must-message "Must configure recovered-clock for this fpc";
           }
           enum "fpc-13" {
             description "Use fpc-13 as a primary source";
             junos:must "((\"chassis fpc 13 pic 0 recovered-clock\" || \"chassis fpc 13 pic 1 recovered-clock\"))";
             junos:must-message "Must configure recovered-clock for this fpc";
           }
           enum "fpc-14" {
             description "Use fpc-14 as a primary source";
             junos:must "((\"chassis fpc 14 pic 0 recovered-clock\" || \"chassis fpc 14 pic 1 recovered-clock\"))";
             junos:must-message "Must configure recovered-clock for this fpc";
           }
           enum "fpc-15" {
             description "Use fpc-15 as a primary source";
             junos:must "((\"chassis fpc 15 pic 0 recovered-clock\" || \"chassis fpc 15 pic 1 recovered-clock\"))";
             junos:must-message "Must configure recovered-clock for this fpc";
           }
         }
       }
       leaf secondary {
         description "Alternative choice synchronization reference source list";
         junos:cli-feature "oneliner-plus";
         junos:must "((!(\"chassis synchronization source\") || \"chassis synchronization esmc-transmit\"))";
         junos:must-message "source or esmc-transmit cannot be configured with secondary";
         type enumeration {
           enum "external-a" {
             description "Use external-a as a secondary source";
             junos:must "(!(\"chassis synchronization primary external-a\"))";
             junos:must-message "external-a can be either primary or secondary";
           }
           enum "external-b" {
             description "Use external-b as a secondary source";
             junos:must "(!(\"chassis synchronization primary external-b\"))";
             junos:must-message "external-b can be either primary or secondary";
           }
           enum "bits-a" {
             description "Use bits-a as a secondary source";
             junos:must "(!(\"chassis synchronization primary bits-a\"))";
             junos:must-message "bits-a can be either primary or secondary";
           }
           enum "bits-b" {
             description "Use bits-b as a secondary source";
             junos:must "(!(\"chassis synchronization primary bits-b\"))";
             junos:must-message "bits-b can be either primary or secondary";
           }
           enum "gps-0" {
             description "Use gps-0 as a secondary source";
             junos:must "(!(\"chassis synchronization primary gps-0\"))";
             junos:must-message "gps-0 can be either primary or secondary";
           }
           enum "gps-1" {
             description "Use gps-1 as a secondary source";
             junos:must "(!(\"chassis synchronization primary gps-1\"))";
             junos:must-message "gps-1 can be either primary or secondary";
           }
           enum "fpc-0" {
             description "Use fpc-0 as a secondary source";
             junos:must "((\"chassis fpc 0 pic 0 recovered-clock\" || \"chassis fpc 0 pic 1 recovered-clock\"))";
             junos:must-message "Must configure recovered-clock for this fpc";
             junos:must "(!(\"chassis synchronization primary fpc-0\"))";
             junos:must-message "fpc-0 can be either primary or secondary";
           }
           enum "fpc-1" {
             description "Use fpc-1 as a secondary source";
             junos:must "((\"chassis fpc 1 pic 0 recovered-clock\" || \"chassis fpc 1 pic 1 recovered-clock\"))";
             junos:must-message "Must configure recovered-clock for this fpc";
             junos:must "(!(\"chassis synchronization primary fpc-1\"))";
             junos:must-message "fpc-1 can be either primary or secondary";
           }
           enum "fpc-2" {
             description "Use fpc-2 as a secondary source";
             junos:must "((\"chassis fpc 2 pic 0 recovered-clock\" || \"chassis fpc 2 pic 1 recovered-clock\"))";
             junos:must-message "Must configure recovered-clock for this fpc";
             junos:must "(!(\"chassis synchronization primary fpc-2\"))";
             junos:must-message "fpc-2 can be either primary or secondary";
           }
           enum "fpc-3" {
             description "Use fpc-3 as a secondary source";
             junos:must "((\"chassis fpc 3 pic 0 recovered-clock\" || \"chassis fpc 3 pic 1 recovered-clock\"))";
             junos:must-message "Must configure recovered-clock for this fpc";
             junos:must "(!(\"chassis synchronization primary fpc-3\"))";
             junos:must-message "fpc-3 can be either primary or secondary";
           }
           enum "fpc-4" {
             description "Use fpc-4 as a secondary source";
             junos:must "((\"chassis fpc 4 pic 0 recovered-clock\" || \"chassis fpc 4 pic 1 recovered-clock\"))";
             junos:must-message "Must configure recovered-clock for this fpc";
             junos:must "(!(\"chassis synchronization primary fpc-4\"))";
             junos:must-message "fpc-4 can be either primary or secondary";
           }
           enum "fpc-5" {
             description "Use fpc-5 as a secondary source";
             junos:must "((\"chassis fpc 5 pic 0 recovered-clock\" || \"chassis fpc 5 pic 1 recovered-clock\"))";
             junos:must-message "Must configure recovered-clock for this fpc";
             junos:must "(!(\"chassis synchronization primary fpc-5\"))";
             junos:must-message "fpc-5 can be either primary or secondary";
           }
           enum "fpc-6" {
             description "Use fpc-6 as a secondary source";
             junos:must "((\"chassis fpc 6 pic 0 recovered-clock\" || \"chassis fpc 6 pic 1 recovered-clock\"))";
             junos:must-message "Must configure recovered-clock for this fpc";
             junos:must "(!(\"chassis synchronization primary fpc-6\"))";
             junos:must-message "fpc-6 can be either primary or secondary";
           }
           enum "fpc-7" {
             description "Use fpc-7 as a secondary source";
             junos:must "((\"chassis fpc 7 pic 0 recovered-clock\" || \"chassis fpc 7 pic 1 recovered-clock\"))";
             junos:must-message "Must configure recovered-clock for this fpc";
             junos:must "(!(\"chassis synchronization primary fpc-7\"))";
             junos:must-message "fpc-7 can be either primary or secondary";
           }
           enum "fpc-8" {
             description "Use fpc-8 as a secondary source";
             junos:must "((\"chassis fpc 8 pic 0 recovered-clock\" || \"chassis fpc 8 pic 1 recovered-clock\"))";
             junos:must-message "Must configure recovered-clock for this fpc";
             junos:must "(!(\"chassis synchronization primary fpc-8\"))";
             junos:must-message "fpc-8 can be either primary or secondary";
           }
           enum "fpc-9" {
             description "Use fpc-9 as a secondary source";
             junos:must "((\"chassis fpc 9 pic 0 recovered-clock\" || \"chassis fpc 9 pic 1 recovered-clock\"))";
             junos:must-message "Must configure recovered-clock for this fpc";
             junos:must "(!(\"chassis synchronization primary fpc-9\"))";
             junos:must-message "fpc-9 can be either primary or secondary";
           }
           enum "fpc-10" {
             description "Use fpc-10 as a secondary source";
             junos:must "((\"chassis fpc 10 pic 0 recovered-clock\" || \"chassis fpc 10 pic 1 recovered-clock\"))";
             junos:must-message "Must configure recovered-clock for this fpc";
             junos:must "(!(\"chassis synchronization primary fpc-10\"))";
             junos:must-message "fpc-10 can be either primary or secondary";
           }
           enum "fpc-11" {
             description "Use fpc-11 as a secondary source";
             junos:must "((\"chassis fpc 11 pic 0 recovered-clock\" || \"chassis fpc 11 pic 1 recovered-clock\"))";
             junos:must-message "Must configure recovered-clock for this fpc";
             junos:must "(!(\"chassis synchronization primary fpc-11\"))";
             junos:must-message "fpc-11 can be either primary or secondary";
           }
           enum "fpc-12" {
             description "Use fpc-12 as a secondary source";
             junos:must "((\"chassis fpc 12 pic 0 recovered-clock\" || \"chassis fpc 12 pic 1 recovered-clock\"))";
             junos:must-message "Must configure recovered-clock for this fpc";
             junos:must "(!(\"chassis synchronization primary fpc-12\"))";
             junos:must-message "fpc-12 can be either primary or secondary";
           }
           enum "fpc-13" {
             description "Use fpc-13 as a secondary source";
             junos:must "((\"chassis fpc 13 pic 0 recovered-clock\" || \"chassis fpc 13 pic 1 recovered-clock\"))";
             junos:must-message "Must configure recovered-clock for this fpc";
             junos:must "(!(\"chassis synchronization primary fpc-13\"))";
             junos:must-message "fpc-13 can be either primary or secondary";
           }
           enum "fpc-14" {
             description "Use fpc-14 as a secondary source";
             junos:must "((\"chassis fpc 14 pic 0 recovered-clock\" || \"chassis fpc 14 pic 1 recovered-clock\"))";
             junos:must-message "Must configure recovered-clock for this fpc";
             junos:must "(!(\"chassis synchronization primary fpc-14\"))";
             junos:must-message "fpc-14 can be either primary or secondary";
           }
           enum "fpc-15" {
             description "Use fpc-15 as a secondary source";
             junos:must "((\"chassis fpc 15 pic 0 recovered-clock\" || \"chassis fpc 15 pic 1 recovered-clock\"))";
             junos:must-message "Must configure recovered-clock for this fpc";
             junos:must "(!(\"chassis synchronization primary fpc-15\"))";
             junos:must-message "fpc-15 can be either primary or secondary";
           }
         }
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               junos:must "(!(\".. unicast-in-lpm\"))";
               junos:must-message "Cannot set both unicast-in-lpm and prefix-65-127-disable at the same time";
               type empty;
             }
             leaf unicast-in-lpm {
               description "Install unicast host entries in LPM table";
               type empty;
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_8 {
           container vxlan-gbp-l2-profile {
             presence "enable vxlan-gbp-l2-profile";
             description "MAC: 64K L3-host: 32K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_9 {
           container vxlan-gbp-l3-profile {
             presence "enable vxlan-gbp-l3-profile";
             description "MAC: 32K L3-host: 64K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_10 {
           container vxlan-gbp-mc-profile {
             presence "enable vxlan-gbp-mc-profile";
             description "MAC: 32K L3-host: 64K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_11 {
           container em-hw-profile {
             presence "enable em-hw-profile";
             description "MAC: 48K L3-host: 48K LPM: 16K EM:32K, needs reboot for VC; restarts PFE if standalone";
           }
         }
         case case_12 {
           container gbp-pure-l2-profile {
             presence "enable gbp-pure-l2-profile";
             description "MAC: 48K L3-host: 48K LPM: 16K EM:16K, needs reboot for VC; restarts PFE if standalone";
           }
         }
         case case_13 {
           container default-profile {
             presence "enable default-profile";
             description "MAC: 64K L3-host: 32K LPM: 24K IFP: 12K, needs reboot for VC; restarts PFE if standalone";
           }
         }
         case case_14 {
           container ifp-profile {
             presence "enable ifp-profile";
             description "MAC: 64K L3-host: 32K LPM: 12K IFP: 18K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_15 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 junos:must "(!(\".. unicast-in-lpm\"))";
                 junos:must-message "Cannot set both unicast-in-lpm and prefix-65-127-disable at the same time";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     leaf loopback-firewallv6-optimization {
       description "Increase ACL scale for loopback IPv6 filters; restarts PFE";
       junos:must "(\"chassis loopback-firewall-optimization\")";
       junos:must-message "Enable loopback-firewall-optimization";
       type empty;
     }
     leaf ipv6linklocal-sourcechecking {
       description "Enable ipv6 linklocal source checking. This will restart PFE";
       type empty;
     }
     leaf input-firewall-optimized-profile {
       description "Optimal default filter usage when IFA/FCoe/FIPsnooping is not used; restarts PFE";
       type empty;
     }
     leaf ivacl-firewall-no-portrange-profile {
       description "L4 Src/Dst Port range optimize is not needed; restarts PFE";
       junos:must "(!(\"chassis ipvacl-firewall-l2-profile\"))";
       junos:must-message "Cannot configure ivacl-firewall-no-portrange-profile when ipvacl-firewall-l2-profile is enabled";
       type empty;
     }
     leaf iracl-firewall-ipv4-profile {
       description "IPv6 address match is not needed for IRACL filters; restarts PFE";
       type empty;
     }
     leaf ipvacl-firewall-l2-profile {
       description "Only Src/Dst MAC,VLAN,EtherType match is needed for IPACL/IVACL filters; restarts PFE";
       junos:must "(!(\"chassis ivacl-firewall-no-portrange-profile\"))";
       junos:must-message "Cannot configure ipvacl-firewall-l2-profile when ivacl-firewall-no-portrange-profile is enabled";
       type empty;
     }
     leaf loopback-firewall-optimization {
       description "Optimal TCAM use,reboot(VC);restarts PFE(IP rsrved mcast dest&ttl=0/1,config explicitly)";
       type empty;
     }
     leaf loopback-firewall-per-vrf {
       description "Enable per vrf control, needs reboot for VC; restarts PFE if standalone";
       type empty;
     }
     leaf epacl-firewall-optimization {
       description "Maximizes Egress Port ACLs TCAM use and restarts PFE";
       type empty;
     }
     leaf per-logical-interface-firewall {
       description "Ingress port firewall can be supported per logical interface, restarts PFE";
       type empty;
     }
     leaf fru-poweron-sequence {
       description "FRUs power on sequence like 0 1 2 3 ... within double quotes";
       type string {
         junos:posix-pattern "^[0-9 ]+$";
         junos:pattern-message "FRU in fru poweron sequence must be a number";
       }
     }
     leaf fpc-empolicy-profile {
       description "FPC EM Policy Profile";
       type enumeration {
         enum "low-power-mode" {
           description "Set low power mode";
         }
       }
     }
     container em-policy {
       presence "enable em-policy";
       description "EM Policy Configuration";
       uses apply-advanced;
       leaf fire-fru-shutdown {
         description "Enable/Disable fire fru shutdown";
         type enumeration {
           enum "Enable" {
             description "Enable Fire Fru Shutdown";
           }
           enum "Disable" {
             description "Disable Fire Fru Shutdown";
           }
         }
       }
     }
     container psm {
       description "Power supply module";
       uses apply-advanced;
       container redundancy {
         description "PSM Source/Feed Redundancy configuration";
         uses apply-advanced;
         leaf source-redundancy {
           description "Toggle source redundancy for PSM";
           junos:must "(!(\"chassis psm redundancy feed-redundancy\"))";
           junos:must-message "'source-redundancy' and 'feed-redundancy' both can not be configured together";
           type empty;
         }
         container feed-redundancy {
           description "Toggle feed redundancy for a PSM slot";
           uses apply-advanced;
           list slot {
             key name;
             description "PSM slot number";
             leaf name {
               description "Select PSM slot";
               junos:cli-feature "nokeyword";
               junos:must "(!(\"chassis psm redundancy source-redundancy\"))";
               junos:must-message "'source-redundancy' and 'feed-redundancy' both can not be configured together";
               type union {
                 type string {
                   pattern "<.*>|$.*";
                 }
                 type uint32;
               }
             }
             uses apply-advanced;
           }
         }
       }
     }
     leaf auto-image-upgrade {
       description "Auto image upgrade using DHCP";
       type empty;
     }
     container error {
       description "Error level configuration for all FPC";
       uses chassis_junos_fru_error_type;
     }
     container oss-map {
       description "Translate Operation Supported System's requirements";
       uses apply-advanced;
       leaf model-name {
         description "Override chassis model name for specific show/snmp output";
         type enumeration {
           enum "t640" {
             description "Set to T640's model";
           }
           enum "t1600" {
             description "Set to T1600's model";
           }
         }
       }
     }
     container jnu-management {
       description "JNU Management configuration";
       uses apply-advanced;
       leaf mode {
         description "JNU Mode";
         type enumeration {
           enum "feature-rich" {
             description "Feature Rich Mode";
           }
           enum "bng-control-plane" {
             description "BNG control-plane mode";
           }
         }
       }
       leaf satellite-name {
         description "Satellite name";
         type string;
       }
       leaf device-group {
         description "Satellite device group";
         type string;
       }
       list device-group-map {
         key name;
         ordered-by user;
         description "Common groups mapping to device groups";
         leaf name {
           description "Satellite Device Group";
           junos:cli-feature "nokeyword";
           type string;
         }
         uses apply-advanced;
         leaf-list include-groups {
           ordered-by user;
           description "Common groups list";
           type string;
         }
       }
       list satellite {
         key name;
         ordered-by user;
         description "List of satellites";
         leaf name {
           description "Satellite name";
           junos:cli-feature "nokeyword";
           type string;
         }
         uses apply-advanced;
         leaf device-group {
           description "Satellite Device Group";
           type string;
         }
         leaf model {
           description "Satellite model";
           type string;
         }
         leaf version {
           description "Satellite version";
           type string {
             junos:posix-pattern "^[[:digit:]][[:alnum:]_.-]+$";
             junos:pattern-message "Version should begin with a number";
           }
         }
       }
       leaf user {
         description "Satellite User Name";
         type string;
       }
       leaf-list controller {
         ordered-by user;
         description "Controller Name";
         type string;
       }
       leaf other-controller {
         description "Dual controller Name";
         type string;
       }
       leaf authentication {
         description "Authentication string";
         type jt:unreadable;
       }
     }
     list satellite {
       key name;
       ordered-by user;
       description "List of available satellite configurations";
       leaf name {
         description "Satellite name";
         junos:cli-feature "nokeyword";
         type string;
       }
       uses apply-advanced;
     }
     leaf auto-satellite-conversion {
       description "Enable remote conversion to satellite device-mode";
       type empty;
     }
     container satellite-management {
       presence "enable satellite-management";
       junos:must "(!(\"chassis aggregated-devices disable-lag-enhanced\"))";
       junos:must-message "To configure chassis satellite-management, chassis aggregated-devices disable-lag-enhanced must not be set";
       description "Satellite management configuration";
       uses apply-advanced;
       container designated-event-forwarding {
         presence "enable designated-event-forwarding";
         description "Designated event forwarding";
       }
       container traceoptions {
         description "Global satelite discovery and provisioning trace options";
         uses apply-advanced;
         leaf no-remote-trace {
           description "Disable remote tracing";
           junos:must "(\"system tracing\")";
           junos:must-message "'no-remote-trace' is valid only when [system tracing] is configured";
           type empty;
         }
         container file {
           junos:cli-feature "oneliner";
           description "Trace file information";
           leaf filename {
             description "Name of file in which to write trace information";
             junos:cli-feature "nokeyword";
             type string {
               length "1 .. 1024";
               junos:posix-pattern "![/ %]";
               junos:pattern-message "Must not contain \'/\', % or a space";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           junos:cli-feature "oneliner";
           description "Tracing parameters";
           leaf name {
             junos:cli-feature "nokeyword";
             type enumeration {
               enum "parse" {
                 description "Trace configuration parsing";
               }
               enum "config-internal" {
                 description "Trace configuration internals";
               }
               enum "normal" {
                 description "Trace normal events";
               }
               enum "general" {
                 description "Trace general events";
               }
               enum "state" {
                 description "Trace state transitions";
               }
               enum "task" {
                 description "Trace SDPD task processing";
               }
               enum "timer" {
                 description "Trace SDPD task timer processing";
               }
               enum "krt" {
                 description "Trace communication over routing socket";
               }
               enum "lldp" {
                 description "Trace LLDP events";
               }
               enum "provision" {
                 description "Trace provisioning events";
               }
               enum "extended-port" {
                 description "Trace extended-port events";
               }
               enum "multi-chassis" {
                 description "Trace multi-chassis events";
               }
               enum "upgrade-group" {
                 description "Trace sw-update events";
               }
               enum "device" {
                 description "Trace device FSM events";
               }
               enum "tcp" {
                 description "Trace TCP events";
               }
               enum "interface" {
                 description "Trace interface events";
               }
               enum "cluster" {
                 description "Trace cluster events";
               }
               enum "all" {
                 description "Trace everything";
               }
             }
           }
           leaf disable {
             description "Disable this trace flag";
             type empty;
           }
         }
       }
       leaf cluster-policy {
         description "Cluster policy";
         junos:must "(\"policy-options satellite-policies candidate-uplink-port-policy $$\")";
         junos:must-message "Satellite cluster-policy not defined";
         type string;
       }
       list cluster {
         key name;
         description "Configure a satellite device cluster";
         leaf name {
           description "Satellite cluster name";
           junos:cli-feature "nokeyword";
           type string {
             length "1 .. 16";
           }
         }
         uses apply-advanced;
         leaf cluster-id {
           description "Satellite cluster identifier";
           junos:must "(unique \"chassis satellite-management cluster <*> cluster-id $$\")";
           junos:must-message "Cluster-id has to be unique among all provisioned clusters";
           type union {
             type string {
               pattern "<.*>|$.*";
             }
             type uint32 {
               range "1 .. 32";
             }
           }
         }
         leaf-list cascade-ports {
           description "Cascade ports";
           type union {
             type jt:interface-device;
             type string {
               pattern "<.*>|$.*";
             }
           }
         }
         leaf cluster-policy {
           description "Candidate uplink policy";
           junos:must "(\"policy-options satellite-policies candidate-uplink-port-policy $$\")";
           junos:must-message "Satellite cluster-policy not defined";
           type string;
         }
         list fpc {
           key name;
           leaf name {
             description "Satellite slot identifier";
             junos:cli-feature "nokeyword";
             type union {
               type string {
                 pattern "<.*>|$.*";
               }
               type uint32 {
                 range "65 .. 254";
               }
             }
           }
           uses apply-advanced;
           leaf alias {
             description "Satellite alias";
             junos:must "(unique \"chassis satellite-management cluster <*> fpc <*> alias $$\")";
             junos:must-message "alias has to be unique among all provisioned satellite-devices";
             junos:must "(unique \"chassis satellite-management fpc <*> alias $$\")";
             junos:must-message "alias has to be unique among all provisioned satellite-devices";
             type string {
               length "1 .. 16";
             }
           }
           leaf description {
             description "Satellite description";
             type string {
               length "1 .. 64";
             }
           }
           leaf member-id {
             description "Satellite member id";
             junos:must "(unique \".. .. fpc <*> member-id $$\")";
             junos:must-message "Member-id has to be unique among all members in a cluster";
             type union {
               type string {
                 pattern "<.*>|$.*";
               }
               type uint32 {
                 range "0 .. 62";
               }
             }
           }
           leaf system-id {
             description "Satellite system id";
             junos:must "(unique \"chassis satellite-management cluster <*> fpc <*> system-id $$\")";
             junos:must-message "System-id has to be unique among all provisioned satellite-devices";
             junos:must "(unique \"chassis satellite-management fpc <*> system-id $$\")";
             junos:must-message "System-id has to be unique among all provisioned satellite-devices";
             type jt:mac-addr;
           }
           leaf cluster-policy {
             description "Candidate uplink policy";
             junos:must "(\"policy-options satellite-policies candidate-uplink-port-policy $$\")";
             junos:must-message "Satellite Cluster policy not defined";
             type string;
           }
         }
       }
       list fpc {
         key name;
         description "FPC identifier for a satellite device";
         leaf name {
           description "Satellite slot identifier";
           junos:cli-feature "nokeyword";
           type union {
             type string {
               pattern "<.*>|$.*";
             }
             type uint32 {
               range "65 .. 254";
             }
           }
         }
         uses apply-advanced;
         leaf serial-number {
           description "Satellite serial number";
           junos:must "(unique \"chassis satellite-management fpc <*> serial-number $$\")";
           junos:must-message "serial-number has to be unique among all provisioned satellite-devices";
           type string {
             length "1 .. 16";
           }
         }
         leaf system-id {
           description "Satellite system id";
           junos:must "(unique \"chassis satellite-management fpc <*> system-id $$\")";
           junos:must-message "System-id has to be unique among all provisioned satellite-devices";
           type jt:mac-addr;
         }
         leaf target-mode {
           description "Enable target mode forwarding for extended-ports";
           type empty;
         }
         leaf alias {
           description "Satellite alias";
           junos:must "(unique \"chassis satellite-management fpc <*> alias $$\")";
           junos:must-message "alias has to be unique among all provisioned satellite-devices";
           type string {
             length "1 .. 16";
           }
         }
         leaf description {
           description "Satellite description";
           type string {
             length "1 .. 64";
           }
         }
         container management-address {
           presence "enable management-address";
           description "Satellite Management Interface IP";
           uses apply-advanced;
           leaf address {
             description "Satellite Management Interface IP address";
             junos:must "(unique \"chassis satellite-management fpc <*> management-address address $$\")";
             junos:must-message "management interface IP address has to be unique among all provisioned satellite-devices";
             type jt:ipv4prefix;
           }
           leaf gateway {
             description "Satellite Management Interface Gateway IP address";
             type jt:ipv4addr;
           }
         }
         leaf-list cascade-ports {
           description "Cascade ports";
           type union {
             type jt:interface-device;
             type string {
               pattern "<.*>|$.*";
             }
           }
         }
         leaf extended-ports-template {
           description "Extended ports template";
           junos:must "(\"policy-options satellite-policies extended-ports-template $$\")";
           junos:must-message "Extended ports template not defined";
           type string;
         }
         choice ufd_type {
           case case_1 {
             container uplink-failure-detection {
               presence "enable uplink-failure-detection";
               description "Enable uplink-failure-detection";
               uses apply-advanced;
               leaf candidate-uplink-policy {
                 description "Candidate uplink policy";
                 junos:must "(\"policy-options satellite-policies candidate-uplink-port-policy $$\")";
                 junos:must-message "Candidate-uplink-port-policy not defined";
                 type string;
               }
             }
           }
         }
         leaf environment-monitoring-policy {
           description "Environment monitoring policy";
           junos:must "(\"policy-options satellite-policies environment-monitoring-policy $$\")";
           junos:must-message "Environment monitoring policy not defined";
           type string;
         }
         choice forwarding-policy-type {
           case case_1 {
             container forwarding-policy {
               presence "enable forwarding-policy";
               description "Enable a forwarding policy";
               uses apply-advanced;
               leaf forwarding-policy-alias {
                 description "Define forwarding policy alias";
                 junos:cli-feature "nokeyword";
                 junos:must "(\"policy-options satellite-policies forwarding-policy $$\")";
                 junos:must-message "forwarding-policy not defined";
                 type string;
               }
             }
           }
         }
       }
       leaf extended-ports-policy {
         description "Extended ports policy";
         junos:must "(\"policy-options satellite-policies extended-ports-policy $$\")";
         junos:must-message "Extended ports policy not defined";
         type string;
       }
       choice ufd_type {
         case case_1 {
           container uplink-failure-detection {
             presence "enable uplink-failure-detection";
             description "Enable uplink-failure-detection";
             uses apply-advanced;
             leaf candidate-uplink-policy {
               description "Candidate uplink policy";
               junos:must "(\"policy-options satellite-policies candidate-uplink-port-policy $$\")";
               junos:must-message "Candidate-uplink-port-policy not defined";
               type string;
             }
           }
         }
       }
       container psu {
         description "Power Supply Unit redundancy configuration";
         uses apply-advanced;
         container redundancy {
           description "PSU Redundancy settings";
           uses apply-advanced;
           leaf n-plus-n {
             description "PSU redundancy: N+N configuration";
             type empty;
           }
         }
       }
       container environment-monitoring-policy {
         presence "enable environment-monitoring-policy";
         description "Environment monitoring policy";
         uses apply-advanced;
         leaf policy-name {
           description "Default environment monitoring policy";
           junos:must "(\"policy-options satellite-policies environment-monitoring-policy $$\")";
           junos:must-message "Environment monitoring policy not defined";
           type string;
         }
       }
       choice forwarding-policy-type {
         case case_1 {
           container forwarding-policy {
             presence "enable forwarding-policy";
             description "Enable a forwarding policy";
             uses apply-advanced;
             leaf forwarding-policy-alias {
               description "Define forwarding policy alias";
               junos:cli-feature "nokeyword";
               junos:must "(\"policy-options satellite-policies forwarding-policy $$\")";
               junos:must-message "forwarding-policy not defined";
               type string;
             }
           }
         }
       }
       container redundancy-groups {
         description "Redundancy groups configuration";
         uses apply-advanced;
         leaf chassis-id {
           description "Chassis identifier";
           type union {
             type string {
               pattern "<.*>|$.*";
             }
             type uint32 {
               range "1 .. 4";
             }
           }
         }
         list rg-group {
           key name;
           ordered-by user;
           description "Redundancy groups";
           uses redundancy-group-type;
           junos:cli-feature "nokeyword";
           junos:cli-feature "homogeneous";
         }
       }
       container upgrade-groups {
         description "Upgrade group configuration";
         uses apply-advanced;
         list upgrade-group {
           key name;
           description "Upgrade group";
           uses upgrade-group-type;
           junos:cli-feature "nokeyword";
           junos:cli-feature "homogeneous";
         }
       }
       container auto-satellite-conversion {
         description "Enable automatic satellite conversion";
         uses apply-advanced;
         leaf-list satellite {
           ordered-by user;
           description "Satellite slot-id or range or all";
           type string {
             length "1 .. 100";
           }
         }
       }
       container single-home {
         description "Devices are connected to local aggregation device only";
         uses apply-advanced;
         leaf-list satellite {
           ordered-by user;
           description "Satellite slot-id or range or all";
           type string {
             length "1 .. 100";
           }
         }
       }
       leaf aging-timer {
         description "Aging-timer";
         units "minutes";
         type union {
           type string {
             pattern "<.*>|$.*";
           }
           type uint32 {
             range "2 .. 60000";
           }
         }
       }
       leaf block-console-access {
         description "Block console access";
         type empty;
       }
       container firewall {
         description "Define a firewall configuration";
         uses apply-advanced;
         container family {
           junos:cli-feature "homogeneous";
           description "Protocol family";
           container bridge {
             description "Protocol family BRIDGE for firewall filter";
             uses apply-advanced;
             list filter {
               key name;
               ordered-by user;
               uses satellite-bridge-filter;
             }
           }
           container ethernet-switching {
             description "Protocol family Ethernet Switching for firewall filter";
             uses apply-advanced;
             list filter {
               key name;
               ordered-by user;
               description "Define an Ethernet Switching firewall filter";
               uses satellite-bridge-filter;
             }
           }
         }
       }
     }
     container periodic {
       description "Chassisd periodic options";
       uses apply-advanced;
       leaf ch-power-check-interval {
         description "Chassis power check interval, 0=default";
         default "0";
         units "seconds";
         type union {
           type string {
             pattern "<.*>|$.*";
           }
           type uint32 {
             range "0 .. 60";
           }
         }
       }
       leaf re-check-interval {
         description "Chassis RE check interval, 0=default";
         default "0";
         units "seconds";
         type union {
           type string {
             pattern "<.*>|$.*";
           }
           type uint32 {
             range "0 .. 60";
           }
         }
       }
     }
     container thermal-health-check {
       presence "enable thermal-health-check";
       description "Enable Thermal Health check of the chassis";
       uses apply-advanced;
       container fet-failure-check {
         presence "enable fet-failure-check";
         uses apply-advanced;
         leaf action-onfail {
           description "Set the action when Oring FET detected";
           default "none";
           type enumeration {
             enum "none" {
               description "No action when Oring FET detected";
             }
             enum "auto-shutdown" {
               description "Shutdown when Oring FET detected";
             }
           }
         }
       }
     }
     container mode {
       description "Set FRU mode";
       uses apply-advanced;
       container standalone {
         presence "enable standalone";
         description "Bringup FRU in standalone mode1";
         uses apply-advanced;
         list fpc {
           key name;
           leaf name {
             description "FPC slot number";
             junos:cli-feature "nokeyword";
             type string {
               length "1 .. 4";
             }
           }
           uses apply-advanced;
           container loopback {
             description "Loopback Configuration for Mode & Type";
             uses apply-advanced;
             leaf wan {
               default "serdes";
               type enumeration {
                 enum "serdes" {
                   description "Serdes type loopback";
                 }
                 enum "retimer" {
                   description "Retimer type loopback";
                 }
               }
             }
             leaf fabric {
               default "serdes";
               type enumeration {
                 enum "serdes" {
                   description "Serdes type loopback";
                 }
                 enum "retimer" {
                   description "Retimer type loopback";
                 }
               }
             }
           }
         }
         list fabric-card {
           key name;
           ordered-by user;
           description "Fabric Card Loopback setting";
           uses chassis_fabric_card_type;
         }
       }
       choice power-mode {
         case case_1 {
           leaf power-optimized {
             description "Set power mode to power-optimized";
             type empty;
           }
         }
       }
     }
     leaf local-station-mac {
       description "Local station mac address configuration";
       type jt:mac-unicast;
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       junos:cli-feature "nokeyword";
       type string;
     }
     list data {
       key name;
       uses macro-data-type;
       junos:cli-feature "nokeyword";
       junos:cli-feature "homogeneous";
       junos:cli-feature "oneliner";
     }
   }
   grouping chassis-pw-type {
     uses apply-advanced;
     leaf device-count {
       description "Number of pseudo-wire ps devices";
       type union {
         type string {
           pattern "<.*>|$.*";
         }
         type uint32 {
           range "1 .. 18000";
         }
       }
     }
   }
   grouping chassis_agg_dev_type {
     uses apply-advanced;
     leaf ae-20 {
       description "Run AE over Container nexthops Infrastructure";
       status deprecated;
       type empty;
     }
     container ethernet {
       description "Aggregated device options for Ethernet";
       uses chassisd_agg_enet_type;
     }
     container sonet {
       description "Aggregated device options for SONET";
       uses chassisd_agg_pos_type;
     }
     leaf maximum-links {
       description "Maximum links limit for aggregated devices";
       type union {
         type int32;
         type string {
           pattern "<.*>|$.*";
         }
       }
     }
   }
   grouping chassis_alarm_port_op_type {
     uses apply-advanced;
     container input {
       description "Input alarm port";
       uses apply-advanced;
       list port {
         key name;
         ordered-by user;
         description "Input Port";
         leaf name {
           description "Alarm port ID";
           junos:cli-feature "nokeyword";
           type union {
             type string {
               pattern "<.*>|$.*";
             }
             type uint32 {
               range "1 .. 3";
             }
           }
         }
         uses apply-advanced;
         leaf active {
           description "Active signal of alarm IO input port";
           type enumeration {
             enum "low" {
               description "Active signal of alarm IO port to low(default)";
             }
             enum "high" {
               description "Active signal of alarm IO port to high";
             }
           }
         }
         leaf admin-state {
           description "Administrative state of alarm IO input port";
           type enumeration {
             enum "disabled" {
               description "Administrative state of alarm IO port to disable(default)";
             }
             enum "enabled" {
               description "Administrative state of alarm IO port to enabled";
             }
           }
         }
         container description {
           junos:cli-feature "oneliner-plus";
           description "Alarm description of alarm IO input port";
           uses apply-advanced;
           leaf descr {
             description "Description to be used for alarm IO output port";
             junos:cli-feature "nokeyword";
             type string;
           }
         }
         leaf severity {
           description "Set alarm severity of alarm IO input port";
           type enumeration {
             enum "critical" {
               description "Alarm severity of alarm IO input port to ciritical(default)";
             }
             enum "major" {
               description "Alarm severity of alarm IO input port to major";
             }
             enum "minor" {
               description "Alarm severity of alarm IO input port to minor";
             }
             enum "warning" {
               description "Alarm severity of alarm IO input port to warning";
             }
           }
         }
       }
     }
     container output {
       description "Output alarm port";
       uses apply-advanced;
       list port {
         key name;
         ordered-by user;
         description "Output port";
         leaf name {
           description "Alarm IO output port ID";
           junos:cli-feature "nokeyword";
           type union {
             type string {
               pattern "<.*>|$.*";
             }
             type uint32 {
               range 1;
             }
           }
         }
         uses apply-advanced;
         leaf admin-state {
           description "Administrative state of alarm IO output port";
           type enumeration {
             enum "disabled" {
               description "Administrative state of alarm IO port to disable(default)";
             }
             enum "enabled" {
               description "Administrative state of alarm IO port to enabled";
             }
           }
         }
         container description {
           junos:cli-feature "oneliner-plus";
           description "Alarm description of alarm IO output port";
           uses apply-advanced;
           leaf descr {
             description "Description to be used for alarm IO output port";
             junos:cli-feature "nokeyword";
             type string;
           }
         }
       }
     }
   }
   grouping chassis_alarm_type {
     uses apply-advanced;
     container management-ethernet {
       description "Management Ethernet alarms";
       uses chassis_alarm_ethernet_type;
     }
     container otn-odu {
       description "OTN ODU alarms";
       uses chassis_alarm_otn_odu_type;
     }
     container otn-otu {
       description "OTN OTU alarms";
       uses chassis_alarm_otn_otu_type;
     }
     container sonet {
       description "SONET alarms";
       uses chassis_alarm_sonet_type;
     }
     container t3 {
       description "DS3 alarms";
       uses chassis_alarm_ds3_type;
     }
     container ds1 {
       description "DS1 alarms";
       uses chassis_alarm_ds1_type;
     }
     container ethernet {
       description "Ethernet alarms";
       uses chassis_alarm_ethernet_type;
     }
     container integrated-services {
       description "Integrated services alarms";
       uses chassis_alarm_integrated_services_type;
     }
     container services {
       description "Services PIC alarms";
       uses chassis_alarm_services_type;
     }
     container serial {
       description "Serial alarms";
       uses chassis_alarm_serial_type;
     }
     container fibre-channel {
       description "Fibre Channel alarms";
       uses chassis_alarm_fibre-channel_type;
     }
     list psm {
       key name;
       description "Alarm for psm input feed";
       leaf name {
         description "PSM slot number";
         junos:cli-feature "nokeyword";
         type union {
           type string {
             pattern "<.*>|$.*";
           }
           type uint32;
         }
       }
       uses apply-advanced;
       container input1 {
         uses apply-advanced;
         leaf ignore {
           description "Ignore input1 alarm of Power Supply Module";
           type empty;
         }
       }
       container input2 {
         uses apply-advanced;
         leaf ignore {
           description "Ignore input2 alarm of Power Supply Module";
           type empty;
         }
       }
     }
     container fru-absence {
       description "FRU module absence";
       uses apply-advanced;
       container ignore {
         description "Ignore the power supply module absence alarm";
         uses apply-advanced;
         list fpc {
           key name;
           ordered-by user;
           description "FPC Slot Number";
           uses chassis_fpc_type_slot;
         }
       }
     }
     leaf ignore-fan-speed-check {
       description "Ignore the Fan speed check alarms";
       type empty;
     }
   }
   grouping chassis_alarm_ds1_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ds3_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf exz {
       description "Excessive zeros";
       type enumeration {
         enum "red" {
           description "Assert red system alarm";
         }
         enum "yellow" {
           description "Assert yellow system alarm";
         }
         enum "ignore" {
           description "Do not assert any alarm signals";
         }
       }
     }
     leaf ferf {
       description "Far-end failure";
       type enumeration {
         enum "red" {
           description "Assert red system alarm";
         }
         enum "yellow" {
           description "Assert yellow system alarm";
         }
         enum "ignore" {
           description "Do not assert any alarm signals";
         }
       }
     }
     leaf idle {
       description "Idle alarm";
       type enumeration {
         enum "red" {
           description "Assert red system alarm";
         }
         enum "yellow" {
           description "Assert yellow system alarm";
         }
         enum "ignore" {
           description "Do not assert any alarm signals";
         }
       }
     }
     leaf lcv {
       description "Line code violation";
       type enumeration {
         enum "red" {
           description "Assert red system alarm";
         }
         enum "yellow" {
           description "Assert yellow system alarm";
         }
         enum "ignore" {
           description "Do not assert any alarm signals";
         }
       }
     }
     leaf lof {
       description "Loss of frame";
       type enumeration {
         enum "red" {
           description "Assert red system alarm";
         }
         enum "yellow" {
           description "Assert yellow system alarm";
         }
         enum "ignore" {
           description "Do not assert any alarm signals";
         }
       }
     }
     leaf los {
       description "Loss of signal";
       type enumeration {
         enum "red" {
           description "Assert red system alarm";
         }
         enum "yellow" {
           description "Assert yellow system alarm";
         }
         enum "ignore" {
           description "Do not assert any alarm signals";
         }
       }
     }
     leaf pll {
       description "Phase-locked loop out of lock";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ethernet_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_fibre-channel_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_integrated_services_type {
     uses apply-advanced;
     leaf failure {
       description "Integrated Services failure";
       type enumeration {
         enum "red" {
           description "Assert red system alarm";
         }
         enum "yellow" {
           description "Assert yellow system alarm";
         }
         enum "ignore" {
           description "Do not assert any alarm signals";
         }
       }
     }
   }
   grouping chassis_alarm_otn_odu_type {
     uses apply-advanced;
     leaf odu-bdi {
       description "ODU backward-defect-indicator, ODU-BDI failure";
       type enumeration {
         enum "red" {
           description "Assert red system alarm";
         }
         enum "yellow" {
           description "Assert yellow system alarm";
         }
         enum "ignore" {
           description "Do not assert any alarm signals";
         }
       }
     }
     leaf odu-ttim {
       description "ODU trail-trace-identifier-mismatch, ODU-TTIM failure";
       type enumeration {
         enum "red" {
           description "Assert red system alarm";
         }
         enum "yellow" {
           description "Assert yellow system alarm";
         }
         enum "ignore" {
           description "Do not assert any alarm signals";
         }
       }
     }
     leaf odu-ptim {
       description "ODU payload-type-mismatch, ODU-PTIM failure";
       type enumeration {
         enum "red" {
           description "Assert red system alarm";
         }
         enum "yellow" {
           description "Assert yellow system alarm";
         }
         enum "ignore" {
           description "Do not assert any alarm signals";
         }
       }
     }
   }
   grouping chassis_alarm_otn_otu_type {
     uses apply-advanced;
     leaf oc-los {
       description "Loss of signal, LOS failure";
       type enumeration {
         enum "red" {
           description "Assert red system alarm";
         }
         enum "yellow" {
           description "Assert yellow system alarm";
         }
         enum "ignore" {
           description "Do not assert any alarm signals";
         }
       }
     }
     leaf oc-lof {
       description "Loss of framing, LOF failure";
       type enumeration {
         enum "red" {
           description "Assert red system alarm";
         }
         enum "yellow" {
           description "Assert yellow system alarm";
         }
         enum "ignore" {
           description "Do not assert any alarm signals";
         }
       }
     }
     leaf oc-lom {
       description "Loss of multiframe, LOM failure";
       type enumeration {
         enum "red" {
           description "Assert red system alarm";
         }
         enum "yellow" {
           description "Assert yellow system alarm";
         }
         enum "ignore" {
           description "Do not assert any alarm signals";
         }
       }
     }
     leaf wavelength-lock {
       description "Wavelength lock alarm";
       type enumeration {
         enum "red" {
           description "Assert red system alarm";
         }
         enum "yellow" {
           description "Assert yellow system alarm";
         }
         enum "ignore" {
           description "Do not assert any alarm signals";
         }
       }
     }
     leaf otu-bdi {
       description "OTU backward-defect-indicator, OTU-BDI failure";
       type enumeration {
         enum "red" {
           description "Assert red system alarm";
         }
         enum "yellow" {
           description "Assert yellow system alarm";
         }
         enum "ignore" {
           description "Do not assert any alarm signals";
         }
       }
     }
     leaf otu-iae {
       description "OTU incoming-alignment-error, OTU-IAE failure";
       type enumeration {
         enum "red" {
           description "Assert red system alarm";
         }
         enum "yellow" {
           description "Assert yellow system alarm";
         }
         enum "ignore" {
           description "Do not assert any alarm signals";
         }
       }
     }
     leaf otu-ttim {
       description "OTU trail-trace-identifier-mismatch, OTU-TTIM failure";
       type enumeration {
         enum "red" {
           description "Assert red system alarm";
         }
         enum "yellow" {
           description "Assert yellow system alarm";
         }
         enum "ignore" {
           description "Do not assert any alarm signals";
         }
       }
     }
     leaf otu-fec-excessive-errs {
       description "OTU fec-excessive-errors, OTU-FEC_EXE failure";
       type enumeration {
         enum "red" {
           description "Assert red system alarm";
         }
         enum "yellow" {
           description "Assert yellow system alarm";
         }
         enum "ignore" {
           description "Do not assert any alarm signals";
         }
       }
     }
   }
   grouping chassis_alarm_serial_type {
     uses apply-advanced;
     leaf loss-of-rx-clock {
       description "RX clock absent";
       type enumeration {
         enum "red" {
           description "Assert red system alarm";
         }
         enum "yellow" {
           description "Assert yellow system alarm";
         }
         enum "ignore" {
           description "Do not assert any alarm signals";
         }
       }
     }
     leaf loss-of-tx-clock {
       description "TX clock absent";
       type enumeration {
         enum "red" {
           description "Assert red system alarm";
         }
         enum "yellow" {
           description "Assert yellow system alarm";
         }
         enum "ignore" {
           description "Do not assert any alarm signals";
         }
       }
     }
     leaf dcd-absent {
       description "DCD signal absent";
       type enumeration {
         enum "red" {
           description "Assert red system alarm";
         }
         enum "yellow" {
           description "Assert yellow system alarm";
         }
         enum "ignore" {
           description "Do not assert any alarm signals";
         }
       }
     }
     leaf cts-absent {
       description "CTS signal absent";
       type enumeration {
         enum "red" {
           description "Assert red system alarm";
         }
         enum "yellow" {
           description "Assert yellow system alarm";
         }
         enum "ignore" {
           description "Do not assert any alarm signals";
         }
       }
     }
     leaf dsr-absent {
       description "DSR signal absent";
       type enumeration {
         enum "red" {
           description "Assert red system alarm";
         }
         enum "yellow" {
           description "Assert yellow system alarm";
         }
         enum "ignore" {
           description "Do not assert any alarm signals";
         }
       }
     }
     leaf tm-absent {
       description "TM signal absent";
       type enumeration {
         enum "red" {
           description "Assert red system alarm";
         }
         enum "yellow" {
           description "Assert yellow system alarm";
         }
         enum "ignore" {
           description "Do not assert any alarm signals";
         }
       }
     }
   }
   grouping chassis_alarm_services_type {
     uses apply-advanced;
     leaf pic-reset {
       description "Services PIC reset";
       type enumeration {
         enum "red" {
           description "Assert red system alarm";
         }
         enum "yellow" {
           description "Assert yellow system alarm";
         }
         enum "ignore" {
           description "Do not assert any alarm signals";
         }
       }
     }
     leaf pic-hold-reset {
       description "Services PIC held in reset";
       type enumeration {
         enum "red" {
           description "Assert red system alarm";
         }
         enum "yellow" {
           description "Assert yellow system alarm";
         }
         enum "ignore" {
           description "Do not assert any alarm signals";
         }
       }
     }
     leaf linkdown {
       description "Services PIC linkdown";
       type enumeration {
         enum "red" {
           description "Assert red system alarm";
         }
         enum "yellow" {
           description "Assert yellow system alarm";
         }
         enum "ignore" {
           description "Do not assert any alarm signals";
         }
       }
     }
     leaf rx-errors {
       description "Services PIC excessive rx errors";
       type enumeration {
         enum "red" {
           description "Assert red system alarm";
         }
         enum "yellow" {
           description "Assert yellow system alarm";
         }
         enum "ignore" {
           description "Do not assert any alarm signals";
         }
       }
     }
     leaf tx-errors {
       description "Services PIC excessive tx errors";
       type enumeration {
         enum "red" {
           description "Assert red system alarm";
         }
         enum "yellow" {
           description "Assert yellow system alarm";
         }
         enum "ignore" {
           description "Do not assert any alarm signals";
         }
       }
     }
     leaf sw-down {
       description "Services PIC software problem";
       type enumeration {
         enum "red" {
           description "Assert red system alarm";
         }
         enum "yellow" {
           description "Assert yellow system alarm";
         }
         enum "ignore" {
           description "Do not assert any alarm signals";
         }
       }
     }
     leaf hw-down {
       description "Services PIC hardware problem";
       type enumeration {
         enum "red" {
           description "Assert red system alarm";
         }
         enum "yellow" {
           description "Assert yellow system alarm";
         }
         enum "ignore" {
           description "Do not assert any alarm signals";
         }
       }
     }
   }
   grouping chassis_alarm_sonet_type {
     uses apply-advanced;
     leaf lol {
       description "Loss of light";
       type enumeration {
         enum "red" {
           description "Assert red system alarm";
         }
         enum "yellow" {
           description "Assert yellow system alarm";
         }
         enum "ignore" {
           description "Do not assert any alarm signals";
         }
       }
     }
     leaf pll {
       description "Phase locked loop out of lock";
       type enumeration {
         enum "red" {
           description "Assert red system alarm";
         }
         enum "yellow" {
           description "Assert yellow system alarm";
         }
         enum "ignore" {
           description "Do not assert any alarm signals";
         }
       }
     }
     leaf lof {
       description "Loss of framing, LOF failure";
       type enumeration {
         enum "red" {
           description "Assert red system alarm";
         }
         enum "yellow" {
           description "Assert yellow system alarm";
         }
         enum "ignore" {
           description "Do not assert any alarm signals";
         }
       }
     }
     leaf los {
       description "Loss of signal, LOS failure";
       type enumeration {
         enum "red" {
           description "Assert red system alarm";
         }
         enum "yellow" {
           description "Assert yellow system alarm";
         }
         enum "ignore" {
           description "Do not assert any alarm signals";
         }
       }
     }
     leaf ais-l {
       description "Line alarm indication signal, AIS-L failure";
       type enumeration {
         enum "red" {
           description "Assert red system alarm";
         }
         enum "yellow" {
           description "Assert yellow system alarm";
         }
         enum "ignore" {
           description "Do not assert any alarm signals";
         }
       }
     }
     leaf ais-p {
       description "Path alarm indication signal, AIS-P failure";
       type enumeration {
         enum "red" {
           description "Assert red system alarm";
         }
         enum "yellow" {
           description "Assert yellow system alarm";
         }
         enum "ignore" {
           description "Do not assert any alarm signals";
         }
       }
     }
     leaf lop-p {
       description "Loss of pointer, LOP-P failure";
       type enumeration {
         enum "red" {
           description "Assert red system alarm";
         }
         enum "yellow" {
           description "Assert yellow system alarm";
         }
         enum "ignore" {
           description "Do not assert any alarm signals";
         }
       }
     }
     leaf ber-sd {
       description "Signal Degrade (SD), bit error rate > 1E-6";
       type enumeration {
         enum "red" {
           description "Assert red system alarm";
         }
         enum "yellow" {
           description "Assert yellow system alarm";
         }
         enum "ignore" {
           description "Do not assert any alarm signals";
         }
       }
     }
     leaf ber-sf {
       description "Signal Fail (SF), bit error rate > 1E-3";
       type enumeration {
         enum "red" {
           description "Assert red system alarm";
         }
         enum "yellow" {
           description "Assert yellow system alarm";
         }
         enum "ignore" {
           description "Do not assert any alarm signals";
         }
       }
     }
     leaf rfi-l {
       description "Line remote failure indication, RFI-L, line FERF";
       type enumeration {
         enum "red" {
           description "Assert red system alarm";
         }
         enum "yellow" {
           description "Assert yellow system alarm";
         }
         enum "ignore" {
           description "Do not assert any alarm signals";
         }
       }
     }
     leaf rfi-p {
       description "Path remote failure indication, RFI-P, STS path yellow";
       type enumeration {
         enum "red" {
           description "Assert red system alarm";
         }
         enum "yellow" {
           description "Assert yellow system alarm";
         }
         enum "ignore" {
           description "Do not assert any alarm signals";
         }
       }
     }
     leaf uneq-p {
       description "STS Path (C2) unequipped, UNEQ-P failure";
       type enumeration {
         enum "red" {
           description "Assert red system alarm";
         }
         enum "yellow" {
           description "Assert yellow system alarm";
         }
         enum "ignore" {
           description "Do not assert any alarm signals";
         }
       }
     }
     leaf locd {
       description "Loss of cell delineation (ATM only)";
       type enumeration {
         enum "red" {
           description "Assert red system alarm";
         }
         enum "yellow" {
           description "Assert yellow system alarm";
         }
         enum "ignore" {
           description "Do not assert any alarm signals";
         }
       }
     }
     leaf plm-p {
       description "STS payload label (C2) mismatch, PLM-P failure";
       type enumeration {
         enum "red" {
           description "Assert red system alarm";
         }
         enum "yellow" {
           description "Assert yellow system alarm";
         }
         enum "ignore" {
           description "Do not assert any alarm signals";
         }
       }
     }
   }
   grouping chassis_cb_type {
     leaf name {
       description "CB slot number";
       junos:cli-feature "nokeyword";
       type union {
         type string {
           pattern "<.*>|$.*";
         }
         type uint32;
       }
     }
     uses apply-advanced;
     container temperature-threshold {
       description "CB temperature thresholds";
       uses chassis-temperature-threshold-type;
     }
     list temperature-sensor {
       key name;
       description "CB temperature sensor";
       uses chassis-temperature-sensor-type;
     }
   }
   grouping chassis-temperature-sensor-type {
     leaf name {
       description "Temperature sensor name";
       junos:cli-feature "nokeyword";
       type string;
     }
     uses apply-advanced;
     container temperature-threshold {
       description "Temperature thresholds";
       uses chassis-temperature-threshold-type;
     }
   }
   grouping chassis-temperature-threshold-type {
     description "Chassis temperature thresholds";
     uses apply-advanced;
     leaf fans-to-normal-speed {
       description "Threshold at which fans return to normal speed";
       units "degrees C";
       type union {
         type uint32;
         type string {
           pattern "<.*>|$.*";
         }
       }
     }
     leaf fans-on-intermediate-speed {
       description "Threshold at which fans run intermediate speed";
       units "degrees C";
       type union {
         type uint32;
         type string {
           pattern "<.*>|$.*";
         }
       }
     }
     leaf fans-on-full-speed {
       description "Threshold at which fans run full speed";
       units "degrees C";
       type union {
         type uint32;
         type string {
           pattern "<.*>|$.*";
         }
       }
     }
     leaf fans-on-full-speed-if-failed-fan {
       description "Threshold at which fans run full speed when bad fan present";
       units "degrees C";
       type union {
         type uint32;
         type string {
           pattern "<.*>|$.*";
         }
       }
     }
     leaf yellow-alarm {
       description "Threshold at which yellow alarm is set";
       units "degrees C";
       type union {
         type uint32;
         type string {
           pattern "<.*>|$.*";
         }
       }
     }
     leaf yellow-alarm-if-failed-fan {
       description "Threshold at which yellow alarm is set when bad fan present";
       units "degrees C";
       type union {
         type uint32;
         type string {
           pattern "<.*>|$.*";
         }
       }
     }
     leaf red-alarm {
       description "Threshold at which red alarm is set";
       units "degrees C";
       type union {
         type uint32;
         type string {
           pattern "<.*>|$.*";
         }
       }
     }
     leaf red-alarm-if-failed-fan {
       description "Threshold at which red alarm is set when bad fan present";
       units "degrees C";
       type union {
         type uint32;
         type string {
           pattern "<.*>|$.*";
         }
       }
     }
     leaf fire-shutdown {
       description "Threshold at which router will be shutdown within 10 seconds";
       units "degrees C";
       type union {
         type uint32;
         type string {
           pattern "<.*>|$.*";
         }
       }
     }
   }
   grouping chassis_fabric_card_type {
     leaf name {
       description "Fabric Card slot number";
       junos:cli-feature "nokeyword";
       type string {
         length "1 .. 5";
       }
     }
     uses apply-advanced;
     container loopback {
       description "Loopback Configuration for Mode & Type";
       uses apply-advanced;
       leaf serdes {
         description "Fabric Card serdes setting";
         type empty;
       }
       leaf retimer {
         description "Fabric card retimer setting";
         type empty;
       }
     }
   }
   grouping chassis_fabric_cards_type {
     uses apply-advanced;
     leaf reset-count {
       description "Number of times sib can be reset by cmerror";
       type union {
         type string {
           pattern "<.*>|$.*";
         }
         type uint32 {
           range "1 .. 10";
         }
       }
     }
   }
   grouping chassis_fabric_type {
     junos:cli-feature "oneliner-plus";
     uses apply-advanced;
     leaf upgrade-mode {
       description "Enable online switch fabric upgrade";
       type enumeration {
         enum "default" {
           description "Fabric upgrade";
         }
         enum "t4000" {
           description "T4000 Fabric upgrade";
           junos:must "(!(any \"class-of-service schedulers <*> drop-profile-map loss-priority <*> protocol non-tcp drop-profile <*>\"))";
           junos:must-message "protocol based classification not allowed, only 'any' protocol config allowed";
           junos:must "(!(any \"class-of-service schedulers <*> drop-profile-map loss-priority <*> protocol tcp drop-profile <*>\"))";
           junos:must-message "protocol based classification not allowed, only 'any' protocol config allowed";
         }
         enum "3d-fabric" {
           description "TXP-3D Fabric upgrade";
           junos:must "(!(any \"class-of-service schedulers <*> drop-profile-map loss-priority <*> protocol non-tcp drop-profile <*>\"))";
           junos:must-message "protocol based classification not allowed, only 'any' protocol config allowed";
           junos:must "(!(any \"class-of-service schedulers <*> drop-profile-map loss-priority <*> protocol tcp drop-profile <*>\"))";
           junos:must-message "protocol based classification not allowed, only 'any' protocol config allowed";
         }
       }
     }
     container event {
       description "Fabric events";
       uses apply-advanced;
       container link-failure {
         presence "enable link-failure";
         description "Fabric link failure";
         uses apply-advanced;
         container action {
           presence "enable action";
           description "Fabric action to be taken";
           uses apply-advanced;
         }
       }
       container reachability-fault {
         presence "enable reachability-fault";
         description "Fabric reachability fault detection";
         uses apply-advanced;
         container degraded {
           presence "enable degraded";
           description "Degraded fabric configuration";
           uses apply-advanced;
           container error-threshold {
             presence "enable error-threshold";
             description "Fabric error threshold for degraded case";
             uses apply-advanced;
             container degradation {
               presence "enable degradation";
               description "Degradation attributes";
               uses apply-advanced;
               leaf percentage {
                 description "The percentage degradation on which action is taken";
                 junos:cli-feature "nokeyword";
                 type union {
                   type string {
                     pattern "<.*>|$.*";
                   }
                   type uint32 {
                     range "1 .. 99";
                   }
                 }
               }
             }
           }
         }
         container actions {
           description "Reachability fault actions";
           uses apply-advanced;
           container recovery-failure {
             description "Recovery failure action to be taken for FHP";
             uses apply-advanced;
           }
         }
       }
     }
     container oam {
       description "Fabric OAM configuration";
       uses apply-advanced;
       leaf detection-disable {
         description "Disable fabric OAM";
         type empty;
       }
       leaf runtime-disable {
         description "Disable runtime fabric OAM";
         type empty;
       }
     }
     container degraded {
       presence "enable degraded";
       description "Degraded fabric configuration";
       uses apply-advanced;
       leaf action-fpc-restart-disable {
         description "Limit degraded fabric actions to Plane restart only";
         type empty;
       }
       leaf degraded-fpc-bad-plane-threshold {
         description "No of bad planes to declare a FPC degraded";
         default "4";
         type union {
           type string {
             pattern "<.*>|$.*";
           }
           type uint32 {
             range "4 .. 18";
           }
         }
       }
       leaf degraded-fabric-detection-enable {
         description "Enable degraded FPC detection";
         type empty;
       }
     }
   }
   grouping chassis_feb_type {
     uses apply-advanced;
     list slot {
       key name;
       ordered-by user;
       leaf name {
         description "FEB slot number";
         junos:cli-feature "nokeyword";
         type union {
           type string {
             pattern "<.*>|$.*";
           }
           type uint32;
         }
       }
       uses apply-advanced;
       leaf power {
         description "Power FEBs on or off";
         type enumeration {
           enum "off" {
             description "Do not provide power to FEBs";
           }
           enum "on" {
             description "Provide power to FEBs";
           }
         }
       }
       choice mode {
       }
       leaf sampling-instance {
         description "Associate a sampling instance with the FEB";
         junos:must "(\"forwarding-options sampling instance $$\")";
         junos:must-message "Referenced sampling instance does not exist";
         type string {
           length "1 .. 64";
         }
       }
       container inline-services {
         uses apply-advanced;
         leaf report-zero-oif-gw-on-discard {
           description "Jflow reports value zero in OIF and GW when traffic is not forwarded";
           type empty;
         }
         leaf flex-flow-sizing {
           description "No fixed size allocation of flow tables for proto families";
           junos:must "(!((\".. flow-table-size ipv4-flow-table-size\" || (\".. flow-table-size ipv6-flow-table-size\" || (\".. flow-table-size vpls-flow-table-size\" || (\".. flow-table-size bridge-flow-table-size\" || \".. flow-table-size mpls-flow-table-size\"))))))";
           junos:must-message "flex-flow-sizing and flow-table-size are mutually exclusive";
           type empty;
         }
         leaf use-extended-flow-memory {
           description "Use extended memory for flow records";
           type empty;
         }
         container flow-table-size {
           uses apply-advanced;
           leaf ipv4-flow-table-size {
             description "IPv4 flow table size in units of 256k";
             junos:must "(!(\".. .. flex-flow-sizing\"))";
             junos:must-message "flex-flow-sizing and flow-table-size are mutually exclusive";
             type union {
               type string {
                 pattern "<.*>|$.*";
               }
               type uint32 {
                 range "1 .. 245";
               }
             }
           }
           leaf ipv6-flow-table-size {
             description "IPv6 flow table size in units of 256k";
             junos:must "(!(\".. .. flex-flow-sizing\"))";
             junos:must-message "flex-flow-sizing and flow-table-size are mutually exclusive";
             type union {
               type string {
                 pattern "<.*>|$.*";
               }
               type uint32 {
                 range "1 .. 245";
               }
             }
           }
           leaf vpls-flow-table-size {
             description "VPLS flow table size in units of 256k";
             junos:must "(!(\".. .. flex-flow-sizing\"))";
             junos:must-message "flex-flow-sizing and flow-table-size are mutually exclusive";
             type union {
               type string {
                 pattern "<.*>|$.*";
               }
               type uint32 {
                 range "1 .. 245";
               }
             }
           }
           leaf bridge-flow-table-size {
             description "BRIDGE flow table size in units of 256k";
             junos:must "(!(\".. .. flex-flow-sizing\"))";
             junos:must-message "flex-flow-sizing and flow-table-size are mutually exclusive";
             type union {
               type string {
                 pattern "<.*>|$.*";
               }
               type uint32 {
                 range "1 .. 245";
               }
             }
           }
           leaf ipv6-extended-attrib {
             description "Enable extended flow attribute";
             type empty;
           }
           leaf mpls-flow-table-size {
             description "MPLS flow table size in units of 256k";
             junos:must "(!(\".. .. flex-flow-sizing\"))";
             junos:must-message "flex-flow-sizing and flow-table-size are mutually exclusive";
             type union {
               type string {
                 pattern "<.*>|$.*";
               }
               type uint32 {
                 range "1 .. 245";
               }
             }
           }
         }
       }
       container inline-video-monitoring {
         uses apply-advanced;
         leaf maximum-flows-count {
           description "Maximum number of inline video monitoring flows per PFE instance";
           type union {
             type string {
               pattern "<.*>|$.*";
             }
             type uint32 {
               range "16 .. 8192";
             }
           }
         }
       }
       container openflow {
         description "Openflow configuration";
         uses apply-advanced;
         leaf access-list-partition {
           description "Space reserved for openflow access-list rules";
           units "percents";
           type union {
             type string {
               pattern "<.*>|$.*";
             }
             type uint32 {
               range "0 .. 100";
             }
           }
         }
       }
     }
   }
   grouping chassis_fpc_type {
     leaf name {
       description "FPC slot number";
       junos:cli-feature "nokeyword";
       type union {
         type string {
           pattern "<.*>|$.*";
         }
         type uint32;
       }
     }
     uses apply-advanced;
     container auto-speed-detection {
       description "Disables auto-speed detection";
       uses apply-advanced;
       choice auto-speed-detections {
         case case_1 {
           leaf disable {
             description "Disables automatic speed detection";
             type empty;
           }
         }
       }
     }
     container linkscan-per-fpc {
       presence "enable linkscan-per-fpc";
       description "Configure linkscan per FPC";
       uses apply-advanced;
       leaf fpc-linkscan-interval {
         description " setting linkscan interval of FPC in microsecond";
         type union {
           type string {
             pattern "<.*>|$.*";
           }
           type uint32 {
             range "10000 .. 500000";
           }
         }
       }
       leaf software-based {
         description "Override linkscan mode to software based";
         type empty;
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               junos:must "(!(\".. unicast-in-lpm\"))";
               junos:must-message "Cannot set both unicast-in-lpm and prefix-65-127-disable at the same time";
               type empty;
             }
             leaf unicast-in-lpm {
               description "Install unicast host entries in LPM table";
               type empty;
             }
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_8 {
           container vxlan-gbp-l2-profile {
             presence "enable vxlan-gbp-l2-profile";
             description "MAC: 64K L3-host: 32K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_9 {
           container vxlan-gbp-l3-profile {
             presence "enable vxlan-gbp-l3-profile";
             description "MAC: 32K L3-host: 64K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_10 {
           container vxlan-gbp-mc-profile {
             presence "enable vxlan-gbp-mc-profile";
             description "MAC: 32K L3-host: 64K LPM: 16K EM:16K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_11 {
           container em-hw-profile {
             presence "enable em-hw-profile";
             description "MAC: 48K L3-host: 48K LPM: 16K EM:32K, needs reboot for VC; restarts PFE if standalone";
           }
         }
         case case_12 {
           container gbp-pure-l2-profile {
             presence "enable gbp-pure-l2-profile";
             description "MAC: 48K L3-host: 48K LPM: 16K EM:16K, needs reboot for VC; restarts PFE if standalone";
           }
         }
         case case_13 {
           container default-profile {
             presence "enable default-profile";
             description "MAC: 64K L3-host: 32K LPM: 24K IFP: 12K, needs reboot for VC; restarts PFE if standalone";
           }
         }
         case case_14 {
           container ifp-profile {
             presence "enable ifp-profile";
             description "MAC: 64K L3-host: 32K LPM: 12K IFP: 18K, needs reboot for VC; restarts PFE if standalone";
             uses apply-advanced;
             leaf lpm-scale {
               description "Num of v4 lpm/ifp entries (1 - 24k/36k, 2 - 36k/27k, 3 - 60k/18k, 4 - 64k/12k)(default 2)";
               default "2";
               type union {
                 type string {
                   pattern "<.*>|$.*";
                 }
                 type int32 {
                   range "1 .. 4";
                 }
               }
             }
           }
         }
         case case_15 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 junos:must "(!(\".. unicast-in-lpm\"))";
                 junos:must-message "Cannot set both unicast-in-lpm and prefix-65-127-disable at the same time";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     list pic {
       key name;
       description "Physical Interface Card number";
       uses chassis_pic_type;
     }
     list mic {
       key name;
       description "Modular Interface Card number";
       uses chassis_mic_type;
     }
     leaf power {
       description "Power FPCs on or off";
       type enumeration {
         enum "off" {
           description "Do not provide power to FPCs";
         }
         enum "on" {
           description "Provide power to FPCs";
         }
       }
     }
     container traffic-manager {
       description "Configure traffic-manager attributes";
       uses apply-advanced;
       leaf buffer-monitor-enable {
         description "Enable port buffer monitoring";
         type empty;
       }
       container queue-threshold {
         description "Set queue thresholds";
         uses apply-advanced;
         container fabric-queue {
           description "Set fabric queue thresholds";
           uses apply-advanced;
           list priority {
             key name;
             ordered-by user;
             description "Queue priority";
             leaf name {
               description "Priority level";
               junos:cli-feature "nokeyword";
               type enumeration {
                 enum "low" {
                   description "Low fabric priority";
                 }
                 enum "high" {
                   description "High fabric priority";
                 }
               }
             }
             uses apply-advanced;
             leaf threshold {
               description "Threshold percentage to be set";
               type union {
                 type string {
                   pattern "<.*>|$.*";
                 }
                 type uint32 {
                   range "1 .. 100";
                 }
               }
             }
           }
         }
         container wan-queue {
           description "Set wan queue thresholds";
           uses apply-advanced;
           list priority {
             key name;
             ordered-by user;
             description "Queue Priority";
             leaf name {
               description "Priority level";
               junos:cli-feature "nokeyword";
               type enumeration {
                 enum "low" {
                   description "Low wan priority";
                 }
                 enum "medium-low" {
                   description "Medium low wan priority";
                 }
                 enum "medium-high" {
                   description "Medium high wan priority";
                 }
                 enum "high" {
                   description "High wan priority";
                 }
               }
             }
             uses apply-advanced;
             leaf threshold {
               description "Threshold percentage to be set";
               type union {
                 type string {
                   pattern "<.*>|$.*";
                 }
                 type uint32 {
                   range "1 .. 100";
                 }
               }
             }
           }
         }
       }
       choice enhanced-priority-mode-choice {
         leaf enhanced-priority-mode {
           description "Enable enhanced priority mode";
           type empty;
         }
         leaf no-enhanced-priority-mode {
           description "Don't enable enhanced priority mode";
           type empty;
         }
       }
       leaf packet-timestamp {
         description "Configure collecting CoS last packet enqueued timestamp";
         default "disable";
         type enumeration {
           enum "enable" {
             description "Enables collecting CoS last packet enqueued timestamp";
           }
           enum "disable" {
             description "Disables collecting CoS last packet enqueued timestamp";
           }
         }
       }
     }
     leaf max-power {
       description "Max power to be consumed by MPC";
       type union {
         type uint32;
         type string {
           pattern "<.*>|$.*";
         }
       }
     }
     leaf power-budget-priority {
       description "FPC priority number";
       type union {
         type string {
           pattern "<.*>|$.*";
         }
         type uint32;
       }
     }
     choice mode {
       case case_1 {
         leaf disable-power {
           description "Do not provide power to the card";
           status deprecated;
           type empty;
         }
       }
       case case_2 {
         leaf allow-sram-parity-errors {
           description "Do not power cycle FPC when SRAM parity errors occur";
           type empty;
         }
       }
     }
     choice riot-mode {
       case case_1 {
       }
       case case_2 {
       }
     }
     leaf cfp-to-et {
       description "Enable ET interface and remove CFP client";
       type empty;
     }
     container lossless-flow-control {
       presence "enable lossless-flow-control";
       description "Lossless buffer config for Ethernet Mac pause";
       uses apply-advanced;
       choice enable_choice {
         case case_1 {
           leaf lossless-flow-control-enable {
             description "Enable Lossless buffer config for Ethernet Mac pause";
             type empty;
           }
         }
         case case_2 {
           leaf no-lossless-flow-control-enable {
             description "Disable Lossless buffer config for Ethernet Mac pause";
             type empty;
           }
         }
       }
     }
     leaf license-mode {
       description "Configure license mode for PTX FPC3 and later cards";
       type enumeration {
         enum "r" {
           description "Set card to R mode";
         }
         enum "ir" {
           description "Set card to IR mode";
         }
         enum "lsr" {
           description "Set card to LSR mode";
         }
         enum "ip" {
           description "Set card to full IP mode";
         }
       }
     }
     list port-mirror-instance {
       key name;
       ordered-by user;
       max-elements 2;
       leaf name {
         description "Associate a port mirroring instance with the FPC";
         junos:cli-feature "nokeyword";
         junos:must "(!(\"forwarding-options port-mirroring instance $$ input-parameters-instance\"))";
         junos:must-message "Derived instance cannot be binded";
         junos:must "(((!(\"chassis network-services lan\") && (\"forwarding-options port-mirroring instance $$\" || \"forwarding-options analyzer $$\")) || \"chassis network-services lan\"))";
         junos:must-message "Referenced port-mirroring instance does not exist";
         type string {
           length "1 .. 64";
         }
       }
       uses apply-advanced;
     }
     list sampling-instance {
       key name;
       ordered-by user;
       max-elements 1;
       leaf name {
         description "Associate a sampling instance with the FPC";
         junos:cli-feature "nokeyword";
         junos:must "(\"forwarding-options sampling instance $$\")";
         junos:must-message "Referenced sampling instance does not exist";
         type string {
           length "1 .. 64";
         }
       }
       uses apply-advanced;
     }
     list pfe {
       key name;
       description "Packet forwarding engine parameters";
       uses chassis_pfe_type;
     }
     leaf service-package {
       description "Service package to be loaded on FPC";
       default "bundle-rfc2544";
       type enumeration {
         enum "bundle-rfc2544" {
           description "Service Package for RFC2544";
         }
         enum "bundle-nat-ipsec" {
           description "Service Package for NAT and IPSEC";
         }
         enum "bundle-ptp-enterprise-profile" {
           description "Service Package for PTP Enterprise Profile";
         }
       }
     }
     container error {
       description "Error level configuration for FPC";
       uses chassis_fpc_error_type;
     }
     list ether-type {
       key name;
       ordered-by user;
       description "Set Ethernet type on FPC";
       leaf name {
         description "TCAM slot";
         junos:cli-feature "nokeyword";
         type union {
           type string {
             pattern "<.*>|$.*";
           }
           type uint8 {
             range "6 .. 27";
           }
         }
       }
       uses apply-advanced;
       leaf etype {
         description "Ether type";
         junos:cli-feature "nokeyword";
         type string;
       }
     }
     container relay {
       description "Alarm relays";
       uses chassis_alarm_relay_type;
     }
     leaf ignore-poe-feed {
       description "Ignore PoE feed";
       type empty;
     }
     container openflow {
       description "Openflow configuration";
       uses apply-advanced;
       leaf access-list-partition {
         description "Space reserved for openflow access-list rules";
         units "percents";
         type union {
           type string {
             pattern "<.*>|$.*";
           }
           type uint32 {
             range "0 .. 100";
           }
         }
       }
       leaf buffer-partition {
         description "Buffer space reserved for openflow traffic";
         units "percents";
         type union {
           type string {
             pattern "<.*>|$.*";
           }
           type uint32 {
             range "0 .. 100";
           }
         }
       }
     }
   }
   grouping chassis_alarm_relay_type {
     uses apply-advanced;
     container input {
       description "Input relays";
       uses apply-advanced;
       list port {
         key name;
         ordered-by user;
         leaf name {
           description "Relay port number";
           junos:cli-feature "nokeyword";
           type union {
             type string {
               pattern "<.*>|$.*";
             }
             type uint32 {
               range "0 .. 3";
             }
           }
         }
         uses apply-advanced;
         leaf mode {
           description "Relay mode in de-active state";
           type enumeration {
             enum "open" {
               description "Normally open";
             }
             enum "close" {
               description "Normally closed";
             }
           }
         }
         leaf trigger {
           description "Relay triggered";
           type enumeration {
             enum "red" {
               description "Assert red system alarm";
             }
             enum "yellow" {
               description "Assert yellow system alarm";
             }
             enum "ignore" {
               description "Do not assert any alarm signals";
             }
           }
         }
       }
     }
     container output {
       description "Output relays";
       uses apply-advanced;
       list port {
         key name;
         ordered-by user;
         leaf name {
           description "Relay port number";
           junos:cli-feature "nokeyword";
           type union {
             type string {
               pattern "<.*>|$.*";
             }
             type uint32 {
               range "0 .. 3";
             }
           }
         }
         uses apply-advanced;
         leaf mode {
           description "Relay mode in de-active state";
           type enumeration {
             enum "open" {
               description "Normally open";
             }
             enum "close" {
               description "Normally closed";
             }
           }
         }
         leaf temperature {
           description "Trigger on temperature alarm red";
           type empty;
         }
         leaf input-relay {
           description "Trigger on input relay trigger";
           type union {
             type string {
               pattern "<.*>|$.*";
             }
             type uint32 {
               range "0 .. 3";
             }
           }
         }
       }
     }
   }
   grouping chassis_fpc_error_type {
     description "Chassis Fpc Error level";
     uses apply-advanced;
     container fatal {
       description "FPC Fatal errors (default threshold = 1)";
       uses chassis_fpc_error_level_major_fatal;
     }
     container major {
       description "FPC Major Level errors (default threshold = 1)";
       uses chassis_fpc_error_level_major_fatal;
     }
     container minor {
       description "FPC Minor Level errors (default threshold = 10)";
       uses chassis_fpc_error_level_minor;
     }
     list override-cmerror {
       key name;
       ordered-by user;
       description "Error configuration override";
       max-elements 100;
       uses chassis_fru_cmerror_override_type;
       junos:cli-feature "nokeyword";
       junos:cli-feature "homogeneous";
     }
     container reset-pfe {
       description "FPC config reset-pfe options";
       presence "enable reset-pfe";
       uses chassis_fpc_error_config_reset_pfe_opt;
     }
     container scope {
       description "Error scope";
       uses chassis_fpc_scope_type;
     }
   }
   grouping chassis_fpc_error_config_reset_pfe_opt {
     uses apply-advanced;
     leaf retry-limit {
       description "Reset pfe retry limit";
       type union {
         type string {
           pattern "<.*>|$.*";
         }
         type uint32 {
           range "0 .. 3";
         }
       }
     }
     leaf pause-period {
       description "Reset pfe pause period in minutes";
       type union {
         type string {
           pattern "<.*>|$.*";
         }
         type uint32 {
           range "0 .. 10000000";
         }
       }
     }
     leaf pfe-disable-period {
       description "Reset pfe disable period in minutes";
       type union {
         type string {
           pattern "<.*>|$.*";
         }
         type uint32 {
           range "1 .. 10000000";
         }
       }
     }
   }
   grouping chassis_fpc_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         junos:cli-feature "nokeyword";
         type enumeration {
           enum "reset" {
             description "Reset FPC";
             junos:must "(!(\".. .. action offline-pfe\"))";
             junos:must-message "'reset' and 'offline-pfe' cannot be both configured";
             junos:must "(!(\".. .. action reset-pfe\"))";
             junos:must-message "'reset' and 'reset-pfe' cannot be both configured";
             junos:must "(!(\".. .. action offline\"))";
             junos:must-message "'reset' and 'offline' cannot be both configured";
           }
           enum "offline" {
             description "Offline FPC";
             junos:must "(!(\".. .. action offline-pfe\"))";
             junos:must-message "'offline' and 'offline-pfe' cannot be both configured";
             junos:must "(!(\".. .. action reset-pfe\"))";
             junos:must-message "'offline' and 'reset-pfe' cannot be both configured";
             junos:must "(!(\".. .. action reset\"))";
             junos:must-message "'offline' and 'reset' cannot be both configured";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
             junos:must "(!(\".. .. action offline\"))";
             junos:must-message "'reset-pfe' and 'offline' cannot be both configured";
             junos:must "(!(\".. .. action reset\"))";
             junos:must-message "'reset-pfe' and 'reset' cannot be both configured";
             junos:must "(!(\".. .. action offline-pfe\"))";
             junos:must-message "'reset-pfe' and 'offline-pfe' cannot be both configured";
             junos:must "(!(\".. .. action disable-pfe\"))";
             junos:must-message "'reset-pfe' and 'disable-pfe' cannot be both configured";
           }
           enum "offline-pic" {
             description "Offline PICs associated with PFE on FPC";
           }
           enum "trap" {
             description "Raise FPC trap";
           }
         }
       }
       uses apply-advanced;
     }
   }
   grouping chassis_fpc_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         junos:cli-feature "nokeyword";
         type enumeration {
           enum "reset" {
             description "Reset FPC";
             junos:must "(!(\".. .. action offline-pfe\"))";
             junos:must-message "'reset' and 'offline-pfe' cannot be both configured";
             junos:must "(!(\".. .. action reset-pfe\"))";
             junos:must-message "'reset' and 'reset-pfe' cannot be both configured";
             junos:must "(!(\".. .. action offline\"))";
             junos:must-message "'reset' and 'offline' cannot be both configured";
           }
           enum "offline" {
             description "Offline FPC";
             junos:must "(!(\".. .. action offline-pfe\"))";
             junos:must-message "'offline' and 'offline-pfe' cannot be both configured";
             junos:must "(!(\".. .. action reset-pfe\"))";
             junos:must-message "'offline' and 'reset-pfe' cannot be both configured";
             junos:must "(!(\".. .. action reset\"))";
             junos:must-message "'offline' and 'reset' cannot be both configured";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
             junos:must "(!(\".. .. action offline\"))";
             junos:must-message "'reset-pfe' and 'offline' cannot be both configured";
             junos:must "(!(\".. .. action reset\"))";
             junos:must-message "'reset-pfe' and 'reset' cannot be both configured";
             junos:must "(!(\".. .. action offline-pfe\"))";
             junos:must-message "'reset-pfe' and 'offline-pfe' cannot be both configured";
             junos:must "(!(\".. .. action disable-pfe\"))";
             junos:must-message "'reset-pfe' and 'disable-pfe' cannot be both configured";
           }
           enum "offline-pic" {
             description "Offline PICs associated with PFE on FPC";
           }
           enum "trap" {
             description "Raise FPC trap";
           }
         }
       }
       uses apply-advanced;
     }
   }
   grouping chassis_fpc_scope_type {
     description "Chassis Fpc Error Scope";
     uses apply-advanced;
     container board {
       description "Board level scope";
       uses chassis_fpc_scope_category;
     }
     container pfe {
       description "Forwarding engine scope ";
       uses chassis_fpc_scope_category;
     }
     container switch {
       description "SIB scope ";
       uses chassis_sib_scope_category;
     }
   }
   grouping chassis_fpc_scope_category {
     description "Chassis Fpc Error Category";
     uses apply-advanced;
     container category {
       description "FPC error category";
       uses chassis_fpc_scope_category_type;
     }
   }
   grouping chassis_fpc_scope_category_type {
     description "Chassis Fpc Category level";
     uses apply-advanced;
     container functional {
       description "FPC functional category";
       uses chassis_fpc_scope_category_error_type;
     }
     container memory {
       description "FPC memory category";
       uses chassis_fpc_scope_category_error_type;
     }
     container io {
       description "FPC input-output category";
       uses chassis_fpc_scope_category_error_type;
     }
     container storage {
       description "FPC storage category";
       uses chassis_fpc_scope_category_error_type;
     }
     container switch {
       description "FPC switch category";
       uses chassis_fpc_scope_category_error_type;
     }
     container processing {
       description "FPC processing category";
       uses chassis_fpc_scope_category_error_type;
     }
   }
   grouping chassis_fpc_scope_category_error_type {
     description "Chassis Fpc Error level";
     uses apply-advanced;
     container fatal {
       description "FPC Fatal errors (default threshold = 1)";
       uses chassis_fpc_error_level_type;
     }
     container major {
       description "FPC Major Level errors (default threshold = 1)";
       uses chassis_fpc_error_level_type;
     }
     container minor {
       description "FPC Minor Level errors (default threshold = 10)";
       uses chassis_fpc_error_level_type;
     }
   }
   grouping chassis_fpc_error_level_type {
     uses apply-advanced;
     leaf threshold {
       description "Error count at which to take the action (0 - valid for minor only)";
       type union {
         type string {
           pattern "<.*>|$.*";
         }
         type uint32 {
           range "0 .. 4294967295";
         }
       }
     }
     list action {
       key name;
       ordered-by user;
       description "Configure the action for this level";
       leaf name {
         junos:cli-feature "nokeyword";
         type enumeration {
           enum "reset" {
             description "Reset FPC";
             junos:must "(!(\".. .. action disable-pfe\"))";
             junos:must-message "'reset' and 'disable-pfe' cannot be both configured";
             junos:must "(!(\".. .. action offline\"))";
             junos:must-message "'reset' and 'offline' cannot be both configured";
           }
           enum "offline" {
             description "Offline FPC";
           }
           enum "alarm" {
             description "Raise FPC alarm";
           }
           enum "get-state" {
             description "Retrieve FPC state for debugging";
           }
           enum "log" {
             description "Log occurrence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise trap";
           }
         }
       }
       uses apply-advanced;
     }
   }
   grouping chassis_fpc_type_slot {
     leaf name {
       description "FPC slot number";
       junos:cli-feature "nokeyword";
       type string;
     }
     uses apply-advanced;
     list pem {
       key name;
       ordered-by user;
       description "Power Supply Module slot";
       uses chassis_pem_type_slot;
     }
   }
   grouping chassis_fru_cmerror_override_type {
     junos:cli-feature "nokeyword";
     junos:cli-feature "homogeneous";
     description "Chassis Fpc Error override";
     leaf name {
       description "Error identifier";
       junos:cli-feature "nokeyword";
       type string {
         length "1 .. 255";
         junos:posix-pattern "^(/[^/ ]+/[0-9]+){4}/[^/ ]+$";
         junos:pattern-message "Invalid error identifier format";
       }
     }
     uses apply-advanced;
     leaf state {
       description "State";
       type enumeration {
         enum "disable" {
           description "Disable error";
         }
       }
     }
     leaf severity {
       description "Severity";
       type enumeration {
         enum "minor" {
           description "Minor Severity";
         }
         enum "major" {
           description "Major Severity";
         }
         enum "fatal" {
           description "Fatal Severity";
         }
       }
     }
     container pfe {
       presence "enable pfe";
       description "Apply to these pfe";
       uses apply-advanced;
       leaf all {
         description "Apply to all pfe";
         type empty;
       }
     }
   }
   grouping chassis_junos_fru_error_type {
     description "Chassis Fru Error level";
     uses apply-advanced;
     container fatal {
       description "FRU Fatal errors (default threshold = 1)";
       uses chassis_fru_error_level_major_fatal;
     }
     container major {
       description "FRU Major errors (default threshold = 1)";
       uses chassis_fru_error_level_major_fatal;
     }
     container minor {
       description "FRU Minor errors (default threshold = 10)";
       uses chassis_fru_error_level_minor;
     }
     list override-cmerror {
       key name;
       ordered-by user;
       description "Error configuration override";
       max-elements 100;
       uses chassis_fru_cmerror_override_type;
       junos:cli-feature "nokeyword";
       junos:cli-feature "homogeneous";
     }
     container reset-pfe {
       description "FPC config reset-pfe options";
       presence "enable reset-pfe";
       uses chassis_fpc_error_config_reset_pfe_opt;
     }
     container scope {
       description "Error scope";
       uses chassis_fpc_scope_type;
     }
   }
   grouping chassis_fru_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         junos:cli-feature "nokeyword";
         type enumeration {
           enum "reset" {
             description "Reset FRU";
             junos:must "(!(\".. .. action disable-pfe\"))";
             junos:must-message "'reset' and 'disable-pfe' cannot be both configured";
             junos:must "(!(\".. .. action offline\"))";
             junos:must-message "'reset' and 'offline' cannot be both configured";
           }
           enum "offline" {
             description "Offline FRU";
             junos:must "(!(\".. .. action disable-pfe\"))";
             junos:must-message "'offline' and 'disable-pfe' cannot be both configured";
           }
           enum "alarm" {
             description "Raise FRU alarm";
           }
           enum "get-state" {
             description "Retrieve FRU state for debugging";
           }
           enum "log" {
             description "Log occurrence to system log file";
           }
           enum "disable-pfe" {
             description "Disable PFE interfaces on FPC";
             junos:must "(!(\".. .. action reset-pfe\"))";
             junos:must-message "'disable-pfe' and 'reset-pfe' cannot be both configured";
             junos:must "(!(\".. .. action offline-pfe\"))";
             junos:must-message "'disable-pfe' and 'offline-pfe' cannot be both configured";
           }
           enum "reset-pfe" {
             description "Reset PFE on FPC";
             junos:must "(!(\".. .. action offline-pfe\"))";
             junos:must-message "'reset-pfe' and 'offline-pfe' cannot be both configured";
             junos:must "(!(\".. .. action disable-pfe\"))";
             junos:must-message "'reset-pfe' and 'disable-pfe' cannot be both configured";
           }
           enum "offline-pic" {
             description "Offline PICs associated with PFE on FPC";
           }
           enum "trap" {
             description "Raise FPC trap";
           }
           enum "offline-pfe" {
             description "Offline PFE on FPC";
             junos:must "(!(\".. .. action reset-pfe\"))";
             junos:must-message "'offline-pfe' and 'reset-pfe' cannot be both configured";
             junos:must "(!(\".. .. action disable-pfe\"))";
             junos:must-message "'offline-pfe' and 'disable-pfe' cannot be both configured";
           }
         }
       }
       uses apply-advanced;
     }
   }
   grouping chassis_fru_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         junos:cli-feature "nokeyword";
         type enumeration {
           enum "reset" {
             description "Reset FRU";
             junos:must "(!(\".. .. action disable-pfe\"))";
             junos:must-message "'reset' and 'disable-pfe' cannot be both configured";
             junos:must "(!(\".. .. action offline\"))";
             junos:must-message "'reset' and 'offline' cannot be both configured";
           }
           enum "offline" {
             description "Offline FRU";
             junos:must "(!(\".. .. action disable-pfe\"))";
             junos:must-message "'offline' and 'disable-pfe' cannot be both configured";
           }
           enum "alarm" {
             description "Raise FRU alarm";
           }
           enum "get-state" {
             description "Retrieve FRU state for debugging";
           }
           enum "log" {
             description "Log occurrence to system log file";
           }
           enum "disable-pfe" {
             description "Disable PFE interfaces on FPC";
             junos:must "(!(\".. .. action reset-pfe\"))";
             junos:must-message "'disable-pfe' and 'reset-pfe' cannot be both configured";
             junos:must "(!(\".. .. action offline-pfe\"))";
             junos:must-message "'disable-pfe' and 'offline-pfe' cannot be both configured";
           }
           enum "reset-pfe" {
             description "Reset PFE on FPC";
             junos:must "(!(\".. .. action offline-pfe\"))";
             junos:must-message "'reset-pfe' and 'offline-pfe' cannot be both configured";
             junos:must "(!(\".. .. action disable-pfe\"))";
             junos:must-message "'reset-pfe' and 'disable-pfe' cannot be both configured";
           }
           enum "offline-pic" {
             description "Offline PICs associated with PFE on FPC";
           }
           enum "trap" {
             description "Raise FPC trap";
           }
           enum "offline-pfe" {
             description "Offline PFE on FPC";
             junos:must "(!(\".. .. action reset-pfe\"))";
             junos:must-message "'offline-pfe' and 'reset-pfe' cannot be both configured";
             junos:must "(!(\".. .. action disable-pfe\"))";
             junos:must-message "'offline-pfe' and 'disable-pfe' cannot be both configured";
           }
         }
       }
       uses apply-advanced;
     }
   }
   grouping chassis_mic_type {
     leaf name {
       description "MIC slot number";
       junos:cli-feature "nokeyword";
       type union {
         type string {
           pattern "<.*>|$.*";
         }
         type uint32;
       }
     }
     uses apply-advanced;
     leaf power {
       description "Power off MIC";
       type enumeration {
         enum "off" {
           description "Do not provide power to MIC";
         }
       }
     }
   }
   grouping chassis_pem_type {
     uses apply-advanced;
     leaf minimum {
       description "Minimum number of power supplies required for normal operation";
       type union {
         type string {
           pattern "<.*>|$.*";
         }
         type uint32;
       }
     }
     leaf input-current {
       description "Input current (Amps) in each feed ";
       default "60";
       type enumeration {
         enum "40" {
           description "40 Amps in each Feed";
           junos:must "((!(\"chassis pem feeds\") || \"chassis pem feeds 6\"))";
           junos:must-message "Must configured with 6 feeds";
         }
         enum "60" {
           description "60 Amps in each Feed";
         }
       }
     }
     container redundancy {
       description "PEM Source/Feed Redundancy configuration";
       uses apply-advanced;
       leaf source-redundancy {
         description "Toggle Source Redundancy for PEM";
         type empty;
       }
       container feed-redundancy {
         description "Toggle Feed Redundancy for a PEM slot";
         uses apply-advanced;
         list slot {
           key name;
           description "PEM Slot Number";
           leaf name {
             description "Select PEM slot";
             junos:cli-feature "nokeyword";
             type union {
               type string {
                 pattern "<.*>|$.*";
               }
               type uint32;
             }
           }
           uses apply-advanced;
         }
       }
     }
   }
   grouping chassis_pem_type_slot {
     leaf name {
       description "PEM slot number";
       junos:cli-feature "nokeyword";
       type string;
     }
     uses apply-advanced;
   }
   grouping chassis_pfe_type {
     description "PFE(Packet forwarding engine)";
     leaf name {
       description "PFE(Packet forwarding engine) identifier";
       junos:cli-feature "nokeyword";
       type union {
         type string {
           pattern "<.*>|$.*";
         }
         type uint32;
       }
     }
     uses apply-advanced;
     leaf node {
       description "PFE(Packet forwarding engine) global identifier";
       junos:must "(unique \"chassis fpc <*> pfe <*> node $$\")";
       junos:must-message "Duplicated node-id can not be configured";
       type union {
         type string {
           pattern "<.*>|$.*";
         }
         type uint64 {
           range "1 .. 18446744073709551615";
         }
       }
     }
     list core {
       key name;
       description "Core number";
       uses chassis_core_type;
     }
   }
   grouping chassis_core_type {
     leaf name {
       description "Core slot number";
       junos:cli-feature "nokeyword";
       type union {
         type string {
           pattern "<.*>|$.*";
         }
         type uint32;
       }
     }
     uses apply-advanced;
     list channel {
       key name;
       description "Channel number";
       uses chassis_core_channel_type;
     }
   }
   grouping chassis_core_channel_type {
     leaf name {
       description "Channel number";
       junos:cli-feature "nokeyword";
       type union {
         type string {
           pattern "<.*>|$.*";
         }
         type uint32;
       }
     }
     uses apply-advanced;
     container tunnel-services {
       description "Tunnel services";
       uses chassis_tunnel_services_type;
     }
   }
   grouping chassis_pic_type {
     leaf name {
       description "PIC slot number";
       junos:cli-feature "nokeyword";
       type union {
         type string {
           pattern "<.*>|$.*";
         }
         type uint32;
       }
     }
     uses apply-advanced;
     leaf alternate-speed-set {
       description "PIC run time mode configuration";
       type enumeration {
         enum "6x100g-1x400g" {
           description "6x100G + 400G mode";
         }
       }
     }
     leaf pic-mode {
       description "PIC mode configuration";
       type enumeration {
         enum "1G" {
           description "1GE mode";
         }
         enum "10G" {
           description "10GE mode";
         }
         enum "25G" {
           description "25GE mode";
         }
         enum "40G" {
           description "40GE mode";
         }
         enum "50G" {
           description "50GE mode";
         }
         enum "100G" {
           description "100GE mode";
         }
         enum "400G" {
           description "400GE mode";
         }
         enum "1G10G" {
           description "1/10GE mode";
         }
         enum "A-1X400G-1X100G-4X50G" {
           description "Port0(400G) Port2(100G) Port6-9(50G)";
         }
         enum "B-1X400G-2X100G-2X50G" {
           description "Port0(400G) Port2,4(100G) Port6,8(50G)";
         }
         enum "C-6X100G-2X50G" {
           description "Port0-5(100G) Port10,12(50G)";
         }
         enum "D-3X100G-8X50G" {
           description "Port0-2(100G) Port6-13(50G)";
         }
         enum "E-4X100G-6X50G" {
           description "Port0-3(100G) Port7,9-13(50G)";
         }
       }
     }
     container tunnel-services {
       presence "enable tunnel-services";
       junos:must "(!(\".. traffic-manager single-stream\"))";
       junos:must-message "Cannot configure tunnel-services if single-stream is configured";
       description "Tunnel services configuration";
       uses apply-advanced;
       leaf bandwidth {
         description "Amount of bandwidth reserved for tunnel service";
         type string;
       }
       leaf tunnel-only {
         description "Support only tunnel traffic";
         type empty;
       }
       container priority {
         presence "enable priority";
         junos:must "(!(\".. bandwidth\"))";
         junos:must-message "Priorities cannot be configured if bandwidth is specified under the tunnel-services hierarchy";
         description "Specify bandwidths with priorities";
         uses apply-advanced;
         container high {
           presence "enable high";
           description "High Priority";
           uses apply-advanced;
           leaf bandwidth {
             description "Amount of bandwidth reserved for tunnel service";
             type string;
           }
         }
         container medium {
           presence "enable medium";
           description "Medium Priority";
           uses apply-advanced;
           leaf bandwidth {
             description "Amount of bandwidth reserved for tunnel service";
             type string;
           }
         }
         container low {
           presence "enable low";
           description "Low Priority";
           uses apply-advanced;
           leaf bandwidth {
             description "Amount of bandwidth reserved for tunnel service";
             type string;
           }
         }
       }
       list tunnel-port {
         key name;
         ordered-by user;
         description "Tunnel port number";
         leaf name {
           description "Port number";
           junos:cli-feature "nokeyword";
           type union {
             type string {
               pattern "<.*>|$.*";
             }
             type uint32;
           }
         }
         uses apply-advanced;
         leaf bandwidth {
           description "Amount of bandwidth reserved for tunnel service";
           type string;
         }
       }
     }
     choice adaptive-or-monitoring {
       case case_1 {
       }
       case case_2 {
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
         enum "lan" {
           description "LAN mode";
         }
       }
     }
     container recovered-clock {
       junos:cli-feature "oneliner-plus";
       description "Select recovered clock for this port";
       uses apply-advanced;
       leaf port {
         description "Port Number";
         junos:must "(unique \"chassis fpc ${fpc} pic <*> recovered-clock\")";
         junos:must-message "Recovered-clock can be configured only on single pic/port";
         type union {
           type string {
             pattern "<.*>|$.*";
           }
           type uint32 {
             range "0 .. 47";
           }
         }
       }
       leaf channel {
         description "Channel Number";
         type union {
           type string {
             pattern "<.*>|$.*";
           }
           type uint32 {
             range "0 .. 3";
           }
         }
       }
     }
     leaf vtmapping {
       description "Virtual tunnel mapping mode";
       type enumeration {
         enum "klm" {
           description "KLM mode";
         }
         enum "itu-t" {
           description "ITU-T mode";
         }
       }
     }
     leaf no-concatenate {
       description "Do not concatenate channels";
       type empty;
     }
     leaf no-multi-rate {
       description "Disable multi-rate mode";
       type empty;
     }
     leaf aggregate-ports {
       description "Aggregate multiple ports on a PIC as a single port";
       type empty;
     }
     leaf power {
       description "Power off PIC";
       type enumeration {
         enum "off" {
           description "Do not provide power to PIC";
         }
       }
     }
     leaf pic-type {
       description "OID of PIC type to be configured";
       type string {
         junos:posix-pattern "^([.]?1|[a-zA-Z][a-zA-Z0-9]*)([.]([a-zA-Z]|[0-9]+))*$";
         junos:pattern-message "Must be an OID of the form 1.x.y.z... or objname[.x.y.z] where x, y, & z are either numbers or a single letter";
       }
     }
     container aggregated-devices {
       description "Aggregated devices configuration";
       uses apply-advanced;
       container ima {
         description "Aggregated device options for Inverse Multiplexing for ATM";
         uses apply-advanced;
         leaf device-count {
           description "Number of IMA groups";
           type union {
             type string {
               pattern "<.*>|$.*";
             }
             type uint32 {
               range "1 .. 42";
             }
           }
         }
       }
     }
     leaf sparse-dlcis {
       description "Run in sparse data-link connection identifier mode";
       type empty;
     }
     container q-pic-large-buffer {
       presence "enable q-pic-large-buffer";
       description "Run in large delay buffer mode";
       uses apply-advanced;
       choice buffer-type {
         case case_1 {
           leaf small-scale {
             description "Supports less number of interfaces";
             type empty;
           }
         }
         case case_2 {
           leaf large-scale {
             description "Supports large number of interfaces";
             type empty;
           }
         }
       }
     }
     container red-buffer-occupancy {
       description "Computation type for RED buffer occupancy";
       uses apply-advanced;
       container weighted-averaged {
         presence "enable weighted-averaged";
         description "Weighted-average computation";
         uses apply-advanced;
         leaf instant-usage-weight-exponent {
           description "Weight for instant buffer usage (negative exponent of 2)";
           type union {
             type uint8;
             type string {
               pattern "<.*>|$.*";
             }
           }
         }
       }
     }
     container traffic-manager {
       description "Configure traffic manager attributes";
       uses apply-advanced;
       leaf ingress-shaping-overhead {
         description "Number of CoS shaping overhead bytes in ingress";
         units "bytes";
         type union {
           type string {
             pattern "<.*>|$.*";
           }
           type int32 {
             range "-62 .. 192";
           }
         }
       }
       leaf egress-shaping-overhead {
         description "Number of CoS shaping overhead bytes in egress";
         units "bytes";
         type union {
           type string {
             pattern "<.*>|$.*";
           }
           type int32 {
             range "-62 .. 192";
           }
         }
       }
       leaf mode {
         description "Configure traffic manager mode";
         type enumeration {
           enum "egress-only" {
             description "Egress traffic manager enabled, ingress traffic manager disabled";
           }
           enum "session-shaping" {
             description "Enable egress session shaping";
           }
           enum "ingress-and-egress" {
             description "Enable the ingress and egress traffic managers";
           }
         }
       }
     }
     container idle-cell-format {
       description "ATM idle cell configuration";
       uses apply-advanced;
       leaf itu-t {
         description "ITU-T idle cell header format";
         type empty;
       }
       leaf payload-pattern {
         description "Payload pattern byte (0x00-0xff)";
         type string;
       }
     }
     container atm-l2circuit-mode {
       description "Enable ATM Layer 2 circuit transport mode";
       uses apply-advanced;
       choice mode_choice {
         case case_1 {
           leaf aal5 {
             description "ATM Layer 2 circuit AAL5 mode";
             type empty;
           }
         }
         case case_2 {
           leaf cell {
             description "ATM Layer 2 circuit cell mode";
             type empty;
           }
         }
         case case_3 {
           container trunk {
             presence "enable trunk";
             description "Set ATM Layer 2 circuit trunk mode";
             uses apply-advanced;
             choice trunk-mode {
               case case_1 {
                 container uni {
                   presence "enable uni";
                   description "ATM Layer 2 circuit user-to-network interface trunk mode";
                   uses apply-advanced;
                 }
               }
               case case_2 {
                 container nni {
                   presence "enable nni";
                   description "ATM Layer 2 circuit network-to-network interface trunk mode";
                   uses apply-advanced;
                 }
               }
             }
           }
         }
       }
     }
     leaf atm-cell-relay-accumulation {
       description "Enable ATM cell-relay accumulation mode";
       type empty;
     }
     leaf mlfr-uni-nni-bundles {
       description "Number of multilink Frame Relay UNI NNI (FRF.16) bundles to allocate on PIC";
       type union {
         type string {
           pattern "<.*>|$.*";
         }
         type uint32 {
           range "1 .. 255";
         }
       }
     }
     leaf mlfr-uni-nni-bundles-inline {
       description "Number of inline multilink frame relay UNI NNI bundles";
       type union {
         type string {
           pattern "<.*>|$.*";
         }
         type uint32 {
           range "1 .. 255";
         }
       }
     }
     container ct3 {
       description "CT3 NxDS0 PIC configuration";
       uses apply-advanced;
       list port {
         key name;
         description "CT3 port";
         uses ct3_port_type;
       }
     }
     container ce1 {
       description "CE1 NxDS0 PIC configuration";
       uses apply-advanced;
       list e1 {
         key name;
         description "E1 link";
         uses ce1_channel_type;
       }
     }
     list port-mirror-instance {
       key name;
       ordered-by user;
       max-elements 2;
       leaf name {
         description "Associate a port mirroring instance with the PIC";
         junos:cli-feature "nokeyword";
         junos:must "(!(\"forwarding-options port-mirroring instance $$ input-parameters-instance\"))";
         junos:must-message "Derived instance cannot be binded";
         junos:must "(((!(\"chassis network-services lan\") && (\"forwarding-options port-mirroring instance $$\" || \"forwarding-options analyzer $$\")) || \"chassis network-services lan\"))";
         junos:must-message "Referenced port-mirroring instance does not exist";
         type string {
           length "1 .. 64";
         }
       }
       uses apply-advanced;
     }
     list port {
       key name;
       description "Port number";
       uses chassis_pic_port_framing;
     }
     list port-range {
       key "port-range-low port-range-high";
       ordered-by user;
       description "Physical ports to channelize";
       leaf port-range-low {
         description "Port range low number";
         junos:cli-feature "nokeyword";
         type union {
           type string {
             pattern "<.*>|$.*";
           }
           type uint32;
         }
       }
       leaf port-range-high {
         description "Port range high number";
         junos:cli-feature "nokeyword";
         type union {
           type string {
             pattern "<.*>|$.*";
           }
           type uint32;
         }
       }
       uses apply-advanced;
       leaf short-reach-mode {
         description "Short reach mode (For ports 0..47)";
         type enumeration {
           enum "disable" {
             description "Disable";
           }
           enum "enable" {
             description "Enable";
           }
         }
       }
       leaf channel-speed {
         description "Port channel speed";
         type enumeration {
           enum "10g" {
             description "Set the port speed to 10G. This will restart PFE";
           }
           enum "25g" {
             description "Set the port speed to 25G.";
           }
           enum "50g" {
             description "Set the port speed to 50G.";
           }
           enum "disable-auto-speed-detection" {
             description "Disables automatic speed detection";
           }
         }
       }
     }
     container fibre-channel {
       description "Fibre channel configuration option";
       junos:cli-feature "oneliner-plus";
       uses chassis_fibre_channel_type;
     }
     container xe {
       junos:cli-feature "oneliner-plus";
       description "Ports configurable in 10G mode";
       uses apply-advanced;
       list port {
         key port-number;
         ordered-by user;
         description "Attribute port";
         leaf port-number {
           description "Port number";
           junos:cli-feature "nokeyword";
           type union {
             type string {
               pattern "<.*>|$.*";
             }
             type uint32;
           }
         }
         uses apply-advanced;
       }
       list port-range {
         key "port-range-low port-range-high";
         ordered-by user;
         description "Attribute port range";
         leaf port-range-low {
           description "Port range low number";
           junos:cli-feature "nokeyword";
           type union {
             type string {
               pattern "<.*>|$.*";
             }
             type uint32;
           }
         }
         leaf port-range-high {
           description "Port range high number";
           junos:cli-feature "nokeyword";
           type union {
             type string {
               pattern "<.*>|$.*";
             }
             type uint32;
           }
         }
         uses apply-advanced;
       }
     }
     container xle {
       junos:cli-feature "oneliner-plus";
       description "Ports configurable in 40G mode ";
       uses apply-advanced;
       list port {
         key port-number;
         ordered-by user;
         description "Attribute port";
         leaf port-number {
           description "Port number";
           junos:cli-feature "nokeyword";
           type union {
             type string {
               pattern "<.*>|$.*";
             }
             type uint32;
           }
         }
         uses apply-advanced;
       }
       list port-range {
         key "port-range-low port-range-high";
         ordered-by user;
         description "Attribute port range";
         leaf port-range-low {
           description "Port range low number";
           junos:cli-feature "nokeyword";
           type union {
             type string {
               pattern "<.*>|$.*";
             }
             type uint32;
           }
         }
         leaf port-range-high {
           description "Port range high number";
           junos:cli-feature "nokeyword";
           type union {
             type string {
               pattern "<.*>|$.*";
             }
             type uint32;
           }
         }
         uses apply-advanced;
       }
     }
     container fte {
       junos:cli-feature "oneliner-plus";
       description "Ports configurable in 40G HIGIG mode";
       uses apply-advanced;
       list port {
         key port-number;
         ordered-by user;
         description "Attribute port";
         leaf port-number {
           description "Port number";
           junos:cli-feature "nokeyword";
           type union {
             type string {
               pattern "<.*>|$.*";
             }
             type uint32;
           }
         }
         uses apply-advanced;
       }
       list port-range {
         key "port-range-low port-range-high";
         ordered-by user;
         description "Attribute port range";
         leaf port-range-low {
           description "Port range low number";
           junos:cli-feature "nokeyword";
           type union {
             type string {
               pattern "<.*>|$.*";
             }
             type uint32;
           }
         }
         leaf port-range-high {
           description "Port range high number";
           junos:cli-feature "nokeyword";
           type union {
             type string {
               pattern "<.*>|$.*";
             }
             type uint32;
           }
         }
         uses apply-advanced;
       }
     }
     leaf account-layer2-overhead {
       description "Account Layer2 overhead in egress and ingress IFD/IFL stats";
       type empty;
     }
     leaf subscriber-aware-services {
       description "Enable subscriber aware services";
       type empty;
     }
     leaf ptp-mode {
       description "Set hardware to run PTP BC applications.";
       type empty;
     }
     leaf cpu-port-access {
       description "Configure MUX to select cpu-port";
       type empty;
     }
     list port-group {
       key name;
       description "Port group number";
       leaf name {
         description "Port group number";
         junos:cli-feature "nokeyword";
         type union {
           type string {
             pattern "<.*>|$.*";
           }
           type uint32 {
             range "0 .. 3";
           }
         }
       }
       uses apply-advanced;
       leaf speed-group {
         description "Specify speed group";
         type enumeration {
           enum "high" {
             description "High speed group";
           }
           enum "low" {
             description "Low speed group";
           }
           enum "10g" {
             description "Supporting 10G/40G/4x10G with common speeds";
           }
         }
       }
     }
   }
   grouping ce1_channel_type {
     leaf name {
       description "E1 link number";
       junos:cli-feature "nokeyword";
       type union {
         type string {
           pattern "<.*>|$.*";
         }
         type uint32 {
           range "0 .. 9";
         }
       }
     }
     uses apply-advanced;
     list channel-group {
       key name;
       junos:cli-feature "oneliner";
       description "Define channel group";
       leaf name {
         description "Channel group number";
         junos:cli-feature "nokeyword";
         type union {
           type string {
             pattern "<.*>|$.*";
           }
           type uint32 {
             range "0 .. 23";
           }
         }
       }
       leaf timeslots {
         description "DS0 timeslots (1..31); for example, 1-3,4,9,22-24 (no spaces)";
         type string;
       }
     }
   }
   grouping chassis_fibre_channel_type {
     junos:cli-feature "oneliner-plus";
     description "Fibre channel configuration option";
     uses apply-advanced;
     list port {
       key name;
       ordered-by user;
       description "Fibre channel port";
       leaf name {
         description "Port number for fibre channel mode";
         junos:cli-feature "nokeyword";
         type union {
           type string {
             pattern "<.*>|$.*";
           }
           type uint32 {
             range "0 .. 47";
           }
         }
       }
       uses apply-advanced;
     }
     list port-range {
       key "port-range-low port-range-high";
       ordered-by user;
       description "Fibre channel port range";
       leaf port-range-low {
         description "Port range low number";
         junos:cli-feature "nokeyword";
         type union {
           type string {
             pattern "<.*>|$.*";
           }
           type uint32 {
             range "0 .. 47";
           }
         }
       }
       leaf port-range-high {
         description "Port range high number";
         junos:cli-feature "nokeyword";
         type union {
           type string {
             pattern "<.*>|$.*";
           }
           type uint32 {
             range "0 .. 47";
           }
         }
       }
       uses apply-advanced;
     }
   }
   grouping chassis_pic_port_framing {
     leaf name {
       description "Port number";
       junos:cli-feature "nokeyword";
       type union {
         type string {
           pattern "<.*>|$.*";
         }
         type uint32;
       }
     }
     uses apply-advanced;
     leaf short-reach-mode {
       description "Short reach mode (For ports 0...47)";
       type enumeration {
         enum "disable" {
           description "Disable";
         }
         enum "enable" {
           description "Enable";
         }
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
       }
     }
     leaf number-of-sub-ports {
       description "Number of subports per physical port";
       type union {
         type string {
           pattern "<.*>|$.*";
         }
         type uint32;
       }
     }
     leaf unused {
       description "Keep the port unused.";
       type empty;
     }
     leaf speed {
       description "Port speed";
       junos:must "(!((\".. .. pic-mode\" || \".. .. number-of-ports\")))";
       junos:must-message " speed config can neither co-exist with pic <> number-of-ports <> nor pic <> pic-mode config";
       type enumeration {
         enum "oc3-stm1" {
           description "OC3 or STM1";
         }
         enum "oc12-stm4" {
           description "OC12 or STM4";
         }
         enum "oc48-stm16" {
           description "OC48 or STM16";
         }
         enum "1g" {
           description "1GE-Gigabit Ethernet";
         }
         enum "10g" {
           description "Sets the interface mode to 10Gbps";
         }
         enum "25g" {
           description "Sets the interface mode to 25Gbps";
         }
         enum "40g" {
           description "Sets the interface mode to 40Gbps";
         }
         enum "100g" {
           description "Sets the interface mode to 100Gbps";
         }
         enum "50g" {
           description "Sets the interface mode to 50Gbps";
         }
         enum "200g" {
           description "Sets the interface mode to 200 Gbps";
         }
         enum "400g" {
           description "Sets the interface mode to 400Gbps";
         }
       }
     }
     leaf channel-speed {
       description "Port channel speed";
       type enumeration {
         enum "10g" {
           description "Set the port speed to 10G. This will restart PFE on some platforms.";
         }
         enum "25g" {
           description "Set the port speed to 25G.";
         }
         enum "50g" {
           description "Set the port speed to 50G.";
         }
         enum "disable-auto-speed-detection" {
           description "Disables automatic speed detection";
         }
       }
     }
     container forwarding-mode {
       description "PIC packet distribution mode - Brooklyn interop mode";
       uses apply-advanced;
       leaf sa-multicast {
         description "SA multicast mode - interop with 100G Brooklyn PIC";
         type empty;
       }
     }
     leaf no-mcast-replication {
       description "No multicast replication";
       type empty;
     }
     leaf no-temperature-monitoring {
       description "Disable empolicy";
       type empty;
     }
     leaf xcvr-power-off {
       description "Shutdown transceiver power";
       type empty;
     }
   }
   grouping chassis_redundancy_type {
     uses apply-advanced;
     list routing-engine {
       key name;
       description "Redundancy options for Routing Engines";
       uses chassis_rdd_re_type;
       junos:cli-feature "oneliner";
     }
     container failover {
       description "Failover to other Routing Engine";
       presence "enable failover";
       junos:cli-feature "oneliner-plus";
       uses chassis_rdd_failover_type;
     }
     leaf keepalive-time {
       description "Time before Routing Engine failover";
       units "seconds";
       junos:must "(!(\"chassis redundancy graceful-switchover\"))";
       junos:must-message "Graceful switchover configured, cannot change the default keepalive interval";
       type union {
         type string {
           pattern "<.*>|$.*";
         }
         type uint32 {
           range "2 .. 10000";
         }
       }
     }
     container graceful-switchover {
       description "Enable graceful switchover on supported hardware";
       presence "enable graceful-switchover";
       junos:must "(!(any \"chassis fpc <*> pic <*> monitoring-services application\"))";
       junos:must-message "Graceful Switchover is not supported on monitoring-services application";
       uses chassis_non_stop_forwarding_type;
     }
     leaf no-graceful-switchover {
       description "Disable graceful switchover on supported hardware";
       junos:must "(!((\"system node offline re0\" || \"system node offline re1\")))";
       junos:must-message "No-graceful-switchover can't be enabled if any RE is offline";
       type empty;
     }
   }
   grouping chassis_non_stop_forwarding_type {
     junos:must "((!(\"system inet6-backup-router\") || \"system inet6-backup-router destination\"))";
     junos:must-message "Please define destination subnet with the inet6-backup-router configuration";
     junos:must "((!(\"system backup-router\") || \"system backup-router destination\"))";
     junos:must-message "Please define destination subnet with the backup-router configuration";
     uses apply-advanced;
     container traceoptions {
       description "Graceful switchover trace options";
       status deprecated;
       uses apply-advanced;
       list flag {
         key name;
         ordered-by user;
         junos:cli-feature "oneliner";
         description "Tracing parameters";
         leaf name {
           junos:cli-feature "nokeyword";
           type enumeration {
             enum "update" {
               description "Trace state updates";
             }
             enum "all" {
               description "Trace everything";
             }
           }
         }
       }
     }
   }
   grouping chassis_rdd_failover_type {
     junos:cli-feature "oneliner-plus";
     uses apply-advanced;
     container category {
       description "Failover category";
       presence "enable category";
       uses chassis_rdd_fail_cat_type;
     }
     leaf on-loss-of-keepalives {
       description "Failover on loss of keepalives";
       type empty;
     }
     leaf on-re-to-fpc-stale {
       description "Failover on loss of communication between the re and fpc";
       type empty;
     }
     leaf on-disk-failure {
       description "Failover on disk failure";
       junos:must "((\"chassis redundancy failover on-loss-of-keepalives\" || \"chassis redundancy graceful-switchover\"))";
       junos:must-message "Option on-loss-of-keepalives or graceful-switchover must be set";
       type empty;
     }
     leaf not-on-disk-underperform {
       description "Prevent gstatd from initiating failovers in response to slow disks";
       type empty;
     }
     leaf disk-read-threshold {
       description "Read threshold (ms) on disk underperform monitoring";
       type union {
         type string {
           pattern "<.*>|$.*";
         }
         type uint32 {
           range "1000 .. 10000";
         }
       }
     }
     leaf disk-write-threshold {
       description "Write threshold (ms) on disk underperform monitoring";
       type union {
         type string {
           pattern "<.*>|$.*";
         }
         type uint32 {
           range "1000 .. 10000";
         }
       }
     }
     leaf on-loss-of-vm-host-connection {
       description "Failover on loss of vm host connection";
       type empty;
     }
     leaf on-mcontrol-slip {
       description "Failover on mastership control thread slip";
       type empty;
     }
   }
   grouping chassis_rdd_fail_cat_type {
     uses apply-advanced;
     container component-failure {
       description "Failover due to component failure";
       presence "enable component-failure";
       uses chassis_rdd_fail_cat_sev_type;
     }
     container software-failure {
       description "Failover due to software failure";
       presence "enable software-failure";
       uses chassis_rdd_fail_cat_sev_type;
     }
     container power-failure {
       description "Failover due to power failure";
       presence "enable power-failure";
       uses chassis_rdd_fail_cat_sev_type;
     }
     container clock-failure {
       description "Failover due to clock failure";
       presence "enable clock-failure";
       uses chassis_rdd_fail_cat_sev_type;
     }
     container link-failure {
       description "Failover due to link failure";
       presence "enable link-failure";
       uses chassis_rdd_fail_cat_sev_type;
     }
     container degraded-health {
       description "Failover due to degraded health";
       presence "enable degraded-health";
       uses chassis_rdd_fail_cat_sev_type;
     }
   }
   grouping chassis_rdd_fail_cat_sev_type {
     uses apply-advanced;
     container critical {
       description "Critical severity";
       presence "enable critical";
       uses chassis_rdd_fail_cat_sev_act_type;
     }
     container important {
       description "Important severity";
       presence "enable important";
       uses chassis_rdd_fail_cat_sev_act_type;
     }
   }
   grouping chassis_rdd_fail_cat_sev_act_type {
     uses apply-advanced;
     leaf disable {
       description "Disable action";
       type empty;
     }
   }
   grouping chassis_rdd_re_type {
     junos:cli-feature "oneliner";
     leaf name {
       description "Routing Engine slot number";
       junos:cli-feature "nokeyword";
       type union {
         type string {
           pattern "<.*>|$.*";
         }
         type uint32 {
           range "0 .. 1";
         }
       }
     }
     choice priority {
       case case_1 {
         leaf master {
           description "Master Routing Engine";
           type empty;
         }
       }
       case case_2 {
         leaf backup {
           description "Backup Routing Engine";
           type empty;
         }
       }
       case case_3 {
         leaf disabled {
           description "Routing Engine disabled";
           type empty;
         }
       }
     }
   }
   grouping chassis_routing_engine_type {
     uses apply-advanced;
     container on-disk-failure {
       description "Action to take when Routing Engine disk fails";
       junos:cli-feature "oneliner";
       uses chassis_re_on_disk_failure;
     }
     container disk {
       description "Action to take for Routing Engine disk";
       uses apply-advanced;
       leaf write-threshold-rate {
         description "Write threshold rate";
         default "4";
         units "MBPS";
         type union {
           type string {
             pattern "<.*>|$.*";
           }
           type uint32 {
             range "1 .. 20";
           }
         }
       }
       leaf write-threshold-duration {
         description "Write threshold duration";
         default "1000";
         units "seconds";
         type union {
           type string {
             pattern "<.*>|$.*";
           }
           type uint32 {
             range "300 .. 2592000";
           }
         }
       }
       leaf smart-check {
         description "Enable smart check command to disk";
         type empty;
       }
       list ssd-series {
         key name;
         ordered-by user;
         description "Specify the ssd vendor series";
         leaf name {
           description "SSD series name";
           junos:cli-feature "nokeyword";
           type string {
             length "1 .. 40";
           }
         }
         uses apply-advanced;
         list id {
           key name;
           ordered-by user;
           description "Attribute ids to monitor of this series type";
           max-elements 30;
           leaf name {
             description "SSD smart attribute id";
             junos:cli-feature "nokeyword";
             type union {
               type string {
                 pattern "<.*>|$.*";
               }
               type uint32 {
                 range "1 .. 255";
               }
             }
           }
           uses apply-advanced;
           leaf id-threshold {
             description "SSD smart attribute threshold";
             type union {
               type string {
                 pattern "<.*>|$.*";
               }
               type uint32 {
                 range "1 .. 4294967295";
               }
             }
           }
           leaf id-value {
             description "SSD attribute value";
             type enumeration {
               enum "raw" {
                 description "Raw value to be used for this smart id";
               }
               enum "norm" {
                 description "Normalised value to be used for this smart id";
               }
             }
           }
           leaf id-flag {
             description "SSD attribute flag";
             type enumeration {
               enum "low" {
                 description "Check if value is less than smart threshold";
               }
               enum "high" {
                 description "Check if value is greater than smart threshold";
               }
             }
           }
         }
       }
     }
   }
   grouping chassis_re_on_disk_failure {
     junos:cli-feature "oneliner";
     choice reboot_or_halt {
       case case_1 {
         leaf reboot {
           description "Reboot on disk failure";
           status deprecated;
           type empty;
         }
       }
       case case_2 {
         leaf disk-failure-action {
           type enumeration {
             enum "reboot" {
               description "Reboot on disk failure";
             }
             enum "halt" {
               description "Halt on disk failure";
             }
           }
         }
       }
     }
   }
   grouping chassis_sib_scope_category {
     description "Chassis SIB Error Category";
     uses apply-advanced;
     container category {
       description "SIB error category";
       uses chassis_sib_scope_category_type;
     }
   }
   grouping chassis_sib_scope_category_type {
     description "Chassis SIB Category level";
     uses apply-advanced;
     container functional {
       description "SIB functional category";
       uses chassis_sib_scope_category_error_type;
     }
     container memory {
       description "SIB memory category";
       uses chassis_sib_scope_category_error_type;
     }
     container io {
       description "SIB input-output category";
       uses chassis_sib_scope_category_error_type;
     }
     container storage {
       description "SIB storage category";
       uses chassis_sib_scope_category_error_type;
     }
     container switch {
       description "SIB switch category";
       uses chassis_sib_scope_category_error_type;
     }
     container processing {
       description "SIB processing category";
       uses chassis_sib_scope_category_error_type;
     }
   }
   grouping chassis_sib_scope_category_error_type {
     description "Chassis SIB Error level";
     uses apply-advanced;
     container fatal {
       description "SIB Fatal errors (default threshold = 1)";
       uses chassis_sib_error_level_type;
     }
     container major {
       description "SIB Major Level errors (default threshold = 1)";
       uses chassis_sib_error_level_type;
     }
     container minor {
       description "SIB Minor Level errors (default threshold = 10)";
       uses chassis_sib_error_level_type;
     }
   }
   grouping chassis_sib_error_level_type {
     uses apply-advanced;
     leaf threshold {
       description "Error count at which to take the action (0 - valid for minor only)";
       type union {
         type string {
           pattern "<.*>|$.*";
         }
         type uint32 {
           range "0 .. 1024";
         }
       }
     }
     list action {
       key name;
       ordered-by user;
       description "Configure the action for this level";
       leaf name {
         junos:cli-feature "nokeyword";
         type enumeration {
           enum "reset" {
             description "Reset device";
             junos:must "(!(\".. .. action offline\"))";
             junos:must-message "'reset' and 'offline' cannot be both configured";
           }
           enum "offline" {
             description "Offline device";
             junos:must "(!(\".. .. action reset\"))";
             junos:must-message "'offline' and 'reset' cannot be both configured";
           }
           enum "alarm" {
             description "Raise chassis alarm";
           }
           enum "get-state" {
             description "Retreive device state for debugging";
           }
           enum "log" {
             description "Log occurence to system log file";
           }
           enum "trap" {
             description "Raise trap";
           }
         }
       }
       uses apply-advanced;
     }
   }
   grouping chassis_sib_type {
     uses apply-advanced;
     list slot {
       key name;
       description "SIB slot number";
       leaf name {
         description "SIB slot number";
         junos:cli-feature "nokeyword";
         type union {
           type string {
             pattern "<.*>|$.*";
           }
           type uint32;
         }
       }
       uses apply-advanced;
       container error {
         description "Error level configuration for SIB";
         uses chassis_sib_error_type;
       }
       leaf power {
         description "Power SIBs on or off";
         type enumeration {
           enum "off" {
             description "Do not provide power to SIBs";
           }
           enum "on" {
             description "Provide power to SIBs";
           }
         }
       }
     }
     container power-off {
       description "Power off the SIB slot";
       uses apply-advanced;
       list slot {
         key name;
         ordered-by user;
         description "SIB slot number to be powered off";
         leaf name {
           description "SIB slot number to be offlined";
           junos:cli-feature "nokeyword";
           type union {
             type string {
               pattern "<.*>|$.*";
             }
             type uint32;
           }
         }
         uses apply-advanced;
       }
     }
   }
   grouping chassis_sib_error_type {
     description "Chassis SIB Error level";
     uses apply-advanced;
     container fatal {
       description "SIB Fatal errors (default threshold = 1)";
       uses chassis_sib_error_level_major_fatal;
     }
     container major {
       description "SIB Major Level errors (default threshold = 1)";
       uses chassis_sib_error_level_major_fatal;
     }
     container minor {
       description "SIB Minor Level errors (default threshold = 10)";
       uses chassis_sib_error_level_minor;
     }
     list override-cmerror {
       key name;
       ordered-by user;
       description "Error configuration override";
       max-elements 100;
       uses chassis_sib_cmerror_override_type;
       junos:cli-feature "nokeyword";
       junos:cli-feature "homogeneous";
     }
     container scope {
       description "Error scope";
       uses chassis_sib_scope_type;
     }
   }
   grouping chassis_sib_cmerror_override_type {
     junos:cli-feature "nokeyword";
     junos:cli-feature "homogeneous";
     description "Chassis SIB Error override";
     leaf name {
       description "Error identifier";
       junos:cli-feature "nokeyword";
       type string {
         length "1 .. 255";
         junos:posix-pattern "^(/[^/ ]+/[0-9]+(:[0-9]+)?(:[0-9]+)?)(/[^/ ]+/[0-9]+){3}/[^/ ]+$";
         junos:pattern-message "Invalid error identifier format";
       }
     }
     uses apply-advanced;
     leaf state {
       description "State";
       type enumeration {
         enum "disable" {
           description "Disable error";
         }
       }
     }
     leaf severity {
       description "Severity";
       type enumeration {
         enum "minor" {
           description "Minor Severity";
         }
         enum "major" {
           description "Major Severity";
         }
         enum "fatal" {
           description "Fatal Severity";
         }
       }
     }
   }
   grouping chassis_sib_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         junos:cli-feature "nokeyword";
         type enumeration {
           enum "reset" {
             description "Reset SIB";
             junos:must "(!(\".. .. action offline\"))";
             junos:must-message "'reset' and 'offline' cannot be both configured";
           }
           enum "offline" {
             description "Offline SIB";
             junos:must "(!(\".. .. action reset\"))";
             junos:must-message "'offline' and 'reset' cannot be both configured";
           }
           enum "alarm" {
             description "Raise SIB alarm";
           }
           enum "get-state" {
             description "Retreive SIB state for debugging";
           }
           enum "log" {
             description "Log occurence to system log file";
           }
           enum "trap" {
             description "Raise SIB trap";
           }
         }
       }
       uses apply-advanced;
     }
   }
   grouping chassis_sib_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         junos:cli-feature "nokeyword";
         type enumeration {
           enum "reset" {
             description "Reset SIB";
             junos:must "(!(\".. .. action offline\"))";
             junos:must-message "'reset' and 'offline' cannot be both configured";
           }
           enum "offline" {
             description "Offline SIB";
             junos:must "(!(\".. .. action reset\"))";
             junos:must-message "'offline' and 'reset' cannot be both configured";
           }
           enum "alarm" {
             description "Raise SIB alarm";
           }
           enum "get-state" {
             description "Retreive SIB state for debugging";
           }
           enum "log" {
             description "Log occurence to system log file";
           }
           enum "trap" {
             description "Raise SIB trap";
           }
         }
       }
       uses apply-advanced;
     }
   }
   grouping chassis_sib_scope_type {
     description "Chassis SIB Error Scope";
     uses apply-advanced;
     container board {
       description "Board level scope";
       uses chassis_sib_scope_category;
     }
     container switch {
       description "SIB scope ";
       uses chassis_sib_scope_category;
     }
   }
   grouping chassis_tunnel_services_type {
     uses apply-advanced;
     leaf bandwidth {
       description "Bandwidth reserved for tunnel service";
       type string;
     }
     leaf multicast {
       description "Multicast tunnel";
       type empty;
     }
   }
   grouping chassisd-redundancy-group-type {
     uses apply-advanced;
     container interface-type {
       uses apply-advanced;
       container redundant-logical-tunnel {
         description "Redundant logical tunnel interface group";
         uses apply-advanced;
         leaf device-count {
           description "Number of devices";
           type union {
             type string {
               pattern "<.*>|$.*";
             }
             type uint32 {
               range "1 .. 255";
             }
           }
         }
       }
       container redundant-virtual-tunnel {
         description "Redundant virtual tunnel interface group";
         uses apply-advanced;
         leaf device-count {
           description "Number of devices";
           type union {
             type string {
               pattern "<.*>|$.*";
             }
             type uint32 {
               range "1 .. 16";
             }
           }
         }
       }
     }
   }
   grouping chassisd_agg_container_type {
     uses apply-advanced;
     leaf device-count {
       description "Number of container devices";
       type union {
         type string {
           pattern "<.*>|$.*";
         }
         type uint32 {
           range "1 .. 128";
         }
       }
     }
   }
   grouping chassisd_agg_enet_type {
     uses apply-advanced;
     leaf device-count {
       description "Number of aggregated Ethernet devices";
       type union {
         type string {
           pattern "<.*>|$.*";
         }
         type uint32;
       }
     }
     container lacp {
       description "Global Link Aggregation Control Protocol configuration";
       uses apply-advanced;
       leaf system-priority {
         description "Priority of the system (0 ... 65535)";
         type string;
       }
       container link-protection {
         presence "enable link-protection";
         uses apply-advanced;
         leaf non-revertive {
           description "Don't revert links when better priority link comes up";
           type empty;
         }
       }
     }
   }
   grouping chassisd_agg_pos_type {
     uses apply-advanced;
     leaf device-count {
       description "Number of aggregated SONET devices";
       type union {
         type string {
           pattern "<.*>|$.*";
         }
         type uint32 {
           range "1 .. 64";
         }
       }
     }
   }
   grouping ct3_port_type {
     leaf name {
       description "CT3  L2NG_PRODUCTSport number";
       junos:cli-feature "nokeyword";
       type union {
         type string {
           pattern "<.*>|$.*";
         }
         type int32 {
           range "0 .. 1";
         }
       }
     }
     uses apply-advanced;
     list t1 {
       key name;
       description "T1 link";
       uses ct3_channel_type;
     }
   }
   grouping ct3_channel_type {
     leaf name {
       description "T1 link number";
       junos:cli-feature "nokeyword";
       type union {
         type string {
           pattern "<.*>|$.*";
         }
         type int32 {
           range "0 .. 27";
         }
       }
     }
     uses apply-advanced;
     list channel-group {
       key name;
       junos:cli-feature "oneliner";
       description "Define channel group";
       leaf name {
         description "Channel group number";
         junos:cli-feature "nokeyword";
         type union {
           type string {
             pattern "<.*>|$.*";
           }
           type uint32 {
             range "0 .. 7";
           }
         }
       }
       leaf timeslots {
         description "DS0 timeslots (1..24); for example, 1-3,4,9,22-24 (no spaces)";
         type string;
       }
     }
   }
   grouping macro-data-type {
     junos:cli-feature "nokeyword";
     junos:cli-feature "homogeneous";
     junos:cli-feature "oneliner";
     leaf name {
       description "Keyword part of the keyword-value pair";
       junos:cli-feature "nokeyword";
       type string;
     }
     leaf value {
       description "Value part of the keyword-value pair";
       junos:cli-feature "nokeyword";
       type string;
     }
   }
   grouping redundancy-group-type {
     junos:cli-feature "nokeyword";
     junos:cli-feature "homogeneous";
     description "Redundancy-group provisioning";
     leaf name {
       description "Redundancy-group name";
       junos:cli-feature "nokeyword";
       type string {
         length "2 .. 64";
         junos:posix-pattern "^[[:alpha:]][[:alnum:]_.-]+$";
         junos:pattern-message "Must be a string of length at least 2 beginning with a letter and consisting of letters, numbers, periods, dashes, and underscores";
       }
     }
     uses apply-advanced;
     leaf redundancy-group-id {
       description "Redundancy Group ID";
       junos:must "((!((any \"protocols iccp peer <*> redundancy-group-id-list <*>\" || any \"logical-systems <*> protocols iccp peer <*> redundancy-group-id-list <*>\")) || (any \"protocols iccp peer <*> redundancy-group-id-list $$\" || any \"logical-systems <*> protocols iccp peer <*> redundancy-group-id-list $$\")))";
       junos:must-message "The redundancy group id must match with one defined at <protocols iccp peer redundancy-group-id-list> and must be less than 256";
       junos:must "(unique \"chassis satellite-management redundancy-groups <*> redundancy-group-id $$\")";
       junos:must-message "Redundancy-group-id has to be unique";
       type union {
         type string {
           pattern "<.*>|$.*";
         }
         type uint32 {
           range "1 .. 255";
         }
       }
     }
     container protocol {
       description "Redundancy-group Protocol";
       uses apply-advanced;
       container evpn {
         description "EVPN Redundancy Group";
         uses apply-advanced;
         leaf-list peer-ip {
           ordered-by user;
           description "Peer chassis IPs for EVPN Cluster";
           junos:must "(!(any \"chassis satellite-management redundancy-groups <*> peer-chassis-id <*>\"))";
           junos:must-message "peer-chassis-id configuration invalid for EVPN redundancy-group protocol";
           type jt:ipv4addr;
         }
         leaf local-ip {
           description "Local chassis IP for EVPN Cluster";
           type jt:ipv4addr;
         }
         leaf routing-instance {
           description "Name of routing instance for EVPN Cluster";
           type string;
         }
       }
     }
     list peer-chassis-id {
       key name;
       ordered-by user;
       description "Peer Chassis ID";
       leaf name {
         description "Peer chassis identifier";
         junos:cli-feature "nokeyword";
         junos:must "(unique \"satellite-management redundancy-groups <*> peer-chassis-id $$\")";
         junos:must-message "Peer chassis ID must be unique";
         junos:must "(!(\"chassis satellite-management redundancy-groups chassis-id $$\"))";
         junos:must-message "Peer chassis ID can't be same as local chassis ID";
         type union {
           type string {
             pattern "<.*>|$.*";
           }
           type uint32 {
             range "1 .. 4";
           }
         }
       }
       uses apply-advanced;
       leaf no-auto-vlan-provisioning {
         description "Disable auto VLAN provisioning on inter-chassis-link";
         type empty;
       }
       leaf inter-chassis-link {
         description "ICL interface name";
         junos:must "((((\"interfaces $$ unit $$={0} family bridge interface-mode trunk\" || \"interfaces $$ unit $$={0} family ethernet-switching interface-mode trunk\") && !(\" .. no-auto-vlan-provisioning\")) || \" .. no-auto-vlan-provisioning\"))";
         junos:must-message "bridge or ethernet-switching family with unit 0 must be present for ICL trunk interface if auto-vlan-provisioning is enabled";
         junos:must "(\"interfaces $$\")";
         junos:must-message "ICL interface must be defined in the [edit interfaces] hierarchy";
         junos:must "(!(\"interfaces $$ cascade-port\"))";
         junos:must-message "ICL interface can't be provisioned as cascade-port";
         type union {
           type jt:interface-device;
           type string {
             pattern "<.*>|$.*";
           }
         }
       }
       leaf no-auto-iccp-provisioning {
         description "Disable auto ICCP provisioning";
         junos:must "(any \"protocols iccp peer <*>\")";
         junos:must-message "ICCP configuration must be present if auto ICCP provisioning is disabled";
         type empty;
       }
       leaf session-establishment-hold-time {
         description "Time within which connection must succeed with this peer";
         units "seconds";
         type union {
           type string {
             pattern "<.*>|$.*";
           }
           type uint32 {
             range "45 .. 600";
           }
         }
       }
       container liveness-detection {
         presence "enable liveness-detection";
         description "Bidirectional Forwarding Detection options for the peer";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
       }
       leaf authentication-key {
         description "MD5 authentication key";
         type string {
           length "1 .. 126";
         }
       }
       container traceoptions {
         description "Trace options for ICCP";
         uses apply-advanced;
         leaf no-remote-trace {
           description "Disable remote tracing";
           junos:must "(\"system tracing\")";
           junos:must-message "'no-remote-trace' is valid only when [system tracing] is configured";
           type empty;
         }
         container file {
           junos:cli-feature "oneliner";
           description "Trace file information";
           leaf filename {
             description "Name of file in which to write trace information";
             junos:cli-feature "nokeyword";
             type string {
               length "1 .. 1024";
               junos:posix-pattern "![/ %]";
               junos:pattern-message "Must not contain \'/\', % or a space";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           junos:cli-feature "oneliner";
           description "Trace flag information";
           leaf name {
             junos:cli-feature "nokeyword";
             type enumeration {
               enum "error" {
                 description "Trace all errors";
               }
               enum "event" {
                 description "Trace all events";
               }
               enum "packet" {
                 description "Trace all packets";
               }
               enum "pipe" {
                 description "Trace pipe messages";
               }
               enum "pipe-detail" {
                 description "Trace pipe messages in detail";
               }
               enum "all" {
                 description "Trace everything";
               }
             }
           }
         }
       }
     }
     leaf-list satellite {
       ordered-by user;
       description "Satellite slot-id or range or all";
       type string {
         length "1 .. 100";
       }
     }
     leaf system-mac-address {
       description "System MAC address";
       type jt:mac-unicast;
     }
     list cluster {
       key name;
       description "Cluster member of redundancy-group";
       leaf name {
         description "Cluster name";
         junos:cli-feature "nokeyword";
         junos:must "(\"chassis satellite-management cluster $$\")";
         junos:must-message "Cluster must be defined";
         type string;
       }
       uses apply-advanced;
     }
   }
   grouping satellite-bridge-filter {
     leaf name {
       description "Filter name";
       junos:cli-feature "nokeyword";
       type string {
         junos:posix-pattern "!^((__.*)|(.{65,}))$";
         junos:pattern-message "Must be a non-reserved string of 64 characters or less";
       }
     }
     uses apply-advanced;
     list term {
       key name;
       ordered-by user;
       description "Define a firewall term";
       leaf name {
         description "Term name";
         junos:cli-feature "nokeyword";
         type string {
           junos:posix-pattern "!^((__.*)|(.{65,}))$";
           junos:pattern-message "Must be a non-reserved string of 64 characters or less";
         }
       }
       uses apply-advanced;
       container from {
         description "Define match criteria";
         uses apply-advanced;
         list source-mac-address {
           key name;
           ordered-by user;
           description "Match MAC source address";
           uses firewall_mac_addr_object;
           junos:cli-feature "homogeneous";
           junos:cli-feature "oneliner";
         }
         list destination-mac-address {
           key name;
           ordered-by user;
           description "Match MAC destination address";
           uses firewall_mac_addr_object;
           junos:cli-feature "homogeneous";
           junos:cli-feature "oneliner";
         }
         list ip-source-address {
           key name;
           ordered-by user;
           description "Match IP source address";
           uses firewall_addr_object;
           junos:cli-feature "homogeneous";
           junos:cli-feature "oneliner";
         }
         list ip-destination-address {
           key name;
           ordered-by user;
           description "Match IP destination address";
           uses firewall_addr_object;
           junos:cli-feature "homogeneous";
           junos:cli-feature "oneliner";
         }
         choice ip-protocol_choice {
           case case_1 {
             leaf-list ip-protocol {
               ordered-by user;
               type string;
             }
           }
           case case_2 {
             leaf-list ip-protocol-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
       }
       container then {
         junos:cli-feature "oneliner-plus";
         description "Action to take if the 'from' condition is matched";
         uses apply-advanced;
         choice designation {
           case case_1 {
             leaf accept {
               description "Accept the packet";
               type empty;
             }
           }
           case case_2 {
             leaf discard {
               description "Discard the packets";
               type empty;
             }
           }
         }
         leaf next-hop-group {
           description "Use specified next-hop group";
           junos:must "((\"policy-options satellite-policies port-group-alias $$\" || \"policy-options satellite-policies chassis-group-alias $$\"))";
           junos:must-message "port-group-alias or chassis-group-alias not defined";
           type string;
         }
       }
     }
   }
   grouping firewall_addr_object {
     junos:cli-feature "homogeneous";
     junos:cli-feature "oneliner";
     leaf name {
       description "Prefix to match";
       junos:cli-feature "nokeyword";
       type jt:ipv4prefix;
     }
     leaf except {
       description "Match address not in this prefix";
       type empty;
     }
   }
   grouping firewall_mac_addr_object {
     junos:cli-feature "homogeneous";
     junos:cli-feature "oneliner";
     leaf name {
       description "MAC address to match";
       junos:cli-feature "nokeyword";
       type jt:mac-addr-prefix;
     }
     leaf except {
       description "Match MAC address not in this range";
       type empty;
     }
   }
   grouping upgrade-group-type {
     junos:cli-feature "nokeyword";
     junos:cli-feature "homogeneous";
     description "Upgrade group";
     leaf name {
       description "Upgrade group name";
       junos:cli-feature "nokeyword";
       type string {
         length "2 .. 64";
         junos:posix-pattern "![^a-zA-Z0-9_-]|^[^a-zA-Z]|(^(all|.{64,}|.{0,1})$)";
         junos:pattern-message "Must be a string of length at least 2 beginning with a letter and consisting of letters, numbers, periods, dashes, and underscores. Must not be \'all\'";
       }
     }
     uses apply-advanced;
     leaf-list satellite {
       ordered-by user;
       description "Satellite slot-id or range or all";
       type string {
         length "1 .. 100";
       }
     }
   }
 }
