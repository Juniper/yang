/*
 * Copyright (c) 2026 Juniper Networks, Inc.
 * All rights reserved.
 */
 module junos-qfx-conf-dynamic-profiles {
   namespace "http://yang.juniper.net/junos-qfx/conf/dynamic-profiles";

   prefix jc-dynamic-profiles;

   import junos-common-ddl-extensions {
     prefix junos;
     revision-date 2026-01-01;
   }

   import junos-common-types {
     prefix jt;
     revision-date 2026-01-01;
   }

   import junos-qfx-conf-root {
     prefix jc;
     revision-date 2026-01-01;
   }

   organization "Juniper Networks, Inc.";

   contact "yang-support@juniper.net";

   description "Junos dynamic-profiles configuration module";

   revision 2026-01-01 {
     description "Junos: 26.2R1.7";
   }

   augment /jc:configuration {
     uses dynamic-profiles-group;
   }
   augment /jc:configuration/jc:groups {
     uses dynamic-profiles-group;
   }
   grouping dynamic-profiles-group {
     list dynamic-profiles {
       key name;
       ordered-by user;
       description "Dynamic profiles configuration";
       uses juniper-dynamic-profile-object;
       junos:cli-feature "homogeneous";
     }
   }
   grouping juniper-dynamic-profile-object {
     junos:cli-feature "homogeneous";
     leaf name {
       description "Name for dynamic profile";
       junos:cli-feature "nokeyword";
       type string {
         length "1 .. 80";
       }
     }
     uses apply-advanced;
     leaf version-alias {
       description "Dynamic profile version alias, transmitted to RADIUS during authentication";
       type string {
         length "1 .. 63";
       }
     }
     list variables {
       key name;
       ordered-by user;
       description "Dynamic variable configuration";
       uses juniper-dynamic-variable-object;
       junos:cli-feature "homogeneous";
       junos:cli-feature "oneliner-plus";
     }
     container predefined-variable-defaults {
       description "Assign default values to predefined variables";
       uses apply-advanced;
       container aggregation-interface-set-name {
         presence "enable aggregation-interface-set-name";
         junos:cli-feature "oneliner-plus";
         description "Default for junos-aggregation-interface-set-name";
         uses apply-advanced;
         choice def-value {
           case case_1 {
             leaf default-value {
               description "Default value for junos-aggregation-interface-set-name";
               junos:cli-feature "nokeyword";
               type string;
             }
           }
           case case_2 {
             leaf equals {
               description "Computable expression of dynamic profile variables";
               type string;
             }
           }
         }
       }
       container interface-set-name {
         presence "enable interface-set-name";
         junos:cli-feature "oneliner-plus";
         description "Default for junos-interface-set-name";
         uses apply-advanced;
         choice def-value {
           case case_1 {
             leaf default-value {
               description "Default value for junos-interface-set-name";
               junos:cli-feature "nokeyword";
               type string;
             }
           }
           case case_2 {
             leaf equals {
               description "Computable expression of dynamic profile variables";
               type string;
             }
           }
         }
       }
       container default-interface-set-name {
         presence "enable default-interface-set-name";
         junos:cli-feature "oneliner-plus";
         description "Default for junos-default-interface-set-name";
         uses apply-advanced;
         leaf equals {
           description "Computable expression of dynamic profile variables";
           type string;
         }
       }
       container phy-ifd-interface-set-name {
         presence "enable phy-ifd-interface-set-name";
         junos:cli-feature "oneliner-plus";
         description "Default for junos-phy-ifd-interface-set-name";
         uses apply-advanced;
         choice def-value {
           case case_1 {
             leaf default-value {
               description "Default value for junos-phy-ifd-interface-set-name";
               junos:cli-feature "nokeyword";
               type string;
             }
           }
           case case_2 {
             leaf equals {
               description "Computable expression of dynamic profile variables";
               type string;
             }
           }
         }
       }
       container phy-ifd-underlying-intf-set-name {
         presence "enable phy-ifd-underlying-intf-set-name";
         junos:cli-feature "oneliner-plus";
         description "Default for junos-phy-ifd-underlying-intf-set-name";
         uses apply-advanced;
         choice def-value {
           case case_1 {
             leaf default-value {
               description "Default value for junos-phy-ifd-underlying-intf-set-name";
               junos:cli-feature "nokeyword";
               type string;
             }
           }
           case case_2 {
             leaf equals {
               description "Computable expression of dynamic profile variables";
               type string;
             }
           }
         }
       }
       container cos-excess-rate {
         junos:cli-feature "oneliner-plus";
         description "Default for junos-cos-excess-rate";
         uses apply-advanced;
         leaf proportion {
           description "Excess rate as proportion";
           type union {
             type string {
               pattern "<.*>|$.*";
             }
             type uint32 {
               range "0 .. 1000";
             }
           }
         }
         leaf percent {
           description "Excess rate as percentage";
           type union {
             type string {
               pattern "<.*>|$.*";
             }
             type uint32 {
               range "1 .. 100";
             }
           }
         }
       }
       container cos-excess-rate-high {
         junos:cli-feature "oneliner-plus";
         description "Default for junos-cos-excess-rate-high";
         uses apply-advanced;
         leaf proportion {
           description "Excess rate as proportion";
           type union {
             type string {
               pattern "<.*>|$.*";
             }
             type uint32 {
               range "0 .. 1000";
             }
           }
         }
         leaf percent {
           description "Excess rate as percentage";
           type union {
             type string {
               pattern "<.*>|$.*";
             }
             type uint32 {
               range "1 .. 100";
             }
           }
         }
       }
       container cos-excess-rate-low {
         junos:cli-feature "oneliner-plus";
         description "Default for junos-cos-excess-rate-low";
         uses apply-advanced;
         leaf proportion {
           description "Excess rate as proportion";
           type union {
             type string {
               pattern "<.*>|$.*";
             }
             type uint32 {
               range "0 .. 1000";
             }
           }
         }
         leaf percent {
           description "Excess rate as percentage";
           type union {
             type string {
               pattern "<.*>|$.*";
             }
             type uint32 {
               range "1 .. 100";
             }
           }
         }
       }
       container cos-scheduler-tx {
         junos:cli-feature "oneliner-plus";
         description "Default for junos-cos-scheduler-tx";
         uses apply-advanced;
         leaf rate {
           description "Transmit rate as rate";
           type string;
         }
         leaf percent {
           description "Transmit rate as percentage";
           type union {
             type string {
               pattern "<.*>|$.*";
             }
             type uint32 {
               range "0 .. 100";
             }
           }
         }
       }
       container cos-scheduler-bs {
         junos:cli-feature "oneliner-plus";
         description "Default for junos-cos-scheduler-bs";
         uses apply-advanced;
         leaf percent {
           description "Buffer size as percentage";
           type union {
             type string {
               pattern "<.*>|$.*";
             }
             type uint32 {
               range "0 .. 100";
             }
           }
         }
         leaf temporal {
           description "Buffer size as temporal";
           units "microseconds";
           type union {
             type uint32;
             type string {
               pattern "<.*>|$.*";
             }
           }
         }
         leaf temporal-absolute {
           description "Absolute temporal value";
           units "bytes";
           type string;
         }
       }
       container cos-scheduler-shaping-rate {
         junos:cli-feature "oneliner-plus";
         description "Default for junos-cos-scheduler-shaping-rate";
         uses apply-advanced;
         leaf rate {
           description "Shaping rate as rate";
           units "bits per second";
           type string;
         }
         leaf percent {
           description "Shaping rate as percentage";
           type union {
             type string {
               pattern "<.*>|$.*";
             }
             type uint32 {
               range "1 .. 100";
             }
           }
         }
       }
       list other-variables {
         key name;
         ordered-by user;
         uses base-default-variable-object;
         junos:cli-feature "nokeyword";
         junos:cli-feature "homogeneous";
         junos:cli-feature "oneliner-plus";
       }
     }
     container routing-instances {
       description "Routing instance configuration";
       uses apply-advanced;
       list instance {
         key name;
         ordered-by user;
         junos:cli-feature "nokeyword";
         junos:cli-feature "homogeneous";
         leaf name {
           junos:cli-feature "nokeyword";
           type enumeration {
             enum "$junos-routing-instance" {
               description "Dynamic profile routing instance name";
             }
           }
         }
         uses apply-advanced;
         list interface {
           key name;
           description "Interface name for this routing instance";
           leaf name {
             junos:cli-feature "nokeyword";
             junos:must "((!(\".. .. protocols evpn esi\") || \"interfaces $$ esi df-election-granularity per-evi\"))";
             junos:must-message "IFL must have df-election-granularity knob set to per-evi";
             junos:must "((!(\"interfaces $$-IFL etree-ac-role\") || \".. .. protocols evpn evpn-etree\"))";
             junos:must-message "etree must be enabled under routing-instance";
             junos:must "(!((\"interfaces $$-IFL family bridge interface-mode\" && \".. .. instance-type evpn\")))";
             junos:must-message "access/trunk interfaces are not allowed in evpn instance";
             junos:must "((!((\"interfaces $$-IFL vlan-id-list\" || \"interfaces $$-IFL vlan-tags inner-list\")) || !((\".. .. vlan-id\" || \".. .. vlan-tags\"))))";
             junos:must-message "interface with vlan-id-list/inner-list cannot be added to routing-instance with a vlan-id/vlan-tags configured";
             junos:must "((!((\"interfaces $$-IFL family bridge interface-mode\" || \"interfaces $$-IFL family ethernet-switching interface-mode\")) || (\".. .. instance-type virtual-switch\" || \".. .. instance-type mac-vrf\")))";
             junos:must-message "Interface with 'interface-mode' is allowed only in a virtual-switch or mac-vrf instance";
             junos:must "((!(\".. .. instance-type virtual-switch\") || (!(\"interfaces $$-IFL family inet\") && !(\"interfaces $$-IFL family inet6\"))))";
             junos:must-message "Only layer-2 interface is allowed in a virtual-switch";
             junos:must "((!(\"interfaces $$-IFL vlan-id-range\") || (\".. .. instance-type vpls\" || (\".. .. instance-type evpn\" || \"security forwarding-options mode tap interface $$\"))))";
             junos:must-message "vlan-id-range is specified for this logical interface; the routing instance must be of type vpls or evpn or in Security TAP mode";
             junos:must "(((\".. .. vlan-id all\" && \"interfaces $$-IFL input-vlan-map pop\") || (\".. .. vlan-id inner-all\" || (!((\".. .. vlan-id\" || \".. .. vlan-tags\")) || (!((\"interfaces $$-IFL input-vlan-map\" || \"interfaces $$-IFL output-vlan-map\")) || (\".. .. no-normalization\" || \".. .. bridge-options no-normalization\"))))))";
             junos:must-message "interface with input/output vlan-maps cannot be added to a routing-instance with a vlan-id/vlan-tags configured";
             junos:must "((!(\"interfaces $$-IFL vlan-tags inner-range\") || ((\".. .. vlan-id all\" || \".. .. vlan-id inner-all\") || (\".. .. no-normalization\" || \".. .. bridge-options no-normalization\"))))";
             junos:must-message "vlan-tags inner-range is specified for this logical interface; 'vlan-id all' or 'vlan-id inner-all' should also be enabled";
             junos:must "(!((\"interfaces $$-IFL family ethernet-switching\" && \".. instance-type virtual-switch\")))";
             junos:must-message "Interface with family ethernet-switching is not allowed in this routing instance type";
             type string;
           }
           uses apply-advanced;
           choice mode {
             case case_1 {
               leaf any {
                 description "Interface used for both unicast and multicast traffic";
                 type empty;
               }
             }
             case case_2 {
               leaf unicast {
                 description "Interface used for unicast traffic only";
                 type empty;
               }
             }
             case case_3 {
               leaf multicast {
                 description "Interface used for multicast traffic only";
                 type empty;
               }
             }
           }
           leaf primary {
             description "Preferred multicast vt interface for the routing-instance";
             junos:must "(!(\".. unicast\"))";
             junos:must-message "'primary' option can not be configured for unicast interface";
             junos:must "((\".. .. instance-type vrf\" || \".. .. instance-type mpls-internet-multicast\"))";
             junos:must-message "'primary' option can only be configured for instance-type 'vrf' or 'mpls-internet-multicast'";
             type empty;
           }
           leaf protect-interface {
             description "Name of protect interface";
             junos:must "(\"interfaces $$\")";
             junos:must-message "Interface must be part of this routing instance";
             junos:must "(!(\"interfaces ${inter_name} esi\"))";
             junos:must-message "ESI can not be configured for protect interface";
             junos:must "(\"routing-instances ${instance} protocols evpn\")";
             junos:must-message "Protocol EVPN must be configured in the evpn instance";
             type union {
               type jt:interface-name;
               type string {
                 pattern "<.*>|$.*";
               }
             }
           }
         }
         container routing-options {
           description "Protocol-independent routing option configuration";
           uses apply-advanced;
           list rib {
             key name;
             description "Routing table options";
             leaf name {
               description "Routing table name";
               junos:cli-feature "nokeyword";
               type string;
             }
             uses apply-advanced;
             container static {
               description "Static routes";
               uses apply-advanced;
               leaf rib-group {
                 description "Routing table group";
                 type string;
               }
               container defaults {
                 description "Global route options";
                 uses apply-advanced;
                 choice retain-choice {
                   leaf retain {
                     description "Always keep route in forwarding table";
                     junos:must "(!(\".. resolve\"))";
                     junos:must-message "Must not specify resolve with retain";
                     type empty;
                   }
                   leaf no-retain {
                     description "Don't always keep route in forwarding table";
                     junos:must "(!(\".. resolve\"))";
                     junos:must-message "Must not specify resolve with retain";
                     type empty;
                   }
                 }
                 choice install-choice {
                   leaf install {
                     description "Install route into forwarding table";
                     type empty;
                   }
                   leaf no-install {
                     description "Don't install route into forwarding table";
                     type empty;
                   }
                 }
                 choice readvertise-choice {
                   leaf readvertise {
                     description "Mark route as eligible to be readvertised";
                     type empty;
                   }
                   leaf no-readvertise {
                     description "Don't mark route as eligible to be readvertised";
                     type empty;
                   }
                 }
                 choice resolve-choice {
                   leaf resolve {
                     description "Allow resolution of indirectly connected next hops";
                     type empty;
                   }
                   leaf no-resolve {
                     description "Don't allow resolution of indirectly connected next hops";
                     type empty;
                   }
                 }
                 leaf explicit-null {
                   description "Allows service label to be popped and will lookup nexthop-table inet6.0";
                   junos:must "(\".. resolve\")";
                   junos:must-message "Requires resolve to be configured";
                   type empty;
                 }
                 choice longest-match-choice {
                   leaf longest-match {
                     description "Always use longest prefix match to resolve next hops";
                     junos:must "(\".. resolve\")";
                     junos:must-message "Requires resolve to be configured";
                     type empty;
                   }
                   leaf no-longest-match {
                     description "Don't always use longest prefix match to resolve next hops";
                     junos:must "(\".. resolve\")";
                     junos:must-message "Requires resolve to be configured";
                     type empty;
                   }
                 }
                 choice passive_flag {
                   case case_1 {
                     leaf active {
                       description "Remove inactive route from forwarding table";
                       type empty;
                     }
                   }
                   case case_2 {
                     leaf passive {
                       description "Retain inactive route in forwarding table";
                       type empty;
                     }
                   }
                 }
                 container metric {
                   description "Metric value";
                   presence "enable metric";
                   junos:cli-feature "oneliner";
                   uses rib_static_metric_type;
                 }
                 container metric2 {
                   description "Metric value 2";
                   presence "enable metric2";
                   junos:cli-feature "oneliner";
                   uses rib_static_metric_type;
                 }
                 container metric3 {
                   description "Metric value 3";
                   presence "enable metric3";
                   junos:cli-feature "oneliner";
                   uses rib_static_metric_type;
                 }
                 container metric4 {
                   description "Metric value 4";
                   presence "enable metric4";
                   junos:cli-feature "oneliner";
                   uses rib_static_metric_type;
                 }
                 container tag {
                   description "Tag string";
                   presence "enable tag";
                   junos:cli-feature "oneliner";
                   uses rib_static_metric_type;
                 }
                 container tag2 {
                   description "Tag string 2";
                   presence "enable tag2";
                   junos:cli-feature "oneliner";
                   uses rib_static_metric_type;
                 }
                 container preference {
                   description "Preference value";
                   presence "enable preference";
                   junos:cli-feature "oneliner";
                   uses rib_static_metric_type;
                 }
                 container preference2 {
                   description "Preference value 2";
                   presence "enable preference2";
                   junos:cli-feature "oneliner";
                   uses rib_static_metric_type;
                 }
                 container color {
                   description "Color (preference) value";
                   presence "enable color";
                   junos:cli-feature "oneliner";
                   uses rib_static_metric_type;
                 }
                 container color2 {
                   description "Color (preference) value 2";
                   presence "enable color2";
                   junos:cli-feature "oneliner";
                   uses rib_static_metric_type;
                 }
                 leaf-list community {
                   ordered-by user;
                   description "BGP community identifier";
                   type jt:community;
                 }
                 container as-path {
                   description "Autonomous system path";
                   uses apply-advanced;
                   leaf path {
                     description "Autonomous system path";
                     type string;
                   }
                   leaf origin {
                     type enumeration {
                       enum "igp" {
                         description "Path originated in the local IGP";
                       }
                       enum "egp" {
                         description "Path originated in another AS";
                       }
                       enum "incomplete" {
                         description "Path was learned by some other means";
                       }
                     }
                   }
                   leaf atomic-aggregate {
                     description "Add ATOMIC_AGGREGATE path attribute to route";
                     type empty;
                   }
                   container aggregator {
                     presence "enable aggregator";
                     description "Add AGGREGATOR path attribute to route";
                   }
                   leaf as-number {
                     description " Autonomous system number in plain number or 'higher 16bits'.'Lower 16 bits' (asdot notation) format";
                     junos:cli-feature "nokeyword";
                     type string {
                       junos:posix-pattern "^[0-9]+(.[0-9]+)?$";
                       junos:pattern-message "Use format \'x\' or \'x.y\' to specify number \'x\' (Range 1 .. 4294967295) or number with higher 2 bytes \'x\' (Range 0 .. 65535) and lower 2 bytes \'y\' (Range 0 .. 65535) respectively";
                     }
                   }
                   leaf address {
                     description "Address of BGP system that formed the route";
                     junos:cli-feature "nokeyword";
                     type jt:ipv4addr;
                   }
                 }
               }
               list route {
                 key name;
                 junos:cli-feature "oneliner-plus";
                 description "Static route";
                 leaf name {
                   junos:cli-feature "nokeyword";
                   type jt:ipprefix;
                 }
                 uses apply-advanced;
                 leaf priority {
                   description "Static route priority high/medium/low";
                   type enumeration {
                     enum "medium" {
                       description "Static route medium priority";
                     }
                     enum "low" {
                       description "Static route low priority";
                     }
                     enum "high" {
                       description "Static route high priority";
                     }
                   }
                 }
                 choice next_hop {
                   case case_1 {
                     leaf-list next-hop {
                       ordered-by user;
                       description "Next hop to destination";
                       type union {
                         type jt:ipaddr-or-interface;
                         type string {
                           pattern "<.*>|$.*";
                         }
                       }
                     }
                   }
                   case case_2 {
                     leaf reject {
                       description "Drop packets to destination; send ICMP unreachables";
                       type empty;
                     }
                   }
                   case case_3 {
                     leaf discard {
                       description "Drop packets to destination; send no ICMP unreachables";
                       type empty;
                     }
                   }
                   case case_4 {
                     leaf receive {
                       description "Install a receive route for the destination";
                       type empty;
                     }
                   }
                   case case_5 {
                     leaf next-table {
                       description "Next hop to another table";
                       type string {
                         junos:posix-pattern "^(((.{0,128})[:](.{1,128})[.]|((.{1,128})[.]))?([a-z]|[0-9]|[-_])+[.]((1?[0-9]{1,2})|(2[0-4][0-9])|(25[0-5])))$";
                         junos:pattern-message "Must match the format [<instance-name>[:<topology-name>].]<family-name>.<rib-id>";
                       }
                     }
                   }
                 }
                 leaf description {
                   description "Static route description";
                   type string {
                     junos:posix-pattern "^.{1,255}$";
                     junos:pattern-message "Must be a string of 255 characters or less";
                   }
                 }
                 list qualified-next-hop {
                   key name;
                   ordered-by user;
                   description "Next hop with qualifiers";
                   uses qualified_nh_obj;
                 }
                 leaf backup-pe-group {
                   description "Multicast source redundancy group";
                   junos:must "(\".. p2mp-lsp-next-hop\")";
                   junos:must-message "Backup groups only allowed for static routes with p2mp lsp next-hop";
                   type string;
                 }
                 container bfd-liveness-detection {
                   description "Bidirectional Forwarding Detection (BFD) options";
                   uses apply-advanced;
                   leaf version {
                     description "BFD protocol version number";
                     default "automatic";
                     type enumeration {
                       enum "0" {
                         description "BFD version 0 (deprecated)";
                       }
                       enum "1" {
                         description "BFD version 1";
                       }
                       enum "automatic" {
                         description "Choose BFD version automatically";
                       }
                     }
                   }
                   leaf minimum-interval {
                     description "Minimum transmit and receive interval";
                     units "milliseconds";
                     type union {
                       type string {
                         pattern "<.*>|$.*";
                       }
                       type uint32 {
                         range "1 .. 255000";
                       }
                     }
                   }
                   leaf minimum-transmit-interval {
                     description "Minimum transmit interval";
                     status deprecated;
                     units "milliseconds";
                     type union {
                       type string {
                         pattern "<.*>|$.*";
                       }
                       type uint32 {
                         range "1 .. 255000";
                       }
                     }
                   }
                   leaf minimum-receive-interval {
                     description "Minimum receive interval";
                     units "milliseconds";
                     type union {
                       type string {
                         pattern "<.*>|$.*";
                       }
                       type uint32 {
                         range "1 .. 255000";
                       }
                     }
                   }
                   leaf multiplier {
                     description "Detection time multiplier";
                     default "3";
                     type union {
                       type string {
                         pattern "<.*>|$.*";
                       }
                       type uint32 {
                         range "1 .. 255";
                       }
                     }
                   }
                   leaf inline-disable {
                     description "Disable inline mode for this BFD session";
                     type empty;
                   }
                   leaf pdu-size {
                     description "BFD transport protocol payload size";
                     default "24";
                     type union {
                       type string {
                         pattern "<.*>|$.*";
                       }
                       type uint32 {
                         range "24 .. 16000";
                       }
                     }
                   }
                   choice adaptation-choice {
                     case case_1 {
                       leaf no-adaptation {
                         description "Disable adaptation";
                         type empty;
                       }
                     }
                   }
                   container transmit-interval {
                     description "Transmit-interval options";
                     uses apply-advanced;
                     leaf minimum-interval {
                       description "Minimum transmit interval";
                       units "milliseconds";
                       type union {
                         type string {
                           pattern "<.*>|$.*";
                         }
                         type uint32 {
                           range "1 .. 255000";
                         }
                       }
                     }
                     leaf threshold {
                       description "High transmit interval triggering a trap";
                       units "milliseconds";
                       type union {
                         type uint32;
                         type string {
                           pattern "<.*>|$.*";
                         }
                       }
                     }
                   }
                   container detection-time {
                     description "Detection-time options";
                     uses apply-advanced;
                     leaf threshold {
                       description "High detection-time triggering a trap";
                       units "milliseconds";
                       type union {
                         type uint32;
                         type string {
                           pattern "<.*>|$.*";
                         }
                       }
                     }
                   }
                   container authentication {
                     description "Authentication options";
                     uses apply-advanced;
                     leaf key-chain {
                       description "Key chain name";
                       junos:must "(\".. algorithm\")";
                       junos:must-message "May not be configured without algorithm";
                       junos:must "(\"security authentication-key-chains key-chain $$\")";
                       junos:must-message "Referenced key-chain must be defined";
                       type string;
                     }
                     leaf algorithm {
                       description "Algorithm name";
                       junos:must "(\".. key-chain\")";
                       junos:must-message "May not be configured without key-chain";
                       type enumeration {
                         enum "simple-password" {
                           description "Simple password";
                         }
                         enum "keyed-md5" {
                           description "Keyed message Digest 5";
                         }
                         enum "meticulous-keyed-md5" {
                           description "Meticulous keyed message Digest 5";
                         }
                         enum "keyed-sha-1" {
                           description "Keyed secure hash algorithm (SHA1) ";
                         }
                         enum "meticulous-keyed-sha-1" {
                           description "Meticulous keyed secure hash algorithm (SHA1) ";
                         }
                       }
                     }
                     leaf loose-check {
                       description "Verify authentication only if authentication is negotiated";
                       type empty;
                     }
                   }
                   container echo {
                     junos:must "(!(\".. echo-lite\"))";
                     junos:must-message "'echo-lite' and 'echo' mode cannot be configured at the same time";
                     description "Echo mode parameters";
                     uses apply-advanced;
                     leaf minimum-interval {
                       description "Minimum transmit and receive interval";
                       units "milliseconds";
                       type union {
                         type string {
                           pattern "<.*>|$.*";
                         }
                         type uint32 {
                           range "100 .. 255000";
                         }
                       }
                     }
                   }
                   container echo-lite {
                     junos:must "(!(\".. echo\"))";
                     junos:must-message "'echo-lite' and 'echo' mode cannot be configured at the same time";
                     description "Echo-lite more parameters";
                     uses apply-advanced;
                     leaf minimum-interval {
                       description "Minimum transmit and receive interval";
                       units "milliseconds";
                       type union {
                         type string {
                           pattern "<.*>|$.*";
                         }
                         type uint32 {
                           range "1 .. 255000";
                         }
                       }
                     }
                   }
                   leaf neighbor {
                     description "BFD neighbor address";
                     type jt:ipaddr;
                   }
                   leaf local-address {
                     description "BFD local address (for multihop only)";
                     type jt:ipaddr;
                   }
                   leaf holddown-interval {
                     description "Time to hold the session-UP notification to the client";
                     units "milliseconds";
                     type union {
                       type string {
                         pattern "<.*>|$.*";
                       }
                       type uint32 {
                         range "0 .. 255000";
                       }
                     }
                   }
                   leaf minimum-receive-ttl {
                     description "Minimum receive TTL below which to drop";
                     type union {
                       type string {
                         pattern "<.*>|$.*";
                       }
                       type uint8 {
                         range "1 .. 255";
                       }
                     }
                   }
                 }
                 choice retain-choice {
                   leaf retain {
                     description "Always keep route in forwarding table";
                     junos:must "(!(\".. resolve\"))";
                     junos:must-message "Must not specify resolve with retain";
                     type empty;
                   }
                   leaf no-retain {
                     description "Don't always keep route in forwarding table";
                     junos:must "(!(\".. resolve\"))";
                     junos:must-message "Must not specify resolve with retain";
                     type empty;
                   }
                 }
                 choice install-choice {
                   leaf install {
                     description "Install route into forwarding table";
                     type empty;
                   }
                   leaf no-install {
                     description "Don't install route into forwarding table";
                     type empty;
                   }
                 }
                 choice readvertise-choice {
                   leaf readvertise {
                     description "Mark route as eligible to be readvertised";
                     type empty;
                   }
                   leaf no-readvertise {
                     description "Don't mark route as eligible to be readvertised";
                     type empty;
                   }
                 }
                 choice resolve-choice {
                   leaf resolve {
                     description "Allow resolution of indirectly connected next hops";
                     type empty;
                   }
                   leaf no-resolve {
                     description "Don't allow resolution of indirectly connected next hops";
                     type empty;
                   }
                 }
                 leaf explicit-null {
                   description "Allows service label to be popped and will lookup nexthop-table inet6.0";
                   junos:must "(\".. resolve\")";
                   junos:must-message "Requires resolve to be configured";
                   type empty;
                 }
                 choice longest-match-choice {
                   leaf longest-match {
                     description "Always use longest prefix match to resolve next hops";
                     junos:must "(\".. resolve\")";
                     junos:must-message "Requires resolve to be configured";
                     type empty;
                   }
                   leaf no-longest-match {
                     description "Don't always use longest prefix match to resolve next hops";
                     junos:must "(\".. resolve\")";
                     junos:must-message "Requires resolve to be configured";
                     type empty;
                   }
                 }
                 choice passive_flag {
                   case case_1 {
                     leaf active {
                       description "Remove inactive route from forwarding table";
                       type empty;
                     }
                   }
                   case case_2 {
                     leaf passive {
                       description "Retain inactive route in forwarding table";
                       type empty;
                     }
                   }
                 }
                 container metric {
                   description "Metric value";
                   presence "enable metric";
                   junos:cli-feature "oneliner";
                   uses rib_static_metric_type;
                 }
                 container metric2 {
                   description "Metric value 2";
                   presence "enable metric2";
                   junos:cli-feature "oneliner";
                   uses rib_static_metric_type;
                 }
                 container metric3 {
                   description "Metric value 3";
                   presence "enable metric3";
                   junos:cli-feature "oneliner";
                   uses rib_static_metric_type;
                 }
                 container metric4 {
                   description "Metric value 4";
                   presence "enable metric4";
                   junos:cli-feature "oneliner";
                   uses rib_static_metric_type;
                 }
                 container tag {
                   description "Tag string";
                   presence "enable tag";
                   junos:cli-feature "oneliner";
                   uses rib_static_metric_type;
                 }
                 container tag2 {
                   description "Tag string 2";
                   presence "enable tag2";
                   junos:cli-feature "oneliner";
                   uses rib_static_metric_type;
                 }
                 container preference {
                   description "Preference value";
                   presence "enable preference";
                   junos:cli-feature "oneliner";
                   uses rib_static_metric_type;
                 }
                 container preference2 {
                   description "Preference value 2";
                   presence "enable preference2";
                   junos:cli-feature "oneliner";
                   uses rib_static_metric_type;
                 }
                 container color {
                   description "Color (preference) value";
                   presence "enable color";
                   junos:cli-feature "oneliner";
                   uses rib_static_metric_type;
                 }
                 container color2 {
                   description "Color (preference) value 2";
                   presence "enable color2";
                   junos:cli-feature "oneliner";
                   uses rib_static_metric_type;
                 }
                 leaf-list community {
                   ordered-by user;
                   description "BGP community identifier";
                   type jt:community;
                 }
                 container as-path {
                   description "Autonomous system path";
                   uses apply-advanced;
                   leaf path {
                     description "Autonomous system path";
                     type string;
                   }
                   leaf origin {
                     type enumeration {
                       enum "igp" {
                         description "Path originated in the local IGP";
                       }
                       enum "egp" {
                         description "Path originated in another AS";
                       }
                       enum "incomplete" {
                         description "Path was learned by some other means";
                       }
                     }
                   }
                   leaf atomic-aggregate {
                     description "Add ATOMIC_AGGREGATE path attribute to route";
                     type empty;
                   }
                   container aggregator {
                     presence "enable aggregator";
                     description "Add AGGREGATOR path attribute to route";
                   }
                   leaf as-number {
                     description " Autonomous system number in plain number or 'higher 16bits'.'Lower 16 bits' (asdot notation) format";
                     junos:cli-feature "nokeyword";
                     type string {
                       junos:posix-pattern "^[0-9]+(.[0-9]+)?$";
                       junos:pattern-message "Use format \'x\' or \'x.y\' to specify number \'x\' (Range 1 .. 4294967295) or number with higher 2 bytes \'x\' (Range 0 .. 65535) and lower 2 bytes \'y\' (Range 0 .. 65535) respectively";
                     }
                   }
                   leaf address {
                     description "Address of BGP system that formed the route";
                     junos:cli-feature "nokeyword";
                     type jt:ipv4addr;
                   }
                 }
                 list lsp-next-hop {
                   key name;
                   ordered-by user;
                   description "LSP next hop";
                   uses lsp_nh_obj;
                 }
                 list p2mp-lsp-next-hop {
                   key name;
                   ordered-by user;
                   description "Point-to-multipoint LSP next hop";
                   max-elements 1;
                   uses lsp_nh_obj;
                 }
                 container spring-te-lsp-next-hop {
                   description "SPRING-TE LSP next hop";
                   junos:must "(\"protocols source-packet-routing tunnel-tracking\")";
                   junos:must-message "Please enable the tunnel-tracking  under 'protocols source-packet-routing' hierarchy";
                   uses springte_lsp_nh_obj;
                 }
                 container p2mp-ldp-next-hop {
                   description "Point-to-multipoint LDP LSP next hop";
                   uses p2mp_ldp_lsp_nh_obj;
                 }
                 list static-lsp-next-hop {
                   key name;
                   ordered-by user;
                   description "Static LSP next hop";
                   uses lsp_nh_obj;
                 }
               }
               leaf protocol-instance-name {
                 description "Name of protocol instance under routing instance";
                 type string;
               }
               container static-route {
                 junos:cli-feature "oneliner";
                 description "Static route Status";
                 leaf bfd-admin-down {
                   description "Static route State on BFD ADMIN DOWN";
                   type enumeration {
                     enum "active" {
                       description "Static route will be inactive on bfd-admin-down";
                     }
                     enum "passive" {
                       description "Static route will remain active on bfd-admin-down";
                     }
                   }
                 }
               }
               list route-target-filter {
                 key name;
                 junos:cli-feature "oneliner-plus";
                 description "Route-target-filter route";
                 leaf name {
                   junos:cli-feature "nokeyword";
                   type string {
                     length "1 .. 47";
                     junos:posix-pattern "^[0-9.]{1,15}L?:[0-9]{1,10}/([0-9]|[2-5][0-9]|6[0-4])$";
                     junos:pattern-message "Use format \'x:y/len\' where \'x\' is an AS number followed by an optional \'L\' (To indicate 4 byte AS), or an IP address and \'y\' is a number. e.g. 123456L:100 and len is a prefix length from 0 to 64";
                   }
                 }
                 uses apply-advanced;
                 leaf autonomous-system {
                   description "BGP AS for filter, overriding global configuration";
                   type string {
                     junos:posix-pattern "^[0-9]+(.[0-9]+)?$";
                     junos:pattern-message "Use format \'x\' or \'x.y\' to specify number \'x\' (Range 1 .. 4294967295) or number with higher 2 bytes \'x\' (Range 0 .. 65535) and lower 2 bytes \'y\' (Range 0 .. 65535) respectively";
                   }
                 }
                 leaf-list community {
                   ordered-by user;
                   description "BGP community identifier";
                   type jt:community;
                 }
                 leaf-list neighbor {
                   ordered-by user;
                   description "BGP peers for filter";
                   type jt:ipaddr-scoped;
                 }
                 leaf-list group {
                   ordered-by user;
                   description "BGP groups for filter";
                   type string;
                 }
                 leaf local {
                   description "Locally originated filter";
                   type empty;
                 }
               }
               list route-target-community-filter {
                 key name;
                 junos:cli-feature "oneliner-plus";
                 description "Route-target-filter communites";
                 leaf name {
                   junos:cli-feature "nokeyword";
                   junos:must "(\"policy-options community $$\")";
                   junos:must-message "The referenced community is not defined under 'policy-options community'";
                   type string;
                 }
                 uses apply-advanced;
                 leaf autonomous-system {
                   description "BGP AS for filter, overriding global configuration";
                   type string {
                     junos:posix-pattern "^[0-9]+(.[0-9]+)?$";
                     junos:pattern-message "Use format \'x\' or \'x.y\' to specify number \'x\' (Range 1 .. 4294967295) or number with higher 2 bytes \'x\' (Range 0 .. 65535) and lower 2 bytes \'y\' (Range 0 .. 65535) respectively";
                   }
                 }
                 leaf-list community {
                   ordered-by user;
                   description "BGP community identifier";
                   type jt:community;
                 }
                 leaf-list neighbor {
                   ordered-by user;
                   description "BGP peers for filter";
                   type jt:ipaddr-scoped;
                 }
                 leaf-list group {
                   ordered-by user;
                   description "BGP groups for filter";
                   type string;
                 }
                 leaf local {
                   description "Locally originated filter";
                   type empty;
                 }
               }
             }
             list martians {
               key "address choice-ident choice-value";
               ordered-by user;
               description "Invalid routes";
               uses martian_type;
               junos:cli-feature "homogeneous";
               junos:cli-feature "oneliner";
             }
             container aggregate {
               description "Coalesced routes";
               uses rib_aggregate_type;
             }
             container generate {
               description "Route of last resort";
               uses rib_aggregate_type;
             }
             choice maximum-paths-type {
               case case_1 {
                 container maximum-routes {
                   junos:cli-feature "oneliner";
                   description "Maximum number of routes";
                   status deprecated;
                   leaf limit {
                     description "Maximum number of routes";
                     junos:cli-feature "nokeyword";
                     type union {
                       type string {
                         pattern "<.*>|$.*";
                       }
                       type uint32 {
                         range "1 .. 4294967295";
                       }
                     }
                   }
                   choice log_type {
                     case case_1 {
                       leaf threshold {
                         description "Percentage of limit at which to start generating warnings";
                         type union {
                           type string {
                             pattern "<.*>|$.*";
                           }
                           type uint32 {
                             range "1 .. 100";
                           }
                         }
                       }
                     }
                     case case_2 {
                       leaf log-only {
                         description "Generate warning messages only";
                         type empty;
                       }
                     }
                   }
                   leaf log-interval {
                     description "Minimum interval between log messages";
                     units "seconds";
                     type union {
                       type string {
                         pattern "<.*>|$.*";
                       }
                       type uint32 {
                         range "5 .. 86400";
                       }
                     }
                   }
                 }
               }
               case case_2 {
                 container maximum-paths {
                   junos:cli-feature "oneliner";
                   description "Maximum number of paths";
                   leaf limit {
                     description "Maximum number of paths";
                     junos:cli-feature "nokeyword";
                     type union {
                       type string {
                         pattern "<.*>|$.*";
                       }
                       type uint32 {
                         range "1 .. 4294967295";
                       }
                     }
                   }
                   choice log_type {
                     case case_1 {
                       leaf threshold {
                         description "Percentage of limit at which to start generating warnings";
                         type union {
                           type string {
                             pattern "<.*>|$.*";
                           }
                           type uint32 {
                             range "1 .. 100";
                           }
                         }
                       }
                     }
                     case case_2 {
                       leaf log-only {
                         description "Generate warning messages only";
                         type empty;
                       }
                     }
                   }
                   leaf log-interval {
                     description "Minimum interval between log messages";
                     units "seconds";
                     type union {
                       type string {
                         pattern "<.*>|$.*";
                       }
                       type uint32 {
                         range "5 .. 86400";
                       }
                     }
                   }
                 }
               }
             }
             container maximum-prefixes {
               junos:cli-feature "oneliner";
               description "Maximum number of prefixes";
               leaf limit {
                 description "Maximum number of prefixes";
                 junos:cli-feature "nokeyword";
                 type union {
                   type string {
                     pattern "<.*>|$.*";
                   }
                   type uint32 {
                     range "1 .. 4294967295";
                   }
                 }
               }
               choice log_type {
                 case case_1 {
                   leaf threshold {
                     description "Percentage of limit at which to start generating warnings";
                     type union {
                       type string {
                         pattern "<.*>|$.*";
                       }
                       type uint32 {
                         range "1 .. 100";
                       }
                     }
                   }
                 }
                 case case_2 {
                   leaf log-only {
                     description "Generate warning messages only";
                     type empty;
                   }
                 }
               }
               leaf log-interval {
                 description "Minimum interval between log messages";
                 units "seconds";
                 type union {
                   type string {
                     pattern "<.*>|$.*";
                   }
                   type uint32 {
                     range "5 .. 86400";
                   }
                 }
               }
             }
             container multipath {
               presence "enable multipath";
               junos:cli-feature "oneliner-plus";
               description "Protocol-independent load balancing";
               uses apply-advanced;
               container vpn-unequal-cost {
                 presence "enable vpn-unequal-cost";
                 junos:cli-feature "oneliner";
                 description "Include VPN routes with unequal IGP metrics";
                 leaf equal-external-internal {
                   description "Include external and internal VPN routes";
                   type empty;
                 }
               }
               leaf as-path-compare {
                 description "Compare AS path sequences in addition to AS path length";
                 type empty;
               }
               leaf preserve-nexthop-hierarchy {
                 description "Force multipath to create List nexthop";
                 type empty;
               }
             }
             container policy-multipath {
               junos:must "(!((\".. .. rib any.inet.3 policy-multipath\" || \".. .. rib any.inet6.3 policy-multipath\")))";
               junos:must-message "policy-multipath is configured by default for any.inet[6].3";
               junos:cli-feature "oneliner-plus";
               description "Policy based multipath";
               uses apply-advanced;
               leaf-list policy {
                 ordered-by user;
                 description "Import policy to create policy based multipath";
                 type jt:policy-algebra;
               }
               container traceoptions {
                 description "Trace options";
                 uses apply-advanced;
                 container file {
                   junos:cli-feature "oneliner";
                   description "Trace file options";
                   leaf filename {
                     description "Name of file in which to write trace information";
                     junos:cli-feature "nokeyword";
                     type string {
                       length "1 .. 1024";
                       junos:posix-pattern "![/ %]";
                       junos:pattern-message "Must not contain \'/\', % or a space";
                     }
                   }
                   leaf replace {
                     description "Replace trace file rather than appending to it";
                     status deprecated;
                     type empty;
                   }
                   leaf size {
                     description "Maximum trace file size";
                     type string;
                   }
                   leaf files {
                     description "Maximum number of trace files";
                     default "10";
                     type union {
                       type string {
                         pattern "<.*>|$.*";
                       }
                       type uint32 {
                         range "2 .. 1000";
                       }
                     }
                   }
                   leaf no-stamp {
                     description "Do not timestamp trace file";
                     status deprecated;
                     type empty;
                   }
                   choice world-readable-choice {
                     leaf world-readable {
                       description "Allow any user to read the log file";
                       type empty;
                     }
                     leaf no-world-readable {
                       description "Don't allow any user to read the log file";
                       type empty;
                     }
                   }
                 }
                 list flag {
                   key name;
                   ordered-by user;
                   junos:cli-feature "oneliner";
                   description "Tracing parameters";
                   leaf name {
                     junos:cli-feature "nokeyword";
                     type enumeration {
                       enum "route" {
                         description "Policy-multipath route tracing.";
                       }
                     }
                   }
                   leaf send {
                     description "Trace transmitted packets";
                     type empty;
                   }
                   leaf receive {
                     description "Trace received packets";
                     type empty;
                   }
                   leaf detail {
                     description "Trace detailed information";
                     type empty;
                   }
                   leaf disable {
                     description "Disable this trace flag";
                     type empty;
                   }
                 }
               }
               leaf preserve-nexthop-hierarchy {
                 description "Enable preserved nexthop hierarchy";
                 junos:must "(\"routing-options resolution preserve-nexthop-hierarchy\")";
                 junos:must-message "routing-options resolution preserve-nexthop-hierarchy         configuration is mandatory";
                 type empty;
               }
             }
             container protect {
               junos:cli-feature "oneliner";
               description "Protocol-independent protection";
               leaf core {
                 description "Protect against unreachability to service-edge router";
                 type empty;
               }
             }
             container access {
               description "Access routes";
               uses apply-advanced;
               list route {
                 key name;
                 ordered-by user;
                 junos:cli-feature "oneliner-plus";
                 description "Access route";
                 leaf name {
                   description "IP address of destination";
                   junos:cli-feature "nokeyword";
                   type jt:ipprefix;
                 }
                 uses apply-advanced;
                 leaf-list next-hop {
                   ordered-by user;
                   description "Next hop to destination";
                   type union {
                     type jt:ipaddr-or-interface;
                     type string {
                       pattern "<.*>|$.*";
                     }
                   }
                 }
                 list qualified-next-hop {
                   key name;
                   ordered-by user;
                   description "Next hop with qualifiers";
                   uses qualified_nh_obj;
                 }
                 leaf metric {
                   description "Metric value";
                   type union {
                     type string {
                       pattern "<.*>|$.*";
                     }
                     type uint32 {
                       range "1 .. 255";
                     }
                   }
                 }
                 leaf preference {
                   description "Preference value";
                   type union {
                     type uint32;
                     type string {
                       pattern "<.*>|$.*";
                     }
                   }
                 }
                 leaf tag {
                   description "Tag string";
                   type union {
                     type uint32;
                     type string {
                       pattern "<.*>|$.*";
                     }
                   }
                 }
                 leaf tag2 {
                   description "Tag2 string";
                   type union {
                     type uint32;
                     type string {
                       pattern "<.*>|$.*";
                     }
                   }
                 }
               }
             }
             container access-internal {
               description "Access-internal routes";
               uses apply-advanced;
               list route {
                 key name;
                 ordered-by user;
                 junos:cli-feature "oneliner-plus";
                 description "Access-internal route";
                 leaf name {
                   description "IP address and optional prefix length of destination";
                   junos:cli-feature "nokeyword";
                   type jt:ipprefix;
                 }
                 uses apply-advanced;
                 leaf-list next-hop {
                   ordered-by user;
                   description "Next hop to destination";
                   type union {
                     type jt:ipaddr-or-interface;
                     type string {
                       pattern "<.*>|$.*";
                     }
                   }
                 }
                 list qualified-next-hop {
                   key name;
                   ordered-by user;
                   description "Next hop with qualifiers";
                   uses qualified_nh_obj;
                 }
               }
             }
             container bgp-static {
               description "Routes for BGP static advertisements";
               uses apply-advanced;
               list route {
                 key name;
                 ordered-by user;
                 junos:cli-feature "oneliner-plus";
                 description "BGP-static route";
                 leaf name {
                   description "IP address and optional prefix length of destination";
                   junos:cli-feature "nokeyword";
                   type jt:ipprefix;
                 }
                 uses apply-advanced;
                 container metric {
                   description "Metric value";
                   presence "enable metric";
                   junos:cli-feature "oneliner";
                   uses rib_static_metric_type;
                 }
                 container metric2 {
                   description "Metric value 2";
                   presence "enable metric2";
                   junos:cli-feature "oneliner";
                   uses rib_static_metric_type;
                 }
                 container metric3 {
                   description "Metric value 3";
                   presence "enable metric3";
                   junos:cli-feature "oneliner";
                   uses rib_static_metric_type;
                 }
                 container metric4 {
                   description "Metric value 4";
                   presence "enable metric4";
                   junos:cli-feature "oneliner";
                   uses rib_static_metric_type;
                 }
                 container tag {
                   description "Tag string";
                   presence "enable tag";
                   junos:cli-feature "oneliner";
                   uses rib_static_metric_type;
                 }
                 container tag2 {
                   description "Tag string 2";
                   presence "enable tag2";
                   junos:cli-feature "oneliner";
                   uses rib_static_metric_type;
                 }
                 container preference {
                   description "Preference value";
                   presence "enable preference";
                   junos:cli-feature "oneliner";
                   uses rib_static_metric_type;
                 }
                 container preference2 {
                   description "Preference value 2";
                   presence "enable preference2";
                   junos:cli-feature "oneliner";
                   uses rib_static_metric_type;
                 }
                 container color {
                   description "Color (preference) value";
                   presence "enable color";
                   junos:cli-feature "oneliner";
                   uses rib_static_metric_type;
                 }
                 container color2 {
                   description "Color (preference) value 2";
                   presence "enable color2";
                   junos:cli-feature "oneliner";
                   uses rib_static_metric_type;
                 }
                 leaf-list community {
                   ordered-by user;
                   description "BGP community identifier";
                   type jt:community;
                 }
                 container as-path {
                   description "Autonomous system path";
                   uses apply-advanced;
                   leaf path {
                     description "Autonomous system path";
                     type string;
                   }
                   leaf origin {
                     type enumeration {
                       enum "igp" {
                         description "Path originated in the local IGP";
                       }
                       enum "egp" {
                         description "Path originated in another AS";
                       }
                       enum "incomplete" {
                         description "Path was learned by some other means";
                       }
                     }
                   }
                   leaf atomic-aggregate {
                     description "Add ATOMIC_AGGREGATE path attribute to route";
                     type empty;
                   }
                   container aggregator {
                     presence "enable aggregator";
                     description "Add AGGREGATOR path attribute to route";
                   }
                   leaf as-number {
                     description " Autonomous system number in plain number or 'higher 16bits'.'Lower 16 bits' (asdot notation) format";
                     junos:cli-feature "nokeyword";
                     type string {
                       junos:posix-pattern "^[0-9]+(.[0-9]+)?$";
                       junos:pattern-message "Use format \'x\' or \'x.y\' to specify number \'x\' (Range 1 .. 4294967295) or number with higher 2 bytes \'x\' (Range 0 .. 65535) and lower 2 bytes \'y\' (Range 0 .. 65535) respectively";
                     }
                   }
                   leaf address {
                     description "Address of BGP system that formed the route";
                     junos:cli-feature "nokeyword";
                     type jt:ipv4addr;
                   }
                 }
               }
             }
             container flow {
               description "Locally defined flow routing information";
               uses apply-advanced;
               container validation {
                 description "Flow route validation options";
                 presence "enable validation";
                 uses flow-validation;
               }
               list route {
                 key name;
                 ordered-by user;
                 description "Flow route";
                 uses flow-route-inet6;
               }
               container interface-group {
                 description "Interface-group for applying flow-spec filter";
                 junos:cli-feature "oneliner";
                 junos:cli-feature "oneliner-plus";
                 uses flow-interface-group;
               }
               leaf discard-action-for-unresolved-redir-addr {
                 description "For action redirect IP if redirect address is unresolved install discard action filter";
                 type empty;
               }
               choice per-route-accounting-choice {
                 leaf per-route-accounting {
                   description "Enable traffic accounting per flowspec route";
                   type empty;
                 }
                 leaf no-per-route-accounting {
                   description "Don't enable traffic accounting per flowspec route";
                   type empty;
                 }
               }
             }
             container rib-export {
               presence "enable rib-export";
               description "Group of routing tables to import the routes";
               uses apply-advanced;
               leaf ribexport-name {
                 description "RIB export group name";
                 junos:cli-feature "nokeyword";
                 type string;
               }
             }
             container label {
               presence "enable label";
               junos:cli-feature "oneliner-plus";
               description "Label processing";
               uses apply-advanced;
               leaf-list allocation {
                 ordered-by user;
                 description "Label allocation policy";
                 junos:must "(\".. .. .. instance-type vrf\")";
                 junos:must-message "'allocation' policy is valid only for 'instance-type vrf'";
                 type jt:policy-algebra;
               }
               leaf-list substitution {
                 ordered-by user;
                 description "Label substitution policy";
                 junos:must "(\".. .. .. instance-type vrf\")";
                 junos:must-message "'substitution' policy is valid only for 'instance-type vrf'";
                 type jt:policy-algebra;
               }
             }
             leaf-list vpn-global-import {
               ordered-by user;
               description "Import policy for L3VPN routes to global RIB";
               type jt:policy-algebra;
             }
           }
           container access {
             description "Access routes";
             uses apply-advanced;
             list route {
               key name;
               ordered-by user;
               junos:cli-feature "oneliner-plus";
               description "Access route";
               leaf name {
                 description "IP address of destination";
                 junos:cli-feature "nokeyword";
                 type jt:ipprefix;
               }
               uses apply-advanced;
               leaf-list next-hop {
                 ordered-by user;
                 description "Next hop to destination";
                 type union {
                   type jt:ipaddr-or-interface;
                   type string {
                     pattern "<.*>|$.*";
                   }
                 }
               }
               list qualified-next-hop {
                 key name;
                 ordered-by user;
                 description "Next hop with qualifiers";
                 uses qualified_nh_obj;
               }
               leaf metric {
                 description "Metric value";
                 type union {
                   type string {
                     pattern "<.*>|$.*";
                   }
                   type uint32 {
                     range "1 .. 255";
                   }
                 }
               }
               leaf preference {
                 description "Preference value";
                 type union {
                   type uint32;
                   type string {
                     pattern "<.*>|$.*";
                   }
                 }
               }
               leaf tag {
                 description "Tag string";
                 type union {
                   type uint32;
                   type string {
                     pattern "<.*>|$.*";
                   }
                 }
               }
               leaf tag2 {
                 description "Tag2 string";
                 type union {
                   type uint32;
                   type string {
                     pattern "<.*>|$.*";
                   }
                 }
               }
             }
           }
           container access-internal {
             description "Access-internal routes";
             uses apply-advanced;
             list route {
               key name;
               ordered-by user;
               junos:cli-feature "oneliner-plus";
               description "Access-internal route";
               leaf name {
                 description "IP address and optional prefix length of destination";
                 junos:cli-feature "nokeyword";
                 type jt:ipprefix;
               }
               uses apply-advanced;
               leaf-list next-hop {
                 ordered-by user;
                 description "Next hop to destination";
                 type union {
                   type jt:ipaddr-or-interface;
                   type string {
                     pattern "<.*>|$.*";
                   }
                 }
               }
               list qualified-next-hop {
                 key name;
                 ordered-by user;
                 description "Next hop with qualifiers";
                 uses qualified_nh_obj;
               }
             }
           }
           container multicast {
             description "Global multicast options";
             uses apply-advanced;
             container traceoptions {
               description "Global multicast trace options";
               uses apply-advanced;
               container file {
                 junos:cli-feature "oneliner";
                 description "Trace file options";
                 leaf filename {
                   description "Name of file in which to write trace information";
                   junos:cli-feature "nokeyword";
                   type string {
                     length "1 .. 1024";
                     junos:posix-pattern "![/ %]";
                     junos:pattern-message "Must not contain \'/\', % or a space";
                   }
                 }
                 leaf replace {
                   description "Replace trace file rather than appending to it";
                   status deprecated;
                   type empty;
                 }
                 leaf size {
                   description "Maximum trace file size";
                   type string;
                 }
                 leaf files {
                   description "Maximum number of trace files";
                   default "10";
                   type union {
                     type string {
                       pattern "<.*>|$.*";
                     }
                     type uint32 {
                       range "2 .. 1000";
                     }
                   }
                 }
                 leaf no-stamp {
                   description "Do not timestamp trace file";
                   status deprecated;
                   type empty;
                 }
                 choice world-readable-choice {
                   leaf world-readable {
                     description "Allow any user to read the log file";
                     type empty;
                   }
                   leaf no-world-readable {
                     description "Don't allow any user to read the log file";
                     type empty;
                   }
                 }
               }
               list flag {
                 key name;
                 ordered-by user;
                 junos:cli-feature "oneliner";
                 description "Tracing parameters";
                 leaf name {
                   junos:cli-feature "nokeyword";
                   type enumeration {
                     enum "parse" {
                       description "Trace configuration parsing";
                     }
                     enum "config-internal" {
                       description "Trace configuration internals";
                     }
                     enum "route" {
                       description "Trace routing information";
                     }
                     enum "normal" {
                       description "Trace normal events";
                     }
                     enum "general" {
                       description "Trace general events";
                     }
                     enum "state" {
                       description "Trace state transitions";
                     }
                     enum "policy" {
                       description "Trace policy processing";
                     }
                     enum "task" {
                       description "Trace routing protocol task processing";
                     }
                     enum "timer" {
                       description "Trace routing protocol timer processing";
                     }
                     enum "all" {
                       description "Trace everything";
                     }
                   }
                 }
                 leaf disable {
                   description "Disable this trace flag";
                   type empty;
                 }
               }
             }
             leaf rpf {
               status deprecated;
               type string;
             }
             list scope {
               key name;
               ordered-by user;
               description "Multicast address scope";
               leaf name {
                 description "Name to identify multicast address scope";
                 junos:cli-feature "nokeyword";
                 type string;
               }
               uses apply-advanced;
               leaf prefix {
                 description "Administratively scoped address";
                 type jt:ipprefix;
               }
               leaf-list interface {
                 ordered-by user;
                 description "Interface on which to configure scoping";
                 type union {
                   type jt:interface-name;
                   type string {
                     pattern "<.*>|$.*";
                   }
                 }
               }
             }
             leaf-list scope-policy {
               ordered-by user;
               description "Scoping policy";
               type jt:policy-algebra;
             }
             list flow-map {
               key name;
               ordered-by user;
               description "Multicast flow map configuration";
               leaf name {
                 description "Name of the flow map";
                 junos:cli-feature "nokeyword";
                 type string;
               }
               uses apply-advanced;
               leaf-list policy {
                 ordered-by user;
                 description "Policy for matched flows";
                 type jt:policy-algebra;
               }
               container bandwidth {
                 presence "enable bandwidth";
                 junos:cli-feature "oneliner";
                 description "Bandwidth properties for matched flows";
                 leaf bandwidth-value {
                   description "Static or default bandwidth for the matched flows";
                   junos:cli-feature "nokeyword";
                   units "bps";
                   type string;
                 }
                 leaf adaptive {
                   description "Auto-sense bandwidth for matched flows";
                   type empty;
                 }
               }
               leaf-list redundant-sources {
                 ordered-by user;
                 description "Redundant source addresses";
                 junos:must "(\".. bandwidth adaptive\")";
                 junos:must-message "redundant-sources can only be configured together with 'bandwidth adaptive'";
                 type jt:ipaddr;
               }
               container forwarding-cache {
                 description "Forwarding cache properties for matched flows";
                 uses apply-advanced;
                 container timeout {
                   junos:cli-feature "oneliner";
                   description "Timeout properties for matched flows";
                   choice timeout_choice {
                     case case_1 {
                       leaf timeout-value {
                         description "Timeout for forwarding cache entry";
                         junos:cli-feature "nokeyword";
                         units "minutes";
                         type union {
                           type string {
                             pattern "<.*>|$.*";
                           }
                           type uint32 {
                             range "1 .. 720";
                           }
                         }
                       }
                     }
                     case case_2 {
                       container never {
                         presence "enable never";
                         description "Forwarding cache entries never time out";
                         uses apply-advanced;
                         leaf non-discard-entry-only {
                           description "Apply only to non-discard entries";
                           type empty;
                         }
                       }
                     }
                   }
                 }
               }
             }
             leaf-list resolve-filter {
               ordered-by user;
               description "Multicast resolve policy filter";
               status deprecated;
               type jt:policy-algebra;
             }
             leaf-list ssm-groups {
               ordered-by user;
               description "Source-specific multicast group ranges";
               type jt:ipprefix;
             }
             leaf cont-stats-collection-interval {
               description "IGMP/MLD continuous statistics collection interval";
               default "300";
               type union {
                 type string {
                   pattern "<.*>|$.*";
                 }
                 type uint16 {
                   range "60 .. 3600";
                 }
               }
             }
             leaf asm-override-ssm {
               description "Allow ASM state for SSM group ranges";
               type empty;
             }
             leaf-list rpf-check-policy {
               ordered-by user;
               description "Disable RPF check for a source group pair";
               type jt:policy-algebra;
             }
             container pim-to-igmp-proxy {
               description "PIM-to-IGMP proxy";
               uses apply-advanced;
               leaf-list upstream-interface {
                 ordered-by user;
                 description "Upstream interface list";
                 type union {
                   type jt:interface-name;
                   type string {
                     pattern "<.*>|$.*";
                   }
                 }
                 max-elements 2;
               }
             }
             container pim-to-mld-proxy {
               description "PIM-to-MLD proxy";
               uses apply-advanced;
               leaf-list upstream-interface {
                 ordered-by user;
                 description "Upstream interface list";
                 type union {
                   type jt:interface-name;
                   type string {
                     pattern "<.*>|$.*";
                   }
                 }
                 max-elements 2;
               }
             }
             leaf resolve-request-holdcount {
               description "Set resolve request holdcount for multicast";
               type union {
                 type string {
                   pattern "<.*>|$.*";
                 }
                 type uint32 {
                   range "0 .. 256";
                 }
               }
             }
             container forwarding-cache {
               description "Multicast forwarding cache";
               uses apply-advanced;
               leaf allow-maximum {
                 description "Allow maximum of global and family level threshold values for suppress and reuse";
                 type empty;
               }
               list family {
                 key name;
                 ordered-by user;
                 description "Protocol family";
                 junos:must "((!(\".. threshold\") || \".. allow-maximum\"))";
                 junos:must-message "Family threshold cannot be configured if global threshold is already configured";
                 leaf name {
                   description "Protocol family";
                   junos:cli-feature "nokeyword";
                   type enumeration {
                     enum "inet" {
                       description "IPv4 family";
                     }
                     enum "inet6" {
                       description "IPv6 family";
                     }
                   }
                 }
                 uses apply-advanced;
                 container threshold {
                   presence "enable threshold";
                   description "Multicast forwarding cache suppress threshold";
                   uses apply-advanced;
                   leaf suppress {
                     description "Suppress threshold";
                     type union {
                       type string {
                         pattern "<.*>|$.*";
                       }
                       type uint32 {
                         range "1 .. 200000";
                       }
                     }
                   }
                   leaf reuse {
                     description "Reuse threshold";
                     junos:must "(\".. suppress\")";
                     junos:must-message "To configure reuse, suppress must be configured";
                     type union {
                       type string {
                         pattern "<.*>|$.*";
                       }
                       type uint32 {
                         range "1 .. 200000";
                       }
                     }
                   }
                   leaf mvpn-rpt-suppress {
                     description "MVPN RP tree entry suppress threshold";
                     junos:must "(\".. suppress\")";
                     junos:must-message "To configure mvpn-rpt-suppress, suppress must be configured";
                     type union {
                       type string {
                         pattern "<.*>|$.*";
                       }
                       type uint32 {
                         range "1 .. 200000";
                       }
                     }
                   }
                   leaf mvpn-rpt-reuse {
                     description "MVPN RP tree entry reuse threshold";
                     junos:must "(\".. mvpn-rpt-suppress\")";
                     junos:must-message "To configure mvpn-rpt-reuse, mvpn-rpt-suppress must be configured";
                     type union {
                       type string {
                         pattern "<.*>|$.*";
                       }
                       type uint32 {
                         range "1 .. 200000";
                       }
                     }
                   }
                   leaf log-warning {
                     description "Percentage at which to start generating warnings";
                     junos:must "(\".. suppress\")";
                     junos:must-message "To configure log-warning, suppress must be configured";
                     type union {
                       type string {
                         pattern "<.*>|$.*";
                       }
                       type uint32 {
                         range "1 .. 100";
                       }
                     }
                   }
                 }
               }
               container threshold {
                 junos:must "((!(\".. family\") || \".. allow-maximum\"))";
                 junos:must-message "Global threshold cannot be configured if family threshold is configured";
                 description "Threshold";
                 uses apply-advanced;
                 leaf suppress {
                   description "Suppress threshold";
                   type union {
                     type string {
                       pattern "<.*>|$.*";
                     }
                     type uint32 {
                       range "1 .. 200000";
                     }
                   }
                 }
                 leaf reuse {
                   description "Reuse threshold";
                   junos:must "(\".. suppress\")";
                   junos:must-message "To configure reuse, suppress must be configured";
                   type union {
                     type string {
                       pattern "<.*>|$.*";
                     }
                     type uint32 {
                       range "1 .. 200000";
                     }
                   }
                 }
                 leaf mvpn-rpt-suppress {
                   description "MVPN RP tree entry suppress threshold";
                   junos:must "(\".. suppress\")";
                   junos:must-message "To configure mvpn-rpt-suppress, suppress must be configured";
                   type union {
                     type string {
                       pattern "<.*>|$.*";
                     }
                     type uint32 {
                       range "1 .. 200000";
                     }
                   }
                 }
                 leaf mvpn-rpt-reuse {
                   description "MVPN RP tree entry reuse threshold";
                   junos:must "(\".. mvpn-rpt-suppress\")";
                   junos:must-message "To configure mvpn-rpt-reuse, mvpn-rpt-suppress must be configured";
                   type union {
                     type string {
                       pattern "<.*>|$.*";
                     }
                     type uint32 {
                       range "1 .. 200000";
                     }
                   }
                 }
                 leaf log-warning {
                   description "Percentage at which to start generating warnings";
                   junos:must "(\".. suppress\")";
                   junos:must-message "To configure log-warning, suppress must be configured";
                   type union {
                     type string {
                       pattern "<.*>|$.*";
                     }
                     type uint32 {
                       range "1 .. 100";
                     }
                   }
                 }
               }
               leaf timeout {
                 description "Forwarding cache entry timeout in minutes";
                 type union {
                   type string {
                     pattern "<.*>|$.*";
                   }
                   type uint32 {
                     range "1 .. 720";
                   }
                 }
               }
             }
             list interface {
               key name;
               ordered-by user;
               description "Multicast interface options";
               uses multicast_interface_options_type;
               junos:cli-feature "oneliner-plus";
             }
             list ssm-map {
               key name;
               ordered-by user;
               description "SSM map definitions";
               leaf name {
                 description "SSM map name";
                 junos:cli-feature "nokeyword";
                 type string;
               }
               uses apply-advanced;
               leaf-list policy {
                 ordered-by user;
                 description "Policy for matching group";
                 type jt:policy-algebra;
               }
               leaf-list source {
                 ordered-by user;
                 description "One or more source addresses";
                 type jt:ipaddr;
               }
             }
             container stream-protection {
               presence "enable stream-protection";
               description "Multicast only Fast Re-Route";
               uses apply-advanced;
               leaf mofrr-primary-path-selection-by-routing {
                 description "Multicast only Fast Re-Route primary path by Routing";
                 type empty;
               }
               leaf mofrr-disjoint-upstream-only {
                 description "Multicast only Fast Re-Route disjoint upstream only";
                 type empty;
               }
               leaf mofrr-no-backup-join {
                 description "Multicast only Fast Re-Route no backup join";
                 type empty;
               }
               leaf mofrr-asm-starg {
                 description "Multicast only Fast Re-Route asm (*,G)";
                 type empty;
               }
               leaf-list policy {
                 ordered-by user;
                 description "MoFRR Policy";
                 type jt:policy-algebra;
               }
             }
             list backup-pe-group {
               key name;
               ordered-by user;
               description "Backup PE group definitions";
               leaf name {
                 description "PE group name";
                 junos:cli-feature "nokeyword";
                 type string;
               }
               uses apply-advanced;
               leaf-list backups {
                 ordered-by user;
                 description "One or more IP addresses";
                 type jt:ipaddr;
                 max-elements 8;
               }
               leaf local-address {
                 description "Address to be used as local-address for this group";
                 type jt:ipaddr;
               }
             }
             leaf omit-wildcard-address {
               description "Omit wildcard source/group fields in SPMSI AD NLRI";
               type empty;
             }
             leaf local-address {
               description "Local address for PIM and MVPN sessions";
               type jt:ipv4addr;
             }
           }
         }
       }
     }
     container telemetry {
       description "Telemetry configuration";
       uses apply-advanced;
       container service-statistics {
         presence "enable service-statistics";
         description "Subscriber Service-statistics configuration";
       }
       container subscriber-statistics {
         presence "enable subscriber-statistics";
         description "Subscriber statistics configuration";
       }
       container subscriber-info {
         presence "enable subscriber-info";
         description "Subscriber related information";
         uses apply-advanced;
         leaf service-statistics {
           description "Subscriber Service-statistics configuration";
           type empty;
         }
         leaf subscriber-statistics {
           description "Subscriber statistics configuration";
           type empty;
         }
       }
       container queue-statistics {
         description "Telemetry Queue-Statistics configuration";
         uses apply-advanced;
         list interface {
           key name;
           ordered-by user;
           description "Interface name for this telemetry configuration";
           leaf name {
             junos:cli-feature "nokeyword";
             type enumeration {
               enum "$junos-interface-name" {
                 description "Dynamic profile interface";
               }
             }
           }
           uses apply-advanced;
           leaf refresh {
             description "Refresh interval range 300-86400";
             type union {
               type string {
                 pattern "<.*>|$.*";
               }
               type uint32 {
                 range "300 .. 86400";
               }
             }
           }
           leaf queues {
             description "Queues to be exported 0-7 separated by ,";
             type string {
               junos:posix-pattern "^[0-7,]{1,15}$";
               junos:pattern-message "Must be 0 to 7 separated by comma";
             }
           }
         }
         list interface-set {
           key name;
           ordered-by user;
           description "Logical interface set configuration";
           leaf name {
             junos:cli-feature "nokeyword";
             type enumeration {
               enum "$junos-interface-set-name" {
                 description "Dynamic profile Interface set name";
               }
             }
           }
           uses apply-advanced;
           leaf refresh {
             description "Refresh interval range 300-86400";
             type union {
               type string {
                 pattern "<.*>|$.*";
               }
               type uint32 {
                 range "300 .. 86400";
               }
             }
           }
           leaf queues {
             description "Queues to be exported 0-7 separated by ,";
             type string {
               junos:posix-pattern "^[0-7,]{1,15}$";
               junos:pattern-message "Must be 0 to 7 separated by comma";
             }
           }
         }
       }
     }
     container interfaces {
       description "Interface configuration";
       uses apply-advanced;
       list interface-set {
         key name;
         description "Logical interface set configuration";
         leaf name {
           junos:cli-feature "nokeyword";
           type string;
         }
         uses apply-advanced;
         list interface {
           key name;
           description "One or more interfaces that belong to interface set";
           leaf name {
             description "Interface name";
             junos:cli-feature "nokeyword";
             junos:must "(\"interfaces $$\")";
             junos:must-message "Interface should have configuration defined for adding to interface-set";
             type union {
               type jt:interface-device;
               type string {
                 pattern "<.*>|$.*";
               }
             }
           }
           uses apply-advanced;
           list unit {
             key name;
             description "One or more logical interface unit numbers";
             junos:must "(!(\".. vlan-tags-outer\"))";
             junos:must-message "'unit' statement cannot be included along with 'vlan-tags-outer' statement";
             leaf name {
               description "Unit number";
               junos:cli-feature "nokeyword";
               junos:must "(\"interfaces ${interface} unit $$\")";
               junos:must-message "Interface unit should have configuration defined for adding to interface-set";
               type union {
                 type string {
                   pattern "<.*>|$.*";
                 }
                 type uint32 {
                   range "0 .. 1073741823";
                 }
               }
             }
             uses apply-advanced;
           }
           list vlan-tags-outer {
             key name;
             description "One or more outer VLAN tags";
             junos:must "(!(\".. unit\"))";
             junos:must-message "'vlan-tags-outer' statement cannot be included along with 'unit' statement";
             leaf name {
               description "VLAN tag ID";
               junos:cli-feature "nokeyword";
               type union {
                 type string {
                   pattern "<.*>|$.*";
                 }
                 type uint32 {
                   range "0 .. 4094";
                 }
               }
             }
             uses apply-advanced;
           }
         }
       }
       container stacked-interface-set {
         presence "enable stacked-interface-set";
         description "Stacked interface set configuration";
         uses apply-advanced;
         list interface-set {
           key name;
           ordered-by user;
           description "Stacked parent interface set configuration";
           leaf name {
             junos:cli-feature "nokeyword";
             type string;
           }
           uses apply-advanced;
           list interface-set {
             key name;
             ordered-by user;
             description "Stacked child interface set configuration";
             leaf name {
               junos:cli-feature "nokeyword";
               type string;
             }
             uses apply-advanced;
           }
         }
       }
       container traceoptions {
         description "Interface trace options";
         uses apply-advanced;
         leaf no-remote-trace {
           description "Disable remote tracing";
           junos:must "(\"system tracing\")";
           junos:must-message "'no-remote-trace' is valid only when [system tracing] is configured";
           type empty;
         }
         container file {
           junos:cli-feature "oneliner";
           description "Trace file information";
           leaf filename {
             description "Name of file in which to write trace information";
             junos:cli-feature "nokeyword";
             type string {
               length "1 .. 1024";
               junos:posix-pattern "![/ %]";
               junos:pattern-message "Must not contain \'/\', % or a space";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           junos:cli-feature "oneliner";
           description "Tracing parameters";
           leaf name {
             junos:cli-feature "nokeyword";
             type enumeration {
               enum "all" {
                 description "Enable all configuration logging";
               }
               enum "kernel" {
                 description "Log configuration IPC messages to kernel";
               }
               enum "change-events" {
                 description "Log changes that produce configuration events";
               }
               enum "kernel-detail" {
                 description "Log details of configuration messages to kernel";
               }
               enum "config-states" {
                 description "Log the configuration state machine changes";
               }
               enum "resource-usage" {
                 description "Log the resource usage for different states";
               }
               enum "gres-events" {
                 description "Log the events related to GRES ";
               }
               enum "select-events" {
                 description "Log the events on select state machine ";
               }
               enum "bfd-events" {
                 description "Log BFD related events";
               }
               enum "lib-events" {
                 description "Log DCD library related events";
               }
               enum "reserved" {
                 description "Reserved DCD logs";
               }
               enum "emergency" {
                 description "Log DCD emergency events";
               }
               enum "alert" {
                 description "Log DCD alert events";
               }
               enum "critical" {
                 description "Log DCD critical events";
               }
               enum "error" {
                 description "Log DCD error events";
               }
               enum "warning" {
                 description "Log DCD warning events";
               }
               enum "notice" {
                 description "Log DCD notification events";
               }
               enum "informational" {
                 description "Log DCD informations";
               }
               enum "debugging" {
                 description "Log DCD debug events";
               }
               enum "verbose" {
                 description "Log DCD debug all events";
               }
               enum "japi" {
                 description "Log DCD JAPI events";
               }
             }
           }
           leaf disable {
             description "Disable this trace flag";
             type empty;
           }
         }
       }
       list interface-range {
         key name;
         ordered-by user;
         description "Interface ranges configuration";
         leaf name {
           description "Interface-range name";
           junos:cli-feature "nokeyword";
           type string {
             length "1 .. 128";
             junos:posix-pattern "^[[:alpha:]][[:alnum:]_.-]+$";
             junos:pattern-message "Must start with a letter followed by letters, numbers, dashes or underscore";
           }
         }
         list member {
           key name;
           ordered-by user;
           description "Interfaces belonging to the interface range";
           leaf name {
             description "Member interface name";
             junos:cli-feature "nokeyword";
             type union {
               type jt:interface-range-wild;
               type string {
                 pattern "<.*>|$.*";
               }
             }
           }
           uses apply-advanced;
         }
         list member-range {
           key name;
           ordered-by user;
           junos:cli-feature "oneliner";
           description "Interfaces range in <start-range> to <end-range> format";
           leaf name {
             junos:cli-feature "nokeyword";
             type union {
               type jt:interface-device;
               type string {
                 pattern "<.*>|$.*";
               }
             }
           }
           leaf end-range {
             type union {
               type jt:interface-device;
               type string {
                 pattern "<.*>|$.*";
               }
             }
           }
         }
         uses apply-advanced;
         leaf description {
           description "Text description of interface";
           type string;
         }
         leaf external-model-name {
           description "Name for interface as configured using 3rd-party model";
           type string;
         }
         container management-ethernet-redundancy {
           presence "enable management-ethernet-redundancy";
           description "Management Interface Redundancy";
           uses apply-advanced;
           choice enable_choice {
             case case_1 {
               leaf redundancy-enable {
                 description "Enable Managment Ethernet Redundancy";
                 type empty;
               }
             }
             case case_2 {
               leaf redundancy-disable {
                 description "Disable  Managment Ethernet Redundancy";
                 type empty;
               }
             }
           }
           leaf connectivity-test-interval {
             description "Connectivity test interval";
             default "5";
             units "seconds";
             type union {
               type string {
                 pattern "<.*>|$.*";
               }
               type uint32 {
                 range "1 .. 10";
               }
             }
           }
           leaf connectivity-test-response-interval {
             description "Connectivity test response wait time";
             default "5";
             units "seconds";
             type union {
               type string {
                 pattern "<.*>|$.*";
               }
               type uint32 {
                 range "1 .. 10";
               }
             }
           }
           leaf remote-ipv4-address {
             description "Destination IPV4 address to reach remote ";
             default "nil";
             type jt:ipv4addr;
           }
           leaf remote-ipv6-address {
             description "Destination IPV6 address to reach remote";
             default "nil";
             type jt:ipv6addr;
           }
           leaf number-of-connectivity-retries {
             description "Number of Connectivity retries ";
             default "2";
             type union {
               type string {
                 pattern "<.*>|$.*";
               }
               type uint32 {
                 range "1 .. 8";
               }
             }
           }
         }
         leaf metadata {
           description "Text metadata attached to interface";
           type string;
         }
         choice enable-disable {
           case case_1 {
             leaf disable {
               description "Disable this interface";
               type empty;
             }
           }
         }
         container fabric-options {
           description "Fabric interface specific options";
           uses apply-advanced;
           list member-interfaces {
             key name;
             junos:cli-feature "homogeneous";
             description "Member interface for the fabric interface";
             leaf name {
               description "Interface name of member";
               junos:cli-feature "nokeyword";
               junos:must "(!((\"interfaces $$ flexible-vlan-tagging\" || (\"interfaces $$ stacked-vlan-tagging\" || (\"interfaces $$ vlan-vci-tagging\" || \"interfaces $$ vlan-tagging\")))))";
               junos:must-message "VLAN configuration is not allowed on fabric member";
               junos:must "(!(any \"tenants <*> interfaces $$\"))";
               junos:must-message "Fabric member can't be part of any tenants";
               junos:must "(!(any \"logical-systems <*> interfaces $$\"))";
               junos:must-message "Fabric member can't be part of any logical system";
               junos:must "(!(\"interfaces $$ disable\"))";
               junos:must-message "fabric member device disable setting is not allowed";
               junos:must "(!(\"interfaces $$ encapsulation\"))";
               junos:must-message "fabric member device encapsulation is not allowed";
               junos:must "(!(\"interfaces $$ mac\"))";
               junos:must-message "fabric member device mac address setting is not allowed";
               junos:must "(!(\"interfaces $$ mtu\"))";
               junos:must-message "fabric member device mtu setting and vlan-tagging is not allowed";
               junos:must "(!(\"interfaces $$ passive-monitor-mode\"))";
               junos:must-message "Fabric member cannot be configured in passive monitor mode";
               junos:must "(!(\"interfaces $$ gigether-options 802.3ad\"))";
               junos:must-message "Fabric member cannot be part of aggregated ethernet";
               junos:must "(!(\"interfaces $$ gigether-options redundant-parent\"))";
               junos:must-message "Fabric member cannot be part of redundant ethernet";
               junos:must "(!(\"interfaces $$ unit\"))";
               junos:must-message "Logical unit is not allowed on fabric member";
               junos:must "(!(\"system autoinstallation\"))";
               junos:must-message "incompatible with 'system autoinstallation'";
               type union {
                 type jt:interface-device;
                 type string {
                   pattern "<.*>|$.*";
                 }
               }
             }
             uses apply-advanced;
           }
           container remote-chassis {
             presence "enable remote-chassis";
             description "Remote chassis reachability";
             uses apply-advanced;
             leaf destination {
               description "Destination IP address to reach remote chassis";
               type jt:ipv4addr;
             }
           }
         }
         container traceoptions {
           presence "enable traceoptions";
           description "Interface trace options";
           uses apply-advanced;
           list flag {
             key name;
             ordered-by user;
             junos:cli-feature "oneliner";
             description "Tracing parameters";
             leaf name {
               junos:cli-feature "nokeyword";
               type enumeration {
                 enum "ipc" {
                   description "Trace interface IPC messages";
                 }
                 enum "event" {
                   description "Trace interface events";
                 }
                 enum "media" {
                   description "Trace interface media changes";
                 }
                 enum "all" {
                   description "Enable all interface trace flags";
                 }
               }
             }
           }
         }
         leaf passive-monitor-mode {
           description "Use interface to tap packets from another router";
           junos:must "(!((\"services nat ipv6-multicast-interfaces $$={all}\" || \"services nat ipv6-multicast-interfaces ${interface}\")))";
           junos:must-message "Can not configure 'services nat ipv6-multicast-interfaces' when passive montioring is enabled for the interface";
           junos:must "(!((\".. encapsulation ethernet-ccc\" || (\".. encapsulation ethernet-tcc\" || (\".. encapsulation ethernet-bridge\" || (\".. encapsulation ethernet-vpls\" || (\".. encapsulation extended-vlan-ccc\" || (\".. encapsulation extended-vlan-tcc\" || (\".. encapsulation extended-vlan-vpls\" || (\".. encapsulation extended-vlan-bridge\" || (\".. encapsulation flexible-ethernet-services\" || (\".. encapsulation vlan-ccc\" || (\".. encapsulation vlan-vci-ccc\" || \".. encapsulation vlan-vpls\")))))))))))))";
           junos:must-message "Not compatible with specified 'encapsulation`";
           type empty;
         }
         choice keepalive_choices {
           case case_1 {
             container keepalives {
               description "Send or demand keepalive messages";
               presence "enable keepalives";
               junos:cli-feature "oneliner";
               uses keepalives_type;
             }
           }
           case case_2 {
             leaf no-keepalives {
               description "Do not send keepalive messages";
               type empty;
             }
           }
         }
         choice traps-choice {
           leaf traps {
             description "Enable SNMP notifications on state changes";
             type empty;
           }
           leaf no-traps {
             description "Don't enable SNMP notifications on state changes";
             type empty;
           }
         }
         choice interface-mib-choice {
           leaf interface-mib {
             description "Enable interface-related MIBs";
             type empty;
           }
           leaf no-interface-mib {
             description "Don't enable interface-related MIBs";
             type empty;
           }
         }
         leaf accounting-profile {
           description "Accounting profile name";
           junos:must "((\"accounting-options interface-profile $$\" || \"accounting-options flat-file-profile $$\"))";
           junos:must-message "referenced accounting profile must be defined";
           type string;
         }
         container anchor-point {
           description "Anchor point";
           uses apply-advanced;
           leaf interface-name {
             description "Interface name";
             junos:cli-feature "nokeyword";
             type union {
               type jt:interface-device;
               type string {
                 pattern "<.*>|$.*";
               }
             }
           }
         }
         choice scheduler_type {
           case case_1 {
             choice per-unit-scheduler-choice {
               leaf per-unit-scheduler {
                 description "Enable subunit queuing on Frame Relay or VLAN IQ interface";
                 type empty;
               }
               leaf no-per-unit-scheduler {
                 description "Don't enable subunit queuing on Frame Relay or VLAN IQ interface";
                 type empty;
               }
             }
           }
           case case_2 {
             leaf shared-scheduler {
               description "Enabled shared queuing on an IQ2 interface";
               junos:must "((\".. vlan-tagging\" || (\".. stacked-vlan-tagging\" || (\".. flexible-vlan-tagging\" || \".. vlan-vci-tagging\"))))";
               junos:must-message "vlan tagging needs to be enabled for shared scheduler";
               type empty;
             }
           }
           case case_3 {
             container hierarchical-scheduler {
               presence "enable hierarchical-scheduler";
               junos:cli-feature "oneliner";
               description "Enable hierarchical scheduling";
               leaf maximum-hierarchy-levels {
                 description "Maximum hierarchy levels";
                 type union {
                   type string {
                     pattern "<.*>|$.*";
                   }
                   type uint32;
                 }
               }
               leaf implicit-hierarchy {
                 description "Implicit hierarchy (follows interface hierarchy)";
                 type empty;
               }
               leaf no-priority-propogation {
                 description "Hierarchical scheduling priority propogation";
                 type empty;
               }
             }
           }
         }
         leaf l2tp-maximum-session {
           description "Maximum L2TP session";
           type union {
             type string {
               pattern "<.*>|$.*";
             }
             type uint32 {
               range "0 .. 64000";
             }
           }
         }
         leaf schedulers {
           description "Number of schedulers to allocate for interface";
           type union {
             type uint32;
             type string {
               pattern "<.*>|$.*";
             }
           }
         }
         leaf cascade-port {
           description "Cascade port";
           junos:must "(!(any \"logical-systems <*> interfaces ${interface}\"))";
           junos:must-message "cascade-port cannot be part of logical-systems config";
           junos:must "(!(\".. flexible-vlan-tagging\"))";
           junos:must-message "cascade-port cannot have flexible-vlan-tagging config";
           junos:must "(!(\".. stacked-vlan-tagging\"))";
           junos:must-message "cascade-port cannot have stacked-vlan-tagging config";
           junos:must "(!(\".. vlan-tagging\"))";
           junos:must-message "cascade-port cannot have vlan-tagging config";
           junos:must "(\"chassis satellite-management\")";
           junos:must-message "chassis satellite-management must be defined";
           type empty;
         }
         leaf port-extender-cascade-port {
           description "NGPE Cascade port";
           junos:must "(!(\".. shared-scheduler\"))";
           junos:must-message "NGPE cascade-port cannot have shared-scheduler config";
           junos:must "(!(\".. hierarchical-scheduler\"))";
           junos:must-message "NGPE cascade-port cannot have hierarchical-scheduler config";
           type empty;
         }
         leaf dce {
           description "Respond to Frame Relay status enquiry messages";
           type empty;
         }
         choice vlan_tag_mode {
           case case_1 {
             leaf vlan-tagging {
               description "802.1q VLAN tagging support";
               type empty;
             }
           }
           case case_2 {
             leaf stacked-vlan-tagging {
               description "Stacked 802.1q VLAN tagging support";
               junos:must "(!((\".. passive-monitor-mode\" || \".. 802.3ad\")))";
               junos:must-message "Not compatible with passive-monitor-mode statement";
               type empty;
             }
           }
           case case_3 {
             leaf flexible-vlan-tagging {
               description "Support for no tagging, or single and double 802.1q VLAN tagging";
               type empty;
             }
           }
           case case_4 {
           }
         }
         leaf native-vlan-id {
           description "Virtual LAN identifier for untagged frames";
           type union {
             type string {
               pattern "<.*>|$.*";
             }
             type uint32 {
               range "0 .. 4094";
             }
           }
         }
         leaf no-native-vlan-insert {
           description "Disable native-vlan-id insertion to untagged frames";
           junos:must "(\".. native-vlan-id\")";
           junos:must-message "native-vlan-id should be configured";
           type empty;
         }
         leaf input-native-vlan-push {
           description "Control native-vlan-id insertion to untagged frames when input-vlan-map push is configured";
           default "enable";
           junos:must "(any \"interfaces ${interface}  unit <*> input-vlan-map push \")";
           junos:must-message "input-native-vlan-push can be set only when input-vlan-map push is configured";
           type enumeration {
             enum "disable" {
               description "Disable input-native-vlan-push";
             }
             enum "enable" {
               description "Enable input-native-vlan-push";
             }
           }
         }
         leaf number-of-sub-ports {
           description "Number of channels to create for a port";
           type union {
             type string {
               pattern "<.*>|$.*";
             }
             type uint32 {
               range "1 .. 8";
             }
           }
         }
         leaf unused {
           description "Disable physical port";
           type empty;
         }
         container timestamp {
           presence "enable timestamp";
           junos:must "(!(\"interfaces ${interface} aggregated-ether-options\"))";
           junos:must-message "timestamp cannot be configured for an aggregated ethernet interface";
           junos:must "(\"forwarding-options tap-aggregation tap-enable\")";
           junos:must-message "Tap-enable under tap aggregation must be set";
           description "Enable timestamp";
           uses apply-advanced;
           leaf ingress {
             description "Enable ingress timestamping";
             type empty;
           }
         }
         leaf speed {
           description "Link speed";
           type enumeration {
             enum "auto" {
               description "Enable auto negotiation of interface speed";
               junos:must "((!(\"interfaces ${interface} gigether-options 802.3ad\") || !(\"interfaces ${interface} ether-options 802.3ad\")))";
               junos:must-message "Auto speed cannot be configured for an aggregated ethernet member link";
               junos:must "((\"interfaces ${interface} gigether-options auto-negotiation\" || \"interfaces ${interface} ether-options auto-negotiation\"))";
               junos:must-message "gigether-options/ether-options auto-negotiation must be enabled";
             }
             enum "auto-10m-100m" {
               description "Enable auto negotiation of limiting interface speed to 10m/100m";
               junos:must "((!(\"interfaces ${interface} gigether-options 802.3ad\") || !(\"interfaces ${interface} ether-options 802.3ad\")))";
               junos:must-message "Auto speed cannot be configured for an aggregated ethernet member link";
               junos:must "((\"interfaces ${interface} gigether-options auto-negotiation\" || \"interfaces ${interface} ether-options auto-negotiation\"))";
               junos:must-message "gigether-options/ether-options auto-negotiation must be enabled";
             }
             enum "10m" {
             }
             enum "100m" {
             }
             enum "1g" {
             }
             enum "2.5g" {
             }
             enum "5g" {
             }
             enum "10g" {
             }
             enum "25g" {
             }
             enum "40g" {
             }
             enum "50g" {
             }
             enum "100g" {
             }
             enum "200g" {
             }
             enum "400g" {
             }
             enum "800g" {
             }
             enum "oc3" {
             }
             enum "oc12" {
             }
             enum "oc48" {
             }
             enum "1.6t" {
             }
           }
         }
         leaf mtu {
           description "Maximum transmit packet size";
           junos:must "(!(\"interfaces ${interface} container-options container-list\"))";
           junos:must-message "mtu is not supported for container child interfaces";
           type union {
             type string {
               pattern "<.*>|$.*";
             }
             type uint32;
           }
         }
         container hold-time {
           junos:cli-feature "oneliner";
           description "Hold time for link up and link down";
           leaf up {
             description "Link up hold time";
             units "milliseconds";
             type union {
               type uint32;
               type string {
                 pattern "<.*>|$.*";
               }
             }
           }
           leaf down {
             description "Link down hold time";
             units "milliseconds";
             type union {
               type uint32;
               type string {
                 pattern "<.*>|$.*";
               }
             }
           }
         }
         container port-extender {
           description "Tunnel binding information for the extended port";
           uses apply-advanced;
           container vxlan {
             presence "enable vxlan";
             description "VXLAN binding information for the extended port";
             uses apply-advanced;
             leaf end-point {
               description "Satellite loopback IP address";
               type jt:ipaddr;
             }
             leaf vni {
               description "VNI of the satellite extended-port";
               type union {
                 type string {
                   pattern "<.*>|$.*";
                 }
                 type uint32 {
                   range "0 .. 16777214";
                 }
               }
             }
           }
         }
         container damping {
           description "Interface damping parameters";
           uses apply-advanced;
           leaf half-life {
             description "Damping half life time";
             default "5";
             units "seconds";
             type union {
               type string {
                 pattern "<.*>|$.*";
               }
               type uint32 {
                 range "1 .. 30";
               }
             }
           }
           leaf max-suppress {
             description "Maximum suppress time";
             default "20";
             units "seconds";
             type union {
               type string {
                 pattern "<.*>|$.*";
               }
               type uint32 {
                 range "1 .. 20000";
               }
             }
           }
           leaf reuse {
             description "Reuse threshold";
             default "1000";
             type union {
               type string {
                 pattern "<.*>|$.*";
               }
               type uint32 {
                 range "1 .. 20000";
               }
             }
           }
           leaf suppress {
             description "Suppress threshold";
             default "2000";
             type union {
               type string {
                 pattern "<.*>|$.*";
               }
               type uint32 {
                 range "1 .. 20000";
               }
             }
           }
           leaf enable {
             description "Enable interface damping";
             type empty;
           }
         }
         container link-degrade-monitor {
           presence "enable link-degrade-monitor";
           description "Enable link degrade monitoring";
           uses apply-advanced;
           choice enable_choice {
             case case_1 {
               leaf link-degrade-monitor-enable {
                 description "Enable Link Degrade Monitoring";
                 type empty;
               }
             }
             case case_2 {
               leaf no-link-degrade-monitor-enable {
                 description "Disable Link Degrade Monitoring";
                 type empty;
               }
             }
           }
           container actions {
             description "Action upon link degrade event";
             uses apply-advanced;
             choice action_choice {
               case case_1 {
                 leaf media-based {
                   description "Media based";
                   type empty;
                 }
               }
             }
           }
           container recovery {
             description "Link degrade recovery mechanism";
             uses apply-advanced;
             leaf timer {
               description "Auto recovery timer in seconds";
               default "1800";
               junos:must "(!(\".. manual\"))";
               junos:must-message "Recovery mechanism must be auto to configure recovery timer";
               type union {
                 type uint32;
                 type string {
                   pattern "<.*>|$.*";
                 }
               }
             }
             choice receovery_choice {
               case case_1 {
                 leaf auto {
                   description "Automatic recovery";
                   type empty;
                 }
               }
               case case_2 {
                 leaf manual {
                   description "Manual recovery";
                   type empty;
                 }
               }
             }
           }
           container thresholds {
             description "Link degrade threshold parameters";
             uses apply-advanced;
             leaf set {
               description "BER at which link considered degraded(1..16)";
               default "1e-7";
               type string {
                 junos:posix-pattern "^1e-(1[0-6]?|[2-9])$";
                 junos:pattern-message "Ber threshold value in format: 1e-n, n = 1..16";
               }
             }
             leaf clear {
               description "BER at which link considered improved(1..16)";
               default "1e-12";
               type string {
                 junos:posix-pattern "^1e-(1[0-6]?|[2-9])$";
                 junos:pattern-message "Ber threshold value in format: 1e-n, n = 1..16";
               }
             }
             leaf warning-set {
               description "BER at which link degrade warning raised(1..16)";
               default "1e-9";
               type string {
                 junos:posix-pattern "^1e-(1[0-6]?|[2-9])$";
                 junos:pattern-message "Ber threshold value in format: 1e-n, n = 1..16";
               }
             }
             leaf warning-clear {
               description "BER at which link degrade warning cleared(1..16)";
               default "1e-11";
               type string {
                 junos:posix-pattern "^1e-(1[0-6]?|[2-9])$";
                 junos:pattern-message "Ber threshold value in format: 1e-n, n = 1..16";
               }
             }
             leaf interval {
               description "Consecutive link degrade events";
               default "10";
               type union {
                 type string {
                   pattern "<.*>|$.*";
                 }
                 type uint32 {
                   range "1 .. 256";
                 }
               }
             }
           }
         }
         container satop-options {
           junos:must "((!(\".. t1-options framing\") && !(\".. e1-options framing\")))";
           junos:must-message "SAToP & Framing cannot be configured on same interface";
           junos:must "(!(\".. ima-link-options\"))";
           junos:must-message "SAToP & IMA cannot be configured on same interface";
           junos:must "((!(\"interfaces ${interface} container-options\") || (\"interfaces ${interface} container-options container-type\" || \"interfaces ${interface} container-options allow-configuration-override\")))";
           junos:must-message "satop-options cannot be configured without allow-configuration-override";
           junos:cli-feature "oneliner-plus";
           description "Structure-Agnostic TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf payload-size {
             description "Number of payload bytes per packet";
             type union {
               type string {
                 pattern "<.*>|$.*";
               }
               type uint32 {
                 range "64 .. 1024";
               }
             }
           }
           container excessive-packet-loss-rate {
             junos:cli-feature "oneliner-plus";
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         container cesopsn-options {
           junos:must "((!(\"interfaces ${interface} container-options\") || (\"interfaces ${interface} container-options container-type\" || \"interfaces ${interface} container-options allow-configuration-override\")))";
           junos:must-message "cesopsn-options cannot be configured without allow-configuration-override";
           junos:cli-feature "oneliner-plus";
           description "Structure-Aware TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf packetization-latency {
             description "Number of microseconds to create packets";
             units "microseconds";
             type union {
               type string {
                 pattern "<.*>|$.*";
               }
               type uint32 {
                 range "1000 .. 8000";
               }
             }
           }
           leaf payload-size {
             description "Number of payload bytes per packet";
             type union {
               type string {
                 pattern "<.*>|$.*";
               }
               type uint32 {
                 range "64 .. 1024";
               }
             }
           }
           container excessive-packet-loss-rate {
             junos:cli-feature "oneliner-plus";
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         list multi-chassis-protection {
           key name;
           description "Inter-Chassis protection configuration";
           junos:must "(\"interfaces ${interface} aggregated-ether-options mc-ae mode active-active\")";
           junos:must-message "multi-chassis-protection is only supported for MC-AE active-active mode";
           uses multi-chassis-protection-group;
         }
         container clocking {
           junos:cli-feature "oneliner";
           description "Interface clock source";
           choice clocking_choices {
             case case_1 {
               leaf internal {
                 description "Clocking provided by local system";
                 type empty;
               }
             }
             case case_2 {
               container external {
                 presence "enable external";
                 description "Clocking provided by DCE (loop timing)";
               }
             }
           }
         }
         leaf link-mode {
           description "Link operational mode";
           type enumeration {
             enum "automatic" {
               description "Automatically negotiate duplex";
             }
             enum "half-duplex" {
               description "Half-duplex operation";
             }
             enum "full-duplex" {
               description "Full-duplex operation";
             }
           }
         }
         leaf encapsulation {
           description "Physical link-layer encapsulation";
           junos:must "(!(\"interfaces ${interface} container-options container-list\"))";
           junos:must-message "encapsulation is not supported for container child interfaces";
           type enumeration {
             enum "ethernet" {
               description "Ethernet physical media";
             }
             enum "fddi" {
               description "FDDI physical media";
             }
             enum "token-ring" {
               description "Token Ring physical media";
             }
             enum "ppp" {
               description "Serial PPP device";
             }
             enum "ppp-ccc" {
               description "Serial PPP device for a cross-connect";
             }
             enum "ppp-tcc" {
               description "Serial PPP device for a translational cross-connect";
             }
             enum "ether-vpls-ppp" {
               description "Ethernet VPLS over PPP (bridging) device";
             }
             enum "frame-relay" {
               description "Frame Relay encapsulation";
             }
             enum "frame-relay-ccc" {
               description "Frame Relay for cross-connect";
             }
             enum "frame-relay-tcc" {
               description "Frame Relay for translational cross-connect";
             }
             enum "extended-frame-relay-ccc" {
               description "Any Frame Relay DLCI for cross-connect";
             }
             enum "extended-frame-relay-tcc" {
               description "Any Frame Relay DLCI for translational cross-connect";
             }
             enum "flexible-frame-relay" {
               description "Multiple Frame Relay encapsulations";
             }
             enum "frame-relay-port-ccc" {
               description "Frame Relay port encapsulation for a cross-connect";
             }
             enum "frame-relay-ether-type" {
               description "Cisco-compatible Frame Relay encapsulation";
             }
             enum "frame-relay-ether-type-tcc" {
               description "Cisco-compatible Frame Relay encapsulation for translational cross-connect";
             }
             enum "extended-frame-relay-ether-type-tcc" {
               description "Cisco-compatible Frame Relay encapsulation any DLCI for translational cross-connect";
             }
             enum "cisco-hdlc" {
               description "Cisco-compatible HDLC framing";
             }
             enum "cisco-hdlc-ccc" {
               description "Cisco-compatible HDLC framing for a cross-connect";
             }
             enum "cisco-hdlc-tcc" {
               description "Cisco-compatible HDLC framing for a translational cross-connect";
             }
             enum "vlan-ccc" {
               description "802.1q tagging for a cross-connect";
             }
             enum "extended-vlan-ccc" {
               description "Nonstandard TPID tagging for a cross-connect";
             }
             enum "ethernet-ccc" {
               description "Ethernet cross-connect";
             }
             enum "flexible-ethernet-services" {
               description "Allows per-unit Ethernet encapsulation configuration";
             }
             enum "smds-dxi" {
               description "SMDS DXI framing";
             }
             enum "atm-pvc" {
               description "ATM permanent virtual circuits";
             }
             enum "atm-ccc-cell-relay" {
               description "ATM cell relay encapsulation for cross-connect";
             }
             enum "ethernet-over-atm" {
               description "Ethernet over ATM encapsulation";
             }
             enum "ethernet-tcc" {
               description "Ethernet translational cross-connect";
             }
             enum "extended-vlan-tcc" {
               description "802.1q tagging for a translational cross-connect";
             }
             enum "multilink-frame-relay-uni-nni" {
               description "Multilink Frame Relay UNI NNI (FRF.16) encapsulation";
             }
             enum "satop" {
               description "Structure-Agnostic TDM over Packet encapsulation";
               junos:must "((!(\".. t1-options framing\") && !(\".. e1-options framing\")))";
               junos:must-message "SAToP & Framing cannot be configured on same interface";
               junos:must "(!(\".. ima-link-options\"))";
               junos:must-message "SAToP & IMA cannot be configured on same interface";
             }
             enum "cesopsn" {
               description "Structure-Agnostic TDM over Packet encapsulation";
             }
             enum "ima" {
               description "Inverse Multiplexing for ATM";
               junos:must "(!(\".. satop-options\"))";
               junos:must-message "SAToP & IMA cannot be configured on same interface";
             }
             enum "ethernet-vpls" {
               description "Ethernet virtual private LAN service";
             }
             enum "ethernet-bridge" {
               description "Ethernet layer-2 bridging";
             }
             enum "vlan-vpls" {
               description "VLAN virtual private LAN service";
             }
             enum "vlan-vci-ccc" {
               description "CCC for VLAN Q-in-Q and ATM VPI/VCI interworking";
               junos:must "(\"interfaces ${interface} vlan-vci-tagging\")";
               junos:must-message "valid only with vlan-vci-tagging mode";
             }
             enum "extended-vlan-vpls" {
               description "Extended VLAN virtual private LAN service";
             }
             enum "extended-vlan-bridge" {
               description "VLAN layer-2 bridging";
             }
             enum "multilink-ppp" {
               description "Multilink PPP";
             }
             enum "generic-services" {
               description "Generic services";
             }
           }
         }
         leaf network-isolation-profile {
           description "Attach a network isolation profile on this interface";
           junos:must "(!((\".. .. .. protocols network-isolation group $$ service-tracking-action lacp-out-of-sync\" && !(\".. aggregated-ether-options lacp\"))))";
           junos:must-message "lacp-out-of-sync is allowed only on LACP interfaces";
           junos:must "(\".. .. .. protocols network-isolation group $$ service-tracking-action\")";
           junos:must-message "service-tracking-action must be configured";
           junos:must "((\".. .. .. protocols network-isolation group $$ detection service-tracking\" || \".. .. .. protocols network-isolation group $$ detection link-tracking\"))";
           junos:must-message "service-tracking or link-tracking must be configured";
           type string;
         }
         container esi {
           description "ESI configuration of multi-homed interface";
           uses apply-advanced;
           container auto-derive {
             description "Auto-derive ESI value for the interface";
             uses apply-advanced;
             choice esitype {
               case case_1 {
                 leaf lacp-pe-system-id-and-admin-key {
                   description "Auto-derive ESI from lacp pe system-id and admin key";
                   type empty;
                 }
               }
               case case_2 {
                 leaf type-1-lacp {
                   description "Auto-generate Type1 ESI LACP";
                   junos:must "(\".. .. .. aggregated-ether-options lacp\")";
                   junos:must-message "Aggregated-ether-options lacp must be configured";
                   type empty;
                 }
               }
               case case_3 {
                 container type-3-system-mac {
                   description "Auto-generate Type3 ESI System-mac";
                   uses apply-advanced;
                   leaf mac {
                     description "System mac";
                     junos:must "(\".. local-discriminator\")";
                     junos:must-message "Local-discriminator must be configured";
                     type jt:mac-unicast;
                   }
                   leaf local-discriminator {
                     description "Local-discriminator";
                     junos:must "(\".. mac\")";
                     junos:must-message "Mac must be configured";
                     type union {
                       type string {
                         pattern "<.*>|$.*";
                       }
                       type int32 {
                         range "0 .. 16777215";
                       }
                     }
                   }
                 }
               }
             }
           }
           leaf identifier {
             description "ESI value for the interface";
             junos:cli-feature "nokeyword";
             junos:must "(!(\".. .. gigether-options 802.3ad\"))";
             junos:must-message "ESI cannot be configured for member link interfaces";
             junos:must "(!(any \"interfaces <*> unit <*> esi $$\"))";
             junos:must-message "ESI value must be unique across all IFDs";
             junos:must "(unique \"interfaces <*> esi $$\")";
             junos:must-message "ESI value must be unique across all IFDs";
             junos:must "(!(\"interfaces ${interface} esi auto-derive\"))";
             junos:must-message "ESI identifier can not be configured when auto-derive is configured under IFD";
             type jt:esi;
           }
           choice mode {
             case case_1 {
               leaf single-active {
                 description "Single-active mode";
                 type empty;
               }
             }
             case case_2 {
               leaf all-active {
                 description "All-active mode";
                 type empty;
               }
             }
           }
           container df-election-granularity {
             presence "enable df-election-granularity";
             description "DF Election Granularity Selection ";
             uses apply-advanced;
             choice mode {
               case case_1 {
                 container per-esi {
                   presence "enable per-esi";
                   description "DF Election Granularity Per Esi";
                   uses apply-advanced;
                   leaf lacp-oos-on-ndf {
                     description "Lacp Oos";
                     junos:must "(!(\"interfaces ${interface} esi all-active\"))";
                     junos:must-message "lacp-oos-on-ndf can be configured only with single-active";
                     junos:must "(\"interfaces ${interface} aggregated-ether-options lacp\")";
                     junos:must-message "LACP must be enbled for lacp-oos-on-ndf";
                     type empty;
                   }
                 }
               }
               case case_2 {
                 leaf per-esi-vlan {
                   description "Per Esi Vlan";
                   type empty;
                 }
               }
               case case_3 {
                 leaf per-evi {
                   description "Per Esi EVI";
                   type empty;
                 }
               }
             }
           }
           container df-election-type {
             presence "enable df-election-type";
             description "DF Election Type";
             uses apply-advanced;
             choice pref_choice {
               case case_1 {
                 container preference {
                   presence "enable preference";
                   description "Preference based DF election";
                   uses apply-advanced;
                   leaf value {
                     description "Preference value for EVPN Multihoming DF election";
                     default "32767";
                     type union {
                       type string {
                         pattern "<.*>|$.*";
                       }
                       type uint32 {
                         range "0 .. 65535";
                       }
                     }
                   }
                   leaf non-revertive {
                     description "Don't allow DF Election preemption";
                     type empty;
                   }
                   leaf least {
                     description "Use least preference in DF election";
                     type empty;
                   }
                 }
               }
             }
             choice mod_choice {
               case case_1 {
                 container mod {
                   presence "enable mod";
                   junos:must "(!(\".. preference\"))";
                   junos:must-message "preference must not be configured";
                   description "MOD based DF election";
                 }
               }
             }
           }
           leaf source-bmac {
             description "Unicast Source B-MAC address per ESI for PBB-EVPN";
             junos:must "(!(any \"routing-instances <*> service-groups <*> pbb-service-options source-bmac $$\"))";
             junos:must-message "Source B-MAC must be unique across all routing-instances";
             junos:must "(!(any \"interfaces <*> unit <*> esi source-bmac $$\"))";
             junos:must-message "Source B-MAC must be unique under all IFDs and IFLs";
             junos:must "(unique \"interfaces <*> esi source-bmac $$\")";
             junos:must-message "Source B-MAC must be unique under all IFDs and IFLs";
             type jt:mac-unicast;
           }
           leaf anycast {
             description "ESI anycast Multihoming";
             type empty;
           }
         }
         container framing {
           description "Frame type";
           uses apply-advanced;
           choice frame {
             case case_1 {
               leaf lan-phy {
                 description "802.3ae 10-Gbps LAN-mode interface";
                 type empty;
               }
             }
             case case_2 {
               leaf wan-phy {
                 description "802.3ae 10-Gbps WAN-mode interface";
                 type empty;
               }
             }
             case case_3 {
               leaf sonet {
                 description "SONET framing";
                 type empty;
               }
             }
             case case_4 {
               leaf sdh {
                 description "SDH framing";
                 type empty;
               }
             }
           }
         }
         container lmi {
           description "Local Management Interface settings";
           uses apply-advanced;
           leaf n391dte {
             description "DTE full status polling interval";
             junos:must "(!((\".. .. dce\" || \".. .. loose-ncp\")))";
             junos:must-message "LMI DTE options not valid for DCE interface";
             type union {
               type string {
                 pattern "<.*>|$.*";
               }
               type uint16 {
                 range "1 .. 255";
               }
             }
           }
           leaf n392dce {
             description "DCE error threshold";
             junos:must "((\".. .. dce\" || \".. .. loose-ncp\"))";
             junos:must-message "LMI DCE options not valid for DTE interface";
             type union {
               type string {
                 pattern "<.*>|$.*";
               }
               type uint16 {
                 range "1 .. 10";
               }
             }
           }
           leaf n392dte {
             description "DTE error threshold";
             junos:must "(!((\".. .. dce\" || \".. .. loose-ncp\")))";
             junos:must-message "LMI DTE options not valid for DCE interface";
             type union {
               type string {
                 pattern "<.*>|$.*";
               }
               type uint16 {
                 range "1 .. 10";
               }
             }
           }
           leaf n393dce {
             description "DCE monitored event count";
             junos:must "((\".. .. dce\" || \".. .. loose-ncp\"))";
             junos:must-message "LMI DCE options not valid for DTE interface.";
             type union {
               type string {
                 pattern "<.*>|$.*";
               }
               type uint16 {
                 range "1 .. 10";
               }
             }
           }
           leaf n393dte {
             description "DTE monitored event count";
             junos:must "(!((\".. .. dce\" || \".. .. loose-ncp\")))";
             junos:must-message "LMI DTE options not valid for DCE interface";
             type union {
               type string {
                 pattern "<.*>|$.*";
               }
               type uint16 {
                 range "1 .. 10";
               }
             }
           }
           leaf t391dte {
             description "DTE polling timer";
             units "seconds";
             junos:must "(!((\".. .. dce\" || \".. .. loose-ncp\")))";
             junos:must-message "LMI DTE options not valid for DCE interface";
             type union {
               type string {
                 pattern "<.*>|$.*";
               }
               type uint16 {
                 range "5 .. 30";
               }
             }
           }
           leaf t392dce {
             description "DCE polling verification timer";
             units "seconds";
             junos:must "((\".. .. dce\" || \".. .. loose-ncp\"))";
             junos:must-message "LMI DCE options not valid for DTE interface.";
             type union {
               type string {
                 pattern "<.*>|$.*";
               }
               type uint16 {
                 range "5 .. 30";
               }
             }
           }
           leaf lmi-type {
             description "Specify the Frame Relay LMI type";
             type enumeration {
               enum "ansi" {
                 description "Use ANSI Annex D LMI";
               }
               enum "itu" {
                 description "Use ITU Q933a Annex A LMI";
               }
               enum "c-lmi" {
                 description "Use Consortium LMI";
               }
             }
           }
         }
         container mlfr-uni-nni-bundle-options {
           description "Multilink Frame Relay UNI NNI (FRF.16) management settings";
           uses apply-advanced;
           container cisco-interoperability {
             description "FRF.16 Cisco interoperability settings";
             uses apply-advanced;
             leaf send-lip-remove-link-for-link-reject {
               description "Send Link Integrity Protocol remove link on receiving add-link rejection";
               type empty;
             }
           }
           leaf mrru {
             description "Maximum received reconstructed unit";
             units "bytes";
             type union {
               type string {
                 pattern "<.*>|$.*";
               }
               type uint16 {
                 range "1500 .. 4500";
               }
             }
           }
           leaf yellow-differential-delay {
             description "Yellow differential delay among bundle links to give warning";
             units "milliseconds";
             type union {
               type string {
                 pattern "<.*>|$.*";
               }
               type uint16 {
                 range "3 .. 2000";
               }
             }
           }
           leaf red-differential-delay {
             description "Red differential delay among bundle links to take action";
             units "milliseconds";
             type union {
               type string {
                 pattern "<.*>|$.*";
               }
               type uint16 {
                 range "5 .. 2000";
               }
             }
           }
           leaf action-red-differential-delay {
             description "Type of actions when differential delay exceeds red limit";
             type enumeration {
               enum "remove-link" {
                 description "Remove bundle link from service when exceeding red limit";
               }
               enum "disable-tx" {
                 description "Disable transfer of bundle link when exceeding red limit";
               }
             }
           }
           leaf fragment-threshold {
             description "Fragmentation threshold";
             units "bytes";
             type union {
               type string {
                 pattern "<.*>|$.*";
               }
               type uint32 {
                 range "64 .. 16320";
               }
             }
           }
           leaf drop-timeout {
             description "Drop timeout";
             units "milliseconds";
             type union {
               type string {
                 pattern "<.*>|$.*";
               }
               type uint16 {
                 range "0 .. 2000";
               }
             }
           }
           leaf link-layer-overhead {
             description "Link layer bit stuffing overhead (0.0 .. 50.0 percent)";
             type jt:unsigned-float;
           }
           leaf lmi-type {
             description "Specify the multilink Frame Relay UNI NNI LMI type";
             type enumeration {
               enum "ansi" {
                 description "Use ANSI Annex D LMI";
               }
               enum "itu" {
                 description "Use ITU Q933a Annex A LMI";
               }
               enum "c-lmi" {
                 description "Use Consortium LMI";
               }
             }
           }
           leaf minimum-links {
             description "Minimum number of links to sustain the bundle";
             type union {
               type string {
                 pattern "<.*>|$.*";
               }
               type uint16 {
                 range "1 .. 8";
               }
             }
           }
           leaf hello-timer {
             description "LIP hello timer";
             type union {
               type string {
                 pattern "<.*>|$.*";
               }
               type uint16 {
                 range "5 .. 180";
               }
             }
           }
           leaf acknowledge-timer {
             description "LIP ack timer";
             type union {
               type string {
                 pattern "<.*>|$.*";
               }
               type uint16 {
                 range "1 .. 10";
               }
             }
           }
           leaf acknowledge-retries {
             description "LIP ack retry times";
             type union {
               type string {
                 pattern "<.*>|$.*";
               }
               type uint16 {
                 range "1 .. 5";
               }
             }
           }
           leaf n391 {
             description "Multilink Frame Relay UNI NNI full status polling counter";
             type union {
               type string {
                 pattern "<.*>|$.*";
               }
               type uint16 {
                 range "1 .. 255";
               }
             }
           }
           leaf n392 {
             description "Multilink Frame Relay UNI NNI LMI error threshold";
             type union {
               type string {
                 pattern "<.*>|$.*";
               }
               type uint16 {
                 range "1 .. 10";
               }
             }
           }
           leaf n393 {
             description "Multilink Frame Relay UNI NNI LMI monitored event count";
             type union {
               type string {
                 pattern "<.*>|$.*";
               }
               type uint16 {
                 range "1 .. 10";
               }
             }
           }
           leaf t391 {
             description "Multilink Frame Relay UNI NNI link integrity verify polling timer";
             type union {
               type string {
                 pattern "<.*>|$.*";
               }
               type uint16 {
                 range "5 .. 30";
               }
             }
           }
           leaf t392 {
             description "Multilink Frame Relay UNI NNI polling verification timer";
             type union {
               type string {
                 pattern "<.*>|$.*";
               }
               type uint16 {
                 range "5 .. 30";
               }
             }
           }
         }
         leaf mac {
           description "Hardware MAC address";
           type jt:mac-unicast;
         }
         leaf no-forwarding-viable {
           description "Disable forwarding";
           type empty;
         }
         container p4rt {
           description "P4-runtime interfaces";
           uses apply-advanced;
           leaf id {
             description "Port number";
             type union {
               type string {
                 pattern "<.*>|$.*";
               }
               type uint64 {
                 range "1 .. 4294967296";
               }
             }
           }
           leaf node-id {
             description "Device Id";
             type union {
               type string {
                 pattern "<.*>|$.*";
               }
               type uint64 {
                 range "1 .. 18446744073709551615";
               }
             }
           }
         }
         container receive-bucket {
           description "Set receive bucket parameters";
           uses dcd_rx_bucket_config;
         }
         container transmit-bucket {
           description "Set transmit bucket parameters";
           uses dcd_tx_bucket_config;
         }
         leaf shared-interface {
           description "Enable shared interface on the interface";
           type empty;
         }
         container sonet-options {
           description "SONET interface-specific options";
           junos:must "((!(\"interfaces ${interface} container-options\") || (\"interfaces ${interface} container-options container-type\" || \"interfaces ${interface} container-options allow-configuration-override\")))";
           junos:must-message "sonet-options cannot be configured without allow-configuration-override";
           uses sonet_options_type;
         }
         container logical-tunnel-options {
           description "Logical Tunnel interface-specific options";
           uses apply-advanced;
           container link-protection {
             presence "enable link-protection";
             junos:must "(any \"interfaces ${interface} redundancy-group member-interface <*> active\")";
             junos:must-message "Active and Backup child links must be configured to use link-protection";
             description "Enable link protection mode";
             uses apply-advanced;
             leaf revertive {
               description "Revert back (Default mode) from active backup link to primary, if primary is UP";
               junos:must "(!(\"interfaces ${interface} logical-tunnel-options link-protection non-revertive\"))";
               junos:must-message "link-protection revertive and non-revertive are mutually exclusive";
               junos:must "(any \"interfaces ${interface} redundancy-group member-interface <*> active\")";
               junos:must-message "link-protection mode can be configured only when link-protection is enabled";
               type empty;
             }
             leaf non-revertive {
               description "Do not revert back from active backup link to primary, if primary is UP";
               junos:must "(!(\"interfaces ${interface} logical-tunnel-options link-protection revertive\"))";
               junos:must-message "link-protection revertive and non-revertive are mutually exclusive";
               junos:must "(any \"interfaces ${interface} redundancy-group member-interface <*> active\")";
               junos:must-message "link-protection mode can be configured only when link-protection is enabled";
               type empty;
             }
           }
           leaf per-unit-mac-disable {
             description "Disable the creation of per unit mac address on LT IFLs for VPLS/CCC encaps";
             type empty;
           }
         }
         container aggregated-sonet-options {
           description "Aggregated SONET interface-specific options";
           uses apply-advanced;
           leaf minimum-links {
             description "Minimum number of aggregated links";
             type union {
               type string {
                 pattern "<.*>|$.*";
               }
               type uint16;
             }
           }
           leaf link-speed {
             description "Aggregated links speed";
             type enumeration {
               enum "oc3" {
                 description "Links are OC-3c or STM-1c";
               }
               enum "oc12" {
                 description "Links are OC-12c or STM-4c";
               }
               enum "oc48" {
                 description "Links are OC-48c or STM-16c";
               }
               enum "oc192" {
                 description "Links are OC-192c or STM-64c";
               }
               enum "oc768" {
                 description "Links are OC-768c or STM-256c";
               }
               enum "mixed" {
                 description "Links are various speeds";
               }
             }
           }
           leaf minimum-bandwidth {
             description "Minimum bandwidth necessary to sustain bundle";
             units "bps";
             type union {
               type string {
                 pattern "<.*>|$.*";
               }
               type uint64 {
                 range "0 .. 159232000000";
               }
             }
           }
         }
         container atm-options {
           junos:must "((!(\"interfaces ${interface} container-options\") || (\"interfaces ${interface} container-options container-type\" || !(\"interfaces ${interface} container-options container-list\"))))";
           junos:must-message "atm-options cannot be configured on container children";
           description "ATM interface-specific options";
           uses apply-advanced;
           leaf pic-type {
             description "Type of ATM PIC (ATM I, ATM II or ATM CE)";
             type enumeration {
               enum "atm-ce" {
                 description "CE PIC";
               }
               enum "atm2" {
                 description "ATM II IQ PIC";
               }
               enum "atm1" {
                 description "ATM I PIC";
                 junos:must "(!(\"interfaces ${interface} container-options\"))";
                 junos:must-message "Only ATM-II pics are supported as container member link";
               }
             }
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf use-null-cw {
             description "Always insert/strip null control words with cell-relay";
             type empty;
           }
           container promiscuous-mode {
             presence "enable promiscuous-mode";
             description "Set ATM interface to promiscuous mode";
             uses apply-advanced;
             list vpi {
               key name;
               ordered-by user;
               junos:cli-feature "oneliner";
               description "Open this VPI in promiscuous mode";
               leaf name {
                 description "Virtual path index";
                 junos:cli-feature "nokeyword";
                 type union {
                   type string {
                     pattern "<.*>|$.*";
                   }
                   type uint32 {
                     range "0 .. 255";
                   }
                 }
               }
             }
           }
           list vpi {
             key name;
             ordered-by user;
             description "Define a virtual path";
             leaf name {
               description "Virtual path index";
               junos:cli-feature "nokeyword";
               type union {
                 type string {
                   pattern "<.*>|$.*";
                 }
                 type uint32 {
                   range "0 .. 255";
                 }
               }
             }
             uses apply-advanced;
             leaf maximum-vcs {
               description "Maximum number of virtual circuits on this VP";
               junos:must "(!(\"interfaces ${interface} container-options\"))";
               junos:must-message "Only ATM-II pics are supported as container member link";
               type union {
                 type uint32;
                 type string {
                   pattern "<.*>|$.*";
                 }
               }
             }
             container shaping {
               description "Virtual path traffic-shaping options";
               uses dcd_shaping_config;
             }
             container oam-period {
               junos:cli-feature "oneliner";
               description "F4 OAM cell period";
               choice oam_period_choices {
                 case case_1 {
                   leaf oam-period {
                     description "F4 OAM cell period";
                     junos:cli-feature "nokeyword";
                     units "seconds";
                     type union {
                       type string {
                         pattern "<.*>|$.*";
                       }
                       type uint32 {
                         range "1 .. 900";
                       }
                     }
                   }
                 }
                 case case_2 {
                   container disable {
                     presence "enable disable";
                     junos:cli-feature "oneliner";
                     description "Disable F4 OAM loopback";
                   }
                 }
               }
             }
             container oam-liveness {
               description "F4 OAM virtual path liveness parameters";
               uses apply-advanced;
               leaf up-count {
                 description "Number of F4 OAM cells to consider VP up";
                 type union {
                   type string {
                     pattern "<.*>|$.*";
                   }
                   type uint32 {
                     range "1 .. 255";
                   }
                 }
               }
               leaf down-count {
                 description "Number of F4 OAM cells to consider VP down";
                 type union {
                   type string {
                     pattern "<.*>|$.*";
                   }
                   type uint32 {
                     range "1 .. 255";
                   }
                 }
               }
             }
           }
           container ilmi {
             presence "enable ilmi";
             description "Enable Interim Local Management Interface";
             uses apply-advanced;
           }
           list linear-red-profiles {
             key name;
             ordered-by user;
             junos:cli-feature "homogeneous";
             junos:cli-feature "oneliner";
             description "ATM2 CoS virtual circuit drop profiles";
             leaf name {
               description "Linear RED profile name";
               junos:cli-feature "nokeyword";
               type string {
                 junos:posix-pattern "^.{1,64}$";
                 junos:pattern-message "Must be string of 64 characters or less";
               }
             }
             leaf queue-depth {
               description "Maximum queue depth";
               units "cells";
               type string;
             }
             leaf high-plp-threshold {
               description "Fill level percentage when linear RED is applied for high PLP";
               type union {
                 type string {
                   pattern "<.*>|$.*";
                 }
                 type uint32 {
                   range "0 .. 100";
                 }
               }
             }
             leaf low-plp-threshold {
               description "Fill level percentage when linear RED is applied for low PLP";
               type union {
                 type string {
                   pattern "<.*>|$.*";
                 }
                 type uint32 {
                   range "0 .. 100";
                 }
               }
             }
             leaf high-plp-max-threshold {
               description "Fill level percentage with 100 percent packet drop for high PLP";
               type union {
                 type string {
                   pattern "<.*>|$.*";
                 }
                 type uint32 {
                   range "0 .. 100";
                 }
               }
             }
             leaf low-plp-max-threshold {
               description "Fill level percentage with 100 percent packet drop for low PLP";
               type union {
                 type string {
                   pattern "<.*>|$.*";
                 }
                 type uint32 {
                   range "0 .. 100";
                 }
               }
             }
           }
           list scheduler-maps {
             key name;
             ordered-by user;
             junos:cli-feature "homogeneous";
             description "ATM2 CoS parameters assigned to forwarding classes";
             leaf name {
               description "ATM2 CoS scheduler map name";
               junos:cli-feature "nokeyword";
               type string {
                 junos:posix-pattern "^((default)|(.{1,64}))$";
                 junos:pattern-message "Must be a string of 64 characters or less and not \'default\'";
               }
             }
             uses apply-advanced;
             leaf vc-cos-mode {
               description "ATM2 virtual circuit CoS mode";
               type enumeration {
                 enum "strict" {
                   description "Always schedule high priority queue first";
                 }
                 enum "alternate" {
                   description "Every other packet from high priority queue (default)";
                 }
               }
             }
             list forwarding-class {
               key name;
               ordered-by user;
               description "Scheduling parameters associated with forwarding class";
               leaf name {
                 description "Forwarding class name";
                 junos:cli-feature "nokeyword";
                 type string {
                   junos:posix-pattern "^.{1,64}$";
                   junos:pattern-message "Must be string of 64 characters or less";
                 }
               }
               uses apply-advanced;
               leaf priority {
                 description "Queuing priority assigned to forwarding class";
                 type enumeration {
                   enum "low" {
                     description "Low priority queuing";
                   }
                   enum "high" {
                     description "High priority queuing";
                   }
                 }
               }
               container transmit-weight {
                 junos:cli-feature "oneliner";
                 description "Transmit weight";
                 choice weight-method {
                   case case_1 {
                     leaf percent {
                       description "Transmit weight as percentage";
                       type union {
                         type string {
                           pattern "<.*>|$.*";
                         }
                         type uint32 {
                           range "5 .. 100";
                         }
                       }
                     }
                   }
                   case case_2 {
                     leaf cells {
                       description "Transmit weight by cells count";
                       type string;
                     }
                   }
                 }
               }
               choice drop-profile-method {
                 case case_1 {
                   container epd-threshold {
                     description "Early packet discard threshold for ATM2";
                     junos:cli-feature "oneliner";
                     uses epd_threshold_config;
                   }
                 }
                 case case_2 {
                   leaf linear-red-profile {
                     description "Linear RED profile profile name";
                     type string;
                   }
                 }
               }
             }
           }
           container mpls {
             description "MPLS options";
             uses mpls_ifd_options;
           }
           choice payload-scrambler-choice {
             leaf payload-scrambler {
               description "Enable payload scrambling";
               type empty;
             }
             leaf no-payload-scrambler {
               description "Don't enable payload scrambling";
               type empty;
             }
           }
         }
         container multiservice-options {
           description "Multiservice interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
           choice dump-on-flow-control-choice {
             leaf dump-on-flow-control {
               description "Enable dumping for this interface on prolonged flow-control";
               status deprecated;
               type empty;
             }
             leaf no-dump-on-flow-control {
               description "Don't enable dumping for this interface on prolonged flow-control";
               status deprecated;
               type empty;
             }
           }
           choice reset-on-flow-control-choice {
             leaf reset-on-flow-control {
               description "Enable resetting this interface on prolonged flow-control";
               status deprecated;
               type empty;
             }
             leaf no-reset-on-flow-control {
               description "Don't enable resetting this interface on prolonged flow-control";
               status deprecated;
               type empty;
             }
           }
           container flow-control-options {
             description "Flow control configuration";
             uses apply-advanced;
             leaf dump-on-flow-control {
               description "Cause core dump during prolonged flow-control";
               junos:must "(!(\".. up-on-flow-control\"))";
               junos:must-message "Option not valid with up-on-flow-control";
               junos:must "(!(\".. down-on-flow-control\"))";
               junos:must-message "Option not valid with down-on-flow-control";
               junos:must "(!(\".. reset-on-flow-control\"))";
               junos:must-message "Option not valid with reset-on-flow-control";
               type empty;
             }
             leaf reset-on-flow-control {
               description "Reset interface during prolonged flow-control";
               junos:must "(!(\".. up-on-flow-control\"))";
               junos:must-message "Option not valid with up-on-flow-control";
               junos:must "(!(\".. down-on-flow-control\"))";
               junos:must-message "Option not valid with down-on-flow-control";
               junos:must "(!(\".. dump-on-flow-control\"))";
               junos:must-message "Option not valid with dump-on-flow-control";
               type empty;
             }
             leaf down-on-flow-control {
               description "Bring interface down during prolonged flow-control";
               junos:must "(!(\".. up-on-flow-control\"))";
               junos:must-message "Option not valid with up-on-flow-control";
               junos:must "(!(\".. reset-on-flow-control\"))";
               junos:must-message "Option not valid with reset-on-flow-control";
               junos:must "(!(\".. dump-on-flow-control\"))";
               junos:must-message "Option not valid with dump-on-flow-control";
               type empty;
             }
             leaf up-on-flow-control {
               description "Keep interface up during prolonged flow-control";
               junos:must "(!(\".. down-on-flow-control\"))";
               junos:must-message "Option not valid with down-on-flow-control";
               junos:must "(!(\".. reset-on-flow-control\"))";
               junos:must-message "Option not valid with reset-on-flow-control";
               junos:must "(!(\".. dump-on-flow-control\"))";
               junos:must-message "Option not valid with dump-on-flow-control";
               type empty;
             }
           }
         }
         container ggsn-options {
           description "GGSN interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
         }
         container ppp-options {
           description "Point-to-Point Protocol (PPP) interface-specific options";
           junos:must "((\".. encapsulation ppp\" || (\".. encapsulation ether-vpls-ppp\" || !(\".. encapsulation\"))))";
           junos:must-message "invalid encapsulation";
           uses ppp_options_type;
         }
         container redundancy-options {
           description "Redundancy options";
           uses apply-advanced;
           leaf primary {
             description "Specify the primary interface";
             type union {
               type jt:interface-device;
               type string {
                 pattern "<.*>|$.*";
               }
             }
           }
           leaf secondary {
             description "Specify the secondary interface";
             type union {
               type jt:interface-device;
               type string {
                 pattern "<.*>|$.*";
               }
             }
           }
           container redundancy-peer {
             description "Specify information for peer";
             uses apply-advanced;
             leaf ipaddress {
               description "Specify the IP address";
               type jt:ipv4addr;
             }
           }
           container redundancy-local {
             description "Specify information for the local peer";
             uses apply-advanced;
             leaf data-address {
               description "Specify the HA local data IP address";
               type jt:ipv4addr;
             }
           }
           leaf routing-instance {
             description "Specify routing-instance for the HA traffic";
             junos:must "((\"routing-instances $$\" || any \"tenants <*> routing-instances $$\"))";
             junos:must-message "referenced routing-instance must be defined";
             type string;
           }
           leaf replication-threshold {
             description "Duration for which flow should remain active for replication";
             default "180";
             units "seconds";
             type union {
               type string {
                 pattern "<.*>|$.*";
               }
               type uint32 {
                 range "60 .. 3600";
               }
             }
           }
           container replication-options {
             description "Specify state replication attributes";
             uses apply-advanced;
             leaf mtu {
               description "Specify the maximal packet size for replicated data";
               default "1500";
               type union {
                 type string {
                   pattern "<.*>|$.*";
                 }
                 type uint32 {
                   range "1500 .. 8000";
                 }
               }
             }
           }
           container replicate-services {
             description "Replicate services state from active to backup";
             uses apply-advanced;
             leaf pgcp {
               description "Replicate the PGCP service state";
               type empty;
             }
           }
         }
         container lsq-failure-options {
           description "Link services queuing failure options";
           uses apply-advanced;
           list trigger-link-failure {
             key name;
             ordered-by user;
             junos:cli-feature "oneliner-plus";
             description "Link on which to trigger failure";
             leaf name {
               description "Interface name";
               junos:cli-feature "nokeyword";
               type union {
                 type jt:interface-device;
                 type string {
                   pattern "<.*>|$.*";
                 }
               }
             }
             uses apply-advanced;
           }
           choice no-termination-request-choice {
             leaf no-termination-request {
               description "Do not send PPP termination requests";
               type empty;
             }
             leaf no-no-termination-request {
               description "Don't do not send PPP termination requests";
               type empty;
             }
           }
         }
         container services-options {
           description "Services interface-specific options";
           uses apply-advanced;
           container syslog {
             description "Define system log parameters";
             uses log-object;
           }
           container jflow-log {
             description "Define Jflow-log parameters.";
             uses apply-advanced;
             leaf message-rate-limit {
               description "Maximum jflow-log NAT error events allowed per second from this interface";
               units "messages per second";
               type union {
                 type string {
                   pattern "<.*>|$.*";
                 }
                 type uint32 {
                   range "1 .. 2147483647";
                 }
               }
             }
           }
           container deterministic-nat-configuration-log-interval {
             presence "enable deterministic-nat-configuration-log-interval";
             description "Define Deterministic NAT parameters";
             uses apply-advanced;
             leaf interval {
               description "Interval in which deterministic NAT logs are generated";
               units "seconds";
               type union {
                 type string {
                   pattern "<.*>|$.*";
                 }
                 type uint32 {
                   range "1800 .. 86400";
                 }
               }
             }
           }
           leaf open-timeout {
             description "Timeout period for TCP session establishment";
             units "seconds";
             type union {
               type string {
                 pattern "<.*>|$.*";
               }
               type uint32 {
                 range "4 .. 300";
               }
             }
           }
           leaf close-timeout {
             description "Timeout period for TCP session tear-down";
             units "seconds";
             type union {
               type string {
                 pattern "<.*>|$.*";
               }
               type uint32 {
                 range "2 .. 300";
               }
             }
           }
           leaf inactivity-timeout {
             description "Inactivity timeout period for established sessions (4..86400)";
             units "seconds";
             type union {
               type uint32;
               type string {
                 pattern "<.*>|$.*";
               }
             }
           }
           leaf inactivity-tcp-timeout {
             description "Inactivity timeout period for TCP established sessions";
             units "seconds";
             type union {
               type string {
                 pattern "<.*>|$.*";
               }
               type uint32 {
                 range "4 .. 86400";
               }
             }
           }
           leaf inactivity-asymm-tcp-timeout {
             description "Inactivity timeout period for asymmetric TCP established sessions";
             units "seconds";
             type union {
               type string {
                 pattern "<.*>|$.*";
               }
               type uint32 {
                 range "4 .. 86400";
               }
             }
           }
           leaf inactivity-non-tcp-timeout {
             description "Inactivity timeout period for non-TCP established sessions";
             units "seconds";
             type union {
               type string {
                 pattern "<.*>|$.*";
               }
               type uint32 {
                 range "4 .. 86400";
               }
             }
           }
           leaf session-timeout {
             description "Session timeout period for established sessions";
             units "seconds";
             type union {
               type string {
                 pattern "<.*>|$.*";
               }
               type uint32 {
                 range "4 .. 86400";
               }
             }
           }
           leaf disable-global-timeout-override {
             description "Disallow overriding  global inactivity or session timeout";
             type empty;
           }
           leaf tcp-tickles {
             description "Number of TCP keep-alive packets to be sent for bi-directional TCP flows";
             default "4";
             type union {
               type string {
                 pattern "<.*>|$.*";
               }
               type uint8 {
                 range "0 .. 30";
               }
             }
           }
           leaf fragment-limit {
             description "Maximum number of fragments allowed for a packet";
             default "64";
             type union {
               type string {
                 pattern "<.*>|$.*";
               }
               type uint8 {
                 range "1 .. 250";
               }
             }
           }
           leaf reassembly-timeout {
             description "Re-assembly timeout (seconds) for fragments of a packet";
             default "4";
             units "seconds";
             type union {
               type string {
                 pattern "<.*>|$.*";
               }
               type uint8 {
                 range "1 .. 60";
               }
             }
           }
           leaf cgn-pic {
             description "PIC will be used for Carrier Grade NAT configuration only";
             type empty;
           }
           leaf pba-interim-logging-interval {
             description "Interim logging interval in seconds";
             default "0";
             units "seconds";
             type union {
               type string {
                 pattern "<.*>|$.*";
               }
               type uint32 {
                 range "0 .. 86400";
               }
             }
           }
           container session-limit {
             presence "enable session-limit";
             description "Session limit";
             uses apply-advanced;
             leaf maximum {
               description "Maximum number of sessions allowed simultaneously";
               type string;
             }
             leaf rate {
               description "Maximum number of new sessions allowed per second";
               type string;
             }
             leaf cpu-load-threshold {
               description "CPU limit in percentage for auto-tuning of session rate";
               units "percent";
               type union {
                 type string {
                   pattern "<.*>|$.*";
                 }
                 type uint8 {
                   range "1 .. 100";
                 }
               }
             }
           }
           leaf enable-subscriber-analysis {
             description "Enable subscriber analysis on the interface";
             junos:must "(!(\".. disable-subscriber-analysis\"))";
             junos:must-message "can not set with enable-subscriber-analysis";
             type empty;
           }
           leaf disable-subscriber-analysis {
             description "Disable subscriber analysis on the interface";
             junos:must "(!(\".. enable-subscriber-analysis\"))";
             junos:must-message "can not set with disable-subscriber-analysis";
             type empty;
           }
           leaf disable-usp-tracing {
             description "Disable usp tracing on this pic";
             type empty;
           }
           leaf disable-drop-flows {
             description "Disable drop flows on this pic";
             type empty;
           }
           container ignore-errors {
             presence "enable ignore-errors";
             junos:cli-feature "oneliner";
             description "Ignore anomalies or errors";
             leaf tcp {
               description "TCP protocol errors";
               type empty;
             }
             leaf alg {
               description "ALG anomalies or errors";
               type empty;
             }
           }
           container capture {
             description "Packet capture for SFW and NAT on the Services PIC";
             uses apply-advanced;
             leaf capture-size {
               description "The number of packets to store";
               type union {
                 type string {
                   pattern "<.*>|$.*";
                 }
                 type uint32 {
                   range "1 .. 344000";
                 }
               }
             }
             leaf pkt-size {
               description "Number of bytes to be saved from each packet";
               type union {
                 type string {
                   pattern "<.*>|$.*";
                 }
                 type uint16 {
                   range "64 .. 15000";
                 }
               }
             }
             leaf logs-per-packet {
               description "The number of trace messages stored for each packet";
               type union {
                 type string {
                   pattern "<.*>|$.*";
                 }
                 type uint16 {
                   range "0 .. 500";
                 }
               }
             }
             leaf max-log-line-size {
               description "The maximum length of a stored trace message";
               type union {
                 type uint8;
                 type string {
                   pattern "<.*>|$.*";
                 }
               }
             }
             container filter {
               presence "enable filter";
               description "Filtering options for the packet capture";
               uses apply-advanced;
               container source-ip {
                 junos:cli-feature "oneliner";
                 description "Filter based on source-ip (and wildcard)";
                 leaf ip {
                   description "Source IP";
                   junos:cli-feature "nokeyword";
                   type jt:ipaddr;
                 }
                 leaf wildcard {
                   description "Source IP wildcard";
                   type jt:ipaddr;
                 }
               }
               container dest-ip {
                 junos:cli-feature "oneliner";
                 description "Filter based on dest-ip (and wildcard)";
                 leaf ip {
                   description "Dest IP";
                   junos:cli-feature "nokeyword";
                   type jt:ipaddr;
                 }
                 leaf wildcard {
                   description "Dest IP wildcard";
                   type jt:ipaddr;
                 }
               }
               container sw-sip {
                 junos:cli-feature "oneliner";
                 description "Filter based on source softwire ip (and wildcard)";
                 leaf ip {
                   description "Source softwire IP";
                   junos:cli-feature "nokeyword";
                   type jt:ipv6addr;
                 }
                 leaf wildcard {
                   description "Source IP wildcard";
                   type jt:ipv6addr;
                 }
               }
               container sw-dip {
                 junos:cli-feature "oneliner";
                 description "Filter based on destination softwire ip (and wildcard)";
                 leaf ip {
                   description "Destination softwire IP";
                   junos:cli-feature "nokeyword";
                   type jt:ipaddr;
                 }
                 leaf wildcard {
                   description "Destination IP wildcard";
                   type jt:ipaddr;
                 }
               }
               container sport-range {
                 junos:cli-feature "oneliner";
                 description "Filter based on source port";
                 leaf low {
                   description "Source port range start";
                   type union {
                     type uint16;
                     type string {
                       pattern "<.*>|$.*";
                     }
                   }
                 }
                 leaf high {
                   description "Source port range end";
                   type union {
                     type uint16;
                     type string {
                       pattern "<.*>|$.*";
                     }
                   }
                 }
               }
               container dport-range {
                 junos:cli-feature "oneliner";
                 description "Filter based on destination port";
                 leaf low {
                   description "Destination port range start";
                   type union {
                     type uint16;
                     type string {
                       pattern "<.*>|$.*";
                     }
                   }
                 }
                 leaf high {
                   description "Destination port range end";
                   type union {
                     type uint16;
                     type string {
                       pattern "<.*>|$.*";
                     }
                   }
                 }
               }
               leaf proto {
                 description "Filter based on L4 protocol";
                 type enumeration {
                   enum "icmp" {
                   }
                   enum "tcp" {
                   }
                   enum "udp" {
                   }
                 }
               }
             }
           }
           container flow {
             description "Define flow parameters";
             uses apply-advanced;
             container traceoptions {
               description "Trace options for flow services";
             }
           }
           leaf fpc-pic-information {
             description "Include FPC and PIC slot number in the syslogs";
             type empty;
           }
           leaf utc-timestamp {
             description "Use UTC time for security log timestamps";
             type empty;
           }
           leaf syslog-local-system-timestamp {
             description "Use local system time for services syslog timestamp";
             type empty;
           }
         }
         container t3-options {
           junos:must "((!(\"interfaces ${interface} container-options\") || (\"interfaces ${interface} container-options container-type\" || \"interfaces ${interface} container-options allow-configuration-override\")))";
           junos:must-message "t1-options cannot be configured without allow-configuration-override";
           description "T3 interface-specific options";
           uses apply-advanced;
           leaf loopback {
             description "Loopback mode";
             type enumeration {
               enum "local" {
                 description "Local loopback";
               }
               enum "remote" {
                 description "Remote loopback";
               }
               enum "payload" {
                 description "Payload loopback";
               }
             }
           }
           choice long-buildout-choice {
             leaf long-buildout {
               description "Set hardware to drive line longer than 255 feet";
               type empty;
             }
             leaf no-long-buildout {
               description "Don't set hardware to drive line longer than 255 feet";
               type empty;
             }
           }
           choice loop-timing-choice {
             leaf loop-timing {
               description "Set loop timing for T3";
               type empty;
             }
             leaf no-loop-timing {
               description "Don't set loop timing for T3";
               type empty;
             }
           }
           container compatibility-mode {
             junos:cli-feature "oneliner";
             description "Set CSU compatibility mode";
             choice vendor {
               case case_1 {
                 container larscom {
                   presence "enable larscom";
                   junos:must "(!(\".. .. unframed\"))";
                   junos:must-message "unframed and larscom cannot coexist";
                   junos:cli-feature "oneliner";
                   description "Compatible with Larscom CSU";
                   leaf subrate {
                     description "Set subrate value";
                     type union {
                       type string {
                         pattern "<.*>|$.*";
                       }
                       type uint32 {
                         range "1 .. 14";
                       }
                     }
                   }
                 }
               }
               case case_2 {
                 container verilink {
                   presence "enable verilink";
                   junos:must "(!(\".. .. unframed\"))";
                   junos:must-message "unframed and verilink cannot coexist";
                   junos:cli-feature "oneliner";
                   description "Compatible with Verilink CSU (not on 2/4-port T3 PIC)";
                   leaf subrate {
                     description "Set subrate value";
                     type union {
                       type string {
                         pattern "<.*>|$.*";
                       }
                       type uint32 {
                         range "1 .. 28";
                       }
                     }
                   }
                 }
               }
               case case_3 {
                 container adtran {
                   presence "enable adtran";
                   junos:must "(!(\".. .. unframed\"))";
                   junos:must-message "unframed and adtran cannot coexist";
                   junos:cli-feature "oneliner";
                   description "Compatible with Adtran CSU (not on 2/4-port T3 PIC)";
                   leaf subrate {
                     description "Set subrate value";
                     type union {
                       type string {
                         pattern "<.*>|$.*";
                       }
                       type uint32 {
                         range "1 .. 588";
                       }
                     }
                   }
                 }
               }
               case case_4 {
                 container kentrox {
                   presence "enable kentrox";
                   junos:cli-feature "oneliner";
                   description "Compatible with Kentrox CSU";
                   leaf subrate {
                     description "Set subrate value (not on 2/4-port T3 PIC)";
                     type union {
                       type string {
                         pattern "<.*>|$.*";
                       }
                       type uint32 {
                         range "1 .. 69";
                       }
                     }
                   }
                 }
               }
               case case_5 {
                 container digital-link {
                   presence "enable digital-link";
                   junos:must "(!(\".. .. unframed\"))";
                   junos:must-message "unframed and digital-link cannot coexist";
                   junos:cli-feature "oneliner";
                   description "Compatible with Digital Link CSU";
                   leaf subrate {
                     description "Set subrate value";
                     type enumeration {
                       enum "301Kb" {
                         description "301 Kbps";
                       }
                       enum "601Kb" {
                         description "601 Kbps";
                       }
                       enum "902Kb" {
                         description "902 Kbps";
                       }
                       enum "1.2Mb" {
                         description "1.2 Mbps";
                       }
                       enum "1.5Mb" {
                         description "1.5 Mbps";
                       }
                       enum "1.8Mb" {
                         description "1.8 Mbps";
                       }
                       enum "2.1Mb" {
                         description "2.1 Mbps";
                       }
                       enum "2.4Mb" {
                         description "2.4 Mbps";
                       }
                       enum "2.7Mb" {
                         description "2.7 Mbps";
                       }
                       enum "3.0Mb" {
                         description "3.0 Mbps";
                       }
                       enum "3.3Mb" {
                         description "3.3 Mbps";
                       }
                       enum "3.6Mb" {
                         description "3.6 Mbps";
                       }
                       enum "3.9Mb" {
                         description "3.9 Mbps";
                       }
                       enum "4.2Mb" {
                         description "4.2 Mbps";
                       }
                       enum "4.5Mb" {
                         description "4.5 Mbps";
                       }
                       enum "4.8Mb" {
                         description "4.8 Mbps";
                       }
                       enum "5.1Mb" {
                         description "5.1 Mbps";
                       }
                       enum "5.4Mb" {
                         description "5.4 Mbps";
                       }
                       enum "5.7Mb" {
                         description "5.7 Mbps";
                       }
                       enum "6.0Mb" {
                         description "6.0 Mbps";
                       }
                       enum "6.3Mb" {
                         description "6.3 Mbps";
                       }
                       enum "6.6Mb" {
                         description "6.6 Mbps";
                       }
                       enum "6.9Mb" {
                         description "6.9 Mbps";
                       }
                       enum "7.2Mb" {
                         description "7.2 Mbps";
                       }
                       enum "7.5Mb" {
                         description "7.5 Mbps";
                       }
                       enum "7.8Mb" {
                         description "7.8 Mbps";
                       }
                       enum "8.1Mb" {
                         description "8.1 Mbps";
                       }
                       enum "8.4Mb" {
                         description "8.4 Mbps";
                       }
                       enum "8.7Mb" {
                         description "8.7 Mbps";
                       }
                       enum "9.0Mb" {
                         description "9.0 Mbps";
                       }
                       enum "9.3Mb" {
                         description "9.3 Mbps";
                       }
                       enum "9.6Mb" {
                         description "9.6 Mbps";
                       }
                       enum "9.9Mb" {
                         description "9.9 Mbps";
                       }
                       enum "10.2Mb" {
                         description "10.2 Mbps";
                       }
                       enum "10.5Mb" {
                         description "10.5 Mbps";
                       }
                       enum "10.8Mb" {
                         description "10.8 Mbps";
                       }
                       enum "11.1Mb" {
                         description "11.1 Mbps";
                       }
                       enum "11.4Mb" {
                         description "11.4 Mbps";
                       }
                       enum "11.7Mb" {
                         description "11.7 Mbps";
                       }
                       enum "12.0Mb" {
                         description "12.0 Mbps";
                       }
                       enum "12.3Mb" {
                         description "12.3 Mbps";
                       }
                       enum "12.6Mb" {
                         description "12.6 Mbps";
                       }
                       enum "12.9Mb" {
                         description "12.9 Mbps";
                       }
                       enum "13.2Mb" {
                         description "13.2 Mbps";
                       }
                       enum "13.5Mb" {
                         description "13.5 Mbps";
                       }
                       enum "13.8Mb" {
                         description "13.8 Mbps";
                       }
                       enum "14.1Mb" {
                         description "14.1 Mbps";
                       }
                       enum "14.4Mb" {
                         description "14.4 Mbps";
                       }
                       enum "14.7Mb" {
                         description "14.7 Mbps";
                       }
                       enum "15.0Mb" {
                         description "15.0 Mbps";
                       }
                       enum "15.3Mb" {
                         description "15.3 Mbps";
                       }
                       enum "15.6Mb" {
                         description "15.6 Mbps";
                       }
                       enum "15.9Mb" {
                         description "15.9 Mbps";
                       }
                       enum "16.2Mb" {
                         description "16.2 Mbps";
                       }
                       enum "16.5Mb" {
                         description "16.5 Mbps";
                       }
                       enum "16.8Mb" {
                         description "16.8 Mbps";
                       }
                       enum "17.1Mb" {
                         description "17.1 Mbps";
                       }
                       enum "17.4Mb" {
                         description "17.4 Mbps";
                       }
                       enum "17.7Mb" {
                         description "17.7 Mbps";
                       }
                       enum "18.0Mb" {
                         description "18.0 Mbps";
                       }
                       enum "18.3Mb" {
                         description "18.3 Mbps";
                       }
                       enum "18.6Mb" {
                         description "18.6 Mbps";
                       }
                       enum "18.9Mb" {
                         description "18.9 Mbps";
                       }
                       enum "19.2Mb" {
                         description "19.2 Mbps";
                       }
                       enum "19.5Mb" {
                         description "19.5 Mbps";
                       }
                       enum "19.8Mb" {
                         description "19.8 Mbps";
                       }
                       enum "20.1Mb" {
                         description "20.1 Mbps";
                       }
                       enum "20.5Mb" {
                         description "20.5 Mbps";
                       }
                       enum "20.8Mb" {
                         description "20.8 Mbps";
                       }
                       enum "21.1Mb" {
                         description "21.1 Mbps";
                       }
                       enum "21.4Mb" {
                         description "21.4 Mbps";
                       }
                       enum "21.7Mb" {
                         description "21.7 Mbps";
                       }
                       enum "22.0Mb" {
                         description "22.0 Mbps";
                       }
                       enum "22.3Mb" {
                         description "22.3 Mbps";
                       }
                       enum "22.6Mb" {
                         description "22.6 Mbps";
                       }
                       enum "22.9Mb" {
                         description "22.9 Mbps";
                       }
                       enum "23.2Mb" {
                         description "23.2 Mbps";
                       }
                       enum "23.5Mb" {
                         description "23.5 Mbps";
                       }
                       enum "23.8Mb" {
                         description "23.8 Mbps";
                       }
                       enum "24.1Mb" {
                         description "24.1 Mbps";
                       }
                       enum "24.4Mb" {
                         description "24.4 Mbps";
                       }
                       enum "24.7Mb" {
                         description "24.7 Mbps";
                       }
                       enum "25.0Mb" {
                         description "25.0 Mbps";
                       }
                       enum "25.3Mb" {
                         description "25.3 Mbps";
                       }
                       enum "25.6Mb" {
                         description "25.6 Mbps";
                       }
                       enum "25.9Mb" {
                         description "25.9 Mbps";
                       }
                       enum "26.2Mb" {
                         description "26.2 Mbps";
                       }
                       enum "26.5Mb" {
                         description "26.5 Mbps";
                       }
                       enum "26.8Mb" {
                         description "26.8 Mbps";
                       }
                       enum "27.1Mb" {
                         description "27.1 Mbps";
                       }
                       enum "27.4Mb" {
                         description "27.4 Mbps";
                       }
                       enum "27.7Mb" {
                         description "27.7 Mbps";
                       }
                       enum "28.0Mb" {
                         description "28.0 Mbps";
                       }
                       enum "28.3Mb" {
                         description "28.3 Mbps";
                       }
                       enum "28.6Mb" {
                         description "28.6 Mbps";
                       }
                       enum "28.9Mb" {
                         description "28.9 Mbps";
                       }
                       enum "29.2Mb" {
                         description "29.2 Mbps";
                       }
                       enum "29.5Mb" {
                         description "29.5 Mbps";
                       }
                       enum "29.8Mb" {
                         description "29.8 Mbps";
                       }
                       enum "30.1Mb" {
                         description "30.1 Mbps";
                       }
                       enum "30.4Mb" {
                         description "30.4 Mbps";
                       }
                       enum "30.7Mb" {
                         description "30.7 Mbps";
                       }
                       enum "31.0Mb" {
                         description "31.0 Mbps";
                       }
                       enum "31.3Mb" {
                         description "31.3 Mbps";
                       }
                       enum "31.6Mb" {
                         description "31.6 Mbps";
                       }
                       enum "31.9Mb" {
                         description "31.9 Mbps";
                       }
                       enum "32.2Mb" {
                         description "32.2 Mbps";
                       }
                       enum "32.5Mb" {
                         description "32.5 Mbps";
                       }
                       enum "32.8Mb" {
                         description "32.8 Mbps";
                       }
                       enum "33.1Mb" {
                         description "33.1 Mbps";
                       }
                       enum "33.4Mb" {
                         description "33.4 Mbps";
                       }
                       enum "33.7Mb" {
                         description "33.7 Mbps";
                       }
                       enum "34.0Mb" {
                         description "34.0 Mbps";
                       }
                       enum "34.3Mb" {
                         description "34.3 Mbps";
                       }
                       enum "34.6Mb" {
                         description "34.6 Mbps";
                       }
                       enum "34.9Mb" {
                         description "34.9 Mbps";
                       }
                       enum "35.2Mb" {
                         description "35.2 Mbps";
                       }
                       enum "35.5Mb" {
                         description "35.5 Mbps";
                       }
                       enum "35.8Mb" {
                         description "35.8 Mbps";
                       }
                       enum "36.1Mb" {
                         description "36.1 Mbps";
                       }
                       enum "36.4Mb" {
                         description "36.4 Mbps";
                       }
                       enum "36.7Mb" {
                         description "36.7 Mbps";
                       }
                       enum "37.0Mb" {
                         description "37.0 Mbps";
                       }
                       enum "37.3Mb" {
                         description "37.3 Mbps";
                       }
                       enum "37.6Mb" {
                         description "37.6 Mbps";
                       }
                       enum "37.9Mb" {
                         description "37.9 Mbps";
                       }
                       enum "38.2Mb" {
                         description "38.2 Mbps";
                       }
                       enum "38.5Mb" {
                         description "38.5 Mbps";
                       }
                       enum "38.8Mb" {
                         description "38.8 Mbps";
                       }
                       enum "39.1Mb" {
                         description "39.1 Mbps";
                       }
                       enum "39.4Mb" {
                         description "39.4 Mbps";
                       }
                       enum "39.7Mb" {
                         description "39.7 Mbps";
                       }
                       enum "40.0Mb" {
                         description "40.0 Mbps";
                       }
                       enum "40.3Mb" {
                         description "40.3 Mbps";
                       }
                       enum "40.6Mb" {
                         description "40.6 Mbps";
                       }
                       enum "40.9Mb" {
                         description "40.9 Mbps";
                       }
                       enum "41.2Mb" {
                         description "41.2 Mbps";
                       }
                       enum "41.5Mb" {
                         description "41.5 Mbps";
                       }
                       enum "41.8Mb" {
                         description "41.8 Mbps";
                       }
                       enum "42.1Mb" {
                         description "42.1 Mbps";
                       }
                       enum "42.4Mb" {
                         description "42.4 Mbps";
                       }
                       enum "42.7Mb" {
                         description "42.7 Mbps";
                       }
                       enum "43.0Mb" {
                         description "43.0 Mbps";
                       }
                       enum "43.3Mb" {
                         description "43.3 Mbps";
                       }
                       enum "43.6Mb" {
                         description "43.6 Mbps";
                       }
                       enum "43.9Mb" {
                         description "43.9 Mbps";
                       }
                       enum "44.2Mb" {
                         description "44.2 Mbps";
                       }
                     }
                   }
                 }
               }
             }
           }
           choice payload-scrambler-choice {
             leaf payload-scrambler {
               description "Enable payload scrambling";
               type empty;
             }
             leaf no-payload-scrambler {
               description "Don't enable payload scrambling";
               type empty;
             }
           }
           choice cbit-parity-choice {
             leaf cbit-parity {
               description "Enable C-bit parity mode";
               junos:must "(!(\".. unframed\"))";
               junos:must-message "cbit-parity and unframed cannot coexist";
               type empty;
             }
             leaf no-cbit-parity {
               description "Don't enable C-bit parity mode";
               junos:must "(!(\".. unframed\"))";
               junos:must-message "cbit-parity and unframed cannot coexist";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           choice feac-loop-respond-choice {
             leaf feac-loop-respond {
               description "Respond to FEAC loop requests";
               type empty;
             }
             leaf no-feac-loop-respond {
               description "Don't respond to FEAC loop requests";
               type empty;
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "DS-3 interface encapsulation";
             type enumeration {
               enum "plcp" {
                 description "PLCP encapsulation";
               }
               enum "direct" {
                 description "ATM direct mapping";
               }
             }
           }
         }
         container e3-options {
           junos:must "((!(\"interfaces ${interface} container-options\") || (\"interfaces ${interface} container-options container-type\" || \"interfaces ${interface} container-options allow-configuration-override\")))";
           junos:must-message "t1-options cannot be configured without allow-configuration-override";
           description "E3 interface-specific options";
           uses apply-advanced;
           leaf loopback {
             description "Loopback mode";
             type enumeration {
               enum "local" {
                 description "Local loopback";
               }
               enum "remote" {
                 description "Remote loopback";
               }
             }
           }
           choice unframed-choice {
             leaf unframed {
               description "Enable unframed mode";
               type empty;
             }
             leaf no-unframed {
               description "Don't enable unframed mode";
               type empty;
             }
           }
           container compatibility-mode {
             junos:cli-feature "oneliner";
             description "Set CSU compatibility mode";
             choice vendor {
               case case_1 {
                 leaf larscom {
                   description "Compatible with Larscom CSU (only non IQ E3 interfaces)";
                   type empty;
                 }
               }
               case case_2 {
                 container digital-link {
                   presence "enable digital-link";
                   junos:cli-feature "oneliner";
                   description "Compatible with Digital Link CSU";
                   leaf subrate {
                     description "Set subrate value";
                     type enumeration {
                       enum "358Kb" {
                         description "358 Kbps";
                       }
                       enum "716Kb" {
                         description "716 Kbps";
                       }
                       enum "1.1Mb" {
                         description "1.1 Mbps";
                       }
                       enum "1.4Mb" {
                         description "1.4 Mbps";
                       }
                       enum "1.8Mb" {
                         description "1.8 Mbps";
                       }
                       enum "2.1Mb" {
                         description "2.1 Mbps";
                       }
                       enum "2.5Mb" {
                         description "2.5 Mbps";
                       }
                       enum "2.9Mb" {
                         description "2.9 Mbps";
                       }
                       enum "3.2Mb" {
                         description "3.2 Mbps";
                       }
                       enum "3.6Mb" {
                         description "3.6 Mbps";
                       }
                       enum "3.9Mb" {
                         description "3.9 Mbps";
                       }
                       enum "4.3Mb" {
                         description "4.3 Mbps";
                       }
                       enum "4.7Mb" {
                         description "4.7 Mbps";
                       }
                       enum "5.0Mb" {
                         description "5.0 Mbps";
                       }
                       enum "5.4Mb" {
                         description "5.4 Mbps";
                       }
                       enum "5.7Mb" {
                         description "5.7 Mbps";
                       }
                       enum "6.1Mb" {
                         description "6.1 Mbps";
                       }
                       enum "6.4Mb" {
                         description "6.4 Mbps";
                       }
                       enum "6.8Mb" {
                         description "6.8 Mbps";
                       }
                       enum "7.2Mb" {
                         description "7.2 Mbps";
                       }
                       enum "7.5Mb" {
                         description "7.5 Mbps";
                       }
                       enum "7.9Mb" {
                         description "7.9 Mbps";
                       }
                       enum "8.2Mb" {
                         description "8.2 Mbps";
                       }
                       enum "8.6Mb" {
                         description "8.6 Mbps";
                       }
                       enum "9.0Mb" {
                         description "9.0 Mbps";
                       }
                       enum "9.3Mb" {
                         description "9.3 Mbps";
                       }
                       enum "9.7Mb" {
                         description "9.7 Mbps";
                       }
                       enum "10.0Mb" {
                         description "10.0 Mbps";
                       }
                       enum "10.4Mb" {
                         description "10.4 Mbps";
                       }
                       enum "10.7Mb" {
                         description "10.7 Mbps";
                       }
                       enum "11.1Mb" {
                         description "11.1 Mbps";
                       }
                       enum "11.5Mb" {
                         description "11.5 Mbps";
                       }
                       enum "11.8Mb" {
                         description "11.8 Mbps";
                       }
                       enum "12.2Mb" {
                         description "12.2 Mbps";
                       }
                       enum "12.5Mb" {
                         description "12.5 Mbps";
                       }
                       enum "12.9Mb" {
                         description "12.9 Mbps";
                       }
                       enum "13.2Mb" {
                         description "13.2 Mbps";
                       }
                       enum "13.6Mb" {
                         description "13.6 Mbps";
                       }
                       enum "14.0Mb" {
                         description "14.0 Mbps";
                       }
                       enum "14.3Mb" {
                         description "14.3 Mbps";
                       }
                       enum "14.7Mb" {
                         description "14.7 Mbps";
                       }
                       enum "15.0Mb" {
                         description "15.0 Mbps";
                       }
                       enum "15.4Mb" {
                         description "15.4 Mbps";
                       }
                       enum "15.8Mb" {
                         description "15.8 Mbps";
                       }
                       enum "16.1Mb" {
                         description "16.1 Mbps";
                       }
                       enum "16.5Mb" {
                         description "16.5 Mbps";
                       }
                       enum "16.8Mb" {
                         description "16.8 Mbps";
                       }
                       enum "17.2Mb" {
                         description "17.2 Mbps";
                       }
                       enum "17.5Mb" {
                         description "17.5 Mbps";
                       }
                       enum "17.9Mb" {
                         description "17.9 Mbps";
                       }
                       enum "18.3Mb" {
                         description "18.3 Mbps";
                       }
                       enum "18.6Mb" {
                         description "18.6 Mbps";
                       }
                       enum "19.0Mb" {
                         description "19.0 Mbps";
                       }
                       enum "19.3Mb" {
                         description "19.3 Mbps";
                       }
                       enum "19.7Mb" {
                         description "19.7 Mbps";
                       }
                       enum "20.0Mb" {
                         description "20.0 Mbps";
                       }
                       enum "20.4Mb" {
                         description "20.4 Mbps";
                       }
                       enum "20.8Mb" {
                         description "20.8 Mbps";
                       }
                       enum "21.1Mb" {
                         description "21.1 Mbps";
                       }
                       enum "21.5Mb" {
                         description "21.5 Mbps";
                       }
                       enum "21.8Mb" {
                         description "21.8 Mbps";
                       }
                       enum "22.2Mb" {
                         description "22.2 Mbps";
                       }
                       enum "22.6Mb" {
                         description "22.6 Mbps";
                       }
                       enum "22.9Mb" {
                         description "22.9 Mbps";
                       }
                       enum "23.3Mb" {
                         description "23.3 Mbps";
                       }
                       enum "23.6Mb" {
                         description "23.6 Mbps";
                       }
                       enum "24.0Mb" {
                         description "24.0 Mbps";
                       }
                       enum "24.3Mb" {
                         description "24.3 Mbps";
                       }
                       enum "24.7Mb" {
                         description "24.7 Mbps";
                       }
                       enum "25.1Mb" {
                         description "25.1 Mbps";
                       }
                       enum "25.4Mb" {
                         description "25.4 Mbps";
                       }
                       enum "25.8Mb" {
                         description "25.8 Mbps";
                       }
                       enum "26.1Mb" {
                         description "26.1 Mbps";
                       }
                       enum "26.5Mb" {
                         description "26.5 Mbps";
                       }
                       enum "26.9Mb" {
                         description "26.9 Mbps";
                       }
                       enum "27.2Mb" {
                         description "27.2 Mbps";
                       }
                       enum "27.6Mb" {
                         description "27.6 Mbps";
                       }
                       enum "27.9Mb" {
                         description "27.9 Mbps";
                       }
                       enum "28.3Mb" {
                         description "28.3 Mbps";
                       }
                       enum "28.6Mb" {
                         description "28.6 Mbps";
                       }
                       enum "29.0Mb" {
                         description "29.0 Mbps";
                       }
                       enum "29.4Mb" {
                         description "29.4 Mbps";
                       }
                       enum "29.7Mb" {
                         description "29.7 Mbps";
                       }
                       enum "30.1Mb" {
                         description "30.1 Mbps";
                       }
                       enum "30.4Mb" {
                         description "30.4 Mbps";
                       }
                       enum "30.8Mb" {
                         description "30.8 Mbps";
                       }
                       enum "31.1Mb" {
                         description "31.1 Mbps";
                       }
                       enum "31.5Mb" {
                         description "31.5 Mbps";
                       }
                       enum "31.9Mb" {
                         description "31.9 Mbps";
                       }
                       enum "32.2Mb" {
                         description "32.2 Mbps";
                       }
                       enum "32.6Mb" {
                         description "32.6 Mbps";
                       }
                       enum "32.9Mb" {
                         description "32.9 Mbps";
                       }
                       enum "33.3Mb" {
                         description "33.3 Mbps";
                       }
                       enum "33.7Mb" {
                         description "33.7 Mbps";
                       }
                       enum "34.0Mb" {
                         description "34.0 Mbps";
                       }
                     }
                   }
                 }
               }
               case case_3 {
                 container kentrox {
                   presence "enable kentrox";
                   junos:cli-feature "oneliner";
                   description "Compatible with Kentrox CSU";
                   leaf subrate {
                     description "Set subrate value (only for E3 IQ interfaces)";
                     type union {
                       type string {
                         pattern "<.*>|$.*";
                       }
                       type uint32 {
                         range "1 .. 48";
                       }
                     }
                   }
                 }
               }
             }
           }
           choice payload-scrambler-choice {
             leaf payload-scrambler {
               description "Enable payload scrambling";
               type empty;
             }
             leaf no-payload-scrambler {
               description "Don't enable payload scrambling";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf invert-data {
             description "Invert data";
             type empty;
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "E3 interface encapsulation";
             type enumeration {
               enum "plcp" {
                 description "PLCP encapsulation";
               }
               enum "direct" {
                 description "ATM direct mapping";
               }
             }
           }
           leaf framing {
             description "E3 line format";
             type enumeration {
               enum "g.751" {
                 description "G.751 format";
               }
               enum "g.832" {
                 description "G.832 format";
               }
             }
           }
         }
         container e1-options {
           junos:must "((!(\"interfaces ${interface} container-options\") || (\"interfaces ${interface} container-options container-type\" || \"interfaces ${interface} container-options allow-configuration-override\")))";
           junos:must-message "e1-options cannot be configured without allow-configuration-override";
           description "E1 interface-specific options";
           uses apply-advanced;
           leaf timeslots {
             description "Timeslots (1..32); for example, 1-4,6,9-11,32 (no space)";
             type string;
           }
           leaf loopback {
             description "Loopback mode";
             type enumeration {
               enum "local" {
                 description "Local loopback";
               }
               enum "remote" {
                 description "Remote loopback";
               }
             }
           }
           leaf framing {
             description "Framing mode";
             type enumeration {
               enum "g704" {
                 description "G704 mode with CRC4";
               }
               enum "unframed" {
                 description "Unframed mode";
               }
               enum "g704-no-crc4" {
                 description "G704 mode without CRC4";
               }
             }
           }
           leaf fcs {
             description "Frame checksum";
             type enumeration {
               enum "32" {
                 description "32-bit mode";
               }
               enum "16" {
                 description "16-bit mode";
               }
             }
           }
           leaf invert-data {
             description "Invert data";
             type empty;
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
         }
         container t1-options {
           junos:must "((!(\"interfaces ${interface} container-options\") || (\"interfaces ${interface} container-options container-type\" || \"interfaces ${interface} container-options allow-configuration-override\")))";
           junos:must-message "t1-options cannot be configured without allow-configuration-override";
           description "T1 interface-specific options";
           uses apply-advanced;
           leaf timeslots {
             description "Timeslots (1..24; for example, 1-3,4,9,22-24 (no space)";
             type string;
           }
           leaf disable-remote-alarm-detection {
             description "Disable detection of a remote alarm";
             type enumeration {
               enum "yellow" {
                 description "Disable yellow alarm detection";
               }
             }
           }
           leaf loopback {
             description "Loopback mode";
             type enumeration {
               enum "local" {
                 description "Local loopback";
               }
               enum "remote" {
                 description "Remote loopback";
               }
               enum "payload" {
                 description "Payload loopback";
               }
             }
           }
           leaf buildout {
             description "Line buildout";
             type enumeration {
               enum "0-132" {
                 description "Line buildout is between 0-132 feet";
               }
               enum "133-265" {
                 description "Line buildout is between 133-265 feet";
               }
               enum "266-398" {
                 description "Line buildout is between 266-398 feet";
               }
               enum "399-531" {
                 description "Line buildout is between 399-531 feet";
               }
               enum "532-655" {
                 description "Line buildout is between 532-655 feet";
               }
               enum "long-0db" {
                 description "Long buildout with 0 dB transmit attenuation";
               }
               enum "long-7.5db" {
                 description "Long buildout with 7.5 dB transmit attenuation";
               }
               enum "long-15db" {
                 description "Long buildout with 15 dB transmit attenuation";
               }
               enum "long-22.5db" {
                 description "Long buildout with 22.5 dB transmit attenuation";
               }
             }
           }
           leaf byte-encoding {
             description "Byte encoding";
             type enumeration {
               enum "nx64" {
                 description "8 bits per byte";
               }
               enum "nx56" {
                 description "7 bits per byte";
               }
             }
           }
           leaf line-encoding {
             description "Line encoding";
             type enumeration {
               enum "ami" {
                 description "Automatic mark inversion";
               }
               enum "b8zs" {
                 description "8-bit zero suppression";
               }
             }
           }
           leaf invert-data {
             description "Invert data";
             type empty;
           }
           leaf framing {
             description "Framing mode";
             type enumeration {
               enum "sf" {
                 description "Super frame";
               }
               enum "esf" {
                 description "Extended super frame";
               }
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
           leaf remote-loopback-respond {
             description "Respond to loop requests from remote end";
             type empty;
           }
           leaf crc-major-alarm-threshold {
             description "CRC Major alarm threshold value";
             default "5e-5";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
             }
           }
           leaf crc-minor-alarm-threshold {
             description "CRC Minor alarm threshold value";
             default "5e-6";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
               enum "5e-6" {
                 description "5 crc errors in 10^6 bits";
               }
               enum "1e-6" {
                 description "1 crc error in 10^6 bits";
               }
             }
           }
         }
         container ds0-options {
           junos:must "((!(\"interfaces ${interface} container-options\") || (\"interfaces ${interface} container-options container-type\" || \"interfaces ${interface} container-options allow-configuration-override\")))";
           junos:must-message "ds0-options cannot be configured without allow-configuration-override";
           description "DS-0 interface-specific options";
           uses apply-advanced;
           leaf loopback {
             description "Loopback mode";
             type enumeration {
               enum "payload" {
                 description "Payload loopback";
               }
             }
           }
           leaf byte-encoding {
             description "Byte encoding";
             type enumeration {
               enum "nx64" {
                 description "8 bits per byte";
               }
               enum "nx56" {
                 description "7 bits per byte";
               }
             }
           }
           leaf invert-data {
             description "Invert data";
             type empty;
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e11-o152" {
                 description "Pattern is 2^11 -1 (per O.152 standard)";
               }
               enum "pseudo-2e15-o151" {
                 description "Pattern is 2^15 - 1 (per O.151 standard)";
               }
               enum "pseudo-2e20-o153" {
                 description "Pattern is 2^20 - 1 (per O.153 standard)";
               }
               enum "pseudo-2e20-o151" {
                 description "Pattern is 2^20 - 1 (per O.151 standard)";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
               enum "repeating-1-in-16" {
                 description "1 bit in 16 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
         }
         container serial-options {
           description "Serial interface-specific options";
           uses apply-advanced;
           leaf line-protocol {
             description "Line protocol to be used";
             default "eia530";
             type enumeration {
               enum "eia530" {
                 description "Line protocol EIA530";
               }
               enum "v.35" {
                 description "Line protocol V.35";
               }
               enum "x.21" {
                 description "Line protocol X.21";
               }
             }
           }
           choice control_leads_choice {
             case case_1 {
               container dte-options {
                 description "DTE options/control leads";
                 uses apply-advanced;
                 leaf ignore-all {
                   description "Ignore all control leads";
                   junos:must "(!(\".. indication\"))";
                   junos:must-message "SERIAL: ignore-all configured when indication explicitly configured";
                   junos:must "(!(\".. cts\"))";
                   junos:must-message "SERIAL: ignore-all configured when cts explicitly configured";
                   junos:must "(!(\".. dsr\"))";
                   junos:must-message "SERIAL: ignore-all configured when dsr explicitly configured";
                   junos:must "(!(\".. tm\"))";
                   junos:must-message "SERIAL: ignore-all configured when tm explicitly configured";
                   junos:must "(!(\".. dcd\"))";
                   junos:must-message "SERIAL: ignore-all configured when dcd explicitly configured";
                   type empty;
                 }
                 container dtr {
                   junos:cli-feature "oneliner";
                   description "Data Transmit Ready signal handling";
                   choice dtr_choices {
                     case case_1 {
                       leaf assert {
                         description "Assert DTR signal";
                         type empty;
                       }
                     }
                     case case_2 {
                       leaf de-assert {
                         description "Deassert DTR signal";
                         type empty;
                       }
                     }
                     case case_3 {
                       leaf normal {
                         description "Normal DTR signal";
                         type empty;
                       }
                     }
                     case case_4 {
                       container auto-synchronize {
                         presence "enable auto-synchronize";
                         description "Normal DTR signal, with autoresynchronization";
                         uses apply-advanced;
                         leaf duration {
                           description "Duration of autoresynchronization";
                           units "milliseconds";
                           type union {
                             type string {
                               pattern "<.*>|$.*";
                             }
                             type uint16 {
                               range "1 .. 1000";
                             }
                           }
                         }
                         leaf interval {
                           description "Interval for autoresynchronization";
                           units "seconds";
                           type union {
                             type string {
                               pattern "<.*>|$.*";
                             }
                             type uint16 {
                               range "1 .. 31";
                             }
                           }
                         }
                       }
                     }
                   }
                 }
                 leaf control-signal {
                   description "X.21 control signal handling";
                   junos:must "(!(\".. .. line-protocol eia530\"))";
                   junos:must-message "Control signal  invalid on line-protocol eia530";
                   junos:must "(!(\".. .. line-protocol v.35\"))";
                   junos:must-message "Control signal invalid on line-protocol v.35";
                   type enumeration {
                     enum "assert" {
                       description "Assert control signal";
                     }
                     enum "de-assert" {
                       description "Deassert control signal";
                     }
                     enum "normal" {
                       description "Normal control signal";
                     }
                   }
                 }
                 leaf rts {
                   description "Request To Send signal handling";
                   junos:must "(!(\".. .. line-protocol x.21\"))";
                   junos:must-message "rts invalid on line-protocol x.21";
                   type enumeration {
                     enum "assert" {
                       description "Assert RTS signal";
                     }
                     enum "de-assert" {
                       description "Deassert RTS signal";
                     }
                     enum "normal" {
                       description "Normal RTS signal";
                     }
                   }
                 }
                 leaf dcd {
                   description "Data Carrier Detect signal handling";
                   type enumeration {
                     enum "require" {
                       description "Require DCD signal";
                     }
                     enum "ignore" {
                       description "Ignore DCD signal";
                     }
                     enum "normal" {
                       description "Normal DCD signal";
                     }
                   }
                 }
                 leaf dsr {
                   description "Data Set Ready signal handling";
                   type enumeration {
                     enum "require" {
                       description "Require DSR signal";
                     }
                     enum "ignore" {
                       description "Ignore DSR signal";
                     }
                     enum "normal" {
                       description "Normal DSR signal";
                     }
                   }
                 }
                 leaf cts {
                   description "Clear To Send signal handling";
                   junos:must "(!(\".. .. line-protocol x.21\"))";
                   junos:must-message "cts invalid on line-protocol x.21";
                   type enumeration {
                     enum "require" {
                       description "Require CTS signal";
                     }
                     enum "ignore" {
                       description "Ignore CTS signal";
                     }
                     enum "normal" {
                       description "Normal CTS signal";
                     }
                   }
                 }
                 leaf indication {
                   description "X.21 Indication signal handling";
                   junos:must "(!(\".. .. line-protocol eia530\"))";
                   junos:must-message "Indication   invalid on line-protocol eia530";
                   junos:must "(!(\".. .. line-protocol v.35\"))";
                   junos:must-message "Indication invalid on line-protocol v.35";
                   type enumeration {
                     enum "require" {
                       description "Require Indication signal";
                     }
                     enum "ignore" {
                       description "Ignore Indication signal";
                     }
                     enum "normal" {
                       description "Normal Indication signal";
                     }
                   }
                 }
                 leaf tm {
                   description "Test Mode signal handling";
                   type enumeration {
                     enum "require" {
                       description "Require TM signal";
                     }
                     enum "ignore" {
                       description "Ignore TM signal";
                     }
                     enum "normal" {
                       description "Normal TM signal";
                     }
                   }
                 }
               }
             }
             case case_2 {
             }
           }
           leaf dtr-circuit {
             description "Data Transmit Ready circuit mode";
             junos:must "(!(\".. line-protocol x.21\"))";
             junos:must-message "dtr-circuit invalid with line protocol x.21";
             type enumeration {
               enum "balanced" {
                 description "Balanced signal";
               }
               enum "unbalanced" {
                 description "Unbalanced signal";
               }
             }
           }
           leaf dtr-polarity {
             description "Data Transmit Ready signal polarity";
             junos:must "(!(\".. line-protocol x.21\"))";
             junos:must-message "dtr-polarity invalid with line protocol x.21";
             type enumeration {
               enum "positive" {
                 description "Positive polarity";
               }
               enum "negative" {
                 description "Negative polarity";
               }
             }
           }
           leaf rts-polarity {
             description "Request To Send signal polarity";
             junos:must "(!(\".. line-protocol x.21\"))";
             junos:must-message "rts invalid on line-protocol x.21";
             type enumeration {
               enum "positive" {
                 description "Positive polarity";
               }
               enum "negative" {
                 description "Negative polarity";
               }
             }
           }
           leaf control-polarity {
             description "X.21 Control signal polarity";
             junos:must "(!(\".. line-protocol eia530\"))";
             junos:must-message "Control signal  invalid on line-protocol eia530";
             junos:must "(!(\".. line-protocol v.35\"))";
             junos:must-message "Control signal invalid on line-protocol v.35";
             type enumeration {
               enum "positive" {
                 description "Positive polarity";
               }
               enum "negative" {
                 description "Negative polarity";
               }
             }
           }
           leaf dcd-polarity {
             description "Data Carrier Detect signal polarity";
             junos:must "(!(\".. line-protocol x.21\"))";
             junos:must-message "dcd-polarity invalid with line protocol x.21";
             type enumeration {
               enum "positive" {
                 description "Positive polarity";
               }
               enum "negative" {
                 description "Negative polarity";
               }
             }
           }
           leaf dsr-polarity {
             description "Data Set Ready signal polarity";
             junos:must "(!(\".. line-protocol x.21\"))";
             junos:must-message "dsr-polarity invalid with line protocol x.21";
             type enumeration {
               enum "positive" {
                 description "Positive polarity";
               }
               enum "negative" {
                 description "Negative polarity";
               }
             }
           }
           leaf cts-polarity {
             description "Clear To Send signal polarity";
             junos:must "(!(\".. line-protocol x.21\"))";
             junos:must-message "cts invalid on line-protocol x.21";
             type enumeration {
               enum "positive" {
                 description "Positive polarity";
               }
               enum "negative" {
                 description "Negative polarity";
               }
             }
           }
           leaf indication-polarity {
             description "X.21 Indication signal polarity";
             junos:must "(!(\".. line-protocol eia530\"))";
             junos:must-message "Indication  invalid on line-protocol eia530";
             junos:must "(!(\".. line-protocol v.35\"))";
             junos:must-message "Indication invalid on line-protocol v.35";
             type enumeration {
               enum "positive" {
                 description "Positive polarity";
               }
               enum "negative" {
                 description "Negative polarity";
               }
             }
           }
           leaf tm-polarity {
             description "Test Mode signal polarity";
             junos:must "(!(\".. line-protocol x.21\"))";
             junos:must-message "tm-polarity invalid for line protocol x.21";
             junos:must "(!(\".. line-protocol v.35\"))";
             junos:must-message "tm-polarity invalid for line protocol v.35";
             type enumeration {
               enum "positive" {
                 description "Positive polarity";
               }
               enum "negative" {
                 description "Negative polarity";
               }
             }
           }
           leaf clocking-mode {
             description "Clock mode";
             type enumeration {
               enum "dce" {
                 description "DCE timing (DTE mode only, not valid for X.21)";
               }
               enum "internal" {
                 description "Internal baud timing";
               }
               enum "loop" {
                 description "Loop timing";
               }
             }
           }
           leaf transmit-clock {
             description "Transmit clock phase";
             type enumeration {
               enum "invert" {
                 description "Shift clock phase 180 degrees";
               }
             }
           }
           leaf clock-rate {
             description "Interface clock rate";
             type enumeration {
               enum "2.048mhz" {
                 description "2.048 MHz";
               }
               enum "2.341mhz" {
                 description "2.341 MHz";
               }
               enum "2.731mhz" {
                 description "2.731 MHz";
               }
               enum "3.277mhz" {
                 description "3.277 MHz";
               }
               enum "4.096mhz" {
                 description "4.096 MHz";
               }
               enum "5.461mhz" {
                 description "5.461 MHz";
               }
               enum "8.192mhz" {
                 description "8.192 MHz";
               }
               enum "16.384mhz" {
                 description "16.384 MHz";
               }
               enum "1.2khz" {
                 description "1.2 KHz";
               }
               enum "2.4khz" {
                 description "2.4 KHz";
               }
               enum "9.6khz" {
                 description "9.6 KHz";
               }
               enum "19.2khz" {
                 description "19.2 KHz";
               }
               enum "38.4khz" {
                 description "38.4 KHz";
               }
               enum "56.0khz" {
                 description "56.0 KHz";
               }
               enum "64.0khz" {
                 description "64.0 KHz";
               }
               enum "72.0khz" {
                 description "72.0 KHz";
               }
               enum "125.0khz" {
                 description "125.0 KHz";
               }
               enum "148.0khz" {
                 description "148.0 KHz";
               }
               enum "250.0khz" {
                 description "250.0 KHz";
               }
               enum "500.0khz" {
                 description "500.0 KHz";
               }
               enum "800.0khz" {
                 description "800.0 KHz";
               }
               enum "1.0mhz" {
                 description "1.0 MHz";
               }
               enum "1.3mhz" {
                 description "1.3 MHz";
               }
               enum "2.0mhz" {
                 description "2.0 MHz";
               }
               enum "4.0mhz" {
                 description "4.0 MHz";
               }
               enum "8.0mhz" {
                 description "8.0 MHz";
               }
             }
           }
           leaf loopback {
             description "Loopback mode";
             type enumeration {
               enum "local" {
                 description "Local loopback";
               }
               enum "remote" {
                 description "Remote/LIU loopback";
               }
               enum "dce-local" {
                 description "DCE local loopback (DTE mode only)";
               }
               enum "dce-remote" {
                 description "DCE remote loopback";
               }
             }
           }
           leaf encoding {
             description "Line encoding";
             type enumeration {
               enum "nrz" {
                 description "Non-Return-To-Zero";
               }
               enum "nrzi" {
                 description "Non-Return-To-Zero-Invertible";
               }
             }
           }
         }
         choice gratuitous-arp-reply-choice {
           leaf gratuitous-arp-reply {
             description "Enable gratuitous ARP reply";
             type empty;
           }
           leaf no-gratuitous-arp-reply {
             description "Don't enable gratuitous ARP reply";
             type empty;
           }
         }
         choice no-gratuitous-arp-request-choice {
           leaf no-gratuitous-arp-request {
             description "Ignore gratuitous ARP request";
             type empty;
           }
           leaf no-no-gratuitous-arp-request {
             description "Don't ignore gratuitous ARP request";
             type empty;
           }
         }
         leaf arp-l2-validate {
           description "Validate ARP against L2";
           type empty;
         }
         container ether-options {
           description "Ethernet interface-specific options";
           uses apply-advanced;
           choice loopback-choice {
             leaf loopback {
               description "Enable loopback";
               type empty;
             }
             leaf no-loopback {
               description "Don't enable loopback";
               type empty;
             }
           }
           leaf loopback-remote {
             description "Enable remote loopback";
             junos:must "(!(\".. .. optics-options loopback\"))";
             junos:must-message "'optics-options loopback' and loopback-remote are mutually exclusive";
             junos:must "(!(\".. loopback\"))";
             junos:must-message "loopback and loopback-remote are mutually exclusive";
             type empty;
           }
           choice source-filtering-choice {
             leaf source-filtering {
               description "Enable source address filtering";
               type empty;
             }
             leaf no-source-filtering {
               description "Don't enable source address filtering";
               type empty;
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             container ethernet-policer-profile {
               description "Ethernet level CoS-based policer configuration";
               uses apply-advanced;
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container storm-control {
               junos:must "(!(any \"interfaces ${interface} unit <*> family ethernet-switching storm-control <*>\"))";
               junos:must-message "An interface cannot have storm control on both family ethernet-switching and ethernet switch profile";
               junos:cli-feature "oneliner-plus";
               description "Storm control profile name to bind";
               uses apply-advanced;
               leaf profile-name {
                 description "Profile name";
                 junos:cli-feature "nokeyword";
                 junos:must "(\"forwarding-options storm-control-profiles $$\")";
                 junos:must-message "Storm profile name must be defined in the [edit forwarding-options storm-control-profiles] hierarchy";
                 type string;
               }
             }
             container recovery-timeout {
               junos:cli-feature "oneliner";
               description "Recovery timeout for this interface";
               leaf time-in-seconds {
                 junos:cli-feature "nokeyword";
                 units "seconds";
                 type union {
                   type string {
                     pattern "<.*>|$.*";
                   }
                   type uint32 {
                     range "10 .. 3600";
                   }
                 }
               }
             }
             choice mac-learn-enable-choice {
               leaf mac-learn-enable {
                 description "Learn MAC addresses dynamically";
                 type empty;
               }
               leaf no-mac-learn-enable {
                 description "Don't learn MAC addresses dynamically";
                 type empty;
               }
             }
           }
           leaf asynchronous-notification {
             description "Enable sending asynchronous notification to peer on CCC-down";
             type empty;
           }
           list source-address-filter {
             key name;
             junos:cli-feature "homogeneous";
             junos:cli-feature "oneliner";
             description "Source address filters";
             leaf name {
               description "Remote MAC address";
               junos:cli-feature "nokeyword";
               type jt:mac-addr;
             }
           }
           choice auto-negotiation-choice {
             leaf auto-negotiation {
               description "Enable auto-negotiation";
               type empty;
             }
             leaf no-auto-negotiation {
               description "Don't enable auto-negotiation";
               type empty;
             }
           }
           choice flow-control-choice {
             leaf flow-control {
               description "Enable flow control";
               type empty;
             }
             leaf no-flow-control {
               description "Don't enable flow control";
               type empty;
             }
           }
           container configured-flow-control {
             presence "enable configured-flow-control";
             junos:must "(!((\".. flow-control\" || \".. no-flow-control\")))";
             junos:must-message "flow-control and configured-flow-control are not allowed together";
             description "Enable flow control";
             uses apply-advanced;
             leaf rx-buffers {
               description "Enable/Disable Rx buffers";
               type enumeration {
                 enum "on" {
                   description "Enable Rx buffers";
                 }
                 enum "off" {
                   description "Disable Rx buffers";
                 }
               }
             }
             leaf tx-buffers {
               description "Enable/Disable Tx buffers";
               type enumeration {
                 enum "on" {
                   description "Enable Tx buffers";
                 }
                 enum "off" {
                   description "Disable Tx buffers";
                 }
               }
             }
           }
           leaf link-mode {
             description "Link duplex";
             type enumeration {
               enum "automatic" {
                 description "Automatic negotiate duplex ";
               }
               enum "half-duplex" {
                 description "Half-duplex operation";
               }
               enum "full-duplex" {
                 description "Full-duplex operation";
               }
             }
           }
           container mpls {
             description "MPLS options";
             uses mpls_ifd_options;
           }
           leaf ignore-l3-incompletes {
             description "Ignore L3 incomplete errors";
             type empty;
           }
           leaf no-auto-mdix {
             description "Disable auto MDI/MDIX";
             type empty;
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
               enum "fec-etc" {
                 description "ETC fec based on IEEE 802.3 Clause 119 for 800G links";
               }
               enum "fec172" {
                 description "IEEE 802.3dj Clause 172, RS-FEC for 800G links";
               }
             }
           }
           container speed {
             description "Specify speed";
             choice automatic {
               case case_1 {
                 container auto-negotiation {
                   presence "enable auto-negotiation";
                   junos:cli-feature "oneliner";
                   description "Enable auto-negotiation";
                   leaf auto-negotiate-10-100 {
                     description "Limits the auto-negotiation to 10m/100m only";
                     type empty;
                   }
                 }
               }
               case case_2 {
                 leaf ethernet-10m {
                   description "10Mbps";
                   type empty;
                 }
               }
               case case_3 {
                 leaf ethernet-100m {
                   description "100Mbps";
                   type empty;
                 }
               }
               case case_4 {
                 leaf ethernet-1g {
                   description "1Gbps";
                   type empty;
                 }
               }
               case case_5 {
                 leaf ethernet-10g {
                   description "10Gbps";
                   type empty;
                 }
               }
             }
           }
           container ieee-802.3ad {
             junos:must "(!(\"system autoinstallation\"))";
             junos:must-message "incompatible with 'system autoinstallation'";
             junos:cli-feature "oneliner-plus";
             description "IEEE 802.3ad";
             uses apply-advanced;
             container lacp {
               description "Link Aggregation Control Protocol configuration";
               uses apply-advanced;
               leaf force-up {
                 description "Keep the port up in absence of received LACPDU";
                 type empty;
               }
               leaf port-priority {
                 description "Priority of the port (0 ... 65535)";
                 type union {
                   type uint16;
                   type string {
                     pattern "<.*>|$.*";
                   }
                 }
               }
             }
             leaf bundle {
               description "Join an aggregated Ethernet interface";
               junos:cli-feature "nokeyword";
               junos:must "(!(\"class-of-service interfaces ${interface} dynamic-threshold-profile\"))";
               junos:must-message "dynamic-threshold-profile config cannot be applied on ae child";
               junos:must "(!(any \"class-of-service interfaces ${interface} unit <*> rewrite-rules\"))";
               junos:must-message "rewrite config can not be applied on ae child";
               junos:must "(!(any \"class-of-service interfaces ${interface} unit <*> classifiers\"))";
               junos:must-message "classifier config can not be applied on ae child";
               junos:must "(!(any \"class-of-service interfaces ${interface} unit <*> output-traffic-control-profile\"))";
               junos:must-message "output-traffic-control-profile config can not be applied on ae child";
               junos:must "(!(\"class-of-service interfaces ${interface} output-traffic-control-profile\"))";
               junos:must-message "output-traffic-control-profile config can not be applied on ae child";
               junos:must "(!(\"class-of-service interfaces ${interface} shaping-rate\"))";
               junos:must-message "shaping-rate config can not be applied on ae child";
               junos:must "(!(\"class-of-service interfaces ${interface} scheduler-map\"))";
               junos:must-message "scheduler-map config can not be applied on ae child";
               junos:must "(!(\".. .. .. gigether-options 802.3ad\"))";
               junos:must-message "Member link cannot be a part of multiple aggregation group";
               junos:must "(!(\".. .. .. vlan-offload\"))";
               junos:must-message "ae child device vlan-offload is not allowed";
               junos:must "(!(\".. .. .. flow-control\"))";
               junos:must-message "Setting flow-control on ae child device is not allowed";
               junos:must "(!(\".. .. .. mtu\"))";
               junos:must-message "Setting mtu on ae child device is not allowed";
               junos:must "(!(\".. .. .. vlan-vci-tagging\"))";
               junos:must-message "ae child device vlan-vci-tagging is not allowed";
               junos:must "(!(\".. .. .. stacked-vlan-tagging\"))";
               junos:must-message "ae child device stacked-vlan-tagging is not allowed";
               junos:must "(!(\".. .. .. flexible-vlan-tagging\"))";
               junos:must-message "ae child device flexible-vlan-tagging is not allowed";
               junos:must "(!(\".. .. .. vlan-tagging\"))";
               junos:must-message "ae child device vlan-tagging is not allowed";
               junos:must "(!(\".. .. .. passive-monitor-mode\"))";
               junos:must-message "802.3ad not valid for passive-monitor-mode";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
             container link-protection-sub-group {
               description "Link Protection subgroup configuration";
               uses apply-advanced;
               leaf subgroup-name {
                 description "Name of the subgroup";
                 junos:cli-feature "nokeyword";
                 type string {
                   length "2 .. 64";
                 }
               }
             }
             leaf port-priority {
               description "Link protection Priority of the port (0 ... 65535)";
               type union {
                 type uint16;
                 type string {
                   pattern "<.*>|$.*";
                 }
               }
             }
           }
           leaf ieee-802-3az-eee {
             description "IEEE 802.3az Energy Efficient Ethernet(EEE)";
             type empty;
           }
           leaf autostate-exclude {
             description "Interface will not contribute to IRB state";
             type empty;
           }
         }
         container fibrechannel-options {
           description "Fibre Channel interface-specific options";
           uses apply-advanced;
           choice loopback-choice {
             leaf loopback {
               description "Enable loopback";
               type empty;
             }
             leaf no-loopback {
               description "Don't enable loopback";
               type empty;
             }
           }
           leaf bb-sc-n {
             description "B2B state change number";
             type union {
               type string {
                 pattern "<.*>|$.*";
               }
               type uint16 {
                 range "0 .. 15";
               }
             }
           }
           leaf speed {
             description "Specify speed";
             type enumeration {
               enum "auto-negotiation" {
                 description "Enable auto-negotiation";
               }
               enum "1g" {
                 description "1Gbps";
               }
               enum "2g" {
                 description "2Gbps";
               }
               enum "4g" {
                 description "4Gbps";
               }
               enum "8g" {
                 description "8Gbps";
               }
             }
           }
         }
         container gigether-options {
           description "Gigabit Ethernet interface-specific options";
           uses apply-advanced;
           choice loopback-choice {
             leaf loopback {
               description "Enable loopback";
               type empty;
             }
             leaf no-loopback {
               description "Don't enable loopback";
               type empty;
             }
           }
           leaf loopback-remote {
             description "Enable remote loopback";
             junos:must "(!(\".. .. optics-options loopback\"))";
             junos:must-message "'optics-options loopback' and loopback-remote are mutually exclusive";
             junos:must "(!(\".. loopback\"))";
             junos:must-message "loopback and loopback-remote are mutually exclusive";
             type empty;
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           choice auto_negotiation_option {
             case case_1 {
               leaf no-auto-negotiation {
                 description "Disable auto-negotiation";
                 type empty;
               }
             }
             case case_2 {
               container auto-negotiation {
                 presence "enable auto-negotiation";
                 junos:cli-feature "oneliner";
                 description "Enable auto-negotiation";
                 leaf remote-fault {
                   type enumeration {
                     enum "local-interface-offline" {
                       description "Disable local interface";
                     }
                     enum "local-interface-online" {
                       description "Enable local interface";
                     }
                   }
                 }
               }
             }
           }
           leaf asynchronous-notification {
             description "Enable sending asynchronous notification to peer on CCC-down";
             type empty;
           }
           list source-address-filter {
             key name;
             junos:cli-feature "homogeneous";
             junos:cli-feature "oneliner";
             description "Source address filters";
             leaf name {
               description "Remote MAC address";
               junos:cli-feature "nokeyword";
               type jt:mac-addr;
             }
           }
           container ieee-802.3ad {
             junos:must "(!(\"system autoinstallation\"))";
             junos:must-message "incompatible with 'system autoinstallation'";
             junos:cli-feature "oneliner-plus";
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               junos:cli-feature "nokeyword";
               junos:must "(!(any \"class-of-service interfaces ${interface} unit <*> rewrite-rules\"))";
               junos:must-message "rewrite config can not be applied on ae child";
               junos:must "(!(any \"class-of-service interfaces ${interface} unit <*> classifiers\"))";
               junos:must-message "classifier config can not be applied on ae child";
               junos:must "(!(any \"class-of-service interfaces ${interface} unit <*> output-traffic-control-profile\"))";
               junos:must-message "output-traffic-control-profile config can not be applied on ae child";
               junos:must "(!(\"class-of-service interfaces ${interface} output-traffic-control-profile\"))";
               junos:must-message "output-traffic-control-profile config can not be applied on ae child";
               junos:must "(!(\"class-of-service interfaces ${interface} shaping-rate\"))";
               junos:must-message "shaping-rate config can not be applied on ae child";
               junos:must "(!(\"class-of-service interfaces ${interface} scheduler-map\"))";
               junos:must-message "scheduler-map config can not be applied on ae child";
               junos:must "(!(\".. .. .. ether-options 802.3ad\"))";
               junos:must-message "Member link cannot be a part of multiple aggregation group";
               junos:must "(!(\".. .. .. vlan-offload\"))";
               junos:must-message "ae child device vlan-offload is not allowed";
               junos:must "(!(\".. .. .. flow-control\"))";
               junos:must-message "Setting flow-control on ae child device is not allowed";
               junos:must "(!(\".. .. .. mtu\"))";
               junos:must-message "Setting mtu on ae child device is not allowed";
               junos:must "(!(\".. .. .. vlan-vci-tagging\"))";
               junos:must-message "ae child device vlan-vci-tagging is not allowed";
               junos:must "(!(\".. .. .. stacked-vlan-tagging\"))";
               junos:must-message "ae child device stacked-vlan-tagging is not allowed";
               junos:must "(!(\".. .. .. flexible-vlan-tagging\"))";
               junos:must-message "ae child device flexible-vlan-tagging is not allowed";
               junos:must "(!(\".. .. .. vlan-tagging\"))";
               junos:must-message "ae child device vlan-tagging is not allowed";
               junos:must "(!(\".. .. .. passive-monitor-mode\"))";
               junos:must-message "802.3ad not valid for passive-monitor-mode";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             container ethernet-policer-profile {
               description "Ethernet level CoS-based policer configuration";
               uses apply-advanced;
               container ieee802.1-priority-map {
                 presence "enable ieee802.1-priority-map";
                 description "Premium priority values for IEEE 802.1p bits";
                 status deprecated;
                 uses apply-advanced;
                 leaf-list premium {
                   ordered-by user;
                   description "Premium policer priority map";
                   type union {
                     type string {
                       pattern "<.*>|$.*";
                     }
                     type uint32 {
                       range "0 .. 7";
                     }
                   }
                 }
               }
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container accept-from {
               description "Accept traffic from or to specified remote MAC";
               status deprecated;
               uses apply-advanced;
               list mac-address {
                 key name;
                 description "Remote MAC";
                 uses mac_list;
               }
             }
             choice reject-the-rest-choice {
               leaf reject-the-rest {
                 description "Accept traffic from only the specified MAC addresses";
                 status deprecated;
                 type empty;
               }
               leaf no-reject-the-rest {
                 description "Don't accept traffic from only the specified MAC addresses";
                 status deprecated;
                 type empty;
               }
             }
             leaf mac-learn-enable {
               description "Learn MAC addresses dynamically";
               type empty;
             }
           }
           container mpls {
             description "MPLS options";
             uses mpls_ifd_options;
           }
           leaf ignore-l3-incompletes {
             description "Ignore L3 incomplete errors";
             type empty;
           }
           leaf no-auto-mdix {
             description "Disable auto MDI/MDIX";
             type empty;
           }
           leaf ieee-802-3az-eee {
             description "IEEE 802.3az Energy Efficient Ethernet(EEE)";
             type empty;
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
             }
           }
         }
         container optics-options {
           description "Optics options";
           uses apply-advanced;
           leaf wavelength {
             description "Wavelength of the optics (nanometers) for 50Ghz/100Ghz spacing";
             type enumeration {
               enum "1611.79" {
                 description "1611.79 nm/186.000000 THz 3.125/6.25/12.5/50/75/100GHz spacing";
               }
               enum "1611.76" {
                 description "1611.76 nm/186.003125 THz 3.125GHz spacing";
               }
               enum "1611.73" {
                 description "1611.73 nm/186.006250 THz 3.125/6.25GHz spacing";
               }
               enum "1611.71" {
                 description "1611.71 nm/186.009375 THz 3.125GHz spacing";
               }
               enum "1611.68" {
                 description "1611.68 nm/186.012500 THz 3.125/6.25/12.5GHz spacing";
               }
               enum "1611.65" {
                 description "1611.65 nm/186.015625 THz 3.125GHz spacing";
               }
               enum "1611.62" {
                 description "1611.62 nm/186.018750 THz 3.125/6.25GHz spacing";
               }
               enum "1611.60" {
                 description "1611.60 nm/186.021875 THz 3.125GHz spacing";
               }
               enum "1611.57" {
                 description "1611.57 nm/186.025000 THz 3.125/6.25/12.5GHz spacing";
               }
               enum "1611.54" {
                 description "1611.54 nm/186.028125 THz 3.125GHz spacing";
               }
               enum "1611.52" {
                 description "1611.52 nm/186.031250 THz 3.125/6.25GHz spacing";
               }
               enum "1611.49" {
                 description "1611.49 nm/186.034375 THz 3.125GHz spacing";
               }
               enum "1611.46" {
                 description "1611.46 nm/186.037500 THz 3.125/6.25/12.5GHz spacing";
               }
               enum "1611.44" {
                 description "1611.44 nm/186.040625 THz 3.125GHz spacing";
               }
               enum "1611.41" {
                 description "1611.41 nm/186.043750 THz 3.125/6.25GHz spacing";
               }
               enum "1611.38" {
                 description "1611.38 nm/186.046875 THz 3.125GHz spacing";
               }
               enum "1611.35" {
                 description "1611.35 nm/186.050000 THz 3.125/6.25/12.5/50/75GHz spacing";
               }
               enum "1611.33" {
                 description "1611.33 nm/186.053125 THz 3.125GHz spacing";
               }
               enum "1611.30" {
                 description "1611.30 nm/186.056250 THz 3.125/6.25GHz spacing";
               }
               enum "1611.27" {
                 description "1611.27 nm/186.059375 THz 3.125GHz spacing";
               }
               enum "1611.25" {
                 description "1611.25 nm/186.062500 THz 3.125/6.25/12.5GHz spacing";
               }
               enum "1611.22" {
                 description "1611.22 nm/186.065625 THz 3.125GHz spacing";
               }
               enum "1611.19" {
                 description "1611.19 nm/186.068750 THz 3.125/6.25GHz spacing";
               }
               enum "1611.16" {
                 description "1611.16 nm/186.071875 THz 3.125GHz spacing";
               }
               enum "1611.14" {
                 description "1611.14 nm/186.075000 THz 3.125/6.25/12.5GHz spacing";
               }
               enum "1611.11" {
                 description "1611.11 nm/186.078125 THz 3.125GHz spacing";
               }
               enum "1611.08" {
                 description "1611.08 nm/186.081250 THz 3.125/6.25GHz spacing";
               }
               enum "1611.06" {
                 description "1611.06 nm/186.084375 THz 3.125GHz spacing";
               }
               enum "1611.03" {
                 description "1611.03 nm/186.087500 THz 3.125/6.25/12.5GHz spacing";
               }
               enum "1611.00" {
                 description "1611.00 nm/186.090625 THz 3.125GHz spacing";
               }
               enum "1610.98" {
                 description "1610.98 nm/186.093750 THz 3.125/6.25GHz spacing";
               }
               enum "1610.95" {
                 description "1610.95 nm/186.096875 THz 3.125GHz spacing";
               }
               enum "1610.92" {
                 description "1610.92 nm/186.100000 THz 3.125/6.25/12.5/100GHz spacing";
               }
               enum "1610.89" {
                 description "1610.89 nm/186.103125 THz 3.125GHz spacing";
               }
               enum "1610.87" {
                 description "1610.87 nm/186.106250 THz 3.125/6.25GHz spacing";
               }
               enum "1610.84" {
                 description "1610.84 nm/186.109375 THz 3.125GHz spacing";
               }
               enum "1610.81" {
                 description "1610.81 nm/186.112500 THz 3.125/6.25/12.5GHz spacing";
               }
               enum "1610.79" {
                 description "1610.79 nm/186.115625 THz 3.125GHz spacing";
               }
               enum "1610.76" {
                 description "1610.76 nm/186.118750 THz 3.125/6.25GHz spacing";
               }
               enum "1610.73" {
                 description "1610.73 nm/186.121875 THz 3.125GHz spacing";
               }
               enum "1610.70" {
                 description "1610.70 nm/186.125000 THz 3.125/6.25/12.5/75GHz spacing";
               }
               enum "1610.68" {
                 description "1610.68 nm/186.128125 THz 3.125GHz spacing";
               }
               enum "1610.65" {
                 description "1610.65 nm/186.131250 THz 3.125/6.25GHz spacing";
               }
               enum "1610.62" {
                 description "1610.62 nm/186.134375 THz 3.125GHz spacing";
               }
               enum "1610.60" {
                 description "1610.60 nm/186.137500 THz 3.125/6.25/12.5GHz spacing";
               }
               enum "1610.57" {
                 description "1610.57 nm/186.140625 THz 3.125GHz spacing";
               }
               enum "1610.54" {
                 description "1610.54 nm/186.143750 THz 3.125/6.25GHz spacing";
               }
               enum "1610.52" {
                 description "1610.52 nm/186.146875 THz 3.125GHz spacing";
               }
               enum "1610.49" {
                 description "1610.49 nm/186.150000 THz 3.125/6.25/12.5/50GHz spacing";
               }
               enum "1610.46" {
                 description "1610.46 nm/186.153125 THz 3.125GHz spacing";
               }
               enum "1610.43" {
                 description "1610.43 nm/186.156250 THz 3.125/6.25GHz spacing";
               }
               enum "1610.41" {
                 description "1610.41 nm/186.159375 THz 3.125GHz spacing";
               }
               enum "1610.38" {
                 description "1610.38 nm/186.162500 THz 3.125/6.25/12.5GHz spacing";
               }
               enum "1610.35" {
                 description "1610.35 nm/186.165625 THz 3.125GHz spacing";
               }
               enum "1610.33" {
                 description "1610.33 nm/186.168750 THz 3.125/6.25GHz spacing";
               }
               enum "1610.30" {
                 description "1610.30 nm/186.171875 THz 3.125GHz spacing";
               }
               enum "1610.27" {
                 description "1610.27 nm/186.175000 THz 3.125/6.25/12.5GHz spacing";
               }
               enum "1610.25" {
                 description "1610.25 nm/186.178125 THz 3.125GHz spacing";
               }
               enum "1610.22" {
                 description "1610.22 nm/186.181250 THz 3.125/6.25GHz spacing";
               }
               enum "1610.19" {
                 description "1610.19 nm/186.184375 THz 3.125GHz spacing";
               }
               enum "1610.16" {
                 description "1610.16 nm/186.187500 THz 3.125/6.25/12.5GHz spacing";
               }
               enum "1610.14" {
                 description "1610.14 nm/186.190625 THz 3.125GHz spacing";
               }
               enum "1610.11" {
                 description "1610.11 nm/186.193750 THz 3.125/6.25GHz spacing";
               }
               enum "1610.08" {
                 description "1610.08 nm/186.196875 THz 3.125GHz spacing";
               }
               enum "1610.06" {
                 description "1610.06 nm/186.200000 THz 3.125/6.25/12.5/100GHz spacing";
               }
               enum "1610.03" {
                 description "1610.03 nm/186.203125 THz 3.125GHz spacing";
               }
               enum "1610.00" {
                 description "1610.00 nm/186.206250 THz 3.125/6.25GHz spacing";
               }
               enum "1609.98" {
                 description "1609.98 nm/186.209375 THz 3.125GHz spacing";
               }
               enum "1609.95" {
                 description "1609.95 nm/186.212500 THz 3.125/6.25/12.5GHz spacing";
               }
               enum "1609.92" {
                 description "1609.92 nm/186.215625 THz 3.125GHz spacing";
               }
               enum "1609.89" {
                 description "1609.89 nm/186.218750 THz 3.125/6.25GHz spacing";
               }
               enum "1609.87" {
                 description "1609.87 nm/186.221875 THz 3.125GHz spacing";
               }
               enum "1609.84" {
                 description "1609.84 nm/186.225000 THz 3.125/6.25/12.5GHz spacing";
               }
               enum "1609.81" {
                 description "1609.81 nm/186.228125 THz 3.125GHz spacing";
               }
               enum "1609.79" {
                 description "1609.79 nm/186.231250 THz 3.125/6.25GHz spacing";
               }
               enum "1609.76" {
                 description "1609.76 nm/186.234375 THz 3.125GHz spacing";
               }
               enum "1609.73" {
                 description "1609.73 nm/186.237500 THz 3.125/6.25/12.5GHz spacing";
               }
               enum "1609.70" {
                 description "1609.70 nm/186.240625 THz 3.125GHz spacing";
               }
               enum "1609.68" {
                 description "1609.68 nm/186.243750 THz 3.125/6.25GHz spacing";
               }
               enum "1609.65" {
                 description "1609.65 nm/186.246875 THz 3.125GHz spacing";
               }
               enum "1609.62" {
                 description "1609.62 nm/186.250000 THz 3.125/6.25/12.5/50GHz spacing";
               }
               enum "1609.60" {
                 description "1609.60 nm/186.253125 THz 3.125GHz spacing";
               }
               enum "1609.57" {
                 description "1609.57 nm/186.256250 THz 3.125/6.25GHz spacing";
               }
               enum "1609.54" {
                 description "1609.54 nm/186.259375 THz 3.125GHz spacing";
               }
               enum "1609.52" {
                 description "1609.52 nm/186.262500 THz 3.125/6.25/12.5GHz spacing";
               }
               enum "1609.49" {
                 description "1609.49 nm/186.265625 THz 3.125GHz spacing";
               }
               enum "1609.46" {
                 description "1609.46 nm/186.268750 THz 3.125/6.25GHz spacing";
               }
               enum "1609.43" {
                 description "1609.43 nm/186.271875 THz 3.125GHz spacing";
               }
               enum "1609.41" {
                 description "1609.41 nm/186.275000 THz 3.125/6.25/12.5/75GHz spacing";
               }
               enum "1609.38" {
                 description "1609.38 nm/186.278125 THz 3.125GHz spacing";
               }
               enum "1609.35" {
                 description "1609.35 nm/186.281250 THz 3.125/6.25GHz spacing";
               }
               enum "1609.33" {
                 description "1609.33 nm/186.284375 THz 3.125GHz spacing";
               }
               enum "1609.30" {
                 description "1609.30 nm/186.287500 THz 3.125/6.25/12.5GHz spacing";
               }
               enum "1609.27" {
                 description "1609.27 nm/186.290625 THz 3.125GHz spacing";
               }
               enum "1609.25" {
                 description "1609.25 nm/186.293750 THz 3.125/6.25GHz spacing";
               }
               enum "1609.22" {
                 description "1609.22 nm/186.296875 THz 3.125GHz spacing";
               }
               enum "1609.19" {
                 description "1609.19 nm/186.300000 THz 3.125/6.25/12.5/50/75/100GHz spacing";
               }
               enum "1609.16" {
                 description "1609.16 nm/186.303125 THz 3.125GHz spacing";
               }
               enum "1609.14" {
                 description "1609.14 nm/186.306250 THz 3.125/6.25GHz spacing";
               }
               enum "1609.11" {
                 description "1609.11 nm/186.309375 THz 3.125GHz spacing";
               }
               enum "1609.08" {
                 description "1609.08 nm/186.312500 THz 3.125/6.25/12.5GHz spacing";
               }
               enum "1609.06" {
                 description "1609.06 nm/186.315625 THz 3.125GHz spacing";
               }
               enum "1609.03" {
                 description "1609.03 nm/186.318750 THz 3.125/6.25GHz spacing";
               }
               enum "1609.00" {
                 description "1609.00 nm/186.321875 THz 3.125GHz spacing";
               }
               enum "1608.98" {
                 description "1608.98 nm/186.325000 THz 3.125/6.25/12.5GHz spacing";
               }
               enum "1608.95" {
                 description "1608.95 nm/186.328125 THz 3.125GHz spacing";
               }
               enum "1608.92" {
                 description "1608.92 nm/186.331250 THz 3.125/6.25GHz spacing";
               }
               enum "1608.90" {
                 description "1608.90 nm/186.334375 THz 3.125GHz spacing";
               }
               enum "1608.87" {
                 description "1608.87 nm/186.337500 THz 3.125/6.25/12.5GHz spacing";
               }
               enum "1608.84" {
                 description "1608.84 nm/186.340625 THz 3.125GHz spacing";
               }
               enum "1608.81" {
                 description "1608.81 nm/186.343750 THz 3.125/6.25GHz spacing";
               }
               enum "1608.79" {
                 description "1608.79 nm/186.346875 THz 3.125GHz spacing";
               }
               enum "1608.76" {
                 description "1608.76 nm/186.350000 THz 3.125/6.25/12.5/50/75GHz spacing";
               }
               enum "1608.73" {
                 description "1608.73 nm/186.353125 THz 3.125GHz spacing";
               }
               enum "1608.71" {
                 description "1608.71 nm/186.356250 THz 3.125/6.25GHz spacing";
               }
               enum "1608.68" {
                 description "1608.68 nm/186.359375 THz 3.125GHz spacing";
               }
               enum "1608.65" {
                 description "1608.65 nm/186.362500 THz 3.125/6.25/12.5GHz spacing";
               }
               enum "1608.63" {
                 description "1608.63 nm/186.365625 THz 3.125GHz spacing";
               }
               enum "1608.60" {
                 description "1608.60 nm/186.368750 THz 3.125/6.25GHz spacing";
               }
               enum "1608.57" {
                 description "1608.57 nm/186.371875 THz 3.125GHz spacing";
               }
               enum "1608.54" {
                 description "1608.54 nm/186.375000 THz 3.125/6.25/12.5GHz spacing";
               }
               enum "1608.52" {
                 description "1608.52 nm/186.378125 THz 3.125GHz spacing";
               }
               enum "1608.49" {
                 description "1608.49 nm/186.381250 THz 3.125/6.25GHz spacing";
               }
               enum "1608.46" {
                 description "1608.46 nm/186.384375 THz 3.125GHz spacing";
               }
               enum "1608.44" {
                 description "1608.44 nm/186.387500 THz 3.125/6.25/12.5GHz spacing";
               }
               enum "1608.41" {
                 description "1608.41 nm/186.390625 THz 3.125GHz spacing";
               }
               enum "1608.38" {
                 description "1608.38 nm/186.393750 THz 3.125/6.25GHz spacing";
               }
               enum "1608.36" {
                 description "1608.36 nm/186.396875 THz 3.125GHz spacing";
               }
               enum "1608.33" {
                 description "1608.33 nm/186.400000 THz 3.125/6.25/12.5/100GHz spacing";
               }
               enum "1608.30" {
                 description "1608.30 nm/186.403125 THz 3.125GHz spacing";
               }
               enum "1608.27" {
                 description "1608.27 nm/186.406250 THz 3.125/6.25GHz spacing";
               }
               enum "1608.25" {
                 description "1608.25 nm/186.409375 THz 3.125GHz spacing";
               }
               enum "1608.22" {
                 description "1608.22 nm/186.412500 THz 3.125/6.25/12.5GHz spacing";
               }
               enum "1608.19" {
                 description "1608.19 nm/186.415625 THz 3.125GHz spacing";
               }
               enum "1608.17" {
                 description "1608.17 nm/186.418750 THz 3.125/6.25GHz spacing";
               }
               enum "1608.14" {
                 description "1608.14 nm/186.421875 THz 3.125GHz spacing";
               }
               enum "1608.11" {
                 description "1608.11 nm/186.425000 THz 3.125/6.25/12.5/75GHz spacing";
               }
               enum "1608.09" {
                 description "1608.09 nm/186.428125 THz 3.125GHz spacing";
               }
               enum "1608.06" {
                 description "1608.06 nm/186.431250 THz 3.125/6.25GHz spacing";
               }
               enum "1608.03" {
                 description "1608.03 nm/186.434375 THz 3.125GHz spacing";
               }
               enum "1608.01" {
                 description "1608.01 nm/186.437500 THz 3.125/6.25/12.5GHz spacing";
               }
               enum "1607.98" {
                 description "1607.98 nm/186.440625 THz 3.125GHz spacing";
               }
               enum "1607.95" {
                 description "1607.95 nm/186.443750 THz 3.125/6.25GHz spacing";
               }
               enum "1607.92" {
                 description "1607.92 nm/186.446875 THz 3.125GHz spacing";
               }
               enum "1607.90" {
                 description "1607.90 nm/186.450000 THz 3.125/6.25/12.5/50GHz spacing";
               }
               enum "1607.87" {
                 description "1607.87 nm/186.453125 THz 3.125GHz spacing";
               }
               enum "1607.84" {
                 description "1607.84 nm/186.456250 THz 3.125/6.25GHz spacing";
               }
               enum "1607.82" {
                 description "1607.82 nm/186.459375 THz 3.125GHz spacing";
               }
               enum "1607.79" {
                 description "1607.79 nm/186.462500 THz 3.125/6.25/12.5GHz spacing";
               }
               enum "1607.76" {
                 description "1607.76 nm/186.465625 THz 3.125GHz spacing";
               }
               enum "1607.74" {
                 description "1607.74 nm/186.468750 THz 3.125/6.25GHz spacing";
               }
               enum "1607.71" {
                 description "1607.71 nm/186.471875 THz 3.125GHz spacing";
               }
               enum "1607.68" {
                 description "1607.68 nm/186.475000 THz 3.125/6.25/12.5GHz spacing";
               }
               enum "1607.65" {
                 description "1607.65 nm/186.478125 THz 3.125GHz spacing";
               }
               enum "1607.63" {
                 description "1607.63 nm/186.481250 THz 3.125/6.25GHz spacing";
               }
               enum "1607.60" {
                 description "1607.60 nm/186.484375 THz 3.125GHz spacing";
               }
               enum "1607.57" {
                 description "1607.57 nm/186.487500 THz 3.125/6.25/12.5GHz spacing";
               }
               enum "1607.55" {
                 description "1607.55 nm/186.490625 THz 3.125GHz spacing";
               }
               enum "1607.52" {
                 description "1607.52 nm/186.493750 THz 3.125/6.25GHz spacing";
               }
               enum "1607.49" {
                 description "1607.49 nm/186.496875 THz 3.125GHz spacing";
               }
               enum "1607.47" {
                 description "1607.47 nm/186.500000 THz 3.125/6.25/12.5/100GHz spacing";
               }
               enum "1607.44" {
                 description "1607.44 nm/186.503125 THz 3.125GHz spacing";
               }
               enum "1607.41" {
                 description "1607.41 nm/186.506250 THz 3.125/6.25GHz spacing";
               }
               enum "1607.39" {
                 description "1607.39 nm/186.509375 THz 3.125GHz spacing";
               }
               enum "1607.36" {
                 description "1607.36 nm/186.512500 THz 3.125/6.25/12.5GHz spacing";
               }
               enum "1607.33" {
                 description "1607.33 nm/186.515625 THz 3.125GHz spacing";
               }
               enum "1607.30" {
                 description "1607.30 nm/186.518750 THz 3.125/6.25GHz spacing";
               }
               enum "1607.28" {
                 description "1607.28 nm/186.521875 THz 3.125GHz spacing";
               }
               enum "1607.25" {
                 description "1607.25 nm/186.525000 THz 3.125/6.25/12.5GHz spacing";
               }
               enum "1607.22" {
                 description "1607.22 nm/186.528125 THz 3.125GHz spacing";
               }
               enum "1607.20" {
                 description "1607.20 nm/186.531250 THz 3.125/6.25GHz spacing";
               }
               enum "1607.17" {
                 description "1607.17 nm/186.534375 THz 3.125GHz spacing";
               }
               enum "1607.14" {
                 description "1607.14 nm/186.537500 THz 3.125/6.25/12.5GHz spacing";
               }
               enum "1607.12" {
                 description "1607.12 nm/186.540625 THz 3.125GHz spacing";
               }
               enum "1607.09" {
                 description "1607.09 nm/186.543750 THz 3.125/6.25GHz spacing";
               }
               enum "1607.06" {
                 description "1607.06 nm/186.546875 THz 3.125GHz spacing";
               }
               enum "1607.04" {
                 description "1607.04 nm/186.550000 THz 3.125/6.25/12.5/50GHz spacing";
               }
               enum "1607.01" {
                 description "1607.01 nm/186.553125 THz 3.125GHz spacing";
               }
               enum "1606.98" {
                 description "1606.98 nm/186.556250 THz 3.125/6.25GHz spacing";
               }
               enum "1606.95" {
                 description "1606.95 nm/186.559375 THz 3.125GHz spacing";
               }
               enum "1606.93" {
                 description "1606.93 nm/186.562500 THz 3.125/6.25/12.5GHz spacing";
               }
               enum "1606.90" {
                 description "1606.90 nm/186.565625 THz 3.125GHz spacing";
               }
               enum "1606.87" {
                 description "1606.87 nm/186.568750 THz 3.125/6.25GHz spacing";
               }
               enum "1606.85" {
                 description "1606.85 nm/186.571875 THz 3.125GHz spacing";
               }
               enum "1606.82" {
                 description "1606.82 nm/186.575000 THz 3.125/6.25/12.5/75GHz spacing";
               }
               enum "1606.79" {
                 description "1606.79 nm/186.578125 THz 3.125GHz spacing";
               }
               enum "1606.77" {
                 description "1606.77 nm/186.581250 THz 3.125/6.25GHz spacing";
               }
               enum "1606.74" {
                 description "1606.74 nm/186.584375 THz 3.125GHz spacing";
               }
               enum "1606.71" {
                 description "1606.71 nm/186.587500 THz 3.125/6.25/12.5GHz spacing";
               }
               enum "1606.69" {
                 description "1606.69 nm/186.590625 THz 3.125GHz spacing";
               }
               enum "1606.66" {
                 description "1606.66 nm/186.593750 THz 3.125/6.25GHz spacing";
               }
               enum "1606.63" {
                 description "1606.63 nm/186.596875 THz 3.125GHz spacing";
               }
               enum "1606.60" {
                 description "1606.60 nm/186.600000 THz 3.125/6.25/12.5/50/75/100GHz spacing";
               }
               enum "1606.58" {
                 description "1606.58 nm/186.603125 THz 3.125GHz spacing";
               }
               enum "1606.55" {
                 description "1606.55 nm/186.606250 THz 3.125/6.25GHz spacing";
               }
               enum "1606.52" {
                 description "1606.52 nm/186.609375 THz 3.125GHz spacing";
               }
               enum "1606.50" {
                 description "1606.50 nm/186.612500 THz 3.125/6.25/12.5GHz spacing";
               }
               enum "1606.47" {
                 description "1606.47 nm/186.615625 THz 3.125GHz spacing";
               }
               enum "1606.44" {
                 description "1606.44 nm/186.618750 THz 3.125/6.25GHz spacing";
               }
               enum "1606.42" {
                 description "1606.42 nm/186.621875 THz 3.125GHz spacing";
               }
               enum "1606.39" {
                 description "1606.39 nm/186.625000 THz 3.125/6.25/12.5GHz spacing";
               }
               enum "1606.36" {
                 description "1606.36 nm/186.628125 THz 3.125GHz spacing";
               }
               enum "1606.34" {
                 description "1606.34 nm/186.631250 THz 3.125/6.25GHz spacing";
               }
               enum "1606.31" {
                 description "1606.31 nm/186.634375 THz 3.125GHz spacing";
               }
               enum "1606.28" {
                 description "1606.28 nm/186.637500 THz 3.125/6.25/12.5GHz spacing";
               }
               enum "1606.26" {
                 description "1606.26 nm/186.640625 THz 3.125GHz spacing";
               }
               enum "1606.23" {
                 description "1606.23 nm/186.643750 THz 3.125/6.25GHz spacing";
               }
               enum "1606.20" {
                 description "1606.20 nm/186.646875 THz 3.125GHz spacing";
               }
               enum "1606.17" {
                 description "1606.17 nm/186.650000 THz 3.125/6.25/12.5/50/75GHz spacing";
               }
               enum "1606.15" {
                 description "1606.15 nm/186.653125 THz 3.125GHz spacing";
               }
               enum "1606.12" {
                 description "1606.12 nm/186.656250 THz 3.125/6.25GHz spacing";
               }
               enum "1606.09" {
                 description "1606.09 nm/186.659375 THz 3.125GHz spacing";
               }
               enum "1606.07" {
                 description "1606.07 nm/186.662500 THz 3.125/6.25/12.5GHz spacing";
               }
               enum "1606.04" {
                 description "1606.04 nm/186.665625 THz 3.125GHz spacing";
               }
               enum "1606.01" {
                 description "1606.01 nm/186.668750 THz 3.125/6.25GHz spacing";
               }
               enum "1605.99" {
                 description "1605.99 nm/186.671875 THz 3.125GHz spacing";
               }
               enum "1605.96" {
                 description "1605.96 nm/186.675000 THz 3.125/6.25/12.5GHz spacing";
               }
               enum "1605.93" {
                 description "1605.93 nm/186.678125 THz 3.125GHz spacing";
               }
               enum "1605.91" {
                 description "1605.91 nm/186.681250 THz 3.125/6.25GHz spacing";
               }
               enum "1605.88" {
                 description "1605.88 nm/186.684375 THz 3.125GHz spacing";
               }
               enum "1605.85" {
                 description "1605.85 nm/186.687500 THz 3.125/6.25/12.5GHz spacing";
               }
               enum "1605.82" {
                 description "1605.82 nm/186.690625 THz 3.125GHz spacing";
               }
               enum "1605.80" {
                 description "1605.80 nm/186.693750 THz 3.125/6.25GHz spacing";
               }
               enum "1605.77" {
                 description "1605.77 nm/186.696875 THz 3.125GHz spacing";
               }
               enum "1605.74" {
                 description "1605.74 nm/186.700000 THz 3.125/6.25/12.5/100GHz spacing";
               }
               enum "1605.72" {
                 description "1605.72 nm/186.703125 THz 3.125GHz spacing";
               }
               enum "1605.69" {
                 description "1605.69 nm/186.706250 THz 3.125/6.25GHz spacing";
               }
               enum "1605.66" {
                 description "1605.66 nm/186.709375 THz 3.125GHz spacing";
               }
               enum "1605.64" {
                 description "1605.64 nm/186.712500 THz 3.125/6.25/12.5GHz spacing";
               }
               enum "1605.61" {
                 description "1605.61 nm/186.715625 THz 3.125GHz spacing";
               }
               enum "1605.58" {
                 description "1605.58 nm/186.718750 THz 3.125/6.25GHz spacing";
               }
               enum "1605.56" {
                 description "1605.56 nm/186.721875 THz 3.125GHz spacing";
               }
               enum "1605.53" {
                 description "1605.53 nm/186.725000 THz 3.125/6.25/12.5/75GHz spacing";
               }
               enum "1605.50" {
                 description "1605.50 nm/186.728125 THz 3.125GHz spacing";
               }
               enum "1605.48" {
                 description "1605.48 nm/186.731250 THz 3.125/6.25GHz spacing";
               }
               enum "1605.45" {
                 description "1605.45 nm/186.734375 THz 3.125GHz spacing";
               }
               enum "1605.42" {
                 description "1605.42 nm/186.737500 THz 3.125/6.25/12.5GHz spacing";
               }
               enum "1605.39" {
                 description "1605.39 nm/186.740625 THz 3.125GHz spacing";
               }
               enum "1605.37" {
                 description "1605.37 nm/186.743750 THz 3.125/6.25GHz spacing";
               }
               enum "1605.34" {
                 description "1605.34 nm/186.746875 THz 3.125GHz spacing";
               }
               enum "1605.31" {
                 description "1605.31 nm/186.750000 THz 3.125/6.25/12.5/50GHz spacing";
               }
               enum "1605.29" {
                 description "1605.29 nm/186.753125 THz 3.125GHz spacing";
               }
               enum "1605.26" {
                 description "1605.26 nm/186.756250 THz 3.125/6.25GHz spacing";
               }
               enum "1605.23" {
                 description "1605.23 nm/186.759375 THz 3.125GHz spacing";
               }
               enum "1605.21" {
                 description "1605.21 nm/186.762500 THz 3.125/6.25/12.5GHz spacing";
               }
               enum "1605.18" {
                 description "1605.18 nm/186.765625 THz 3.125GHz spacing";
               }
               enum "1605.15" {
                 description "1605.15 nm/186.768750 THz 3.125/6.25GHz spacing";
               }
               enum "1605.13" {
                 description "1605.13 nm/186.771875 THz 3.125GHz spacing";
               }
               enum "1605.10" {
                 description "1605.10 nm/186.775000 THz 3.125/6.25/12.5GHz spacing";
               }
               enum "1605.07" {
                 description "1605.07 nm/186.778125 THz 3.125GHz spacing";
               }
               enum "1605.05" {
                 description "1605.05 nm/186.781250 THz 3.125/6.25GHz spacing";
               }
               enum "1605.02" {
                 description "1605.02 nm/186.784375 THz 3.125GHz spacing";
               }
               enum "1604.99" {
                 description "1604.99 nm/186.787500 THz 3.125/6.25/12.5GHz spacing";
               }
               enum "1604.97" {
                 description "1604.97 nm/186.790625 THz 3.125GHz spacing";
               }
               enum "1604.94" {
                 description "1604.94 nm/186.793750 THz 3.125/6.25GHz spacing";
               }
               enum "1604.91" {
                 description "1604.91 nm/186.796875 THz 3.125GHz spacing";
               }
               enum "1604.88" {
                 description "1604.88 nm/186.800000 THz 3.125/6.25/12.5/100GHz spacing";
               }
               enum "1604.86" {
                 description "1604.86 nm/186.803125 THz 3.125GHz spacing";
               }
               enum "1604.83" {
                 description "1604.83 nm/186.806250 THz 3.125/6.25GHz spacing";
               }
               enum "1604.80" {
                 description "1604.80 nm/186.809375 THz 3.125GHz spacing";
               }
               enum "1604.78" {
                 description "1604.78 nm/186.812500 THz 3.125/6.25/12.5GHz spacing";
               }
               enum "1604.75" {
                 description "1604.75 nm/186.815625 THz 3.125GHz spacing";
               }
               enum "1604.72" {
                 description "1604.72 nm/186.818750 THz 3.125/6.25GHz spacing";
               }
               enum "1604.70" {
                 description "1604.70 nm/186.821875 THz 3.125GHz spacing";
               }
               enum "1604.67" {
                 description "1604.67 nm/186.825000 THz 3.125/6.25/12.5GHz spacing";
               }
               enum "1604.64" {
                 description "1604.64 nm/186.828125 THz 3.125GHz spacing";
               }
               enum "1604.62" {
                 description "1604.62 nm/186.831250 THz 3.125/6.25GHz spacing";
               }
               enum "1604.59" {
                 description "1604.59 nm/186.834375 THz 3.125GHz spacing";
               }
               enum "1604.56" {
                 description "1604.56 nm/186.837500 THz 3.125/6.25/12.5GHz spacing";
               }
               enum "1604.54" {
                 description "1604.54 nm/186.840625 THz 3.125GHz spacing";
               }
               enum "1604.51" {
                 description "1604.51 nm/186.843750 THz 3.125/6.25GHz spacing";
               }
               enum "1604.48" {
                 description "1604.48 nm/186.846875 THz 3.125GHz spacing";
               }
               enum "1604.46" {
                 description "1604.46 nm/186.850000 THz 3.125/6.25/12.5/50GHz spacing";
               }
               enum "1604.43" {
                 description "1604.43 nm/186.853125 THz 3.125GHz spacing";
               }
               enum "1604.40" {
                 description "1604.40 nm/186.856250 THz 3.125/6.25GHz spacing";
               }
               enum "1604.37" {
                 description "1604.37 nm/186.859375 THz 3.125GHz spacing";
               }
               enum "1604.35" {
                 description "1604.35 nm/186.862500 THz 3.125/6.25/12.5GHz spacing";
               }
               enum "1604.32" {
                 description "1604.32 nm/186.865625 THz 3.125GHz spacing";
               }
               enum "1604.29" {
                 description "1604.29 nm/186.868750 THz 3.125/6.25GHz spacing";
               }
               enum "1604.27" {
                 description "1604.27 nm/186.871875 THz 3.125GHz spacing";
               }
               enum "1604.24" {
                 description "1604.24 nm/186.875000 THz 3.125/6.25/12.5/75GHz spacing";
               }
               enum "1604.21" {
                 description "1604.21 nm/186.878125 THz 3.125GHz spacing";
               }
               enum "1604.19" {
                 description "1604.19 nm/186.881250 THz 3.125/6.25GHz spacing";
               }
               enum "1604.16" {
                 description "1604.16 nm/186.884375 THz 3.125GHz spacing";
               }
               enum "1604.13" {
                 description "1604.13 nm/186.887500 THz 3.125/6.25/12.5GHz spacing";
               }
               enum "1604.11" {
                 description "1604.11 nm/186.890625 THz 3.125GHz spacing";
               }
               enum "1604.08" {
                 description "1604.08 nm/186.893750 THz 3.125/6.25GHz spacing";
               }
               enum "1604.05" {
                 description "1604.05 nm/186.896875 THz 3.125GHz spacing";
               }
               enum "1604.03" {
                 description "1604.03 nm/186.900000 THz 3.125/6.25/12.5/50/75/100GHz spacing";
               }
               enum "1604.00" {
                 description "1604.00 nm/186.903125 THz 3.125GHz spacing";
               }
               enum "1603.97" {
                 description "1603.97 nm/186.906250 THz 3.125/6.25GHz spacing";
               }
               enum "1603.95" {
                 description "1603.95 nm/186.909375 THz 3.125GHz spacing";
               }
               enum "1603.92" {
                 description "1603.92 nm/186.912500 THz 3.125/6.25/12.5GHz spacing";
               }
               enum "1603.89" {
                 description "1603.89 nm/186.915625 THz 3.125GHz spacing";
               }
               enum "1603.87" {
                 description "1603.87 nm/186.918750 THz 3.125/6.25GHz spacing";
               }
               enum "1603.84" {
                 description "1603.84 nm/186.921875 THz 3.125GHz spacing";
               }
               enum "1603.81" {
                 description "1603.81 nm/186.925000 THz 3.125/6.25/12.5GHz spacing";
               }
               enum "1603.78" {
                 description "1603.78 nm/186.928125 THz 3.125GHz spacing";
               }
               enum "1603.76" {
                 description "1603.76 nm/186.931250 THz 3.125/6.25GHz spacing";
               }
               enum "1603.73" {
                 description "1603.73 nm/186.934375 THz 3.125GHz spacing";
               }
               enum "1603.70" {
                 description "1603.70 nm/186.937500 THz 3.125/6.25/12.5GHz spacing";
               }
               enum "1603.68" {
                 description "1603.68 nm/186.940625 THz 3.125GHz spacing";
               }
               enum "1603.65" {
                 description "1603.65 nm/186.943750 THz 3.125/6.25GHz spacing";
               }
               enum "1603.62" {
                 description "1603.62 nm/186.946875 THz 3.125GHz spacing";
               }
               enum "1603.60" {
                 description "1603.60 nm/186.950000 THz 3.125/6.25/12.5/50/75GHz spacing";
               }
               enum "1603.57" {
                 description "1603.57 nm/186.953125 THz 3.125GHz spacing";
               }
               enum "1603.54" {
                 description "1603.54 nm/186.956250 THz 3.125/6.25GHz spacing";
               }
               enum "1603.52" {
                 description "1603.52 nm/186.959375 THz 3.125GHz spacing";
               }
               enum "1603.49" {
                 description "1603.49 nm/186.962500 THz 3.125/6.25/12.5GHz spacing";
               }
               enum "1603.46" {
                 description "1603.46 nm/186.965625 THz 3.125GHz spacing";
               }
               enum "1603.44" {
                 description "1603.44 nm/186.968750 THz 3.125/6.25GHz spacing";
               }
               enum "1603.41" {
                 description "1603.41 nm/186.971875 THz 3.125GHz spacing";
               }
               enum "1603.38" {
                 description "1603.38 nm/186.975000 THz 3.125/6.25/12.5GHz spacing";
               }
               enum "1603.36" {
                 description "1603.36 nm/186.978125 THz 3.125GHz spacing";
               }
               enum "1603.33" {
                 description "1603.33 nm/186.981250 THz 3.125/6.25GHz spacing";
               }
               enum "1603.30" {
                 description "1603.30 nm/186.984375 THz 3.125GHz spacing";
               }
               enum "1603.28" {
                 description "1603.28 nm/186.987500 THz 3.125/6.25/12.5GHz spacing";
               }
               enum "1603.25" {
                 description "1603.25 nm/186.990625 THz 3.125GHz spacing";
               }
               enum "1603.22" {
                 description "1603.22 nm/186.993750 THz 3.125/6.25GHz spacing";
               }
               enum "1603.20" {
                 description "1603.20 nm/186.996875 THz 3.125GHz spacing";
               }
               enum "1603.17" {
                 description "1603.17 nm/187.000000 THz 3.125/6.25/12.5/100GHz spacing";
               }
               enum "1603.14" {
                 description "1603.14 nm/187.003125 THz 3.125GHz spacing";
               }
               enum "1603.11" {
                 description "1603.11 nm/187.006250 THz 3.125/6.25GHz spacing";
               }
               enum "1603.09" {
                 description "1603.09 nm/187.009375 THz 3.125GHz spacing";
               }
               enum "1603.06" {
                 description "1603.06 nm/187.012500 THz 3.125/6.25/12.5GHz spacing";
               }
               enum "1603.03" {
                 description "1603.03 nm/187.015625 THz 3.125GHz spacing";
               }
               enum "1603.01" {
                 description "1603.01 nm/187.018750 THz 3.125/6.25GHz spacing";
               }
               enum "1602.98" {
                 description "1602.98 nm/187.021875 THz 3.125GHz spacing";
               }
               enum "1602.95" {
                 description "1602.95 nm/187.025000 THz 3.125/6.25/12.5/75GHz spacing";
               }
               enum "1602.93" {
                 description "1602.93 nm/187.028125 THz 3.125GHz spacing";
               }
               enum "1602.90" {
                 description "1602.90 nm/187.031250 THz 3.125/6.25GHz spacing";
               }
               enum "1602.87" {
                 description "1602.87 nm/187.034375 THz 3.125GHz spacing";
               }
               enum "1602.85" {
                 description "1602.85 nm/187.037500 THz 3.125/6.25/12.5GHz spacing";
               }
               enum "1602.82" {
                 description "1602.82 nm/187.040625 THz 3.125GHz spacing";
               }
               enum "1602.79" {
                 description "1602.79 nm/187.043750 THz 3.125/6.25GHz spacing";
               }
               enum "1602.77" {
                 description "1602.77 nm/187.046875 THz 3.125GHz spacing";
               }
               enum "1602.74" {
                 description "1602.74 nm/187.050000 THz 3.125/6.25/12.5/50GHz spacing";
               }
               enum "1602.71" {
                 description "1602.71 nm/187.053125 THz 3.125GHz spacing";
               }
               enum "1602.69" {
                 description "1602.69 nm/187.056250 THz 3.125/6.25GHz spacing";
               }
               enum "1602.66" {
                 description "1602.66 nm/187.059375 THz 3.125GHz spacing";
               }
               enum "1602.63" {
                 description "1602.63 nm/187.062500 THz 3.125/6.25/12.5GHz spacing";
               }
               enum "1602.61" {
                 description "1602.61 nm/187.065625 THz 3.125GHz spacing";
               }
               enum "1602.58" {
                 description "1602.58 nm/187.068750 THz 3.125/6.25GHz spacing";
               }
               enum "1602.55" {
                 description "1602.55 nm/187.071875 THz 3.125GHz spacing";
               }
               enum "1602.53" {
                 description "1602.53 nm/187.075000 THz 3.125/6.25/12.5GHz spacing";
               }
               enum "1602.50" {
                 description "1602.50 nm/187.078125 THz 3.125GHz spacing";
               }
               enum "1602.47" {
                 description "1602.47 nm/187.081250 THz 3.125/6.25GHz spacing";
               }
               enum "1602.45" {
                 description "1602.45 nm/187.084375 THz 3.125GHz spacing";
               }
               enum "1602.42" {
                 description "1602.42 nm/187.087500 THz 3.125/6.25/12.5GHz spacing";
               }
               enum "1602.39" {
                 description "1602.39 nm/187.090625 THz 3.125GHz spacing";
               }
               enum "1602.36" {
                 description "1602.36 nm/187.093750 THz 3.125/6.25GHz spacing";
               }
               enum "1602.34" {
                 description "1602.34 nm/187.096875 THz 3.125GHz spacing";
               }
               enum "1602.31" {
                 description "1602.31 nm/187.100000 THz 3.125/6.25/12.5/100GHz spacing";
               }
               enum "1602.28" {
                 description "1602.28 nm/187.103125 THz 3.125GHz spacing";
               }
               enum "1602.26" {
                 description "1602.26 nm/187.106250 THz 3.125/6.25GHz spacing";
               }
               enum "1602.23" {
                 description "1602.23 nm/187.109375 THz 3.125GHz spacing";
               }
               enum "1602.20" {
                 description "1602.20 nm/187.112500 THz 3.125/6.25/12.5GHz spacing";
               }
               enum "1602.18" {
                 description "1602.18 nm/187.115625 THz 3.125GHz spacing";
               }
               enum "1602.15" {
                 description "1602.15 nm/187.118750 THz 3.125/6.25GHz spacing";
               }
               enum "1602.12" {
                 description "1602.12 nm/187.121875 THz 3.125GHz spacing";
               }
               enum "1602.10" {
                 description "1602.10 nm/187.125000 THz 3.125/6.25/12.5GHz spacing";
               }
               enum "1602.07" {
                 description "1602.07 nm/187.128125 THz 3.125GHz spacing";
               }
               enum "1602.04" {
                 description "1602.04 nm/187.131250 THz 3.125/6.25GHz spacing";
               }
               enum "1602.02" {
                 description "1602.02 nm/187.134375 THz 3.125GHz spacing";
               }
               enum "1601.99" {
                 description "1601.99 nm/187.137500 THz 3.125/6.25/12.5GHz spacing";
               }
               enum "1601.96" {
                 description "1601.96 nm/187.140625 THz 3.125GHz spacing";
               }
               enum "1601.94" {
                 description "1601.94 nm/187.143750 THz 3.125/6.25GHz spacing";
               }
               enum "1601.91" {
                 description "1601.91 nm/187.146875 THz 3.125GHz spacing";
               }
               enum "1601.88" {
                 description "1601.88 nm/187.150000 THz 3.125/6.25/12.5/50GHz spacing";
               }
               enum "1601.86" {
                 description "1601.86 nm/187.153125 THz 3.125GHz spacing";
               }
               enum "1601.83" {
                 description "1601.83 nm/187.156250 THz 3.125/6.25GHz spacing";
               }
               enum "1601.80" {
                 description "1601.80 nm/187.159375 THz 3.125GHz spacing";
               }
               enum "1601.78" {
                 description "1601.78 nm/187.162500 THz 3.125/6.25/12.5GHz spacing";
               }
               enum "1601.75" {
                 description "1601.75 nm/187.165625 THz 3.125GHz spacing";
               }
               enum "1601.72" {
                 description "1601.72 nm/187.168750 THz 3.125/6.25GHz spacing";
               }
               enum "1601.70" {
                 description "1601.70 nm/187.171875 THz 3.125GHz spacing";
               }
               enum "1601.67" {
                 description "1601.67 nm/187.175000 THz 3.125/6.25/12.5/75GHz spacing";
               }
               enum "1601.64" {
                 description "1601.64 nm/187.178125 THz 3.125GHz spacing";
               }
               enum "1601.62" {
                 description "1601.62 nm/187.181250 THz 3.125/6.25GHz spacing";
               }
               enum "1601.59" {
                 description "1601.59 nm/187.184375 THz 3.125GHz spacing";
               }
               enum "1601.56" {
                 description "1601.56 nm/187.187500 THz 3.125/6.25/12.5GHz spacing";
               }
               enum "1601.54" {
                 description "1601.54 nm/187.190625 THz 3.125GHz spacing";
               }
               enum "1601.51" {
                 description "1601.51 nm/187.193750 THz 3.125/6.25GHz spacing";
               }
               enum "1601.48" {
                 description "1601.48 nm/187.196875 THz 3.125GHz spacing";
               }
               enum "1601.46" {
                 description "1601.46 nm/187.200000 THz 3.125/6.25/12.5/50/75/100GHz spacing";
               }
               enum "1601.43" {
                 description "1601.43 nm/187.203125 THz 3.125GHz spacing";
               }
               enum "1601.40" {
                 description "1601.40 nm/187.206250 THz 3.125/6.25GHz spacing";
               }
               enum "1601.38" {
                 description "1601.38 nm/187.209375 THz 3.125GHz spacing";
               }
               enum "1601.35" {
                 description "1601.35 nm/187.212500 THz 3.125/6.25/12.5GHz spacing";
               }
               enum "1601.32" {
                 description "1601.32 nm/187.215625 THz 3.125GHz spacing";
               }
               enum "1601.30" {
                 description "1601.30 nm/187.218750 THz 3.125/6.25GHz spacing";
               }
               enum "1601.27" {
                 description "1601.27 nm/187.221875 THz 3.125GHz spacing";
               }
               enum "1601.24" {
                 description "1601.24 nm/187.225000 THz 3.125/6.25/12.5GHz spacing";
               }
               enum "1601.21" {
                 description "1601.21 nm/187.228125 THz 3.125GHz spacing";
               }
               enum "1601.19" {
                 description "1601.19 nm/187.231250 THz 3.125/6.25GHz spacing";
               }
               enum "1601.16" {
                 description "1601.16 nm/187.234375 THz 3.125GHz spacing";
               }
               enum "1601.13" {
                 description "1601.13 nm/187.237500 THz 3.125/6.25/12.5GHz spacing";
               }
               enum "1601.11" {
                 description "1601.11 nm/187.240625 THz 3.125GHz spacing";
               }
               enum "1601.08" {
                 description "1601.08 nm/187.243750 THz 3.125/6.25GHz spacing";
               }
               enum "1601.05" {
                 description "1601.05 nm/187.246875 THz 3.125GHz spacing";
               }
               enum "1601.03" {
                 description "1601.03 nm/187.250000 THz 3.125/6.25/12.5/50/75GHz spacing";
               }
               enum "1601.00" {
                 description "1601.00 nm/187.253125 THz 3.125GHz spacing";
               }
               enum "1600.97" {
                 description "1600.97 nm/187.256250 THz 3.125/6.25GHz spacing";
               }
               enum "1600.95" {
                 description "1600.95 nm/187.259375 THz 3.125GHz spacing";
               }
               enum "1600.92" {
                 description "1600.92 nm/187.262500 THz 3.125/6.25/12.5GHz spacing";
               }
               enum "1600.89" {
                 description "1600.89 nm/187.265625 THz 3.125GHz spacing";
               }
               enum "1600.87" {
                 description "1600.87 nm/187.268750 THz 3.125/6.25GHz spacing";
               }
               enum "1600.84" {
                 description "1600.84 nm/187.271875 THz 3.125GHz spacing";
               }
               enum "1600.81" {
                 description "1600.81 nm/187.275000 THz 3.125/6.25/12.5GHz spacing";
               }
               enum "1600.79" {
                 description "1600.79 nm/187.278125 THz 3.125GHz spacing";
               }
               enum "1600.76" {
                 description "1600.76 nm/187.281250 THz 3.125/6.25GHz spacing";
               }
               enum "1600.73" {
                 description "1600.73 nm/187.284375 THz 3.125GHz spacing";
               }
               enum "1600.71" {
                 description "1600.71 nm/187.287500 THz 3.125/6.25/12.5GHz spacing";
               }
               enum "1600.68" {
                 description "1600.68 nm/187.290625 THz 3.125GHz spacing";
               }
               enum "1600.65" {
                 description "1600.65 nm/187.293750 THz 3.125/6.25GHz spacing";
               }
               enum "1600.63" {
                 description "1600.63 nm/187.296875 THz 3.125GHz spacing";
               }
               enum "1600.60" {
                 description "1600.60 nm/187.300000 THz 3.125/6.25/12.5/100GHz spacing";
               }
               enum "1600.57" {
                 description "1600.57 nm/187.303125 THz 3.125GHz spacing";
               }
               enum "1600.55" {
                 description "1600.55 nm/187.306250 THz 3.125/6.25GHz spacing";
               }
               enum "1600.52" {
                 description "1600.52 nm/187.309375 THz 3.125GHz spacing";
               }
               enum "1600.49" {
                 description "1600.49 nm/187.312500 THz 3.125/6.25/12.5GHz spacing";
               }
               enum "1600.47" {
                 description "1600.47 nm/187.315625 THz 3.125GHz spacing";
               }
               enum "1600.44" {
                 description "1600.44 nm/187.318750 THz 3.125/6.25GHz spacing";
               }
               enum "1600.41" {
                 description "1600.41 nm/187.321875 THz 3.125GHz spacing";
               }
               enum "1600.39" {
                 description "1600.39 nm/187.325000 THz 3.125/6.25/12.5/75GHz spacing";
               }
               enum "1600.36" {
                 description "1600.36 nm/187.328125 THz 3.125GHz spacing";
               }
               enum "1600.33" {
                 description "1600.33 nm/187.331250 THz 3.125/6.25GHz spacing";
               }
               enum "1600.31" {
                 description "1600.31 nm/187.334375 THz 3.125GHz spacing";
               }
               enum "1600.28" {
                 description "1600.28 nm/187.337500 THz 3.125/6.25/12.5GHz spacing";
               }
               enum "1600.25" {
                 description "1600.25 nm/187.340625 THz 3.125GHz spacing";
               }
               enum "1600.23" {
                 description "1600.23 nm/187.343750 THz 3.125/6.25GHz spacing";
               }
               enum "1600.20" {
                 description "1600.20 nm/187.346875 THz 3.125GHz spacing";
               }
               enum "1600.17" {
                 description "1600.17 nm/187.350000 THz 3.125/6.25/12.5/50GHz spacing";
               }
               enum "1600.15" {
                 description "1600.15 nm/187.353125 THz 3.125GHz spacing";
               }
               enum "1600.12" {
                 description "1600.12 nm/187.356250 THz 3.125/6.25GHz spacing";
               }
               enum "1600.09" {
                 description "1600.09 nm/187.359375 THz 3.125GHz spacing";
               }
               enum "1600.07" {
                 description "1600.07 nm/187.362500 THz 3.125/6.25/12.5GHz spacing";
               }
               enum "1600.04" {
                 description "1600.04 nm/187.365625 THz 3.125GHz spacing";
               }
               enum "1600.01" {
                 description "1600.01 nm/187.368750 THz 3.125/6.25GHz spacing";
               }
               enum "1599.99" {
                 description "1599.99 nm/187.371875 THz 3.125GHz spacing";
               }
               enum "1599.96" {
                 description "1599.96 nm/187.375000 THz 3.125/6.25/12.5GHz spacing";
               }
               enum "1599.93" {
                 description "1599.93 nm/187.378125 THz 3.125GHz spacing";
               }
               enum "1599.91" {
                 description "1599.91 nm/187.381250 THz 3.125/6.25GHz spacing";
               }
               enum "1599.88" {
                 description "1599.88 nm/187.384375 THz 3.125GHz spacing";
               }
               enum "1599.85" {
                 description "1599.85 nm/187.387500 THz 3.125/6.25/12.5GHz spacing";
               }
               enum "1599.83" {
                 description "1599.83 nm/187.390625 THz 3.125GHz spacing";
               }
               enum "1599.80" {
                 description "1599.80 nm/187.393750 THz 3.125/6.25GHz spacing";
               }
               enum "1599.77" {
                 description "1599.77 nm/187.396875 THz 3.125GHz spacing";
               }
               enum "1599.75" {
                 description "1599.75 nm/187.400000 THz 3.125/6.25/12.5/100GHz spacing";
               }
               enum "1599.72" {
                 description "1599.72 nm/187.403125 THz 3.125GHz spacing";
               }
               enum "1599.69" {
                 description "1599.69 nm/187.406250 THz 3.125/6.25GHz spacing";
               }
               enum "1599.67" {
                 description "1599.67 nm/187.409375 THz 3.125GHz spacing";
               }
               enum "1599.64" {
                 description "1599.64 nm/187.412500 THz 3.125/6.25/12.5GHz spacing";
               }
               enum "1599.61" {
                 description "1599.61 nm/187.415625 THz 3.125GHz spacing";
               }
               enum "1599.59" {
                 description "1599.59 nm/187.418750 THz 3.125/6.25GHz spacing";
               }
               enum "1599.56" {
                 description "1599.56 nm/187.421875 THz 3.125GHz spacing";
               }
               enum "1599.53" {
                 description "1599.53 nm/187.425000 THz 3.125/6.25/12.5GHz spacing";
               }
               enum "1599.51" {
                 description "1599.51 nm/187.428125 THz 3.125GHz spacing";
               }
               enum "1599.48" {
                 description "1599.48 nm/187.431250 THz 3.125/6.25GHz spacing";
               }
               enum "1599.45" {
                 description "1599.45 nm/187.434375 THz 3.125GHz spacing";
               }
               enum "1599.43" {
                 description "1599.43 nm/187.437500 THz 3.125/6.25/12.5GHz spacing";
               }
               enum "1599.40" {
                 description "1599.40 nm/187.440625 THz 3.125GHz spacing";
               }
               enum "1599.37" {
                 description "1599.37 nm/187.443750 THz 3.125/6.25GHz spacing";
               }
               enum "1599.35" {
                 description "1599.35 nm/187.446875 THz 3.125GHz spacing";
               }
               enum "1599.32" {
                 description "1599.32 nm/187.450000 THz 3.125/6.25/12.5/50GHz spacing";
               }
               enum "1599.29" {
                 description "1599.29 nm/187.453125 THz 3.125GHz spacing";
               }
               enum "1599.27" {
                 description "1599.27 nm/187.456250 THz 3.125/6.25GHz spacing";
               }
               enum "1599.24" {
                 description "1599.24 nm/187.459375 THz 3.125GHz spacing";
               }
               enum "1599.21" {
                 description "1599.21 nm/187.462500 THz 3.125/6.25/12.5GHz spacing";
               }
               enum "1599.19" {
                 description "1599.19 nm/187.465625 THz 3.125GHz spacing";
               }
               enum "1599.16" {
                 description "1599.16 nm/187.468750 THz 3.125/6.25GHz spacing";
               }
               enum "1599.13" {
                 description "1599.13 nm/187.471875 THz 3.125GHz spacing";
               }
               enum "1599.11" {
                 description "1599.11 nm/187.475000 THz 3.125/6.25/12.5/75GHz spacing";
               }
               enum "1599.08" {
                 description "1599.08 nm/187.478125 THz 3.125GHz spacing";
               }
               enum "1599.05" {
                 description "1599.05 nm/187.481250 THz 3.125/6.25GHz spacing";
               }
               enum "1599.03" {
                 description "1599.03 nm/187.484375 THz 3.125GHz spacing";
               }
               enum "1599.00" {
                 description "1599.00 nm/187.487500 THz 3.125/6.25/12.5GHz spacing";
               }
               enum "1598.97" {
                 description "1598.97 nm/187.490625 THz 3.125GHz spacing";
               }
               enum "1598.95" {
                 description "1598.95 nm/187.493750 THz 3.125/6.25GHz spacing";
               }
               enum "1598.92" {
                 description "1598.92 nm/187.496875 THz 3.125GHz spacing";
               }
               enum "1598.89" {
                 description "1598.89 nm/187.500000 THz 3.125/6.25/12.5/50/75/100GHz spacing";
               }
               enum "1598.87" {
                 description "1598.87 nm/187.503125 THz 3.125GHz spacing";
               }
               enum "1598.84" {
                 description "1598.84 nm/187.506250 THz 3.125/6.25GHz spacing";
               }
               enum "1598.81" {
                 description "1598.81 nm/187.509375 THz 3.125GHz spacing";
               }
               enum "1598.79" {
                 description "1598.79 nm/187.512500 THz 3.125/6.25/12.5GHz spacing";
               }
               enum "1598.76" {
                 description "1598.76 nm/187.515625 THz 3.125GHz spacing";
               }
               enum "1598.73" {
                 description "1598.73 nm/187.518750 THz 3.125/6.25GHz spacing";
               }
               enum "1598.71" {
                 description "1598.71 nm/187.521875 THz 3.125GHz spacing";
               }
               enum "1598.68" {
                 description "1598.68 nm/187.525000 THz 3.125/6.25/12.5GHz spacing";
               }
               enum "1598.65" {
                 description "1598.65 nm/187.528125 THz 3.125GHz spacing";
               }
               enum "1598.63" {
                 description "1598.63 nm/187.531250 THz 3.125/6.25GHz spacing";
               }
               enum "1598.60" {
                 description "1598.60 nm/187.534375 THz 3.125GHz spacing";
               }
               enum "1598.57" {
                 description "1598.57 nm/187.537500 THz 3.125/6.25/12.5GHz spacing";
               }
               enum "1598.55" {
                 description "1598.55 nm/187.540625 THz 3.125GHz spacing";
               }
               enum "1598.52" {
                 description "1598.52 nm/187.543750 THz 3.125/6.25GHz spacing";
               }
               enum "1598.49" {
                 description "1598.49 nm/187.546875 THz 3.125GHz spacing";
               }
               enum "1598.47" {
                 description "1598.47 nm/187.550000 THz 3.125/6.25/12.5/50/75GHz spacing";
               }
               enum "1598.44" {
                 description "1598.44 nm/187.553125 THz 3.125GHz spacing";
               }
               enum "1598.41" {
                 description "1598.41 nm/187.556250 THz 3.125/6.25GHz spacing";
               }
               enum "1598.39" {
                 description "1598.39 nm/187.559375 THz 3.125GHz spacing";
               }
               enum "1598.36" {
                 description "1598.36 nm/187.562500 THz 3.125/6.25/12.5GHz spacing";
               }
               enum "1598.33" {
                 description "1598.33 nm/187.565625 THz 3.125GHz spacing";
               }
               enum "1598.31" {
                 description "1598.31 nm/187.568750 THz 3.125/6.25GHz spacing";
               }
               enum "1598.28" {
                 description "1598.28 nm/187.571875 THz 3.125GHz spacing";
               }
               enum "1598.25" {
                 description "1598.25 nm/187.575000 THz 3.125/6.25/12.5GHz spacing";
               }
               enum "1598.23" {
                 description "1598.23 nm/187.578125 THz 3.125GHz spacing";
               }
               enum "1598.20" {
                 description "1598.20 nm/187.581250 THz 3.125/6.25GHz spacing";
               }
               enum "1598.17" {
                 description "1598.17 nm/187.584375 THz 3.125GHz spacing";
               }
               enum "1598.15" {
                 description "1598.15 nm/187.587500 THz 3.125/6.25/12.5GHz spacing";
               }
               enum "1598.12" {
                 description "1598.12 nm/187.590625 THz 3.125GHz spacing";
               }
               enum "1598.09" {
                 description "1598.09 nm/187.593750 THz 3.125/6.25GHz spacing";
               }
               enum "1598.07" {
                 description "1598.07 nm/187.596875 THz 3.125GHz spacing";
               }
               enum "1598.04" {
                 description "1598.04 nm/187.600000 THz 3.125/6.25/12.5/100GHz spacing";
               }
               enum "1598.01" {
                 description "1598.01 nm/187.603125 THz 3.125GHz spacing";
               }
               enum "1597.99" {
                 description "1597.99 nm/187.606250 THz 3.125/6.25GHz spacing";
               }
               enum "1597.96" {
                 description "1597.96 nm/187.609375 THz 3.125GHz spacing";
               }
               enum "1597.93" {
                 description "1597.93 nm/187.612500 THz 3.125/6.25/12.5GHz spacing";
               }
               enum "1597.91" {
                 description "1597.91 nm/187.615625 THz 3.125GHz spacing";
               }
               enum "1597.88" {
                 description "1597.88 nm/187.618750 THz 3.125/6.25GHz spacing";
               }
               enum "1597.85" {
                 description "1597.85 nm/187.621875 THz 3.125GHz spacing";
               }
               enum "1597.83" {
                 description "1597.83 nm/187.625000 THz 3.125/6.25/12.5/75GHz spacing";
               }
               enum "1597.80" {
                 description "1597.80 nm/187.628125 THz 3.125GHz spacing";
               }
               enum "1597.77" {
                 description "1597.77 nm/187.631250 THz 3.125/6.25GHz spacing";
               }
               enum "1597.75" {
                 description "1597.75 nm/187.634375 THz 3.125GHz spacing";
               }
               enum "1597.72" {
                 description "1597.72 nm/187.637500 THz 3.125/6.25/12.5GHz spacing";
               }
               enum "1597.69" {
                 description "1597.69 nm/187.640625 THz 3.125GHz spacing";
               }
               enum "1597.67" {
                 description "1597.67 nm/187.643750 THz 3.125/6.25GHz spacing";
               }
               enum "1597.64" {
                 description "1597.64 nm/187.646875 THz 3.125GHz spacing";
               }
               enum "1597.62" {
                 description "1597.62 nm/187.650000 THz 3.125/6.25/12.5/50GHz spacing";
               }
               enum "1597.59" {
                 description "1597.59 nm/187.653125 THz 3.125GHz spacing";
               }
               enum "1597.56" {
                 description "1597.56 nm/187.656250 THz 3.125/6.25GHz spacing";
               }
               enum "1597.54" {
                 description "1597.54 nm/187.659375 THz 3.125GHz spacing";
               }
               enum "1597.51" {
                 description "1597.51 nm/187.662500 THz 3.125/6.25/12.5GHz spacing";
               }
               enum "1597.48" {
                 description "1597.48 nm/187.665625 THz 3.125GHz spacing";
               }
               enum "1597.46" {
                 description "1597.46 nm/187.668750 THz 3.125/6.25GHz spacing";
               }
               enum "1597.43" {
                 description "1597.43 nm/187.671875 THz 3.125GHz spacing";
               }
               enum "1597.40" {
                 description "1597.40 nm/187.675000 THz 3.125/6.25/12.5GHz spacing";
               }
               enum "1597.38" {
                 description "1597.38 nm/187.678125 THz 3.125GHz spacing";
               }
               enum "1597.35" {
                 description "1597.35 nm/187.681250 THz 3.125/6.25GHz spacing";
               }
               enum "1597.32" {
                 description "1597.32 nm/187.684375 THz 3.125GHz spacing";
               }
               enum "1597.30" {
                 description "1597.30 nm/187.687500 THz 3.125/6.25/12.5GHz spacing";
               }
               enum "1597.27" {
                 description "1597.27 nm/187.690625 THz 3.125GHz spacing";
               }
               enum "1597.24" {
                 description "1597.24 nm/187.693750 THz 3.125/6.25GHz spacing";
               }
               enum "1597.22" {
                 description "1597.22 nm/187.696875 THz 3.125GHz spacing";
               }
               enum "1597.19" {
                 description "1597.19 nm/187.700000 THz 3.125/6.25/12.5/100GHz spacing";
               }
               enum "1597.16" {
                 description "1597.16 nm/187.703125 THz 3.125GHz spacing";
               }
               enum "1597.14" {
                 description "1597.14 nm/187.706250 THz 3.125/6.25GHz spacing";
               }
               enum "1597.11" {
                 description "1597.11 nm/187.709375 THz 3.125GHz spacing";
               }
               enum "1597.08" {
                 description "1597.08 nm/187.712500 THz 3.125/6.25/12.5GHz spacing";
               }
               enum "1597.06" {
                 description "1597.06 nm/187.715625 THz 3.125GHz spacing";
               }
               enum "1597.03" {
                 description "1597.03 nm/187.718750 THz 3.125/6.25GHz spacing";
               }
               enum "1597.00" {
                 description "1597.00 nm/187.721875 THz 3.125GHz spacing";
               }
               enum "1596.98" {
                 description "1596.98 nm/187.725000 THz 3.125/6.25/12.5GHz spacing";
               }
               enum "1596.95" {
                 description "1596.95 nm/187.728125 THz 3.125GHz spacing";
               }
               enum "1596.92" {
                 description "1596.92 nm/187.731250 THz 3.125/6.25GHz spacing";
               }
               enum "1596.90" {
                 description "1596.90 nm/187.734375 THz 3.125GHz spacing";
               }
               enum "1596.87" {
                 description "1596.87 nm/187.737500 THz 3.125/6.25/12.5GHz spacing";
               }
               enum "1596.84" {
                 description "1596.84 nm/187.740625 THz 3.125GHz spacing";
               }
               enum "1596.82" {
                 description "1596.82 nm/187.743750 THz 3.125/6.25GHz spacing";
               }
               enum "1596.79" {
                 description "1596.79 nm/187.746875 THz 3.125GHz spacing";
               }
               enum "1596.76" {
                 description "1596.76 nm/187.750000 THz 3.125/6.25/12.5/50GHz spacing";
               }
               enum "1596.74" {
                 description "1596.74 nm/187.753125 THz 3.125GHz spacing";
               }
               enum "1596.71" {
                 description "1596.71 nm/187.756250 THz 3.125/6.25GHz spacing";
               }
               enum "1596.68" {
                 description "1596.68 nm/187.759375 THz 3.125GHz spacing";
               }
               enum "1596.66" {
                 description "1596.66 nm/187.762500 THz 3.125/6.25/12.5GHz spacing";
               }
               enum "1596.63" {
                 description "1596.63 nm/187.765625 THz 3.125GHz spacing";
               }
               enum "1596.60" {
                 description "1596.60 nm/187.768750 THz 3.125/6.25GHz spacing";
               }
               enum "1596.58" {
                 description "1596.58 nm/187.771875 THz 3.125GHz spacing";
               }
               enum "1596.55" {
                 description "1596.55 nm/187.775000 THz 3.125/6.25/12.5/75GHz spacing";
               }
               enum "1596.52" {
                 description "1596.52 nm/187.778125 THz 3.125GHz spacing";
               }
               enum "1596.50" {
                 description "1596.50 nm/187.781250 THz 3.125/6.25GHz spacing";
               }
               enum "1596.47" {
                 description "1596.47 nm/187.784375 THz 3.125GHz spacing";
               }
               enum "1596.45" {
                 description "1596.45 nm/187.787500 THz 3.125/6.25/12.5GHz spacing";
               }
               enum "1596.42" {
                 description "1596.42 nm/187.790625 THz 3.125GHz spacing";
               }
               enum "1596.39" {
                 description "1596.39 nm/187.793750 THz 3.125/6.25GHz spacing";
               }
               enum "1596.37" {
                 description "1596.37 nm/187.796875 THz 3.125GHz spacing";
               }
               enum "1596.34" {
                 description "1596.34 nm/187.800000 THz 3.125/6.25/12.5/50/75/100GHz spacing";
               }
               enum "1596.31" {
                 description "1596.31 nm/187.803125 THz 3.125GHz spacing";
               }
               enum "1596.29" {
                 description "1596.29 nm/187.806250 THz 3.125/6.25GHz spacing";
               }
               enum "1596.26" {
                 description "1596.26 nm/187.809375 THz 3.125GHz spacing";
               }
               enum "1596.23" {
                 description "1596.23 nm/187.812500 THz 3.125/6.25/12.5GHz spacing";
               }
               enum "1596.21" {
                 description "1596.21 nm/187.815625 THz 3.125GHz spacing";
               }
               enum "1596.18" {
                 description "1596.18 nm/187.818750 THz 3.125/6.25GHz spacing";
               }
               enum "1596.15" {
                 description "1596.15 nm/187.821875 THz 3.125GHz spacing";
               }
               enum "1596.13" {
                 description "1596.13 nm/187.825000 THz 3.125/6.25/12.5GHz spacing";
               }
               enum "1596.10" {
                 description "1596.10 nm/187.828125 THz 3.125GHz spacing";
               }
               enum "1596.07" {
                 description "1596.07 nm/187.831250 THz 3.125/6.25GHz spacing";
               }
               enum "1596.05" {
                 description "1596.05 nm/187.834375 THz 3.125GHz spacing";
               }
               enum "1596.02" {
                 description "1596.02 nm/187.837500 THz 3.125/6.25/12.5GHz spacing";
               }
               enum "1595.99" {
                 description "1595.99 nm/187.840625 THz 3.125GHz spacing";
               }
               enum "1595.97" {
                 description "1595.97 nm/187.843750 THz 3.125/6.25GHz spacing";
               }
               enum "1595.94" {
                 description "1595.94 nm/187.846875 THz 3.125GHz spacing";
               }
               enum "1595.91" {
                 description "1595.91 nm/187.850000 THz 3.125/6.25/12.5/50/75GHz spacing";
               }
               enum "1595.89" {
                 description "1595.89 nm/187.853125 THz 3.125GHz spacing";
               }
               enum "1595.86" {
                 description "1595.86 nm/187.856250 THz 3.125/6.25GHz spacing";
               }
               enum "1595.83" {
                 description "1595.83 nm/187.859375 THz 3.125GHz spacing";
               }
               enum "1595.81" {
                 description "1595.81 nm/187.862500 THz 3.125/6.25/12.5GHz spacing";
               }
               enum "1595.78" {
                 description "1595.78 nm/187.865625 THz 3.125GHz spacing";
               }
               enum "1595.75" {
                 description "1595.75 nm/187.868750 THz 3.125/6.25GHz spacing";
               }
               enum "1595.73" {
                 description "1595.73 nm/187.871875 THz 3.125GHz spacing";
               }
               enum "1595.70" {
                 description "1595.70 nm/187.875000 THz 3.125/6.25/12.5GHz spacing";
               }
               enum "1595.68" {
                 description "1595.68 nm/187.878125 THz 3.125GHz spacing";
               }
               enum "1595.65" {
                 description "1595.65 nm/187.881250 THz 3.125/6.25GHz spacing";
               }
               enum "1595.62" {
                 description "1595.62 nm/187.884375 THz 3.125GHz spacing";
               }
               enum "1595.60" {
                 description "1595.60 nm/187.887500 THz 3.125/6.25/12.5GHz spacing";
               }
               enum "1595.57" {
                 description "1595.57 nm/187.890625 THz 3.125GHz spacing";
               }
               enum "1595.54" {
                 description "1595.54 nm/187.893750 THz 3.125/6.25GHz spacing";
               }
               enum "1595.52" {
                 description "1595.52 nm/187.896875 THz 3.125GHz spacing";
               }
               enum "1595.49" {
                 description "1595.49 nm/187.900000 THz 3.125/6.25/12.5/100GHz spacing";
               }
               enum "1595.46" {
                 description "1595.46 nm/187.903125 THz 3.125GHz spacing";
               }
               enum "1595.44" {
                 description "1595.44 nm/187.906250 THz 3.125/6.25GHz spacing";
               }
               enum "1595.41" {
                 description "1595.41 nm/187.909375 THz 3.125GHz spacing";
               }
               enum "1595.38" {
                 description "1595.38 nm/187.912500 THz 3.125/6.25/12.5GHz spacing";
               }
               enum "1595.36" {
                 description "1595.36 nm/187.915625 THz 3.125GHz spacing";
               }
               enum "1595.33" {
                 description "1595.33 nm/187.918750 THz 3.125/6.25GHz spacing";
               }
               enum "1595.30" {
                 description "1595.30 nm/187.921875 THz 3.125GHz spacing";
               }
               enum "1595.28" {
                 description "1595.28 nm/187.925000 THz 3.125/6.25/12.5/75GHz spacing";
               }
               enum "1595.25" {
                 description "1595.25 nm/187.928125 THz 3.125GHz spacing";
               }
               enum "1595.22" {
                 description "1595.22 nm/187.931250 THz 3.125/6.25GHz spacing";
               }
               enum "1595.20" {
                 description "1595.20 nm/187.934375 THz 3.125GHz spacing";
               }
               enum "1595.17" {
                 description "1595.17 nm/187.937500 THz 3.125/6.25/12.5GHz spacing";
               }
               enum "1595.14" {
                 description "1595.14 nm/187.940625 THz 3.125GHz spacing";
               }
               enum "1595.12" {
                 description "1595.12 nm/187.943750 THz 3.125/6.25GHz spacing";
               }
               enum "1595.09" {
                 description "1595.09 nm/187.946875 THz 3.125GHz spacing";
               }
               enum "1595.06" {
                 description "1595.06 nm/187.950000 THz 3.125/6.25/12.5/50GHz spacing";
               }
               enum "1595.04" {
                 description "1595.04 nm/187.953125 THz 3.125GHz spacing";
               }
               enum "1595.01" {
                 description "1595.01 nm/187.956250 THz 3.125/6.25GHz spacing";
               }
               enum "1594.99" {
                 description "1594.99 nm/187.959375 THz 3.125GHz spacing";
               }
               enum "1594.96" {
                 description "1594.96 nm/187.962500 THz 3.125/6.25/12.5GHz spacing";
               }
               enum "1594.93" {
                 description "1594.93 nm/187.965625 THz 3.125GHz spacing";
               }
               enum "1594.91" {
                 description "1594.91 nm/187.968750 THz 3.125/6.25GHz spacing";
               }
               enum "1594.88" {
                 description "1594.88 nm/187.971875 THz 3.125GHz spacing";
               }
               enum "1594.85" {
                 description "1594.85 nm/187.975000 THz 3.125/6.25/12.5GHz spacing";
               }
               enum "1594.83" {
                 description "1594.83 nm/187.978125 THz 3.125GHz spacing";
               }
               enum "1594.80" {
                 description "1594.80 nm/187.981250 THz 3.125/6.25GHz spacing";
               }
               enum "1594.77" {
                 description "1594.77 nm/187.984375 THz 3.125GHz spacing";
               }
               enum "1594.75" {
                 description "1594.75 nm/187.987500 THz 3.125/6.25/12.5GHz spacing";
               }
               enum "1594.72" {
                 description "1594.72 nm/187.990625 THz 3.125GHz spacing";
               }
               enum "1594.69" {
                 description "1594.69 nm/187.993750 THz 3.125/6.25GHz spacing";
               }
               enum "1594.67" {
                 description "1594.67 nm/187.996875 THz 3.125GHz spacing";
               }
               enum "1594.64" {
                 description "1594.64 nm/188.000000 THz 3.125/6.25/12.5/100GHz spacing";
               }
               enum "1594.61" {
                 description "1594.61 nm/188.003125 THz 3.125GHz spacing";
               }
               enum "1594.59" {
                 description "1594.59 nm/188.006250 THz 3.125/6.25GHz spacing";
               }
               enum "1594.56" {
                 description "1594.56 nm/188.009375 THz 3.125GHz spacing";
               }
               enum "1594.53" {
                 description "1594.53 nm/188.012500 THz 3.125/6.25/12.5GHz spacing";
               }
               enum "1594.51" {
                 description "1594.51 nm/188.015625 THz 3.125GHz spacing";
               }
               enum "1594.48" {
                 description "1594.48 nm/188.018750 THz 3.125/6.25GHz spacing";
               }
               enum "1594.46" {
                 description "1594.46 nm/188.021875 THz 3.125GHz spacing";
               }
               enum "1594.43" {
                 description "1594.43 nm/188.025000 THz 3.125/6.25/12.5GHz spacing";
               }
               enum "1594.40" {
                 description "1594.40 nm/188.028125 THz 3.125GHz spacing";
               }
               enum "1594.38" {
                 description "1594.38 nm/188.031250 THz 3.125/6.25GHz spacing";
               }
               enum "1594.35" {
                 description "1594.35 nm/188.034375 THz 3.125GHz spacing";
               }
               enum "1594.32" {
                 description "1594.32 nm/188.037500 THz 3.125/6.25/12.5GHz spacing";
               }
               enum "1594.30" {
                 description "1594.30 nm/188.040625 THz 3.125GHz spacing";
               }
               enum "1594.27" {
                 description "1594.27 nm/188.043750 THz 3.125/6.25GHz spacing";
               }
               enum "1594.24" {
                 description "1594.24 nm/188.046875 THz 3.125GHz spacing";
               }
               enum "1594.22" {
                 description "1594.22 nm/188.050000 THz 3.125/6.25/12.5/50GHz spacing";
               }
               enum "1594.19" {
                 description "1594.19 nm/188.053125 THz 3.125GHz spacing";
               }
               enum "1594.16" {
                 description "1594.16 nm/188.056250 THz 3.125/6.25GHz spacing";
               }
               enum "1594.14" {
                 description "1594.14 nm/188.059375 THz 3.125GHz spacing";
               }
               enum "1594.11" {
                 description "1594.11 nm/188.062500 THz 3.125/6.25/12.5GHz spacing";
               }
               enum "1594.08" {
                 description "1594.08 nm/188.065625 THz 3.125GHz spacing";
               }
               enum "1594.06" {
                 description "1594.06 nm/188.068750 THz 3.125/6.25GHz spacing";
               }
               enum "1594.03" {
                 description "1594.03 nm/188.071875 THz 3.125GHz spacing";
               }
               enum "1594.00" {
                 description "1594.00 nm/188.075000 THz 3.125/6.25/12.5/75GHz spacing";
               }
               enum "1593.98" {
                 description "1593.98 nm/188.078125 THz 3.125GHz spacing";
               }
               enum "1593.95" {
                 description "1593.95 nm/188.081250 THz 3.125/6.25GHz spacing";
               }
               enum "1593.93" {
                 description "1593.93 nm/188.084375 THz 3.125GHz spacing";
               }
               enum "1593.90" {
                 description "1593.90 nm/188.087500 THz 3.125/6.25/12.5GHz spacing";
               }
               enum "1593.87" {
                 description "1593.87 nm/188.090625 THz 3.125GHz spacing";
               }
               enum "1593.85" {
                 description "1593.85 nm/188.093750 THz 3.125/6.25GHz spacing";
               }
               enum "1593.82" {
                 description "1593.82 nm/188.096875 THz 3.125GHz spacing";
               }
               enum "1593.79" {
                 description "1593.79 nm/188.100000 THz 3.125/6.25/12.5/50/75/100GHz spacing";
               }
               enum "1593.77" {
                 description "1593.77 nm/188.103125 THz 3.125GHz spacing";
               }
               enum "1593.74" {
                 description "1593.74 nm/188.106250 THz 3.125/6.25GHz spacing";
               }
               enum "1593.71" {
                 description "1593.71 nm/188.109375 THz 3.125GHz spacing";
               }
               enum "1593.69" {
                 description "1593.69 nm/188.112500 THz 3.125/6.25/12.5GHz spacing";
               }
               enum "1593.66" {
                 description "1593.66 nm/188.115625 THz 3.125GHz spacing";
               }
               enum "1593.63" {
                 description "1593.63 nm/188.118750 THz 3.125/6.25GHz spacing";
               }
               enum "1593.61" {
                 description "1593.61 nm/188.121875 THz 3.125GHz spacing";
               }
               enum "1593.58" {
                 description "1593.58 nm/188.125000 THz 3.125/6.25/12.5GHz spacing";
               }
               enum "1593.55" {
                 description "1593.55 nm/188.128125 THz 3.125GHz spacing";
               }
               enum "1593.53" {
                 description "1593.53 nm/188.131250 THz 3.125/6.25GHz spacing";
               }
               enum "1593.50" {
                 description "1593.50 nm/188.134375 THz 3.125GHz spacing";
               }
               enum "1593.48" {
                 description "1593.48 nm/188.137500 THz 3.125/6.25/12.5GHz spacing";
               }
               enum "1593.45" {
                 description "1593.45 nm/188.140625 THz 3.125GHz spacing";
               }
               enum "1593.42" {
                 description "1593.42 nm/188.143750 THz 3.125/6.25GHz spacing";
               }
               enum "1593.40" {
                 description "1593.40 nm/188.146875 THz 3.125GHz spacing";
               }
               enum "1593.37" {
                 description "1593.37 nm/188.150000 THz 3.125/6.25/12.5/50/75GHz spacing";
               }
               enum "1593.34" {
                 description "1593.34 nm/188.153125 THz 3.125GHz spacing";
               }
               enum "1593.32" {
                 description "1593.32 nm/188.156250 THz 3.125/6.25GHz spacing";
               }
               enum "1593.29" {
                 description "1593.29 nm/188.159375 THz 3.125GHz spacing";
               }
               enum "1593.26" {
                 description "1593.26 nm/188.162500 THz 3.125/6.25/12.5GHz spacing";
               }
               enum "1593.24" {
                 description "1593.24 nm/188.165625 THz 3.125GHz spacing";
               }
               enum "1593.21" {
                 description "1593.21 nm/188.168750 THz 3.125/6.25GHz spacing";
               }
               enum "1593.18" {
                 description "1593.18 nm/188.171875 THz 3.125GHz spacing";
               }
               enum "1593.16" {
                 description "1593.16 nm/188.175000 THz 3.125/6.25/12.5GHz spacing";
               }
               enum "1593.13" {
                 description "1593.13 nm/188.178125 THz 3.125GHz spacing";
               }
               enum "1593.10" {
                 description "1593.10 nm/188.181250 THz 3.125/6.25GHz spacing";
               }
               enum "1593.08" {
                 description "1593.08 nm/188.184375 THz 3.125GHz spacing";
               }
               enum "1593.05" {
                 description "1593.05 nm/188.187500 THz 3.125/6.25/12.5GHz spacing";
               }
               enum "1593.03" {
                 description "1593.03 nm/188.190625 THz 3.125GHz spacing";
               }
               enum "1593.00" {
                 description "1593.00 nm/188.193750 THz 3.125/6.25GHz spacing";
               }
               enum "1592.97" {
                 description "1592.97 nm/188.196875 THz 3.125GHz spacing";
               }
               enum "1592.95" {
                 description "1592.95 nm/188.200000 THz 3.125/6.25/12.5/100GHz spacing";
               }
               enum "1592.92" {
                 description "1592.92 nm/188.203125 THz 3.125GHz spacing";
               }
               enum "1592.89" {
                 description "1592.89 nm/188.206250 THz 3.125/6.25GHz spacing";
               }
               enum "1592.87" {
                 description "1592.87 nm/188.209375 THz 3.125GHz spacing";
               }
               enum "1592.84" {
                 description "1592.84 nm/188.212500 THz 3.125/6.25/12.5GHz spacing";
               }
               enum "1592.81" {
                 description "1592.81 nm/188.215625 THz 3.125GHz spacing";
               }
               enum "1592.79" {
                 description "1592.79 nm/188.218750 THz 3.125/6.25GHz spacing";
               }
               enum "1592.76" {
                 description "1592.76 nm/188.221875 THz 3.125GHz spacing";
               }
               enum "1592.73" {
                 description "1592.73 nm/188.225000 THz 3.125/6.25/12.5/75GHz spacing";
               }
               enum "1592.71" {
                 description "1592.71 nm/188.228125 THz 3.125GHz spacing";
               }
               enum "1592.68" {
                 description "1592.68 nm/188.231250 THz 3.125/6.25GHz spacing";
               }
               enum "1592.66" {
                 description "1592.66 nm/188.234375 THz 3.125GHz spacing";
               }
               enum "1592.63" {
                 description "1592.63 nm/188.237500 THz 3.125/6.25/12.5GHz spacing";
               }
               enum "1592.60" {
                 description "1592.60 nm/188.240625 THz 3.125GHz spacing";
               }
               enum "1592.58" {
                 description "1592.58 nm/188.243750 THz 3.125/6.25GHz spacing";
               }
               enum "1592.55" {
                 description "1592.55 nm/188.246875 THz 3.125GHz spacing";
               }
               enum "1592.52" {
                 description "1592.52 nm/188.250000 THz 3.125/6.25/12.5/50GHz spacing";
               }
               enum "1592.50" {
                 description "1592.50 nm/188.253125 THz 3.125GHz spacing";
               }
               enum "1592.47" {
                 description "1592.47 nm/188.256250 THz 3.125/6.25GHz spacing";
               }
               enum "1592.44" {
                 description "1592.44 nm/188.259375 THz 3.125GHz spacing";
               }
               enum "1592.42" {
                 description "1592.42 nm/188.262500 THz 3.125/6.25/12.5GHz spacing";
               }
               enum "1592.39" {
                 description "1592.39 nm/188.265625 THz 3.125GHz spacing";
               }
               enum "1592.36" {
                 description "1592.36 nm/188.268750 THz 3.125/6.25GHz spacing";
               }
               enum "1592.34" {
                 description "1592.34 nm/188.271875 THz 3.125GHz spacing";
               }
               enum "1592.31" {
                 description "1592.31 nm/188.275000 THz 3.125/6.25/12.5GHz spacing";
               }
               enum "1592.29" {
                 description "1592.29 nm/188.278125 THz 3.125GHz spacing";
               }
               enum "1592.26" {
                 description "1592.26 nm/188.281250 THz 3.125/6.25GHz spacing";
               }
               enum "1592.23" {
                 description "1592.23 nm/188.284375 THz 3.125GHz spacing";
               }
               enum "1592.21" {
                 description "1592.21 nm/188.287500 THz 3.125/6.25/12.5GHz spacing";
               }
               enum "1592.18" {
                 description "1592.18 nm/188.290625 THz 3.125GHz spacing";
               }
               enum "1592.15" {
                 description "1592.15 nm/188.293750 THz 3.125/6.25GHz spacing";
               }
               enum "1592.13" {
                 description "1592.13 nm/188.296875 THz 3.125GHz spacing";
               }
               enum "1592.10" {
                 description "1592.10 nm/188.300000 THz 3.125/6.25/12.5/100GHz spacing";
               }
               enum "1592.07" {
                 description "1592.07 nm/188.303125 THz 3.125GHz spacing";
               }
               enum "1592.05" {
                 description "1592.05 nm/188.306250 THz 3.125/6.25GHz spacing";
               }
               enum "1592.02" {
                 description "1592.02 nm/188.309375 THz 3.125GHz spacing";
               }
               enum "1591.99" {
                 description "1591.99 nm/188.312500 THz 3.125/6.25/12.5GHz spacing";
               }
               enum "1591.97" {
                 description "1591.97 nm/188.315625 THz 3.125GHz spacing";
               }
               enum "1591.94" {
                 description "1591.94 nm/188.318750 THz 3.125/6.25GHz spacing";
               }
               enum "1591.92" {
                 description "1591.92 nm/188.321875 THz 3.125GHz spacing";
               }
               enum "1591.89" {
                 description "1591.89 nm/188.325000 THz 3.125/6.25/12.5GHz spacing";
               }
               enum "1591.86" {
                 description "1591.86 nm/188.328125 THz 3.125GHz spacing";
               }
               enum "1591.84" {
                 description "1591.84 nm/188.331250 THz 3.125/6.25GHz spacing";
               }
               enum "1591.81" {
                 description "1591.81 nm/188.334375 THz 3.125GHz spacing";
               }
               enum "1591.78" {
                 description "1591.78 nm/188.337500 THz 3.125/6.25/12.5GHz spacing";
               }
               enum "1591.76" {
                 description "1591.76 nm/188.340625 THz 3.125GHz spacing";
               }
               enum "1591.73" {
                 description "1591.73 nm/188.343750 THz 3.125/6.25GHz spacing";
               }
               enum "1591.70" {
                 description "1591.70 nm/188.346875 THz 3.125GHz spacing";
               }
               enum "1591.68" {
                 description "1591.68 nm/188.350000 THz 3.125/6.25/12.5/50GHz spacing";
               }
               enum "1591.65" {
                 description "1591.65 nm/188.353125 THz 3.125GHz spacing";
               }
               enum "1591.62" {
                 description "1591.62 nm/188.356250 THz 3.125/6.25GHz spacing";
               }
               enum "1591.60" {
                 description "1591.60 nm/188.359375 THz 3.125GHz spacing";
               }
               enum "1591.57" {
                 description "1591.57 nm/188.362500 THz 3.125/6.25/12.5GHz spacing";
               }
               enum "1591.55" {
                 description "1591.55 nm/188.365625 THz 3.125GHz spacing";
               }
               enum "1591.52" {
                 description "1591.52 nm/188.368750 THz 3.125/6.25GHz spacing";
               }
               enum "1591.49" {
                 description "1591.49 nm/188.371875 THz 3.125GHz spacing";
               }
               enum "1591.47" {
                 description "1591.47 nm/188.375000 THz 3.125/6.25/12.5/75GHz spacing";
               }
               enum "1591.44" {
                 description "1591.44 nm/188.378125 THz 3.125GHz spacing";
               }
               enum "1591.41" {
                 description "1591.41 nm/188.381250 THz 3.125/6.25GHz spacing";
               }
               enum "1591.39" {
                 description "1591.39 nm/188.384375 THz 3.125GHz spacing";
               }
               enum "1591.36" {
                 description "1591.36 nm/188.387500 THz 3.125/6.25/12.5GHz spacing";
               }
               enum "1591.33" {
                 description "1591.33 nm/188.390625 THz 3.125GHz spacing";
               }
               enum "1591.31" {
                 description "1591.31 nm/188.393750 THz 3.125/6.25GHz spacing";
               }
               enum "1591.28" {
                 description "1591.28 nm/188.396875 THz 3.125GHz spacing";
               }
               enum "1591.26" {
                 description "1591.26 nm/188.400000 THz 3.125/6.25/12.5/50/75/100GHz spacing";
               }
               enum "1591.23" {
                 description "1591.23 nm/188.403125 THz 3.125GHz spacing";
               }
               enum "1591.20" {
                 description "1591.20 nm/188.406250 THz 3.125/6.25GHz spacing";
               }
               enum "1591.18" {
                 description "1591.18 nm/188.409375 THz 3.125GHz spacing";
               }
               enum "1591.15" {
                 description "1591.15 nm/188.412500 THz 3.125/6.25/12.5GHz spacing";
               }
               enum "1591.12" {
                 description "1591.12 nm/188.415625 THz 3.125GHz spacing";
               }
               enum "1591.10" {
                 description "1591.10 nm/188.418750 THz 3.125/6.25GHz spacing";
               }
               enum "1591.07" {
                 description "1591.07 nm/188.421875 THz 3.125GHz spacing";
               }
               enum "1591.04" {
                 description "1591.04 nm/188.425000 THz 3.125/6.25/12.5GHz spacing";
               }
               enum "1591.02" {
                 description "1591.02 nm/188.428125 THz 3.125GHz spacing";
               }
               enum "1590.99" {
                 description "1590.99 nm/188.431250 THz 3.125/6.25GHz spacing";
               }
               enum "1590.96" {
                 description "1590.96 nm/188.434375 THz 3.125GHz spacing";
               }
               enum "1590.94" {
                 description "1590.94 nm/188.437500 THz 3.125/6.25/12.5GHz spacing";
               }
               enum "1590.91" {
                 description "1590.91 nm/188.440625 THz 3.125GHz spacing";
               }
               enum "1590.89" {
                 description "1590.89 nm/188.443750 THz 3.125/6.25GHz spacing";
               }
               enum "1590.86" {
                 description "1590.86 nm/188.446875 THz 3.125GHz spacing";
               }
               enum "1590.83" {
                 description "1590.83 nm/188.450000 THz 3.125/6.25/12.5/50/75GHz spacing";
               }
               enum "1590.81" {
                 description "1590.81 nm/188.453125 THz 3.125GHz spacing";
               }
               enum "1590.78" {
                 description "1590.78 nm/188.456250 THz 3.125/6.25GHz spacing";
               }
               enum "1590.75" {
                 description "1590.75 nm/188.459375 THz 3.125GHz spacing";
               }
               enum "1590.73" {
                 description "1590.73 nm/188.462500 THz 3.125/6.25/12.5GHz spacing";
               }
               enum "1590.70" {
                 description "1590.70 nm/188.465625 THz 3.125GHz spacing";
               }
               enum "1590.67" {
                 description "1590.67 nm/188.468750 THz 3.125/6.25GHz spacing";
               }
               enum "1590.65" {
                 description "1590.65 nm/188.471875 THz 3.125GHz spacing";
               }
               enum "1590.62" {
                 description "1590.62 nm/188.475000 THz 3.125/6.25/12.5GHz spacing";
               }
               enum "1590.60" {
                 description "1590.60 nm/188.478125 THz 3.125GHz spacing";
               }
               enum "1590.57" {
                 description "1590.57 nm/188.481250 THz 3.125/6.25GHz spacing";
               }
               enum "1590.54" {
                 description "1590.54 nm/188.484375 THz 3.125GHz spacing";
               }
               enum "1590.52" {
                 description "1590.52 nm/188.487500 THz 3.125/6.25/12.5GHz spacing";
               }
               enum "1590.49" {
                 description "1590.49 nm/188.490625 THz 3.125GHz spacing";
               }
               enum "1590.46" {
                 description "1590.46 nm/188.493750 THz 3.125/6.25GHz spacing";
               }
               enum "1590.44" {
                 description "1590.44 nm/188.496875 THz 3.125GHz spacing";
               }
               enum "1590.41" {
                 description "1590.41 nm/188.500000 THz 3.125/6.25/12.5/100GHz spacing";
               }
               enum "1590.38" {
                 description "1590.38 nm/188.503125 THz 3.125GHz spacing";
               }
               enum "1590.36" {
                 description "1590.36 nm/188.506250 THz 3.125/6.25GHz spacing";
               }
               enum "1590.33" {
                 description "1590.33 nm/188.509375 THz 3.125GHz spacing";
               }
               enum "1590.31" {
                 description "1590.31 nm/188.512500 THz 3.125/6.25/12.5GHz spacing";
               }
               enum "1590.28" {
                 description "1590.28 nm/188.515625 THz 3.125GHz spacing";
               }
               enum "1590.25" {
                 description "1590.25 nm/188.518750 THz 3.125/6.25GHz spacing";
               }
               enum "1590.23" {
                 description "1590.23 nm/188.521875 THz 3.125GHz spacing";
               }
               enum "1590.20" {
                 description "1590.20 nm/188.525000 THz 3.125/6.25/12.5/75GHz spacing";
               }
               enum "1590.17" {
                 description "1590.17 nm/188.528125 THz 3.125GHz spacing";
               }
               enum "1590.15" {
                 description "1590.15 nm/188.531250 THz 3.125/6.25GHz spacing";
               }
               enum "1590.12" {
                 description "1590.12 nm/188.534375 THz 3.125GHz spacing";
               }
               enum "1590.09" {
                 description "1590.09 nm/188.537500 THz 3.125/6.25/12.5GHz spacing";
               }
               enum "1590.07" {
                 description "1590.07 nm/188.540625 THz 3.125GHz spacing";
               }
               enum "1590.04" {
                 description "1590.04 nm/188.543750 THz 3.125/6.25GHz spacing";
               }
               enum "1590.02" {
                 description "1590.02 nm/188.546875 THz 3.125GHz spacing";
               }
               enum "1589.99" {
                 description "1589.99 nm/188.550000 THz 3.125/6.25/12.5/50GHz spacing";
               }
               enum "1589.96" {
                 description "1589.96 nm/188.553125 THz 3.125GHz spacing";
               }
               enum "1589.94" {
                 description "1589.94 nm/188.556250 THz 3.125/6.25GHz spacing";
               }
               enum "1589.91" {
                 description "1589.91 nm/188.559375 THz 3.125GHz spacing";
               }
               enum "1589.88" {
                 description "1589.88 nm/188.562500 THz 3.125/6.25/12.5GHz spacing";
               }
               enum "1589.86" {
                 description "1589.86 nm/188.565625 THz 3.125GHz spacing";
               }
               enum "1589.83" {
                 description "1589.83 nm/188.568750 THz 3.125/6.25GHz spacing";
               }
               enum "1589.80" {
                 description "1589.80 nm/188.571875 THz 3.125GHz spacing";
               }
               enum "1589.78" {
                 description "1589.78 nm/188.575000 THz 3.125/6.25/12.5GHz spacing";
               }
               enum "1589.75" {
                 description "1589.75 nm/188.578125 THz 3.125GHz spacing";
               }
               enum "1589.73" {
                 description "1589.73 nm/188.581250 THz 3.125/6.25GHz spacing";
               }
               enum "1589.70" {
                 description "1589.70 nm/188.584375 THz 3.125GHz spacing";
               }
               enum "1589.67" {
                 description "1589.67 nm/188.587500 THz 3.125/6.25/12.5GHz spacing";
               }
               enum "1589.65" {
                 description "1589.65 nm/188.590625 THz 3.125GHz spacing";
               }
               enum "1589.62" {
                 description "1589.62 nm/188.593750 THz 3.125/6.25GHz spacing";
               }
               enum "1589.59" {
                 description "1589.59 nm/188.596875 THz 3.125GHz spacing";
               }
               enum "1589.57" {
                 description "1589.57 nm/188.600000 THz 3.125/6.25/12.5/100GHz spacing";
               }
               enum "1589.54" {
                 description "1589.54 nm/188.603125 THz 3.125GHz spacing";
               }
               enum "1589.51" {
                 description "1589.51 nm/188.606250 THz 3.125/6.25GHz spacing";
               }
               enum "1589.49" {
                 description "1589.49 nm/188.609375 THz 3.125GHz spacing";
               }
               enum "1589.46" {
                 description "1589.46 nm/188.612500 THz 3.125/6.25/12.5GHz spacing";
               }
               enum "1589.44" {
                 description "1589.44 nm/188.615625 THz 3.125GHz spacing";
               }
               enum "1589.41" {
                 description "1589.41 nm/188.618750 THz 3.125/6.25GHz spacing";
               }
               enum "1589.38" {
                 description "1589.38 nm/188.621875 THz 3.125GHz spacing";
               }
               enum "1589.36" {
                 description "1589.36 nm/188.625000 THz 3.125/6.25/12.5GHz spacing";
               }
               enum "1589.33" {
                 description "1589.33 nm/188.628125 THz 3.125GHz spacing";
               }
               enum "1589.30" {
                 description "1589.30 nm/188.631250 THz 3.125/6.25GHz spacing";
               }
               enum "1589.28" {
                 description "1589.28 nm/188.634375 THz 3.125GHz spacing";
               }
               enum "1589.25" {
                 description "1589.25 nm/188.637500 THz 3.125/6.25/12.5GHz spacing";
               }
               enum "1589.23" {
                 description "1589.23 nm/188.640625 THz 3.125GHz spacing";
               }
               enum "1589.20" {
                 description "1589.20 nm/188.643750 THz 3.125/6.25GHz spacing";
               }
               enum "1589.17" {
                 description "1589.17 nm/188.646875 THz 3.125GHz spacing";
               }
               enum "1589.15" {
                 description "1589.15 nm/188.650000 THz 3.125/6.25/12.5/50GHz spacing";
               }
               enum "1589.12" {
                 description "1589.12 nm/188.653125 THz 3.125GHz spacing";
               }
               enum "1589.09" {
                 description "1589.09 nm/188.656250 THz 3.125/6.25GHz spacing";
               }
               enum "1589.07" {
                 description "1589.07 nm/188.659375 THz 3.125GHz spacing";
               }
               enum "1589.04" {
                 description "1589.04 nm/188.662500 THz 3.125/6.25/12.5GHz spacing";
               }
               enum "1589.01" {
                 description "1589.01 nm/188.665625 THz 3.125GHz spacing";
               }
               enum "1588.99" {
                 description "1588.99 nm/188.668750 THz 3.125/6.25GHz spacing";
               }
               enum "1588.96" {
                 description "1588.96 nm/188.671875 THz 3.125GHz spacing";
               }
               enum "1588.94" {
                 description "1588.94 nm/188.675000 THz 3.125/6.25/12.5/75GHz spacing";
               }
               enum "1588.91" {
                 description "1588.91 nm/188.678125 THz 3.125GHz spacing";
               }
               enum "1588.88" {
                 description "1588.88 nm/188.681250 THz 3.125/6.25GHz spacing";
               }
               enum "1588.86" {
                 description "1588.86 nm/188.684375 THz 3.125GHz spacing";
               }
               enum "1588.83" {
                 description "1588.83 nm/188.687500 THz 3.125/6.25/12.5GHz spacing";
               }
               enum "1588.80" {
                 description "1588.80 nm/188.690625 THz 3.125GHz spacing";
               }
               enum "1588.78" {
                 description "1588.78 nm/188.693750 THz 3.125/6.25GHz spacing";
               }
               enum "1588.75" {
                 description "1588.75 nm/188.696875 THz 3.125GHz spacing";
               }
               enum "1588.73" {
                 description "1588.73 nm/188.700000 THz 3.125/6.25/12.5/50/75/100GHz spacing";
               }
               enum "1588.70" {
                 description "1588.70 nm/188.703125 THz 3.125GHz spacing";
               }
               enum "1588.67" {
                 description "1588.67 nm/188.706250 THz 3.125/6.25GHz spacing";
               }
               enum "1588.65" {
                 description "1588.65 nm/188.709375 THz 3.125GHz spacing";
               }
               enum "1588.62" {
                 description "1588.62 nm/188.712500 THz 3.125/6.25/12.5GHz spacing";
               }
               enum "1588.59" {
                 description "1588.59 nm/188.715625 THz 3.125GHz spacing";
               }
               enum "1588.57" {
                 description "1588.57 nm/188.718750 THz 3.125/6.25GHz spacing";
               }
               enum "1588.54" {
                 description "1588.54 nm/188.721875 THz 3.125GHz spacing";
               }
               enum "1588.51" {
                 description "1588.51 nm/188.725000 THz 3.125/6.25/12.5GHz spacing";
               }
               enum "1588.49" {
                 description "1588.49 nm/188.728125 THz 3.125GHz spacing";
               }
               enum "1588.46" {
                 description "1588.46 nm/188.731250 THz 3.125/6.25GHz spacing";
               }
               enum "1588.44" {
                 description "1588.44 nm/188.734375 THz 3.125GHz spacing";
               }
               enum "1588.41" {
                 description "1588.41 nm/188.737500 THz 3.125/6.25/12.5GHz spacing";
               }
               enum "1588.38" {
                 description "1588.38 nm/188.740625 THz 3.125GHz spacing";
               }
               enum "1588.36" {
                 description "1588.36 nm/188.743750 THz 3.125/6.25GHz spacing";
               }
               enum "1588.33" {
                 description "1588.33 nm/188.746875 THz 3.125GHz spacing";
               }
               enum "1588.30" {
                 description "1588.30 nm/188.750000 THz 3.125/6.25/12.5/50/75GHz spacing";
               }
               enum "1588.28" {
                 description "1588.28 nm/188.753125 THz 3.125GHz spacing";
               }
               enum "1588.25" {
                 description "1588.25 nm/188.756250 THz 3.125/6.25GHz spacing";
               }
               enum "1588.23" {
                 description "1588.23 nm/188.759375 THz 3.125GHz spacing";
               }
               enum "1588.20" {
                 description "1588.20 nm/188.762500 THz 3.125/6.25/12.5GHz spacing";
               }
               enum "1588.17" {
                 description "1588.17 nm/188.765625 THz 3.125GHz spacing";
               }
               enum "1588.15" {
                 description "1588.15 nm/188.768750 THz 3.125/6.25GHz spacing";
               }
               enum "1588.12" {
                 description "1588.12 nm/188.771875 THz 3.125GHz spacing";
               }
               enum "1588.09" {
                 description "1588.09 nm/188.775000 THz 3.125/6.25/12.5GHz spacing";
               }
               enum "1588.07" {
                 description "1588.07 nm/188.778125 THz 3.125GHz spacing";
               }
               enum "1588.04" {
                 description "1588.04 nm/188.781250 THz 3.125/6.25GHz spacing";
               }
               enum "1588.02" {
                 description "1588.02 nm/188.784375 THz 3.125GHz spacing";
               }
               enum "1587.99" {
                 description "1587.99 nm/188.787500 THz 3.125/6.25/12.5GHz spacing";
               }
               enum "1587.96" {
                 description "1587.96 nm/188.790625 THz 3.125GHz spacing";
               }
               enum "1587.94" {
                 description "1587.94 nm/188.793750 THz 3.125/6.25GHz spacing";
               }
               enum "1587.91" {
                 description "1587.91 nm/188.796875 THz 3.125GHz spacing";
               }
               enum "1587.88" {
                 description "1587.88 nm/188.800000 THz 3.125/6.25/12.5/100GHz spacing";
               }
               enum "1587.86" {
                 description "1587.86 nm/188.803125 THz 3.125GHz spacing";
               }
               enum "1587.83" {
                 description "1587.83 nm/188.806250 THz 3.125/6.25GHz spacing";
               }
               enum "1587.80" {
                 description "1587.80 nm/188.809375 THz 3.125GHz spacing";
               }
               enum "1587.78" {
                 description "1587.78 nm/188.812500 THz 3.125/6.25/12.5GHz spacing";
               }
               enum "1587.75" {
                 description "1587.75 nm/188.815625 THz 3.125GHz spacing";
               }
               enum "1587.73" {
                 description "1587.73 nm/188.818750 THz 3.125/6.25GHz spacing";
               }
               enum "1587.70" {
                 description "1587.70 nm/188.821875 THz 3.125GHz spacing";
               }
               enum "1587.67" {
                 description "1587.67 nm/188.825000 THz 3.125/6.25/12.5/75GHz spacing";
               }
               enum "1587.65" {
                 description "1587.65 nm/188.828125 THz 3.125GHz spacing";
               }
               enum "1587.62" {
                 description "1587.62 nm/188.831250 THz 3.125/6.25GHz spacing";
               }
               enum "1587.59" {
                 description "1587.59 nm/188.834375 THz 3.125GHz spacing";
               }
               enum "1587.57" {
                 description "1587.57 nm/188.837500 THz 3.125/6.25/12.5GHz spacing";
               }
               enum "1587.54" {
                 description "1587.54 nm/188.840625 THz 3.125GHz spacing";
               }
               enum "1587.52" {
                 description "1587.52 nm/188.843750 THz 3.125/6.25GHz spacing";
               }
               enum "1587.49" {
                 description "1587.49 nm/188.846875 THz 3.125GHz spacing";
               }
               enum "1587.46" {
                 description "1587.46 nm/188.850000 THz 3.125/6.25/12.5/50GHz spacing";
               }
               enum "1587.44" {
                 description "1587.44 nm/188.853125 THz 3.125GHz spacing";
               }
               enum "1587.41" {
                 description "1587.41 nm/188.856250 THz 3.125/6.25GHz spacing";
               }
               enum "1587.38" {
                 description "1587.38 nm/188.859375 THz 3.125GHz spacing";
               }
               enum "1587.36" {
                 description "1587.36 nm/188.862500 THz 3.125/6.25/12.5GHz spacing";
               }
               enum "1587.33" {
                 description "1587.33 nm/188.865625 THz 3.125GHz spacing";
               }
               enum "1587.31" {
                 description "1587.31 nm/188.868750 THz 3.125/6.25GHz spacing";
               }
               enum "1587.28" {
                 description "1587.28 nm/188.871875 THz 3.125GHz spacing";
               }
               enum "1587.25" {
                 description "1587.25 nm/188.875000 THz 3.125/6.25/12.5GHz spacing";
               }
               enum "1587.23" {
                 description "1587.23 nm/188.878125 THz 3.125GHz spacing";
               }
               enum "1587.20" {
                 description "1587.20 nm/188.881250 THz 3.125/6.25GHz spacing";
               }
               enum "1587.17" {
                 description "1587.17 nm/188.884375 THz 3.125GHz spacing";
               }
               enum "1587.15" {
                 description "1587.15 nm/188.887500 THz 3.125/6.25/12.5GHz spacing";
               }
               enum "1587.12" {
                 description "1587.12 nm/188.890625 THz 3.125GHz spacing";
               }
               enum "1587.10" {
                 description "1587.10 nm/188.893750 THz 3.125/6.25GHz spacing";
               }
               enum "1587.07" {
                 description "1587.07 nm/188.896875 THz 3.125GHz spacing";
               }
               enum "1587.04" {
                 description "1587.04 nm/188.900000 THz 3.125/6.25/12.5/100GHz spacing";
               }
               enum "1587.02" {
                 description "1587.02 nm/188.903125 THz 3.125GHz spacing";
               }
               enum "1586.99" {
                 description "1586.99 nm/188.906250 THz 3.125/6.25GHz spacing";
               }
               enum "1586.96" {
                 description "1586.96 nm/188.909375 THz 3.125GHz spacing";
               }
               enum "1586.94" {
                 description "1586.94 nm/188.912500 THz 3.125/6.25/12.5GHz spacing";
               }
               enum "1586.91" {
                 description "1586.91 nm/188.915625 THz 3.125GHz spacing";
               }
               enum "1586.89" {
                 description "1586.89 nm/188.918750 THz 3.125/6.25GHz spacing";
               }
               enum "1586.86" {
                 description "1586.86 nm/188.921875 THz 3.125GHz spacing";
               }
               enum "1586.83" {
                 description "1586.83 nm/188.925000 THz 3.125/6.25/12.5GHz spacing";
               }
               enum "1586.81" {
                 description "1586.81 nm/188.928125 THz 3.125GHz spacing";
               }
               enum "1586.78" {
                 description "1586.78 nm/188.931250 THz 3.125/6.25GHz spacing";
               }
               enum "1586.75" {
                 description "1586.75 nm/188.934375 THz 3.125GHz spacing";
               }
               enum "1586.73" {
                 description "1586.73 nm/188.937500 THz 3.125/6.25/12.5GHz spacing";
               }
               enum "1586.70" {
                 description "1586.70 nm/188.940625 THz 3.125GHz spacing";
               }
               enum "1586.68" {
                 description "1586.68 nm/188.943750 THz 3.125/6.25GHz spacing";
               }
               enum "1586.65" {
                 description "1586.65 nm/188.946875 THz 3.125GHz spacing";
               }
               enum "1586.62" {
                 description "1586.62 nm/188.950000 THz 3.125/6.25/12.5/50GHz spacing";
               }
               enum "1586.60" {
                 description "1586.60 nm/188.953125 THz 3.125GHz spacing";
               }
               enum "1586.57" {
                 description "1586.57 nm/188.956250 THz 3.125/6.25GHz spacing";
               }
               enum "1586.54" {
                 description "1586.54 nm/188.959375 THz 3.125GHz spacing";
               }
               enum "1586.52" {
                 description "1586.52 nm/188.962500 THz 3.125/6.25/12.5GHz spacing";
               }
               enum "1586.49" {
                 description "1586.49 nm/188.965625 THz 3.125GHz spacing";
               }
               enum "1586.47" {
                 description "1586.47 nm/188.968750 THz 3.125/6.25GHz spacing";
               }
               enum "1586.44" {
                 description "1586.44 nm/188.971875 THz 3.125GHz spacing";
               }
               enum "1586.41" {
                 description "1586.41 nm/188.975000 THz 3.125/6.25/12.5/75GHz spacing";
               }
               enum "1586.39" {
                 description "1586.39 nm/188.978125 THz 3.125GHz spacing";
               }
               enum "1586.36" {
                 description "1586.36 nm/188.981250 THz 3.125/6.25GHz spacing";
               }
               enum "1586.33" {
                 description "1586.33 nm/188.984375 THz 3.125GHz spacing";
               }
               enum "1586.31" {
                 description "1586.31 nm/188.987500 THz 3.125/6.25/12.5GHz spacing";
               }
               enum "1586.28" {
                 description "1586.28 nm/188.990625 THz 3.125GHz spacing";
               }
               enum "1586.26" {
                 description "1586.26 nm/188.993750 THz 3.125/6.25GHz spacing";
               }
               enum "1586.23" {
                 description "1586.23 nm/188.996875 THz 3.125GHz spacing";
               }
               enum "1586.20" {
                 description "1586.20 nm/189.000000 THz 3.125/6.25/12.5/50/75/100GHz spacing";
               }
               enum "1586.18" {
                 description "1586.18 nm/189.003125 THz 3.125GHz spacing";
               }
               enum "1586.15" {
                 description "1586.15 nm/189.006250 THz 3.125/6.25GHz spacing";
               }
               enum "1586.12" {
                 description "1586.12 nm/189.009375 THz 3.125GHz spacing";
               }
               enum "1586.10" {
                 description "1586.10 nm/189.012500 THz 3.125/6.25/12.5GHz spacing";
               }
               enum "1586.07" {
                 description "1586.07 nm/189.015625 THz 3.125GHz spacing";
               }
               enum "1586.05" {
                 description "1586.05 nm/189.018750 THz 3.125/6.25GHz spacing";
               }
               enum "1586.02" {
                 description "1586.02 nm/189.021875 THz 3.125GHz spacing";
               }
               enum "1585.99" {
                 description "1585.99 nm/189.025000 THz 3.125/6.25/12.5GHz spacing";
               }
               enum "1585.97" {
                 description "1585.97 nm/189.028125 THz 3.125GHz spacing";
               }
               enum "1585.94" {
                 description "1585.94 nm/189.031250 THz 3.125/6.25GHz spacing";
               }
               enum "1585.92" {
                 description "1585.92 nm/189.034375 THz 3.125GHz spacing";
               }
               enum "1585.89" {
                 description "1585.89 nm/189.037500 THz 3.125/6.25/12.5GHz spacing";
               }
               enum "1585.86" {
                 description "1585.86 nm/189.040625 THz 3.125GHz spacing";
               }
               enum "1585.84" {
                 description "1585.84 nm/189.043750 THz 3.125/6.25GHz spacing";
               }
               enum "1585.81" {
                 description "1585.81 nm/189.046875 THz 3.125GHz spacing";
               }
               enum "1585.78" {
                 description "1585.78 nm/189.050000 THz 3.125/6.25/12.5/50/75GHz spacing";
               }
               enum "1585.76" {
                 description "1585.76 nm/189.053125 THz 3.125GHz spacing";
               }
               enum "1585.73" {
                 description "1585.73 nm/189.056250 THz 3.125/6.25GHz spacing";
               }
               enum "1585.71" {
                 description "1585.71 nm/189.059375 THz 3.125GHz spacing";
               }
               enum "1585.68" {
                 description "1585.68 nm/189.062500 THz 3.125/6.25/12.5GHz spacing";
               }
               enum "1585.65" {
                 description "1585.65 nm/189.065625 THz 3.125GHz spacing";
               }
               enum "1585.63" {
                 description "1585.63 nm/189.068750 THz 3.125/6.25GHz spacing";
               }
               enum "1585.60" {
                 description "1585.60 nm/189.071875 THz 3.125GHz spacing";
               }
               enum "1585.57" {
                 description "1585.57 nm/189.075000 THz 3.125/6.25/12.5GHz spacing";
               }
               enum "1585.55" {
                 description "1585.55 nm/189.078125 THz 3.125GHz spacing";
               }
               enum "1585.52" {
                 description "1585.52 nm/189.081250 THz 3.125/6.25GHz spacing";
               }
               enum "1585.50" {
                 description "1585.50 nm/189.084375 THz 3.125GHz spacing";
               }
               enum "1585.47" {
                 description "1585.47 nm/189.087500 THz 3.125/6.25/12.5GHz spacing";
               }
               enum "1585.44" {
                 description "1585.44 nm/189.090625 THz 3.125GHz spacing";
               }
               enum "1585.42" {
                 description "1585.42 nm/189.093750 THz 3.125/6.25GHz spacing";
               }
               enum "1585.39" {
                 description "1585.39 nm/189.096875 THz 3.125GHz spacing";
               }
               enum "1585.36" {
                 description "1585.36 nm/189.100000 THz 3.125/6.25/12.5/100GHz spacing";
               }
               enum "1585.34" {
                 description "1585.34 nm/189.103125 THz 3.125GHz spacing";
               }
               enum "1585.31" {
                 description "1585.31 nm/189.106250 THz 3.125/6.25GHz spacing";
               }
               enum "1585.29" {
                 description "1585.29 nm/189.109375 THz 3.125GHz spacing";
               }
               enum "1585.26" {
                 description "1585.26 nm/189.112500 THz 3.125/6.25/12.5GHz spacing";
               }
               enum "1585.23" {
                 description "1585.23 nm/189.115625 THz 3.125GHz spacing";
               }
               enum "1585.21" {
                 description "1585.21 nm/189.118750 THz 3.125/6.25GHz spacing";
               }
               enum "1585.18" {
                 description "1585.18 nm/189.121875 THz 3.125GHz spacing";
               }
               enum "1585.16" {
                 description "1585.16 nm/189.125000 THz 3.125/6.25/12.5/75GHz spacing";
               }
               enum "1585.13" {
                 description "1585.13 nm/189.128125 THz 3.125GHz spacing";
               }
               enum "1585.10" {
                 description "1585.10 nm/189.131250 THz 3.125/6.25GHz spacing";
               }
               enum "1585.08" {
                 description "1585.08 nm/189.134375 THz 3.125GHz spacing";
               }
               enum "1585.05" {
                 description "1585.05 nm/189.137500 THz 3.125/6.25/12.5GHz spacing";
               }
               enum "1585.02" {
                 description "1585.02 nm/189.140625 THz 3.125GHz spacing";
               }
               enum "1585.00" {
                 description "1585.00 nm/189.143750 THz 3.125/6.25GHz spacing";
               }
               enum "1584.97" {
                 description "1584.97 nm/189.146875 THz 3.125GHz spacing";
               }
               enum "1584.95" {
                 description "1584.95 nm/189.150000 THz 3.125/6.25/12.5/50GHz spacing";
               }
               enum "1584.92" {
                 description "1584.92 nm/189.153125 THz 3.125GHz spacing";
               }
               enum "1584.89" {
                 description "1584.89 nm/189.156250 THz 3.125/6.25GHz spacing";
               }
               enum "1584.87" {
                 description "1584.87 nm/189.159375 THz 3.125GHz spacing";
               }
               enum "1584.84" {
                 description "1584.84 nm/189.162500 THz 3.125/6.25/12.5GHz spacing";
               }
               enum "1584.81" {
                 description "1584.81 nm/189.165625 THz 3.125GHz spacing";
               }
               enum "1584.79" {
                 description "1584.79 nm/189.168750 THz 3.125/6.25GHz spacing";
               }
               enum "1584.76" {
                 description "1584.76 nm/189.171875 THz 3.125GHz spacing";
               }
               enum "1584.74" {
                 description "1584.74 nm/189.175000 THz 3.125/6.25/12.5GHz spacing";
               }
               enum "1584.71" {
                 description "1584.71 nm/189.178125 THz 3.125GHz spacing";
               }
               enum "1584.68" {
                 description "1584.68 nm/189.181250 THz 3.125/6.25GHz spacing";
               }
               enum "1584.66" {
                 description "1584.66 nm/189.184375 THz 3.125GHz spacing";
               }
               enum "1584.63" {
                 description "1584.63 nm/189.187500 THz 3.125/6.25/12.5GHz spacing";
               }
               enum "1584.61" {
                 description "1584.61 nm/189.190625 THz 3.125GHz spacing";
               }
               enum "1584.58" {
                 description "1584.58 nm/189.193750 THz 3.125/6.25GHz spacing";
               }
               enum "1584.55" {
                 description "1584.55 nm/189.196875 THz 3.125GHz spacing";
               }
               enum "1584.53" {
                 description "1584.53 nm/189.200000 THz 3.125/6.25/12.5/100GHz spacing";
               }
               enum "1584.50" {
                 description "1584.50 nm/189.203125 THz 3.125GHz spacing";
               }
               enum "1584.47" {
                 description "1584.47 nm/189.206250 THz 3.125/6.25GHz spacing";
               }
               enum "1584.45" {
                 description "1584.45 nm/189.209375 THz 3.125GHz spacing";
               }
               enum "1584.42" {
                 description "1584.42 nm/189.212500 THz 3.125/6.25/12.5GHz spacing";
               }
               enum "1584.40" {
                 description "1584.40 nm/189.215625 THz 3.125GHz spacing";
               }
               enum "1584.37" {
                 description "1584.37 nm/189.218750 THz 3.125/6.25GHz spacing";
               }
               enum "1584.34" {
                 description "1584.34 nm/189.221875 THz 3.125GHz spacing";
               }
               enum "1584.32" {
                 description "1584.32 nm/189.225000 THz 3.125/6.25/12.5GHz spacing";
               }
               enum "1584.29" {
                 description "1584.29 nm/189.228125 THz 3.125GHz spacing";
               }
               enum "1584.27" {
                 description "1584.27 nm/189.231250 THz 3.125/6.25GHz spacing";
               }
               enum "1584.24" {
                 description "1584.24 nm/189.234375 THz 3.125GHz spacing";
               }
               enum "1584.21" {
                 description "1584.21 nm/189.237500 THz 3.125/6.25/12.5GHz spacing";
               }
               enum "1584.19" {
                 description "1584.19 nm/189.240625 THz 3.125GHz spacing";
               }
               enum "1584.16" {
                 description "1584.16 nm/189.243750 THz 3.125/6.25GHz spacing";
               }
               enum "1584.13" {
                 description "1584.13 nm/189.246875 THz 3.125GHz spacing";
               }
               enum "1584.11" {
                 description "1584.11 nm/189.250000 THz 3.125/6.25/12.5/50GHz spacing";
               }
               enum "1584.08" {
                 description "1584.08 nm/189.253125 THz 3.125GHz spacing";
               }
               enum "1584.06" {
                 description "1584.06 nm/189.256250 THz 3.125/6.25GHz spacing";
               }
               enum "1584.03" {
                 description "1584.03 nm/189.259375 THz 3.125GHz spacing";
               }
               enum "1584.00" {
                 description "1584.00 nm/189.262500 THz 3.125/6.25/12.5GHz spacing";
               }
               enum "1583.98" {
                 description "1583.98 nm/189.265625 THz 3.125GHz spacing";
               }
               enum "1583.95" {
                 description "1583.95 nm/189.268750 THz 3.125/6.25GHz spacing";
               }
               enum "1583.93" {
                 description "1583.93 nm/189.271875 THz 3.125GHz spacing";
               }
               enum "1583.90" {
                 description "1583.90 nm/189.275000 THz 3.125/6.25/12.5/75GHz spacing";
               }
               enum "1583.87" {
                 description "1583.87 nm/189.278125 THz 3.125GHz spacing";
               }
               enum "1583.85" {
                 description "1583.85 nm/189.281250 THz 3.125/6.25GHz spacing";
               }
               enum "1583.82" {
                 description "1583.82 nm/189.284375 THz 3.125GHz spacing";
               }
               enum "1583.79" {
                 description "1583.79 nm/189.287500 THz 3.125/6.25/12.5GHz spacing";
               }
               enum "1583.77" {
                 description "1583.77 nm/189.290625 THz 3.125GHz spacing";
               }
               enum "1583.74" {
                 description "1583.74 nm/189.293750 THz 3.125/6.25GHz spacing";
               }
               enum "1583.72" {
                 description "1583.72 nm/189.296875 THz 3.125GHz spacing";
               }
               enum "1583.69" {
                 description "1583.69 nm/189.300000 THz 3.125/6.25/12.5/50/75/100GHz spacing";
               }
               enum "1583.66" {
                 description "1583.66 nm/189.303125 THz 3.125GHz spacing";
               }
               enum "1583.64" {
                 description "1583.64 nm/189.306250 THz 3.125/6.25GHz spacing";
               }
               enum "1583.61" {
                 description "1583.61 nm/189.309375 THz 3.125GHz spacing";
               }
               enum "1583.59" {
                 description "1583.59 nm/189.312500 THz 3.125/6.25/12.5GHz spacing";
               }
               enum "1583.56" {
                 description "1583.56 nm/189.315625 THz 3.125GHz spacing";
               }
               enum "1583.53" {
                 description "1583.53 nm/189.318750 THz 3.125/6.25GHz spacing";
               }
               enum "1583.51" {
                 description "1583.51 nm/189.321875 THz 3.125GHz spacing";
               }
               enum "1583.48" {
                 description "1583.48 nm/189.325000 THz 3.125/6.25/12.5GHz spacing";
               }
               enum "1583.45" {
                 description "1583.45 nm/189.328125 THz 3.125GHz spacing";
               }
               enum "1583.43" {
                 description "1583.43 nm/189.331250 THz 3.125/6.25GHz spacing";
               }
               enum "1583.40" {
                 description "1583.40 nm/189.334375 THz 3.125GHz spacing";
               }
               enum "1583.38" {
                 description "1583.38 nm/189.337500 THz 3.125/6.25/12.5GHz spacing";
               }
               enum "1583.35" {
                 description "1583.35 nm/189.340625 THz 3.125GHz spacing";
               }
               enum "1583.32" {
                 description "1583.32 nm/189.343750 THz 3.125/6.25GHz spacing";
               }
               enum "1583.30" {
                 description "1583.30 nm/189.346875 THz 3.125GHz spacing";
               }
               enum "1583.27" {
                 description "1583.27 nm/189.350000 THz 3.125/6.25/12.5/50/75GHz spacing";
               }
               enum "1583.25" {
                 description "1583.25 nm/189.353125 THz 3.125GHz spacing";
               }
               enum "1583.22" {
                 description "1583.22 nm/189.356250 THz 3.125/6.25GHz spacing";
               }
               enum "1583.19" {
                 description "1583.19 nm/189.359375 THz 3.125GHz spacing";
               }
               enum "1583.17" {
                 description "1583.17 nm/189.362500 THz 3.125/6.25/12.5GHz spacing";
               }
               enum "1583.14" {
                 description "1583.14 nm/189.365625 THz 3.125GHz spacing";
               }
               enum "1583.11" {
                 description "1583.11 nm/189.368750 THz 3.125/6.25GHz spacing";
               }
               enum "1583.09" {
                 description "1583.09 nm/189.371875 THz 3.125GHz spacing";
               }
               enum "1583.06" {
                 description "1583.06 nm/189.375000 THz 3.125/6.25/12.5GHz spacing";
               }
               enum "1583.04" {
                 description "1583.04 nm/189.378125 THz 3.125GHz spacing";
               }
               enum "1583.01" {
                 description "1583.01 nm/189.381250 THz 3.125/6.25GHz spacing";
               }
               enum "1582.98" {
                 description "1582.98 nm/189.384375 THz 3.125GHz spacing";
               }
               enum "1582.96" {
                 description "1582.96 nm/189.387500 THz 3.125/6.25/12.5GHz spacing";
               }
               enum "1582.93" {
                 description "1582.93 nm/189.390625 THz 3.125GHz spacing";
               }
               enum "1582.91" {
                 description "1582.91 nm/189.393750 THz 3.125/6.25GHz spacing";
               }
               enum "1582.88" {
                 description "1582.88 nm/189.396875 THz 3.125GHz spacing";
               }
               enum "1582.85" {
                 description "1582.85 nm/189.400000 THz 3.125/6.25/12.5/100GHz spacing";
               }
               enum "1582.83" {
                 description "1582.83 nm/189.403125 THz 3.125GHz spacing";
               }
               enum "1582.80" {
                 description "1582.80 nm/189.406250 THz 3.125/6.25GHz spacing";
               }
               enum "1582.78" {
                 description "1582.78 nm/189.409375 THz 3.125GHz spacing";
               }
               enum "1582.75" {
                 description "1582.75 nm/189.412500 THz 3.125/6.25/12.5GHz spacing";
               }
               enum "1582.72" {
                 description "1582.72 nm/189.415625 THz 3.125GHz spacing";
               }
               enum "1582.70" {
                 description "1582.70 nm/189.418750 THz 3.125/6.25GHz spacing";
               }
               enum "1582.67" {
                 description "1582.67 nm/189.421875 THz 3.125GHz spacing";
               }
               enum "1582.64" {
                 description "1582.64 nm/189.425000 THz 3.125/6.25/12.5/75GHz spacing";
               }
               enum "1582.62" {
                 description "1582.62 nm/189.428125 THz 3.125GHz spacing";
               }
               enum "1582.59" {
                 description "1582.59 nm/189.431250 THz 3.125/6.25GHz spacing";
               }
               enum "1582.57" {
                 description "1582.57 nm/189.434375 THz 3.125GHz spacing";
               }
               enum "1582.54" {
                 description "1582.54 nm/189.437500 THz 3.125/6.25/12.5GHz spacing";
               }
               enum "1582.51" {
                 description "1582.51 nm/189.440625 THz 3.125GHz spacing";
               }
               enum "1582.49" {
                 description "1582.49 nm/189.443750 THz 3.125/6.25GHz spacing";
               }
               enum "1582.46" {
                 description "1582.46 nm/189.446875 THz 3.125GHz spacing";
               }
               enum "1582.44" {
                 description "1582.44 nm/189.450000 THz 3.125/6.25/12.5/50GHz spacing";
               }
               enum "1582.41" {
                 description "1582.41 nm/189.453125 THz 3.125GHz spacing";
               }
               enum "1582.38" {
                 description "1582.38 nm/189.456250 THz 3.125/6.25GHz spacing";
               }
               enum "1582.36" {
                 description "1582.36 nm/189.459375 THz 3.125GHz spacing";
               }
               enum "1582.33" {
                 description "1582.33 nm/189.462500 THz 3.125/6.25/12.5GHz spacing";
               }
               enum "1582.31" {
                 description "1582.31 nm/189.465625 THz 3.125GHz spacing";
               }
               enum "1582.28" {
                 description "1582.28 nm/189.468750 THz 3.125/6.25GHz spacing";
               }
               enum "1582.25" {
                 description "1582.25 nm/189.471875 THz 3.125GHz spacing";
               }
               enum "1582.23" {
                 description "1582.23 nm/189.475000 THz 3.125/6.25/12.5GHz spacing";
               }
               enum "1582.20" {
                 description "1582.20 nm/189.478125 THz 3.125GHz spacing";
               }
               enum "1582.17" {
                 description "1582.17 nm/189.481250 THz 3.125/6.25GHz spacing";
               }
               enum "1582.15" {
                 description "1582.15 nm/189.484375 THz 3.125GHz spacing";
               }
               enum "1582.12" {
                 description "1582.12 nm/189.487500 THz 3.125/6.25/12.5GHz spacing";
               }
               enum "1582.10" {
                 description "1582.10 nm/189.490625 THz 3.125GHz spacing";
               }
               enum "1582.07" {
                 description "1582.07 nm/189.493750 THz 3.125/6.25GHz spacing";
               }
               enum "1582.04" {
                 description "1582.04 nm/189.496875 THz 3.125GHz spacing";
               }
               enum "1582.02" {
                 description "1582.02 nm/189.500000 THz 3.125/6.25/12.5/100GHz spacing";
               }
               enum "1581.99" {
                 description "1581.99 nm/189.503125 THz 3.125GHz spacing";
               }
               enum "1581.97" {
                 description "1581.97 nm/189.506250 THz 3.125/6.25GHz spacing";
               }
               enum "1581.94" {
                 description "1581.94 nm/189.509375 THz 3.125GHz spacing";
               }
               enum "1581.91" {
                 description "1581.91 nm/189.512500 THz 3.125/6.25/12.5GHz spacing";
               }
               enum "1581.89" {
                 description "1581.89 nm/189.515625 THz 3.125GHz spacing";
               }
               enum "1581.86" {
                 description "1581.86 nm/189.518750 THz 3.125/6.25GHz spacing";
               }
               enum "1581.84" {
                 description "1581.84 nm/189.521875 THz 3.125GHz spacing";
               }
               enum "1581.81" {
                 description "1581.81 nm/189.525000 THz 3.125/6.25/12.5GHz spacing";
               }
               enum "1581.78" {
                 description "1581.78 nm/189.528125 THz 3.125GHz spacing";
               }
               enum "1581.76" {
                 description "1581.76 nm/189.531250 THz 3.125/6.25GHz spacing";
               }
               enum "1581.73" {
                 description "1581.73 nm/189.534375 THz 3.125GHz spacing";
               }
               enum "1581.71" {
                 description "1581.71 nm/189.537500 THz 3.125/6.25/12.5GHz spacing";
               }
               enum "1581.68" {
                 description "1581.68 nm/189.540625 THz 3.125GHz spacing";
               }
               enum "1581.65" {
                 description "1581.65 nm/189.543750 THz 3.125/6.25GHz spacing";
               }
               enum "1581.63" {
                 description "1581.63 nm/189.546875 THz 3.125GHz spacing";
               }
               enum "1581.60" {
                 description "1581.60 nm/189.550000 THz 3.125/6.25/12.5/50GHz spacing";
               }
               enum "1581.57" {
                 description "1581.57 nm/189.553125 THz 3.125GHz spacing";
               }
               enum "1581.55" {
                 description "1581.55 nm/189.556250 THz 3.125/6.25GHz spacing";
               }
               enum "1581.52" {
                 description "1581.52 nm/189.559375 THz 3.125GHz spacing";
               }
               enum "1581.50" {
                 description "1581.50 nm/189.562500 THz 3.125/6.25/12.5GHz spacing";
               }
               enum "1581.47" {
                 description "1581.47 nm/189.565625 THz 3.125GHz spacing";
               }
               enum "1581.44" {
                 description "1581.44 nm/189.568750 THz 3.125/6.25GHz spacing";
               }
               enum "1581.42" {
                 description "1581.42 nm/189.571875 THz 3.125GHz spacing";
               }
               enum "1581.39" {
                 description "1581.39 nm/189.575000 THz 3.125/6.25/12.5/75GHz spacing";
               }
               enum "1581.37" {
                 description "1581.37 nm/189.578125 THz 3.125GHz spacing";
               }
               enum "1581.34" {
                 description "1581.34 nm/189.581250 THz 3.125/6.25GHz spacing";
               }
               enum "1581.31" {
                 description "1581.31 nm/189.584375 THz 3.125GHz spacing";
               }
               enum "1581.29" {
                 description "1581.29 nm/189.587500 THz 3.125/6.25/12.5GHz spacing";
               }
               enum "1581.26" {
                 description "1581.26 nm/189.590625 THz 3.125GHz spacing";
               }
               enum "1581.24" {
                 description "1581.24 nm/189.593750 THz 3.125/6.25GHz spacing";
               }
               enum "1581.21" {
                 description "1581.21 nm/189.596875 THz 3.125GHz spacing";
               }
               enum "1581.18" {
                 description "1581.18 nm/189.600000 THz 3.125/6.25/12.5/50/75/100GHz spacing";
               }
               enum "1581.16" {
                 description "1581.16 nm/189.603125 THz 3.125GHz spacing";
               }
               enum "1581.13" {
                 description "1581.13 nm/189.606250 THz 3.125/6.25GHz spacing";
               }
               enum "1581.11" {
                 description "1581.11 nm/189.609375 THz 3.125GHz spacing";
               }
               enum "1581.08" {
                 description "1581.08 nm/189.612500 THz 3.125/6.25/12.5GHz spacing";
               }
               enum "1581.05" {
                 description "1581.05 nm/189.615625 THz 3.125GHz spacing";
               }
               enum "1581.03" {
                 description "1581.03 nm/189.618750 THz 3.125/6.25GHz spacing";
               }
               enum "1581.00" {
                 description "1581.00 nm/189.621875 THz 3.125GHz spacing";
               }
               enum "1580.98" {
                 description "1580.98 nm/189.625000 THz 3.125/6.25/12.5GHz spacing";
               }
               enum "1580.95" {
                 description "1580.95 nm/189.628125 THz 3.125GHz spacing";
               }
               enum "1580.92" {
                 description "1580.92 nm/189.631250 THz 3.125/6.25GHz spacing";
               }
               enum "1580.90" {
                 description "1580.90 nm/189.634375 THz 3.125GHz spacing";
               }
               enum "1580.87" {
                 description "1580.87 nm/189.637500 THz 3.125/6.25/12.5GHz spacing";
               }
               enum "1580.85" {
                 description "1580.85 nm/189.640625 THz 3.125GHz spacing";
               }
               enum "1580.82" {
                 description "1580.82 nm/189.643750 THz 3.125/6.25GHz spacing";
               }
               enum "1580.79" {
                 description "1580.79 nm/189.646875 THz 3.125GHz spacing";
               }
               enum "1580.77" {
                 description "1580.77 nm/189.650000 THz 3.125/6.25/12.5/50/75GHz spacing";
               }
               enum "1580.74" {
                 description "1580.74 nm/189.653125 THz 3.125GHz spacing";
               }
               enum "1580.71" {
                 description "1580.71 nm/189.656250 THz 3.125/6.25GHz spacing";
               }
               enum "1580.69" {
                 description "1580.69 nm/189.659375 THz 3.125GHz spacing";
               }
               enum "1580.66" {
                 description "1580.66 nm/189.662500 THz 3.125/6.25/12.5GHz spacing";
               }
               enum "1580.64" {
                 description "1580.64 nm/189.665625 THz 3.125GHz spacing";
               }
               enum "1580.61" {
                 description "1580.61 nm/189.668750 THz 3.125/6.25GHz spacing";
               }
               enum "1580.58" {
                 description "1580.58 nm/189.671875 THz 3.125GHz spacing";
               }
               enum "1580.56" {
                 description "1580.56 nm/189.675000 THz 3.125/6.25/12.5GHz spacing";
               }
               enum "1580.53" {
                 description "1580.53 nm/189.678125 THz 3.125GHz spacing";
               }
               enum "1580.51" {
                 description "1580.51 nm/189.681250 THz 3.125/6.25GHz spacing";
               }
               enum "1580.48" {
                 description "1580.48 nm/189.684375 THz 3.125GHz spacing";
               }
               enum "1580.45" {
                 description "1580.45 nm/189.687500 THz 3.125/6.25/12.5GHz spacing";
               }
               enum "1580.43" {
                 description "1580.43 nm/189.690625 THz 3.125GHz spacing";
               }
               enum "1580.40" {
                 description "1580.40 nm/189.693750 THz 3.125/6.25GHz spacing";
               }
               enum "1580.38" {
                 description "1580.38 nm/189.696875 THz 3.125GHz spacing";
               }
               enum "1580.35" {
                 description "1580.35 nm/189.700000 THz 3.125/6.25/12.5/100GHz spacing";
               }
               enum "1580.32" {
                 description "1580.32 nm/189.703125 THz 3.125GHz spacing";
               }
               enum "1580.30" {
                 description "1580.30 nm/189.706250 THz 3.125/6.25GHz spacing";
               }
               enum "1580.27" {
                 description "1580.27 nm/189.709375 THz 3.125GHz spacing";
               }
               enum "1580.25" {
                 description "1580.25 nm/189.712500 THz 3.125/6.25/12.5GHz spacing";
               }
               enum "1580.22" {
                 description "1580.22 nm/189.715625 THz 3.125GHz spacing";
               }
               enum "1580.19" {
                 description "1580.19 nm/189.718750 THz 3.125/6.25GHz spacing";
               }
               enum "1580.17" {
                 description "1580.17 nm/189.721875 THz 3.125GHz spacing";
               }
               enum "1580.14" {
                 description "1580.14 nm/189.725000 THz 3.125/6.25/12.5/75GHz spacing";
               }
               enum "1580.12" {
                 description "1580.12 nm/189.728125 THz 3.125GHz spacing";
               }
               enum "1580.09" {
                 description "1580.09 nm/189.731250 THz 3.125/6.25GHz spacing";
               }
               enum "1580.06" {
                 description "1580.06 nm/189.734375 THz 3.125GHz spacing";
               }
               enum "1580.04" {
                 description "1580.04 nm/189.737500 THz 3.125/6.25/12.5GHz spacing";
               }
               enum "1580.01" {
                 description "1580.01 nm/189.740625 THz 3.125GHz spacing";
               }
               enum "1579.99" {
                 description "1579.99 nm/189.743750 THz 3.125/6.25GHz spacing";
               }
               enum "1579.96" {
                 description "1579.96 nm/189.746875 THz 3.125GHz spacing";
               }
               enum "1579.93" {
                 description "1579.93 nm/189.750000 THz 3.125/6.25/12.5/50GHz spacing";
               }
               enum "1579.91" {
                 description "1579.91 nm/189.753125 THz 3.125GHz spacing";
               }
               enum "1579.88" {
                 description "1579.88 nm/189.756250 THz 3.125/6.25GHz spacing";
               }
               enum "1579.86" {
                 description "1579.86 nm/189.759375 THz 3.125GHz spacing";
               }
               enum "1579.83" {
                 description "1579.83 nm/189.762500 THz 3.125/6.25/12.5GHz spacing";
               }
               enum "1579.80" {
                 description "1579.80 nm/189.765625 THz 3.125GHz spacing";
               }
               enum "1579.78" {
                 description "1579.78 nm/189.768750 THz 3.125/6.25GHz spacing";
               }
               enum "1579.75" {
                 description "1579.75 nm/189.771875 THz 3.125GHz spacing";
               }
               enum "1579.73" {
                 description "1579.73 nm/189.775000 THz 3.125/6.25/12.5GHz spacing";
               }
               enum "1579.70" {
                 description "1579.70 nm/189.778125 THz 3.125GHz spacing";
               }
               enum "1579.67" {
                 description "1579.67 nm/189.781250 THz 3.125/6.25GHz spacing";
               }
               enum "1579.65" {
                 description "1579.65 nm/189.784375 THz 3.125GHz spacing";
               }
               enum "1579.62" {
                 description "1579.62 nm/189.787500 THz 3.125/6.25/12.5GHz spacing";
               }
               enum "1579.60" {
                 description "1579.60 nm/189.790625 THz 3.125GHz spacing";
               }
               enum "1579.57" {
                 description "1579.57 nm/189.793750 THz 3.125/6.25GHz spacing";
               }
               enum "1579.54" {
                 description "1579.54 nm/189.796875 THz 3.125GHz spacing";
               }
               enum "1579.52" {
                 description "1579.52 nm/189.800000 THz 3.125/6.25/12.5/100GHz spacing";
               }
               enum "1579.49" {
                 description "1579.49 nm/189.803125 THz 3.125GHz spacing";
               }
               enum "1579.47" {
                 description "1579.47 nm/189.806250 THz 3.125/6.25GHz spacing";
               }
               enum "1579.44" {
                 description "1579.44 nm/189.809375 THz 3.125GHz spacing";
               }
               enum "1579.41" {
                 description "1579.41 nm/189.812500 THz 3.125/6.25/12.5GHz spacing";
               }
               enum "1579.39" {
                 description "1579.39 nm/189.815625 THz 3.125GHz spacing";
               }
               enum "1579.36" {
                 description "1579.36 nm/189.818750 THz 3.125/6.25GHz spacing";
               }
               enum "1579.34" {
                 description "1579.34 nm/189.821875 THz 3.125GHz spacing";
               }
               enum "1579.31" {
                 description "1579.31 nm/189.825000 THz 3.125/6.25/12.5GHz spacing";
               }
               enum "1579.28" {
                 description "1579.28 nm/189.828125 THz 3.125GHz spacing";
               }
               enum "1579.26" {
                 description "1579.26 nm/189.831250 THz 3.125/6.25GHz spacing";
               }
               enum "1579.23" {
                 description "1579.23 nm/189.834375 THz 3.125GHz spacing";
               }
               enum "1579.21" {
                 description "1579.21 nm/189.837500 THz 3.125/6.25/12.5GHz spacing";
               }
               enum "1579.18" {
                 description "1579.18 nm/189.840625 THz 3.125GHz spacing";
               }
               enum "1579.15" {
                 description "1579.15 nm/189.843750 THz 3.125/6.25GHz spacing";
               }
               enum "1579.13" {
                 description "1579.13 nm/189.846875 THz 3.125GHz spacing";
               }
               enum "1579.10" {
                 description "1579.10 nm/189.850000 THz 3.125/6.25/12.5/50GHz spacing";
               }
               enum "1579.08" {
                 description "1579.08 nm/189.853125 THz 3.125GHz spacing";
               }
               enum "1579.05" {
                 description "1579.05 nm/189.856250 THz 3.125/6.25GHz spacing";
               }
               enum "1579.02" {
                 description "1579.02 nm/189.859375 THz 3.125GHz spacing";
               }
               enum "1579.00" {
                 description "1579.00 nm/189.862500 THz 3.125/6.25/12.5GHz spacing";
               }
               enum "1578.97" {
                 description "1578.97 nm/189.865625 THz 3.125GHz spacing";
               }
               enum "1578.95" {
                 description "1578.95 nm/189.868750 THz 3.125/6.25GHz spacing";
               }
               enum "1578.92" {
                 description "1578.92 nm/189.871875 THz 3.125GHz spacing";
               }
               enum "1578.89" {
                 description "1578.89 nm/189.875000 THz 3.125/6.25/12.5/75GHz spacing";
               }
               enum "1578.87" {
                 description "1578.87 nm/189.878125 THz 3.125GHz spacing";
               }
               enum "1578.84" {
                 description "1578.84 nm/189.881250 THz 3.125/6.25GHz spacing";
               }
               enum "1578.82" {
                 description "1578.82 nm/189.884375 THz 3.125GHz spacing";
               }
               enum "1578.79" {
                 description "1578.79 nm/189.887500 THz 3.125/6.25/12.5GHz spacing";
               }
               enum "1578.76" {
                 description "1578.76 nm/189.890625 THz 3.125GHz spacing";
               }
               enum "1578.74" {
                 description "1578.74 nm/189.893750 THz 3.125/6.25GHz spacing";
               }
               enum "1578.71" {
                 description "1578.71 nm/189.896875 THz 3.125GHz spacing";
               }
               enum "1578.69" {
                 description "1578.69 nm/189.900000 THz 3.125/6.25/12.5/50/75/100GHz spacing";
               }
               enum "1578.66" {
                 description "1578.66 nm/189.903125 THz 3.125GHz spacing";
               }
               enum "1578.63" {
                 description "1578.63 nm/189.906250 THz 3.125/6.25GHz spacing";
               }
               enum "1578.61" {
                 description "1578.61 nm/189.909375 THz 3.125GHz spacing";
               }
               enum "1578.58" {
                 description "1578.58 nm/189.912500 THz 3.125/6.25/12.5GHz spacing";
               }
               enum "1578.56" {
                 description "1578.56 nm/189.915625 THz 3.125GHz spacing";
               }
               enum "1578.53" {
                 description "1578.53 nm/189.918750 THz 3.125/6.25GHz spacing";
               }
               enum "1578.50" {
                 description "1578.50 nm/189.921875 THz 3.125GHz spacing";
               }
               enum "1578.48" {
                 description "1578.48 nm/189.925000 THz 3.125/6.25/12.5GHz spacing";
               }
               enum "1578.45" {
                 description "1578.45 nm/189.928125 THz 3.125GHz spacing";
               }
               enum "1578.43" {
                 description "1578.43 nm/189.931250 THz 3.125/6.25GHz spacing";
               }
               enum "1578.40" {
                 description "1578.40 nm/189.934375 THz 3.125GHz spacing";
               }
               enum "1578.37" {
                 description "1578.37 nm/189.937500 THz 3.125/6.25/12.5GHz spacing";
               }
               enum "1578.35" {
                 description "1578.35 nm/189.940625 THz 3.125GHz spacing";
               }
               enum "1578.32" {
                 description "1578.32 nm/189.943750 THz 3.125/6.25GHz spacing";
               }
               enum "1578.30" {
                 description "1578.30 nm/189.946875 THz 3.125GHz spacing";
               }
               enum "1578.27" {
                 description "1578.27 nm/189.950000 THz 3.125/6.25/12.5/50/75GHz spacing";
               }
               enum "1578.24" {
                 description "1578.24 nm/189.953125 THz 3.125GHz spacing";
               }
               enum "1578.22" {
                 description "1578.22 nm/189.956250 THz 3.125/6.25GHz spacing";
               }
               enum "1578.19" {
                 description "1578.19 nm/189.959375 THz 3.125GHz spacing";
               }
               enum "1578.17" {
                 description "1578.17 nm/189.962500 THz 3.125/6.25/12.5GHz spacing";
               }
               enum "1578.14" {
                 description "1578.14 nm/189.965625 THz 3.125GHz spacing";
               }
               enum "1578.11" {
                 description "1578.11 nm/189.968750 THz 3.125/6.25GHz spacing";
               }
               enum "1578.09" {
                 description "1578.09 nm/189.971875 THz 3.125GHz spacing";
               }
               enum "1578.06" {
                 description "1578.06 nm/189.975000 THz 3.125/6.25/12.5GHz spacing";
               }
               enum "1578.04" {
                 description "1578.04 nm/189.978125 THz 3.125GHz spacing";
               }
               enum "1578.01" {
                 description "1578.01 nm/189.981250 THz 3.125/6.25GHz spacing";
               }
               enum "1577.98" {
                 description "1577.98 nm/189.984375 THz 3.125GHz spacing";
               }
               enum "1577.96" {
                 description "1577.96 nm/189.987500 THz 3.125/6.25/12.5GHz spacing";
               }
               enum "1577.93" {
                 description "1577.93 nm/189.990625 THz 3.125GHz spacing";
               }
               enum "1577.91" {
                 description "1577.91 nm/189.993750 THz 3.125/6.25GHz spacing";
               }
               enum "1577.88" {
                 description "1577.88 nm/189.996875 THz 3.125GHz spacing";
               }
               enum "1577.86" {
                 description "1577.86 nm/190.000000 THz 3.125/6.25/12.5/100GHz spacing";
               }
               enum "1577.83" {
                 description "1577.83 nm/190.003125 THz 3.125GHz spacing";
               }
               enum "1577.80" {
                 description "1577.80 nm/190.006250 THz 3.125/6.25GHz spacing";
               }
               enum "1577.78" {
                 description "1577.78 nm/190.009375 THz 3.125GHz spacing";
               }
               enum "1577.75" {
                 description "1577.75 nm/190.012500 THz 3.125/6.25/12.5GHz spacing";
               }
               enum "1577.73" {
                 description "1577.73 nm/190.015625 THz 3.125GHz spacing";
               }
               enum "1577.70" {
                 description "1577.70 nm/190.018750 THz 3.125/6.25GHz spacing";
               }
               enum "1577.67" {
                 description "1577.67 nm/190.021875 THz 3.125GHz spacing";
               }
               enum "1577.65" {
                 description "1577.65 nm/190.025000 THz 3.125/6.25/12.5/75GHz spacing";
               }
               enum "1577.62" {
                 description "1577.62 nm/190.028125 THz 3.125GHz spacing";
               }
               enum "1577.60" {
                 description "1577.60 nm/190.031250 THz 3.125/6.25GHz spacing";
               }
               enum "1577.57" {
                 description "1577.57 nm/190.034375 THz 3.125GHz spacing";
               }
               enum "1577.54" {
                 description "1577.54 nm/190.037500 THz 3.125/6.25/12.5GHz spacing";
               }
               enum "1577.52" {
                 description "1577.52 nm/190.040625 THz 3.125GHz spacing";
               }
               enum "1577.49" {
                 description "1577.49 nm/190.043750 THz 3.125/6.25GHz spacing";
               }
               enum "1577.47" {
                 description "1577.47 nm/190.046875 THz 3.125GHz spacing";
               }
               enum "1577.44" {
                 description "1577.44 nm/190.050000 THz 3.125/6.25/12.5/50GHz spacing";
               }
               enum "1577.41" {
                 description "1577.41 nm/190.053125 THz 3.125GHz spacing";
               }
               enum "1577.39" {
                 description "1577.39 nm/190.056250 THz 3.125/6.25GHz spacing";
               }
               enum "1577.36" {
                 description "1577.36 nm/190.059375 THz 3.125GHz spacing";
               }
               enum "1577.34" {
                 description "1577.34 nm/190.062500 THz 3.125/6.25/12.5GHz spacing";
               }
               enum "1577.31" {
                 description "1577.31 nm/190.065625 THz 3.125GHz spacing";
               }
               enum "1577.28" {
                 description "1577.28 nm/190.068750 THz 3.125/6.25GHz spacing";
               }
               enum "1577.26" {
                 description "1577.26 nm/190.071875 THz 3.125GHz spacing";
               }
               enum "1577.23" {
                 description "1577.23 nm/190.075000 THz 3.125/6.25/12.5GHz spacing";
               }
               enum "1577.21" {
                 description "1577.21 nm/190.078125 THz 3.125GHz spacing";
               }
               enum "1577.18" {
                 description "1577.18 nm/190.081250 THz 3.125/6.25GHz spacing";
               }
               enum "1577.15" {
                 description "1577.15 nm/190.084375 THz 3.125GHz spacing";
               }
               enum "1577.13" {
                 description "1577.13 nm/190.087500 THz 3.125/6.25/12.5GHz spacing";
               }
               enum "1577.10" {
                 description "1577.10 nm/190.090625 THz 3.125GHz spacing";
               }
               enum "1577.08" {
                 description "1577.08 nm/190.093750 THz 3.125/6.25GHz spacing";
               }
               enum "1577.05" {
                 description "1577.05 nm/190.096875 THz 3.125GHz spacing";
               }
               enum "1577.03" {
                 description "1577.03 nm/190.100000 THz 3.125/6.25/12.5/100GHz spacing";
               }
               enum "1577.00" {
                 description "1577.00 nm/190.103125 THz 3.125GHz spacing";
               }
               enum "1576.97" {
                 description "1576.97 nm/190.106250 THz 3.125/6.25GHz spacing";
               }
               enum "1576.95" {
                 description "1576.95 nm/190.109375 THz 3.125GHz spacing";
               }
               enum "1576.92" {
                 description "1576.92 nm/190.112500 THz 3.125/6.25/12.5GHz spacing";
               }
               enum "1576.90" {
                 description "1576.90 nm/190.115625 THz 3.125GHz spacing";
               }
               enum "1576.87" {
                 description "1576.87 nm/190.118750 THz 3.125/6.25GHz spacing";
               }
               enum "1576.84" {
                 description "1576.84 nm/190.121875 THz 3.125GHz spacing";
               }
               enum "1576.82" {
                 description "1576.82 nm/190.125000 THz 3.125/6.25/12.5GHz spacing";
               }
               enum "1576.79" {
                 description "1576.79 nm/190.128125 THz 3.125GHz spacing";
               }
               enum "1576.77" {
                 description "1576.77 nm/190.131250 THz 3.125/6.25GHz spacing";
               }
               enum "1576.74" {
                 description "1576.74 nm/190.134375 THz 3.125GHz spacing";
               }
               enum "1576.71" {
                 description "1576.71 nm/190.137500 THz 3.125/6.25/12.5GHz spacing";
               }
               enum "1576.69" {
                 description "1576.69 nm/190.140625 THz 3.125GHz spacing";
               }
               enum "1576.66" {
                 description "1576.66 nm/190.143750 THz 3.125/6.25GHz spacing";
               }
               enum "1576.64" {
                 description "1576.64 nm/190.146875 THz 3.125GHz spacing";
               }
               enum "1576.61" {
                 description "1576.61 nm/190.150000 THz 3.125/6.25/12.5/50GHz spacing";
               }
               enum "1576.58" {
                 description "1576.58 nm/190.153125 THz 3.125GHz spacing";
               }
               enum "1576.56" {
                 description "1576.56 nm/190.156250 THz 3.125/6.25GHz spacing";
               }
               enum "1576.53" {
                 description "1576.53 nm/190.159375 THz 3.125GHz spacing";
               }
               enum "1576.51" {
                 description "1576.51 nm/190.162500 THz 3.125/6.25/12.5GHz spacing";
               }
               enum "1576.48" {
                 description "1576.48 nm/190.165625 THz 3.125GHz spacing";
               }
               enum "1576.45" {
                 description "1576.45 nm/190.168750 THz 3.125/6.25GHz spacing";
               }
               enum "1576.43" {
                 description "1576.43 nm/190.171875 THz 3.125GHz spacing";
               }
               enum "1576.40" {
                 description "1576.40 nm/190.175000 THz 3.125/6.25/12.5/75GHz spacing";
               }
               enum "1576.38" {
                 description "1576.38 nm/190.178125 THz 3.125GHz spacing";
               }
               enum "1576.35" {
                 description "1576.35 nm/190.181250 THz 3.125/6.25GHz spacing";
               }
               enum "1576.33" {
                 description "1576.33 nm/190.184375 THz 3.125GHz spacing";
               }
               enum "1576.30" {
                 description "1576.30 nm/190.187500 THz 3.125/6.25/12.5GHz spacing";
               }
               enum "1576.27" {
                 description "1576.27 nm/190.190625 THz 3.125GHz spacing";
               }
               enum "1576.25" {
                 description "1576.25 nm/190.193750 THz 3.125/6.25GHz spacing";
               }
               enum "1576.22" {
                 description "1576.22 nm/190.196875 THz 3.125GHz spacing";
               }
               enum "1576.20" {
                 description "1576.20 nm/190.200000 THz 3.125/6.25/12.5/50/75/100GHz spacing";
               }
               enum "1576.17" {
                 description "1576.17 nm/190.203125 THz 3.125GHz spacing";
               }
               enum "1576.14" {
                 description "1576.14 nm/190.206250 THz 3.125/6.25GHz spacing";
               }
               enum "1576.12" {
                 description "1576.12 nm/190.209375 THz 3.125GHz spacing";
               }
               enum "1576.09" {
                 description "1576.09 nm/190.212500 THz 3.125/6.25/12.5GHz spacing";
               }
               enum "1576.07" {
                 description "1576.07 nm/190.215625 THz 3.125GHz spacing";
               }
               enum "1576.04" {
                 description "1576.04 nm/190.218750 THz 3.125/6.25GHz spacing";
               }
               enum "1576.01" {
                 description "1576.01 nm/190.221875 THz 3.125GHz spacing";
               }
               enum "1575.99" {
                 description "1575.99 nm/190.225000 THz 3.125/6.25/12.5GHz spacing";
               }
               enum "1575.96" {
                 description "1575.96 nm/190.228125 THz 3.125GHz spacing";
               }
               enum "1575.94" {
                 description "1575.94 nm/190.231250 THz 3.125/6.25GHz spacing";
               }
               enum "1575.91" {
                 description "1575.91 nm/190.234375 THz 3.125GHz spacing";
               }
               enum "1575.89" {
                 description "1575.89 nm/190.237500 THz 3.125/6.25/12.5GHz spacing";
               }
               enum "1575.86" {
                 description "1575.86 nm/190.240625 THz 3.125GHz spacing";
               }
               enum "1575.83" {
                 description "1575.83 nm/190.243750 THz 3.125/6.25GHz spacing";
               }
               enum "1575.81" {
                 description "1575.81 nm/190.246875 THz 3.125GHz spacing";
               }
               enum "1575.78" {
                 description "1575.78 nm/190.250000 THz 3.125/6.25/12.5/50/75GHz spacing";
               }
               enum "1575.76" {
                 description "1575.76 nm/190.253125 THz 3.125GHz spacing";
               }
               enum "1575.73" {
                 description "1575.73 nm/190.256250 THz 3.125/6.25GHz spacing";
               }
               enum "1575.70" {
                 description "1575.70 nm/190.259375 THz 3.125GHz spacing";
               }
               enum "1575.68" {
                 description "1575.68 nm/190.262500 THz 3.125/6.25/12.5GHz spacing";
               }
               enum "1575.65" {
                 description "1575.65 nm/190.265625 THz 3.125GHz spacing";
               }
               enum "1575.63" {
                 description "1575.63 nm/190.268750 THz 3.125/6.25GHz spacing";
               }
               enum "1575.60" {
                 description "1575.60 nm/190.271875 THz 3.125GHz spacing";
               }
               enum "1575.57" {
                 description "1575.57 nm/190.275000 THz 3.125/6.25/12.5GHz spacing";
               }
               enum "1575.55" {
                 description "1575.55 nm/190.278125 THz 3.125GHz spacing";
               }
               enum "1575.52" {
                 description "1575.52 nm/190.281250 THz 3.125/6.25GHz spacing";
               }
               enum "1575.50" {
                 description "1575.50 nm/190.284375 THz 3.125GHz spacing";
               }
               enum "1575.47" {
                 description "1575.47 nm/190.287500 THz 3.125/6.25/12.5GHz spacing";
               }
               enum "1575.45" {
                 description "1575.45 nm/190.290625 THz 3.125GHz spacing";
               }
               enum "1575.42" {
                 description "1575.42 nm/190.293750 THz 3.125/6.25GHz spacing";
               }
               enum "1575.39" {
                 description "1575.39 nm/190.296875 THz 3.125GHz spacing";
               }
               enum "1575.37" {
                 description "1575.37 nm/190.300000 THz 3.125/6.25/12.5/100GHz spacing";
               }
               enum "1575.34" {
                 description "1575.34 nm/190.303125 THz 3.125GHz spacing";
               }
               enum "1575.32" {
                 description "1575.32 nm/190.306250 THz 3.125/6.25GHz spacing";
               }
               enum "1575.29" {
                 description "1575.29 nm/190.309375 THz 3.125GHz spacing";
               }
               enum "1575.26" {
                 description "1575.26 nm/190.312500 THz 3.125/6.25/12.5GHz spacing";
               }
               enum "1575.24" {
                 description "1575.24 nm/190.315625 THz 3.125GHz spacing";
               }
               enum "1575.21" {
                 description "1575.21 nm/190.318750 THz 3.125/6.25GHz spacing";
               }
               enum "1575.19" {
                 description "1575.19 nm/190.321875 THz 3.125GHz spacing";
               }
               enum "1575.16" {
                 description "1575.16 nm/190.325000 THz 3.125/6.25/12.5/75GHz spacing";
               }
               enum "1575.13" {
                 description "1575.13 nm/190.328125 THz 3.125GHz spacing";
               }
               enum "1575.11" {
                 description "1575.11 nm/190.331250 THz 3.125/6.25GHz spacing";
               }
               enum "1575.08" {
                 description "1575.08 nm/190.334375 THz 3.125GHz spacing";
               }
               enum "1575.06" {
                 description "1575.06 nm/190.337500 THz 3.125/6.25/12.5GHz spacing";
               }
               enum "1575.03" {
                 description "1575.03 nm/190.340625 THz 3.125GHz spacing";
               }
               enum "1575.01" {
                 description "1575.01 nm/190.343750 THz 3.125/6.25GHz spacing";
               }
               enum "1574.98" {
                 description "1574.98 nm/190.346875 THz 3.125GHz spacing";
               }
               enum "1574.95" {
                 description "1574.95 nm/190.350000 THz 3.125/6.25/12.5/50GHz spacing";
               }
               enum "1574.93" {
                 description "1574.93 nm/190.353125 THz 3.125GHz spacing";
               }
               enum "1574.90" {
                 description "1574.90 nm/190.356250 THz 3.125/6.25GHz spacing";
               }
               enum "1574.88" {
                 description "1574.88 nm/190.359375 THz 3.125GHz spacing";
               }
               enum "1574.85" {
                 description "1574.85 nm/190.362500 THz 3.125/6.25/12.5GHz spacing";
               }
               enum "1574.82" {
                 description "1574.82 nm/190.365625 THz 3.125GHz spacing";
               }
               enum "1574.80" {
                 description "1574.80 nm/190.368750 THz 3.125/6.25GHz spacing";
               }
               enum "1574.77" {
                 description "1574.77 nm/190.371875 THz 3.125GHz spacing";
               }
               enum "1574.75" {
                 description "1574.75 nm/190.375000 THz 3.125/6.25/12.5GHz spacing";
               }
               enum "1574.72" {
                 description "1574.72 nm/190.378125 THz 3.125GHz spacing";
               }
               enum "1574.70" {
                 description "1574.70 nm/190.381250 THz 3.125/6.25GHz spacing";
               }
               enum "1574.67" {
                 description "1574.67 nm/190.384375 THz 3.125GHz spacing";
               }
               enum "1574.64" {
                 description "1574.64 nm/190.387500 THz 3.125/6.25/12.5GHz spacing";
               }
               enum "1574.62" {
                 description "1574.62 nm/190.390625 THz 3.125GHz spacing";
               }
               enum "1574.59" {
                 description "1574.59 nm/190.393750 THz 3.125/6.25GHz spacing";
               }
               enum "1574.57" {
                 description "1574.57 nm/190.396875 THz 3.125GHz spacing";
               }
               enum "1574.54" {
                 description "1574.54 nm/190.400000 THz 3.125/6.25/12.5/100GHz spacing";
               }
               enum "1574.51" {
                 description "1574.51 nm/190.403125 THz 3.125GHz spacing";
               }
               enum "1574.49" {
                 description "1574.49 nm/190.406250 THz 3.125/6.25GHz spacing";
               }
               enum "1574.46" {
                 description "1574.46 nm/190.409375 THz 3.125GHz spacing";
               }
               enum "1574.44" {
                 description "1574.44 nm/190.412500 THz 3.125/6.25/12.5GHz spacing";
               }
               enum "1574.41" {
                 description "1574.41 nm/190.415625 THz 3.125GHz spacing";
               }
               enum "1574.39" {
                 description "1574.39 nm/190.418750 THz 3.125/6.25GHz spacing";
               }
               enum "1574.36" {
                 description "1574.36 nm/190.421875 THz 3.125GHz spacing";
               }
               enum "1574.33" {
                 description "1574.33 nm/190.425000 THz 3.125/6.25/12.5GHz spacing";
               }
               enum "1574.31" {
                 description "1574.31 nm/190.428125 THz 3.125GHz spacing";
               }
               enum "1574.28" {
                 description "1574.28 nm/190.431250 THz 3.125/6.25GHz spacing";
               }
               enum "1574.26" {
                 description "1574.26 nm/190.434375 THz 3.125GHz spacing";
               }
               enum "1574.23" {
                 description "1574.23 nm/190.437500 THz 3.125/6.25/12.5GHz spacing";
               }
               enum "1574.20" {
                 description "1574.20 nm/190.440625 THz 3.125GHz spacing";
               }
               enum "1574.18" {
                 description "1574.18 nm/190.443750 THz 3.125/6.25GHz spacing";
               }
               enum "1574.15" {
                 description "1574.15 nm/190.446875 THz 3.125GHz spacing";
               }
               enum "1574.13" {
                 description "1574.13 nm/190.450000 THz 3.125/6.25/12.5/50GHz spacing";
               }
               enum "1574.10" {
                 description "1574.10 nm/190.453125 THz 3.125GHz spacing";
               }
               enum "1574.08" {
                 description "1574.08 nm/190.456250 THz 3.125/6.25GHz spacing";
               }
               enum "1574.05" {
                 description "1574.05 nm/190.459375 THz 3.125GHz spacing";
               }
               enum "1574.02" {
                 description "1574.02 nm/190.462500 THz 3.125/6.25/12.5GHz spacing";
               }
               enum "1574.00" {
                 description "1574.00 nm/190.465625 THz 3.125GHz spacing";
               }
               enum "1573.97" {
                 description "1573.97 nm/190.468750 THz 3.125/6.25GHz spacing";
               }
               enum "1573.95" {
                 description "1573.95 nm/190.471875 THz 3.125GHz spacing";
               }
               enum "1573.92" {
                 description "1573.92 nm/190.475000 THz 3.125/6.25/12.5/75GHz spacing";
               }
               enum "1573.89" {
                 description "1573.89 nm/190.478125 THz 3.125GHz spacing";
               }
               enum "1573.87" {
                 description "1573.87 nm/190.481250 THz 3.125/6.25GHz spacing";
               }
               enum "1573.84" {
                 description "1573.84 nm/190.484375 THz 3.125GHz spacing";
               }
               enum "1573.82" {
                 description "1573.82 nm/190.487500 THz 3.125/6.25/12.5GHz spacing";
               }
               enum "1573.79" {
                 description "1573.79 nm/190.490625 THz 3.125GHz spacing";
               }
               enum "1573.77" {
                 description "1573.77 nm/190.493750 THz 3.125/6.25GHz spacing";
               }
               enum "1573.74" {
                 description "1573.74 nm/190.496875 THz 3.125GHz spacing";
               }
               enum "1573.71" {
                 description "1573.71 nm/190.500000 THz 3.125/6.25/12.5/50/75/100GHz spacing";
               }
               enum "1573.69" {
                 description "1573.69 nm/190.503125 THz 3.125GHz spacing";
               }
               enum "1573.66" {
                 description "1573.66 nm/190.506250 THz 3.125/6.25GHz spacing";
               }
               enum "1573.64" {
                 description "1573.64 nm/190.509375 THz 3.125GHz spacing";
               }
               enum "1573.61" {
                 description "1573.61 nm/190.512500 THz 3.125/6.25/12.5GHz spacing";
               }
               enum "1573.58" {
                 description "1573.58 nm/190.515625 THz 3.125GHz spacing";
               }
               enum "1573.56" {
                 description "1573.56 nm/190.518750 THz 3.125/6.25GHz spacing";
               }
               enum "1573.53" {
                 description "1573.53 nm/190.521875 THz 3.125GHz spacing";
               }
               enum "1573.51" {
                 description "1573.51 nm/190.525000 THz 3.125/6.25/12.5GHz spacing";
               }
               enum "1573.48" {
                 description "1573.48 nm/190.528125 THz 3.125GHz spacing";
               }
               enum "1573.46" {
                 description "1573.46 nm/190.531250 THz 3.125/6.25GHz spacing";
               }
               enum "1573.43" {
                 description "1573.43 nm/190.534375 THz 3.125GHz spacing";
               }
               enum "1573.40" {
                 description "1573.40 nm/190.537500 THz 3.125/6.25/12.5GHz spacing";
               }
               enum "1573.38" {
                 description "1573.38 nm/190.540625 THz 3.125GHz spacing";
               }
               enum "1573.35" {
                 description "1573.35 nm/190.543750 THz 3.125/6.25GHz spacing";
               }
               enum "1573.33" {
                 description "1573.33 nm/190.546875 THz 3.125GHz spacing";
               }
               enum "1573.30" {
                 description "1573.30 nm/190.550000 THz 3.125/6.25/12.5/50/75GHz spacing";
               }
               enum "1573.27" {
                 description "1573.27 nm/190.553125 THz 3.125GHz spacing";
               }
               enum "1573.25" {
                 description "1573.25 nm/190.556250 THz 3.125/6.25GHz spacing";
               }
               enum "1573.22" {
                 description "1573.22 nm/190.559375 THz 3.125GHz spacing";
               }
               enum "1573.20" {
                 description "1573.20 nm/190.562500 THz 3.125/6.25/12.5GHz spacing";
               }
               enum "1573.17" {
                 description "1573.17 nm/190.565625 THz 3.125GHz spacing";
               }
               enum "1573.15" {
                 description "1573.15 nm/190.568750 THz 3.125/6.25GHz spacing";
               }
               enum "1573.12" {
                 description "1573.12 nm/190.571875 THz 3.125GHz spacing";
               }
               enum "1573.09" {
                 description "1573.09 nm/190.575000 THz 3.125/6.25/12.5GHz spacing";
               }
               enum "1573.07" {
                 description "1573.07 nm/190.578125 THz 3.125GHz spacing";
               }
               enum "1573.04" {
                 description "1573.04 nm/190.581250 THz 3.125/6.25GHz spacing";
               }
               enum "1573.02" {
                 description "1573.02 nm/190.584375 THz 3.125GHz spacing";
               }
               enum "1572.99" {
                 description "1572.99 nm/190.587500 THz 3.125/6.25/12.5GHz spacing";
               }
               enum "1572.97" {
                 description "1572.97 nm/190.590625 THz 3.125GHz spacing";
               }
               enum "1572.94" {
                 description "1572.94 nm/190.593750 THz 3.125/6.25GHz spacing";
               }
               enum "1572.91" {
                 description "1572.91 nm/190.596875 THz 3.125GHz spacing";
               }
               enum "1572.89" {
                 description "1572.89 nm/190.600000 THz 3.125/6.25/12.5/100GHz spacing";
               }
               enum "1572.86" {
                 description "1572.86 nm/190.603125 THz 3.125GHz spacing";
               }
               enum "1572.84" {
                 description "1572.84 nm/190.606250 THz 3.125/6.25GHz spacing";
               }
               enum "1572.81" {
                 description "1572.81 nm/190.609375 THz 3.125GHz spacing";
               }
               enum "1572.78" {
                 description "1572.78 nm/190.612500 THz 3.125/6.25/12.5GHz spacing";
               }
               enum "1572.76" {
                 description "1572.76 nm/190.615625 THz 3.125GHz spacing";
               }
               enum "1572.73" {
                 description "1572.73 nm/190.618750 THz 3.125/6.25GHz spacing";
               }
               enum "1572.71" {
                 description "1572.71 nm/190.621875 THz 3.125GHz spacing";
               }
               enum "1572.68" {
                 description "1572.68 nm/190.625000 THz 3.125/6.25/12.5/75GHz spacing";
               }
               enum "1572.66" {
                 description "1572.66 nm/190.628125 THz 3.125GHz spacing";
               }
               enum "1572.63" {
                 description "1572.63 nm/190.631250 THz 3.125/6.25GHz spacing";
               }
               enum "1572.60" {
                 description "1572.60 nm/190.634375 THz 3.125GHz spacing";
               }
               enum "1572.58" {
                 description "1572.58 nm/190.637500 THz 3.125/6.25/12.5GHz spacing";
               }
               enum "1572.55" {
                 description "1572.55 nm/190.640625 THz 3.125GHz spacing";
               }
               enum "1572.53" {
                 description "1572.53 nm/190.643750 THz 3.125/6.25GHz spacing";
               }
               enum "1572.50" {
                 description "1572.50 nm/190.646875 THz 3.125GHz spacing";
               }
               enum "1572.48" {
                 description "1572.48 nm/190.650000 THz 3.125/6.25/12.5/50GHz spacing";
               }
               enum "1572.45" {
                 description "1572.45 nm/190.653125 THz 3.125GHz spacing";
               }
               enum "1572.42" {
                 description "1572.42 nm/190.656250 THz 3.125/6.25GHz spacing";
               }
               enum "1572.40" {
                 description "1572.40 nm/190.659375 THz 3.125GHz spacing";
               }
               enum "1572.37" {
                 description "1572.37 nm/190.662500 THz 3.125/6.25/12.5GHz spacing";
               }
               enum "1572.35" {
                 description "1572.35 nm/190.665625 THz 3.125GHz spacing";
               }
               enum "1572.32" {
                 description "1572.32 nm/190.668750 THz 3.125/6.25GHz spacing";
               }
               enum "1572.30" {
                 description "1572.30 nm/190.671875 THz 3.125GHz spacing";
               }
               enum "1572.27" {
                 description "1572.27 nm/190.675000 THz 3.125/6.25/12.5GHz spacing";
               }
               enum "1572.24" {
                 description "1572.24 nm/190.678125 THz 3.125GHz spacing";
               }
               enum "1572.22" {
                 description "1572.22 nm/190.681250 THz 3.125/6.25GHz spacing";
               }
               enum "1572.19" {
                 description "1572.19 nm/190.684375 THz 3.125GHz spacing";
               }
               enum "1572.17" {
                 description "1572.17 nm/190.687500 THz 3.125/6.25/12.5GHz spacing";
               }
               enum "1572.14" {
                 description "1572.14 nm/190.690625 THz 3.125GHz spacing";
               }
               enum "1572.11" {
                 description "1572.11 nm/190.693750 THz 3.125/6.25GHz spacing";
               }
               enum "1572.09" {
                 description "1572.09 nm/190.696875 THz 3.125GHz spacing";
               }
               enum "1572.06" {
                 description "1572.06 nm/190.700000 THz 3.125/6.25/12.5/100GHz spacing";
               }
               enum "1572.04" {
                 description "1572.04 nm/190.703125 THz 3.125GHz spacing";
               }
               enum "1572.01" {
                 description "1572.01 nm/190.706250 THz 3.125/6.25GHz spacing";
               }
               enum "1571.99" {
                 description "1571.99 nm/190.709375 THz 3.125GHz spacing";
               }
               enum "1571.96" {
                 description "1571.96 nm/190.712500 THz 3.125/6.25/12.5GHz spacing";
               }
               enum "1571.93" {
                 description "1571.93 nm/190.715625 THz 3.125GHz spacing";
               }
               enum "1571.91" {
                 description "1571.91 nm/190.718750 THz 3.125/6.25GHz spacing";
               }
               enum "1571.88" {
                 description "1571.88 nm/190.721875 THz 3.125GHz spacing";
               }
               enum "1571.86" {
                 description "1571.86 nm/190.725000 THz 3.125/6.25/12.5GHz spacing";
               }
               enum "1571.83" {
                 description "1571.83 nm/190.728125 THz 3.125GHz spacing";
               }
               enum "1571.81" {
                 description "1571.81 nm/190.731250 THz 3.125/6.25GHz spacing";
               }
               enum "1571.78" {
                 description "1571.78 nm/190.734375 THz 3.125GHz spacing";
               }
               enum "1571.75" {
                 description "1571.75 nm/190.737500 THz 3.125/6.25/12.5GHz spacing";
               }
               enum "1571.73" {
                 description "1571.73 nm/190.740625 THz 3.125GHz spacing";
               }
               enum "1571.70" {
                 description "1571.70 nm/190.743750 THz 3.125/6.25GHz spacing";
               }
               enum "1571.68" {
                 description "1571.68 nm/190.746875 THz 3.125GHz spacing";
               }
               enum "1571.65" {
                 description "1571.65 nm/190.750000 THz 3.125/6.25/12.5/50GHz spacing";
               }
               enum "1571.63" {
                 description "1571.63 nm/190.753125 THz 3.125GHz spacing";
               }
               enum "1571.60" {
                 description "1571.60 nm/190.756250 THz 3.125/6.25GHz spacing";
               }
               enum "1571.57" {
                 description "1571.57 nm/190.759375 THz 3.125GHz spacing";
               }
               enum "1571.55" {
                 description "1571.55 nm/190.762500 THz 3.125/6.25/12.5GHz spacing";
               }
               enum "1571.52" {
                 description "1571.52 nm/190.765625 THz 3.125GHz spacing";
               }
               enum "1571.50" {
                 description "1571.50 nm/190.768750 THz 3.125/6.25GHz spacing";
               }
               enum "1571.47" {
                 description "1571.47 nm/190.771875 THz 3.125GHz spacing";
               }
               enum "1571.45" {
                 description "1571.45 nm/190.775000 THz 3.125/6.25/12.5/75GHz spacing";
               }
               enum "1571.42" {
                 description "1571.42 nm/190.778125 THz 3.125GHz spacing";
               }
               enum "1571.39" {
                 description "1571.39 nm/190.781250 THz 3.125/6.25GHz spacing";
               }
               enum "1571.37" {
                 description "1571.37 nm/190.784375 THz 3.125GHz spacing";
               }
               enum "1571.34" {
                 description "1571.34 nm/190.787500 THz 3.125/6.25/12.5GHz spacing";
               }
               enum "1571.32" {
                 description "1571.32 nm/190.790625 THz 3.125GHz spacing";
               }
               enum "1571.29" {
                 description "1571.29 nm/190.793750 THz 3.125/6.25GHz spacing";
               }
               enum "1571.27" {
                 description "1571.27 nm/190.796875 THz 3.125GHz spacing";
               }
               enum "1571.24" {
                 description "1571.24 nm/190.800000 THz 3.125/6.25/12.5/50/75/100GHz spacing";
               }
               enum "1571.21" {
                 description "1571.21 nm/190.803125 THz 3.125GHz spacing";
               }
               enum "1571.19" {
                 description "1571.19 nm/190.806250 THz 3.125/6.25GHz spacing";
               }
               enum "1571.16" {
                 description "1571.16 nm/190.809375 THz 3.125GHz spacing";
               }
               enum "1571.14" {
                 description "1571.14 nm/190.812500 THz 3.125/6.25/12.5GHz spacing";
               }
               enum "1571.11" {
                 description "1571.11 nm/190.815625 THz 3.125GHz spacing";
               }
               enum "1571.08" {
                 description "1571.08 nm/190.818750 THz 3.125/6.25GHz spacing";
               }
               enum "1571.06" {
                 description "1571.06 nm/190.821875 THz 3.125GHz spacing";
               }
               enum "1571.03" {
                 description "1571.03 nm/190.825000 THz 3.125/6.25/12.5GHz spacing";
               }
               enum "1571.01" {
                 description "1571.01 nm/190.828125 THz 3.125GHz spacing";
               }
               enum "1570.98" {
                 description "1570.98 nm/190.831250 THz 3.125/6.25GHz spacing";
               }
               enum "1570.96" {
                 description "1570.96 nm/190.834375 THz 3.125GHz spacing";
               }
               enum "1570.93" {
                 description "1570.93 nm/190.837500 THz 3.125/6.25/12.5GHz spacing";
               }
               enum "1570.90" {
                 description "1570.90 nm/190.840625 THz 3.125GHz spacing";
               }
               enum "1570.88" {
                 description "1570.88 nm/190.843750 THz 3.125/6.25GHz spacing";
               }
               enum "1570.85" {
                 description "1570.85 nm/190.846875 THz 3.125GHz spacing";
               }
               enum "1570.83" {
                 description "1570.83 nm/190.850000 THz 3.125/6.25/12.5/50/75GHz spacing";
               }
               enum "1570.80" {
                 description "1570.80 nm/190.853125 THz 3.125GHz spacing";
               }
               enum "1570.78" {
                 description "1570.78 nm/190.856250 THz 3.125/6.25GHz spacing";
               }
               enum "1570.75" {
                 description "1570.75 nm/190.859375 THz 3.125GHz spacing";
               }
               enum "1570.72" {
                 description "1570.72 nm/190.862500 THz 3.125/6.25/12.5GHz spacing";
               }
               enum "1570.70" {
                 description "1570.70 nm/190.865625 THz 3.125GHz spacing";
               }
               enum "1570.67" {
                 description "1570.67 nm/190.868750 THz 3.125/6.25GHz spacing";
               }
               enum "1570.65" {
                 description "1570.65 nm/190.871875 THz 3.125GHz spacing";
               }
               enum "1570.62" {
                 description "1570.62 nm/190.875000 THz 3.125/6.25/12.5GHz spacing";
               }
               enum "1570.60" {
                 description "1570.60 nm/190.878125 THz 3.125GHz spacing";
               }
               enum "1570.57" {
                 description "1570.57 nm/190.881250 THz 3.125/6.25GHz spacing";
               }
               enum "1570.54" {
                 description "1570.54 nm/190.884375 THz 3.125GHz spacing";
               }
               enum "1570.52" {
                 description "1570.52 nm/190.887500 THz 3.125/6.25/12.5GHz spacing";
               }
               enum "1570.49" {
                 description "1570.49 nm/190.890625 THz 3.125GHz spacing";
               }
               enum "1570.47" {
                 description "1570.47 nm/190.893750 THz 3.125/6.25GHz spacing";
               }
               enum "1570.44" {
                 description "1570.44 nm/190.896875 THz 3.125GHz spacing";
               }
               enum "1570.42" {
                 description "1570.42 nm/190.900000 THz 3.125/6.25/12.5/100GHz spacing";
               }
               enum "1570.39" {
                 description "1570.39 nm/190.903125 THz 3.125GHz spacing";
               }
               enum "1570.36" {
                 description "1570.36 nm/190.906250 THz 3.125/6.25GHz spacing";
               }
               enum "1570.34" {
                 description "1570.34 nm/190.909375 THz 3.125GHz spacing";
               }
               enum "1570.31" {
                 description "1570.31 nm/190.912500 THz 3.125/6.25/12.5GHz spacing";
               }
               enum "1570.29" {
                 description "1570.29 nm/190.915625 THz 3.125GHz spacing";
               }
               enum "1570.26" {
                 description "1570.26 nm/190.918750 THz 3.125/6.25GHz spacing";
               }
               enum "1570.24" {
                 description "1570.24 nm/190.921875 THz 3.125GHz spacing";
               }
               enum "1570.21" {
                 description "1570.21 nm/190.925000 THz 3.125/6.25/12.5/75GHz spacing";
               }
               enum "1570.18" {
                 description "1570.18 nm/190.928125 THz 3.125GHz spacing";
               }
               enum "1570.16" {
                 description "1570.16 nm/190.931250 THz 3.125/6.25GHz spacing";
               }
               enum "1570.13" {
                 description "1570.13 nm/190.934375 THz 3.125GHz spacing";
               }
               enum "1570.11" {
                 description "1570.11 nm/190.937500 THz 3.125/6.25/12.5GHz spacing";
               }
               enum "1570.08" {
                 description "1570.08 nm/190.940625 THz 3.125GHz spacing";
               }
               enum "1570.06" {
                 description "1570.06 nm/190.943750 THz 3.125/6.25GHz spacing";
               }
               enum "1570.03" {
                 description "1570.03 nm/190.946875 THz 3.125GHz spacing";
               }
               enum "1570.01" {
                 description "1570.01 nm/190.950000 THz 3.125/6.25/12.5/50GHz spacing";
               }
               enum "1569.98" {
                 description "1569.98 nm/190.953125 THz 3.125GHz spacing";
               }
               enum "1569.95" {
                 description "1569.95 nm/190.956250 THz 3.125/6.25GHz spacing";
               }
               enum "1569.93" {
                 description "1569.93 nm/190.959375 THz 3.125GHz spacing";
               }
               enum "1569.90" {
                 description "1569.90 nm/190.962500 THz 3.125/6.25/12.5GHz spacing";
               }
               enum "1569.88" {
                 description "1569.88 nm/190.965625 THz 3.125GHz spacing";
               }
               enum "1569.85" {
                 description "1569.85 nm/190.968750 THz 3.125/6.25GHz spacing";
               }
               enum "1569.83" {
                 description "1569.83 nm/190.971875 THz 3.125GHz spacing";
               }
               enum "1569.80" {
                 description "1569.80 nm/190.975000 THz 3.125/6.25/12.5GHz spacing";
               }
               enum "1569.77" {
                 description "1569.77 nm/190.978125 THz 3.125GHz spacing";
               }
               enum "1569.75" {
                 description "1569.75 nm/190.981250 THz 3.125/6.25GHz spacing";
               }
               enum "1569.72" {
                 description "1569.72 nm/190.984375 THz 3.125GHz spacing";
               }
               enum "1569.70" {
                 description "1569.70 nm/190.987500 THz 3.125/6.25/12.5GHz spacing";
               }
               enum "1569.67" {
                 description "1569.67 nm/190.990625 THz 3.125GHz spacing";
               }
               enum "1569.65" {
                 description "1569.65 nm/190.993750 THz 3.125/6.25GHz spacing";
               }
               enum "1569.62" {
                 description "1569.62 nm/190.996875 THz 3.125GHz spacing";
               }
               enum "1569.59" {
                 description "1569.59 nm/191.000000 THz 3.125/6.25/12.5/100GHz spacing";
               }
               enum "1568.77" {
                 description "1568.77 nm/191.1003 THz 50/100Ghz spacing";
               }
               enum "1568.36" {
                 description "1568.36 nm/191.150000 THz 3.125/6.25/12.5/50/75GHz spacing";
               }
               enum "1568.34" {
                 description "1568.34 nm/191.153125 THz 3.125GHz spacing";
               }
               enum "1568.31" {
                 description "1568.31 nm/191.156250 THz 3.125/6.25GHz spacing";
               }
               enum "1568.29" {
                 description "1568.29 nm/191.159375 THz 3.125GHz spacing";
               }
               enum "1568.26" {
                 description "1568.26 nm/191.162500 THz 3.125/6.25/12.5GHz spacing";
               }
               enum "1568.23" {
                 description "1568.23 nm/191.165625 THz 3.125GHz spacing";
               }
               enum "1568.21" {
                 description "1568.21 nm/191.168750 THz 3.125/6.25GHz spacing";
               }
               enum "1568.18" {
                 description "1568.18 nm/191.171875 THz 3.125GHz spacing";
               }
               enum "1568.16" {
                 description "1568.16 nm/191.175000 THz 3.125/6.25/12.5/75GHz spacing";
               }
               enum "1568.13" {
                 description "1568.13 nm/191.178125 THz 3.125GHz spacing";
               }
               enum "1568.11" {
                 description "1568.11 nm/191.181250 THz 3.125/6.25GHz spacing";
               }
               enum "1568.08" {
                 description "1568.08 nm/191.184375 THz 3.125GHz spacing";
               }
               enum "1568.05" {
                 description "1568.05 nm/191.187500 THz 3.125/6.25/12.5GHz spacing";
               }
               enum "1568.03" {
                 description "1568.03 nm/191.190625 THz 3.125GHz spacing";
               }
               enum "1568.00" {
                 description "1568.00 nm/191.193750 THz 3.125/6.25GHz spacing";
               }
               enum "1567.98" {
                 description "1567.98 nm/191.196875 THz 3.125GHz spacing";
               }
               enum "1567.95" {
                 description "1567.95 nm/191.200000 THz 3.125/6.25/12.5/100GHz spacing";
               }
               enum "1567.93" {
                 description "1567.93 nm/191.203125 THz 3.125GHz spacing";
               }
               enum "1567.90" {
                 description "1567.90 nm/191.206250 THz 3.125/6.25GHz spacing";
               }
               enum "1567.88" {
                 description "1567.88 nm/191.209375 THz 3.125GHz spacing";
               }
               enum "1567.85" {
                 description "1567.85 nm/191.212500 THz 3.125/6.25/12.5GHz spacing";
               }
               enum "1567.82" {
                 description "1567.82 nm/191.215625 THz 3.125GHz spacing";
               }
               enum "1567.80" {
                 description "1567.80 nm/191.218750 THz 3.125/6.25GHz spacing";
               }
               enum "1567.77" {
                 description "1567.77 nm/191.221875 THz 3.125GHz spacing";
               }
               enum "1567.75" {
                 description "1567.75 nm/191.225000 THz 3.125/6.25/12.5/75GHz spacing";
               }
               enum "1567.72" {
                 description "1567.72 nm/191.228125 THz 3.125GHz spacing";
               }
               enum "1567.70" {
                 description "1567.70 nm/191.231250 THz 3.125/6.25GHz spacing";
               }
               enum "1567.67" {
                 description "1567.67 nm/191.234375 THz 3.125GHz spacing";
               }
               enum "1567.64" {
                 description "1567.64 nm/191.237500 THz 3.125/6.25/12.5GHz spacing";
               }
               enum "1567.62" {
                 description "1567.62 nm/191.240625 THz 3.125GHz spacing";
               }
               enum "1567.59" {
                 description "1567.59 nm/191.243750 THz 3.125/6.25GHz spacing";
               }
               enum "1567.57" {
                 description "1567.57 nm/191.246875 THz 3.125GHz spacing";
               }
               enum "1567.54" {
                 description "1567.54 nm/191.250000 THz 3.125/6.25/12.5/50/75GHz spacing";
               }
               enum "1567.52" {
                 description "1567.52 nm/191.253125 THz 3.125GHz spacing";
               }
               enum "1567.49" {
                 description "1567.49 nm/191.256250 THz 3.125/6.25GHz spacing";
               }
               enum "1567.47" {
                 description "1567.47 nm/191.259375 THz 3.125GHz spacing";
               }
               enum "1567.44" {
                 description "1567.44 nm/191.262500 THz 3.125/6.25/12.5GHz spacing";
               }
               enum "1567.41" {
                 description "1567.41 nm/191.265625 THz 3.125GHz spacing";
               }
               enum "1567.39" {
                 description "1567.39 nm/191.268750 THz 3.125/6.25GHz spacing";
               }
               enum "1567.36" {
                 description "1567.36 nm/191.271875 THz 3.125GHz spacing";
               }
               enum "1567.34" {
                 description "1567.34 nm/191.275000 THz 3.125/6.25/12.5GHz spacing";
               }
               enum "1567.31" {
                 description "1567.31 nm/191.278125 THz 3.125GHz spacing";
               }
               enum "1567.29" {
                 description "1567.29 nm/191.281250 THz 3.125/6.25GHz spacing";
               }
               enum "1567.26" {
                 description "1567.26 nm/191.284375 THz 3.125GHz spacing";
               }
               enum "1567.23" {
                 description "1567.23 nm/191.287500 THz 3.125/6.25/12.5GHz spacing";
               }
               enum "1567.21" {
                 description "1567.21 nm/191.290625 THz 3.125GHz spacing";
               }
               enum "1567.18" {
                 description "1567.18 nm/191.293750 THz 3.125/6.25GHz spacing";
               }
               enum "1567.16" {
                 description "1567.16 nm/191.296875 THz 3.125GHz spacing";
               }
               enum "1567.13" {
                 description "1567.13 nm/191.300000 THz 3.125/6.25/12.5/100GHz spacing";
               }
               enum "1567.11" {
                 description "1567.11 nm/191.303125 THz 3.125GHz spacing";
               }
               enum "1567.08" {
                 description "1567.08 nm/191.306250 THz 3.125/6.25GHz spacing";
               }
               enum "1567.06" {
                 description "1567.06 nm/191.309375 THz 3.125GHz spacing";
               }
               enum "1567.03" {
                 description "1567.03 nm/191.312500 THz 3.125/6.25/12.5GHz spacing";
               }
               enum "1567.00" {
                 description "1567.00 nm/191.315625 THz 3.125GHz spacing";
               }
               enum "1566.98" {
                 description "1566.98 nm/191.318750 THz 3.125/6.25GHz spacing";
               }
               enum "1566.95" {
                 description "1566.95 nm/191.321875 THz 3.125GHz spacing";
               }
               enum "1566.93" {
                 description "1566.93 nm/191.325000 THz 3.125/6.25/12.5/75GHz spacing";
               }
               enum "1566.90" {
                 description "1566.90 nm/191.328125 THz 3.125GHz spacing";
               }
               enum "1566.88" {
                 description "1566.88 nm/191.331250 THz 3.125/6.25GHz spacing";
               }
               enum "1566.85" {
                 description "1566.85 nm/191.334375 THz 3.125GHz spacing";
               }
               enum "1566.83" {
                 description "1566.83 nm/191.337500 THz 3.125/6.25/12.5GHz spacing";
               }
               enum "1566.80" {
                 description "1566.80 nm/191.340625 THz 3.125GHz spacing";
               }
               enum "1566.77" {
                 description "1566.77 nm/191.343750 THz 3.125/6.25GHz spacing";
               }
               enum "1566.75" {
                 description "1566.75 nm/191.346875 THz 3.125GHz spacing";
               }
               enum "1566.72" {
                 description "1566.72 nm/191.350000 THz 3.125/6.25/12.5/50GHz spacing";
               }
               enum "1566.70" {
                 description "1566.70 nm/191.353125 THz 3.125GHz spacing";
               }
               enum "1566.67" {
                 description "1566.67 nm/191.356250 THz 3.125/6.25GHz spacing";
               }
               enum "1566.65" {
                 description "1566.65 nm/191.359375 THz 3.125GHz spacing";
               }
               enum "1566.62" {
                 description "1566.62 nm/191.362500 THz 3.125/6.25/12.5GHz spacing";
               }
               enum "1566.60" {
                 description "1566.60 nm/191.365625 THz 3.125GHz spacing";
               }
               enum "1566.57" {
                 description "1566.57 nm/191.368750 THz 3.125/6.25GHz spacing";
               }
               enum "1566.54" {
                 description "1566.54 nm/191.371875 THz 3.125GHz spacing";
               }
               enum "1566.52" {
                 description "1566.52 nm/191.375000 THz 3.125/6.25/12.5GHz spacing";
               }
               enum "1566.49" {
                 description "1566.49 nm/191.378125 THz 3.125GHz spacing";
               }
               enum "1566.47" {
                 description "1566.47 nm/191.381250 THz 3.125/6.25GHz spacing";
               }
               enum "1566.44" {
                 description "1566.44 nm/191.384375 THz 3.125GHz spacing";
               }
               enum "1566.42" {
                 description "1566.42 nm/191.387500 THz 3.125/6.25/12.5GHz spacing";
               }
               enum "1566.39" {
                 description "1566.39 nm/191.390625 THz 3.125GHz spacing";
               }
               enum "1566.36" {
                 description "1566.36 nm/191.393750 THz 3.125/6.25GHz spacing";
               }
               enum "1566.34" {
                 description "1566.34 nm/191.396875 THz 3.125GHz spacing";
               }
               enum "1566.31" {
                 description "1566.31 nm/191.400000 THz 3.125/6.25/12.5/50/75/100GHz spacing";
               }
               enum "1566.29" {
                 description "1566.29 nm/191.403125 THz 3.125GHz spacing";
               }
               enum "1566.26" {
                 description "1566.26 nm/191.406250 THz 3.125/6.25GHz spacing";
               }
               enum "1566.24" {
                 description "1566.24 nm/191.409375 THz 3.125GHz spacing";
               }
               enum "1566.21" {
                 description "1566.21 nm/191.412500 THz 3.125/6.25/12.5GHz spacing";
               }
               enum "1566.19" {
                 description "1566.19 nm/191.415625 THz 3.125GHz spacing";
               }
               enum "1566.16" {
                 description "1566.16 nm/191.418750 THz 3.125/6.25GHz spacing";
               }
               enum "1566.13" {
                 description "1566.13 nm/191.421875 THz 3.125GHz spacing";
               }
               enum "1566.11" {
                 description "1566.11 nm/191.425000 THz 3.125/6.25/12.5GHz spacing";
               }
               enum "1566.08" {
                 description "1566.08 nm/191.428125 THz 3.125GHz spacing";
               }
               enum "1566.06" {
                 description "1566.06 nm/191.431250 THz 3.125/6.25GHz spacing";
               }
               enum "1566.03" {
                 description "1566.03 nm/191.434375 THz 3.125GHz spacing";
               }
               enum "1566.01" {
                 description "1566.01 nm/191.437500 THz 3.125/6.25/12.5GHz spacing";
               }
               enum "1565.98" {
                 description "1565.98 nm/191.440625 THz 3.125GHz spacing";
               }
               enum "1565.96" {
                 description "1565.96 nm/191.443750 THz 3.125/6.25GHz spacing";
               }
               enum "1565.93" {
                 description "1565.93 nm/191.446875 THz 3.125GHz spacing";
               }
               enum "1565.90" {
                 description "1565.90 nm/191.450000 THz 3.125/6.25/12.5/50GHz spacing";
               }
               enum "1565.88" {
                 description "1565.88 nm/191.453125 THz 3.125GHz spacing";
               }
               enum "1565.85" {
                 description "1565.85 nm/191.456250 THz 3.125/6.25GHz spacing";
               }
               enum "1565.83" {
                 description "1565.83 nm/191.459375 THz 3.125GHz spacing";
               }
               enum "1565.80" {
                 description "1565.80 nm/191.462500 THz 3.125/6.25/12.5GHz spacing";
               }
               enum "1565.78" {
                 description "1565.78 nm/191.465625 THz 3.125GHz spacing";
               }
               enum "1565.75" {
                 description "1565.75 nm/191.468750 THz 3.125/6.25GHz spacing";
               }
               enum "1565.73" {
                 description "1565.73 nm/191.471875 THz 3.125GHz spacing";
               }
               enum "1565.70" {
                 description "1565.70 nm/191.475000 THz 3.125/6.25/12.5/75GHz spacing";
               }
               enum "1565.67" {
                 description "1565.67 nm/191.478125 THz 3.125GHz spacing";
               }
               enum "1565.65" {
                 description "1565.65 nm/191.481250 THz 3.125/6.25GHz spacing";
               }
               enum "1565.62" {
                 description "1565.62 nm/191.484375 THz 3.125GHz spacing";
               }
               enum "1565.60" {
                 description "1565.60 nm/191.487500 THz 3.125/6.25/12.5GHz spacing";
               }
               enum "1565.57" {
                 description "1565.57 nm/191.490625 THz 3.125GHz spacing";
               }
               enum "1565.55" {
                 description "1565.55 nm/191.493750 THz 3.125/6.25GHz spacing";
               }
               enum "1565.52" {
                 description "1565.52 nm/191.496875 THz 3.125GHz spacing";
               }
               enum "1565.50" {
                 description "1565.50 nm/191.500000 THz 3.125/6.25/12.5/100GHz spacing";
               }
               enum "1565.47" {
                 description "1565.47 nm/191.503125 THz 3.125GHz spacing";
               }
               enum "1565.44" {
                 description "1565.44 nm/191.506250 THz 3.125/6.25GHz spacing";
               }
               enum "1565.42" {
                 description "1565.42 nm/191.509375 THz 3.125GHz spacing";
               }
               enum "1565.39" {
                 description "1565.39 nm/191.512500 THz 3.125/6.25/12.5GHz spacing";
               }
               enum "1565.37" {
                 description "1565.37 nm/191.515625 THz 3.125GHz spacing";
               }
               enum "1565.34" {
                 description "1565.34 nm/191.518750 THz 3.125/6.25GHz spacing";
               }
               enum "1565.32" {
                 description "1565.32 nm/191.521875 THz 3.125GHz spacing";
               }
               enum "1565.29" {
                 description "1565.29 nm/191.525000 THz 3.125/6.25/12.5GHz spacing";
               }
               enum "1565.27" {
                 description "1565.27 nm/191.528125 THz 3.125GHz spacing";
               }
               enum "1565.24" {
                 description "1565.24 nm/191.531250 THz 3.125/6.25GHz spacing";
               }
               enum "1565.21" {
                 description "1565.21 nm/191.534375 THz 3.125GHz spacing";
               }
               enum "1565.19" {
                 description "1565.19 nm/191.537500 THz 3.125/6.25/12.5GHz spacing";
               }
               enum "1565.16" {
                 description "1565.16 nm/191.540625 THz 3.125GHz spacing";
               }
               enum "1565.14" {
                 description "1565.14 nm/191.543750 THz 3.125/6.25GHz spacing";
               }
               enum "1565.11" {
                 description "1565.11 nm/191.546875 THz 3.125GHz spacing";
               }
               enum "1565.09" {
                 description "1565.09 nm/191.550000 THz 3.125/6.25/12.5/50/75GHz spacing";
               }
               enum "1565.06" {
                 description "1565.06 nm/191.553125 THz 3.125GHz spacing";
               }
               enum "1565.04" {
                 description "1565.04 nm/191.556250 THz 3.125/6.25GHz spacing";
               }
               enum "1565.01" {
                 description "1565.01 nm/191.559375 THz 3.125GHz spacing";
               }
               enum "1564.99" {
                 description "1564.99 nm/191.562500 THz 3.125/6.25/12.5GHz spacing";
               }
               enum "1564.96" {
                 description "1564.96 nm/191.565625 THz 3.125GHz spacing";
               }
               enum "1564.93" {
                 description "1564.93 nm/191.568750 THz 3.125/6.25GHz spacing";
               }
               enum "1564.91" {
                 description "1564.91 nm/191.571875 THz 3.125GHz spacing";
               }
               enum "1564.88" {
                 description "1564.88 nm/191.575000 THz 3.125/6.25/12.5GHz spacing";
               }
               enum "1564.86" {
                 description "1564.86 nm/191.578125 THz 3.125GHz spacing";
               }
               enum "1564.83" {
                 description "1564.83 nm/191.581250 THz 3.125/6.25GHz spacing";
               }
               enum "1564.81" {
                 description "1564.81 nm/191.584375 THz 3.125GHz spacing";
               }
               enum "1564.78" {
                 description "1564.78 nm/191.587500 THz 3.125/6.25/12.5GHz spacing";
               }
               enum "1564.76" {
                 description "1564.76 nm/191.590625 THz 3.125GHz spacing";
               }
               enum "1564.73" {
                 description "1564.73 nm/191.593750 THz 3.125/6.25GHz spacing";
               }
               enum "1564.70" {
                 description "1564.70 nm/191.596875 THz 3.125GHz spacing";
               }
               enum "1564.68" {
                 description "1564.68 nm/191.600000 THz 3.125/6.25/12.5/100GHz spacing";
               }
               enum "1564.65" {
                 description "1564.65 nm/191.603125 THz 3.125GHz spacing";
               }
               enum "1564.63" {
                 description "1564.63 nm/191.606250 THz 3.125/6.25GHz spacing";
               }
               enum "1564.60" {
                 description "1564.60 nm/191.609375 THz 3.125GHz spacing";
               }
               enum "1564.58" {
                 description "1564.58 nm/191.612500 THz 3.125/6.25/12.5GHz spacing";
               }
               enum "1564.55" {
                 description "1564.55 nm/191.615625 THz 3.125GHz spacing";
               }
               enum "1564.53" {
                 description "1564.53 nm/191.618750 THz 3.125/6.25GHz spacing";
               }
               enum "1564.50" {
                 description "1564.50 nm/191.621875 THz 3.125GHz spacing";
               }
               enum "1564.47" {
                 description "1564.47 nm/191.625000 THz 3.125/6.25/12.5/75GHz spacing";
               }
               enum "1564.45" {
                 description "1564.45 nm/191.628125 THz 3.125GHz spacing";
               }
               enum "1564.42" {
                 description "1564.42 nm/191.631250 THz 3.125/6.25GHz spacing";
               }
               enum "1564.40" {
                 description "1564.40 nm/191.634375 THz 3.125GHz spacing";
               }
               enum "1564.37" {
                 description "1564.37 nm/191.637500 THz 3.125/6.25/12.5GHz spacing";
               }
               enum "1564.35" {
                 description "1564.35 nm/191.640625 THz 3.125GHz spacing";
               }
               enum "1564.32" {
                 description "1564.32 nm/191.643750 THz 3.125/6.25GHz spacing";
               }
               enum "1564.30" {
                 description "1564.30 nm/191.646875 THz 3.125GHz spacing";
               }
               enum "1564.27" {
                 description "1564.27 nm/191.650000 THz 3.125/6.25/12.5/50GHz spacing";
               }
               enum "1564.25" {
                 description "1564.25 nm/191.653125 THz 3.125GHz spacing";
               }
               enum "1564.22" {
                 description "1564.22 nm/191.656250 THz 3.125/6.25GHz spacing";
               }
               enum "1564.19" {
                 description "1564.19 nm/191.659375 THz 3.125GHz spacing";
               }
               enum "1564.17" {
                 description "1564.17 nm/191.662500 THz 3.125/6.25/12.5GHz spacing";
               }
               enum "1564.14" {
                 description "1564.14 nm/191.665625 THz 3.125GHz spacing";
               }
               enum "1564.12" {
                 description "1564.12 nm/191.668750 THz 3.125/6.25GHz spacing";
               }
               enum "1564.09" {
                 description "1564.09 nm/191.671875 THz 3.125GHz spacing";
               }
               enum "1564.07" {
                 description "1564.07 nm/191.675000 THz 3.125/6.25/12.5GHz spacing";
               }
               enum "1564.04" {
                 description "1564.04 nm/191.678125 THz 3.125GHz spacing";
               }
               enum "1564.02" {
                 description "1564.02 nm/191.681250 THz 3.125/6.25GHz spacing";
               }
               enum "1563.99" {
                 description "1563.99 nm/191.684375 THz 3.125GHz spacing";
               }
               enum "1563.96" {
                 description "1563.96 nm/191.687500 THz 3.125/6.25/12.5GHz spacing";
               }
               enum "1563.94" {
                 description "1563.94 nm/191.690625 THz 3.125GHz spacing";
               }
               enum "1563.91" {
                 description "1563.91 nm/191.693750 THz 3.125/6.25GHz spacing";
               }
               enum "1563.89" {
                 description "1563.89 nm/191.696875 THz 3.125GHz spacing";
               }
               enum "1563.86" {
                 description "1563.86 nm/191.700000 THz 3.125/6.25/12.5/50/75/100GHz spacing";
               }
               enum "1563.84" {
                 description "1563.84 nm/191.703125 THz 3.125GHz spacing";
               }
               enum "1563.81" {
                 description "1563.81 nm/191.706250 THz 3.125/6.25GHz spacing";
               }
               enum "1563.79" {
                 description "1563.79 nm/191.709375 THz 3.125GHz spacing";
               }
               enum "1563.76" {
                 description "1563.76 nm/191.712500 THz 3.125/6.25/12.5GHz spacing";
               }
               enum "1563.74" {
                 description "1563.74 nm/191.715625 THz 3.125GHz spacing";
               }
               enum "1563.71" {
                 description "1563.71 nm/191.718750 THz 3.125/6.25GHz spacing";
               }
               enum "1563.68" {
                 description "1563.68 nm/191.721875 THz 3.125GHz spacing";
               }
               enum "1563.66" {
                 description "1563.66 nm/191.725000 THz 3.125/6.25/12.5GHz spacing";
               }
               enum "1563.63" {
                 description "1563.63 nm/191.728125 THz 3.125GHz spacing";
               }
               enum "1563.61" {
                 description "1563.61 nm/191.731250 THz 3.125/6.25GHz spacing";
               }
               enum "1563.58" {
                 description "1563.58 nm/191.734375 THz 3.125GHz spacing";
               }
               enum "1563.56" {
                 description "1563.56 nm/191.737500 THz 3.125/6.25/12.5GHz spacing";
               }
               enum "1563.53" {
                 description "1563.53 nm/191.740625 THz 3.125GHz spacing";
               }
               enum "1563.51" {
                 description "1563.51 nm/191.743750 THz 3.125/6.25GHz spacing";
               }
               enum "1563.48" {
                 description "1563.48 nm/191.746875 THz 3.125GHz spacing";
               }
               enum "1563.45" {
                 description "1563.45 nm/191.750000 THz 3.125/6.25/12.5/50GHz spacing";
               }
               enum "1563.43" {
                 description "1563.43 nm/191.753125 THz 3.125GHz spacing";
               }
               enum "1563.40" {
                 description "1563.40 nm/191.756250 THz 3.125/6.25GHz spacing";
               }
               enum "1563.38" {
                 description "1563.38 nm/191.759375 THz 3.125GHz spacing";
               }
               enum "1563.35" {
                 description "1563.35 nm/191.762500 THz 3.125/6.25/12.5GHz spacing";
               }
               enum "1563.33" {
                 description "1563.33 nm/191.765625 THz 3.125GHz spacing";
               }
               enum "1563.30" {
                 description "1563.30 nm/191.768750 THz 3.125/6.25GHz spacing";
               }
               enum "1563.28" {
                 description "1563.28 nm/191.771875 THz 3.125GHz spacing";
               }
               enum "1563.25" {
                 description "1563.25 nm/191.775000 THz 3.125/6.25/12.5/75GHz spacing";
               }
               enum "1563.23" {
                 description "1563.23 nm/191.778125 THz 3.125GHz spacing";
               }
               enum "1563.20" {
                 description "1563.20 nm/191.781250 THz 3.125/6.25GHz spacing";
               }
               enum "1563.17" {
                 description "1563.17 nm/191.784375 THz 3.125GHz spacing";
               }
               enum "1563.15" {
                 description "1563.15 nm/191.787500 THz 3.125/6.25/12.5GHz spacing";
               }
               enum "1563.12" {
                 description "1563.12 nm/191.790625 THz 3.125GHz spacing";
               }
               enum "1563.10" {
                 description "1563.10 nm/191.793750 THz 3.125/6.25GHz spacing";
               }
               enum "1563.07" {
                 description "1563.07 nm/191.796875 THz 3.125GHz spacing";
               }
               enum "1563.05" {
                 description "1563.05 nm/191.800000 THz 3.125/6.25/12.5/100GHz spacing";
               }
               enum "1563.02" {
                 description "1563.02 nm/191.803125 THz 3.125GHz spacing";
               }
               enum "1563.00" {
                 description "1563.00 nm/191.806250 THz 3.125/6.25GHz spacing";
               }
               enum "1562.97" {
                 description "1562.97 nm/191.809375 THz 3.125GHz spacing";
               }
               enum "1562.95" {
                 description "1562.95 nm/191.812500 THz 3.125/6.25/12.5GHz spacing";
               }
               enum "1562.92" {
                 description "1562.92 nm/191.815625 THz 3.125GHz spacing";
               }
               enum "1562.89" {
                 description "1562.89 nm/191.818750 THz 3.125/6.25GHz spacing";
               }
               enum "1562.87" {
                 description "1562.87 nm/191.821875 THz 3.125GHz spacing";
               }
               enum "1562.84" {
                 description "1562.84 nm/191.825000 THz 3.125/6.25/12.5GHz spacing";
               }
               enum "1562.82" {
                 description "1562.82 nm/191.828125 THz 3.125GHz spacing";
               }
               enum "1562.79" {
                 description "1562.79 nm/191.831250 THz 3.125/6.25GHz spacing";
               }
               enum "1562.77" {
                 description "1562.77 nm/191.834375 THz 3.125GHz spacing";
               }
               enum "1562.74" {
                 description "1562.74 nm/191.837500 THz 3.125/6.25/12.5GHz spacing";
               }
               enum "1562.72" {
                 description "1562.72 nm/191.840625 THz 3.125GHz spacing";
               }
               enum "1562.69" {
                 description "1562.69 nm/191.843750 THz 3.125/6.25GHz spacing";
               }
               enum "1562.67" {
                 description "1562.67 nm/191.846875 THz 3.125GHz spacing";
               }
               enum "1562.64" {
                 description "1562.64 nm/191.850000 THz 3.125/6.25/12.5/50/75GHz spacing";
               }
               enum "1562.61" {
                 description "1562.61 nm/191.853125 THz 3.125GHz spacing";
               }
               enum "1562.59" {
                 description "1562.59 nm/191.856250 THz 3.125/6.25GHz spacing";
               }
               enum "1562.56" {
                 description "1562.56 nm/191.859375 THz 3.125GHz spacing";
               }
               enum "1562.54" {
                 description "1562.54 nm/191.862500 THz 3.125/6.25/12.5GHz spacing";
               }
               enum "1562.51" {
                 description "1562.51 nm/191.865625 THz 3.125GHz spacing";
               }
               enum "1562.49" {
                 description "1562.49 nm/191.868750 THz 3.125/6.25GHz spacing";
               }
               enum "1562.46" {
                 description "1562.46 nm/191.871875 THz 3.125GHz spacing";
               }
               enum "1562.44" {
                 description "1562.44 nm/191.875000 THz 3.125/6.25/12.5GHz spacing";
               }
               enum "1562.41" {
                 description "1562.41 nm/191.878125 THz 3.125GHz spacing";
               }
               enum "1562.39" {
                 description "1562.39 nm/191.881250 THz 3.125/6.25GHz spacing";
               }
               enum "1562.36" {
                 description "1562.36 nm/191.884375 THz 3.125GHz spacing";
               }
               enum "1562.33" {
                 description "1562.33 nm/191.887500 THz 3.125/6.25/12.5GHz spacing";
               }
               enum "1562.31" {
                 description "1562.31 nm/191.890625 THz 3.125GHz spacing";
               }
               enum "1562.28" {
                 description "1562.28 nm/191.893750 THz 3.125/6.25GHz spacing";
               }
               enum "1562.26" {
                 description "1562.26 nm/191.896875 THz 3.125GHz spacing";
               }
               enum "1562.23" {
                 description "1562.23 nm/191.900000 THz 3.125/6.25/12.5/100GHz spacing";
               }
               enum "1562.21" {
                 description "1562.21 nm/191.903125 THz 3.125GHz spacing";
               }
               enum "1562.18" {
                 description "1562.18 nm/191.906250 THz 3.125/6.25GHz spacing";
               }
               enum "1562.16" {
                 description "1562.16 nm/191.909375 THz 3.125GHz spacing";
               }
               enum "1562.13" {
                 description "1562.13 nm/191.912500 THz 3.125/6.25/12.5GHz spacing";
               }
               enum "1562.11" {
                 description "1562.11 nm/191.915625 THz 3.125GHz spacing";
               }
               enum "1562.08" {
                 description "1562.08 nm/191.918750 THz 3.125/6.25GHz spacing";
               }
               enum "1562.05" {
                 description "1562.05 nm/191.921875 THz 3.125GHz spacing";
               }
               enum "1562.03" {
                 description "1562.03 nm/191.925000 THz 3.125/6.25/12.5/75GHz spacing";
               }
               enum "1562.00" {
                 description "1562.00 nm/191.928125 THz 3.125GHz spacing";
               }
               enum "1561.98" {
                 description "1561.98 nm/191.931250 THz 3.125/6.25GHz spacing";
               }
               enum "1561.95" {
                 description "1561.95 nm/191.934375 THz 3.125GHz spacing";
               }
               enum "1561.93" {
                 description "1561.93 nm/191.937500 THz 3.125/6.25/12.5GHz spacing";
               }
               enum "1561.90" {
                 description "1561.90 nm/191.940625 THz 3.125GHz spacing";
               }
               enum "1561.88" {
                 description "1561.88 nm/191.943750 THz 3.125/6.25GHz spacing";
               }
               enum "1561.85" {
                 description "1561.85 nm/191.946875 THz 3.125GHz spacing";
               }
               enum "1561.83" {
                 description "1561.83 nm/191.950000 THz 3.125/6.25/12.5/50GHz spacing";
               }
               enum "1561.80" {
                 description "1561.80 nm/191.953125 THz 3.125GHz spacing";
               }
               enum "1561.77" {
                 description "1561.77 nm/191.956250 THz 3.125/6.25GHz spacing";
               }
               enum "1561.75" {
                 description "1561.75 nm/191.959375 THz 3.125GHz spacing";
               }
               enum "1561.72" {
                 description "1561.72 nm/191.962500 THz 3.125/6.25/12.5GHz spacing";
               }
               enum "1561.70" {
                 description "1561.70 nm/191.965625 THz 3.125GHz spacing";
               }
               enum "1561.67" {
                 description "1561.67 nm/191.968750 THz 3.125/6.25GHz spacing";
               }
               enum "1561.65" {
                 description "1561.65 nm/191.971875 THz 3.125GHz spacing";
               }
               enum "1561.62" {
                 description "1561.62 nm/191.975000 THz 3.125/6.25/12.5GHz spacing";
               }
               enum "1561.60" {
                 description "1561.60 nm/191.978125 THz 3.125GHz spacing";
               }
               enum "1561.57" {
                 description "1561.57 nm/191.981250 THz 3.125/6.25GHz spacing";
               }
               enum "1561.55" {
                 description "1561.55 nm/191.984375 THz 3.125GHz spacing";
               }
               enum "1561.52" {
                 description "1561.52 nm/191.987500 THz 3.125/6.25/12.5GHz spacing";
               }
               enum "1561.50" {
                 description "1561.50 nm/191.990625 THz 3.125GHz spacing";
               }
               enum "1561.47" {
                 description "1561.47 nm/191.993750 THz 3.125/6.25GHz spacing";
               }
               enum "1561.44" {
                 description "1561.44 nm/191.996875 THz 3.125GHz spacing";
               }
               enum "1561.42" {
                 description "1561.42 nm/192.000000 THz 3.125/6.25/12.5/50/75/100GHz spacing";
               }
               enum "1561.39" {
                 description "1561.39 nm/192.003125 THz 3.125GHz spacing";
               }
               enum "1561.37" {
                 description "1561.37 nm/192.006250 THz 3.125/6.25GHz spacing";
               }
               enum "1561.34" {
                 description "1561.34 nm/192.009375 THz 3.125GHz spacing";
               }
               enum "1561.32" {
                 description "1561.32 nm/192.012500 THz 3.125/6.25/12.5GHz spacing";
               }
               enum "1561.29" {
                 description "1561.29 nm/192.015625 THz 3.125GHz spacing";
               }
               enum "1561.27" {
                 description "1561.27 nm/192.018750 THz 3.125/6.25GHz spacing";
               }
               enum "1561.24" {
                 description "1561.24 nm/192.021875 THz 3.125GHz spacing";
               }
               enum "1561.22" {
                 description "1561.22 nm/192.025000 THz 3.125/6.25/12.5GHz spacing";
               }
               enum "1561.19" {
                 description "1561.19 nm/192.028125 THz 3.125GHz spacing";
               }
               enum "1561.16" {
                 description "1561.16 nm/192.031250 THz 3.125/6.25GHz spacing";
               }
               enum "1561.14" {
                 description "1561.14 nm/192.034375 THz 3.125GHz spacing";
               }
               enum "1561.11" {
                 description "1561.11 nm/192.037500 THz 3.125/6.25/12.5GHz spacing";
               }
               enum "1561.09" {
                 description "1561.09 nm/192.040625 THz 3.125GHz spacing";
               }
               enum "1561.06" {
                 description "1561.06 nm/192.043750 THz 3.125/6.25GHz spacing";
               }
               enum "1561.04" {
                 description "1561.04 nm/192.046875 THz 3.125GHz spacing";
               }
               enum "1561.01" {
                 description "1561.01 nm/192.050000 THz 3.125/6.25/12.5/50GHz spacing";
               }
               enum "1560.99" {
                 description "1560.99 nm/192.053125 THz 3.125GHz spacing";
               }
               enum "1560.96" {
                 description "1560.96 nm/192.056250 THz 3.125/6.25GHz spacing";
               }
               enum "1560.94" {
                 description "1560.94 nm/192.059375 THz 3.125GHz spacing";
               }
               enum "1560.91" {
                 description "1560.91 nm/192.062500 THz 3.125/6.25/12.5GHz spacing";
               }
               enum "1560.89" {
                 description "1560.89 nm/192.065625 THz 3.125GHz spacing";
               }
               enum "1560.86" {
                 description "1560.86 nm/192.068750 THz 3.125/6.25GHz spacing";
               }
               enum "1560.83" {
                 description "1560.83 nm/192.071875 THz 3.125GHz spacing";
               }
               enum "1560.81" {
                 description "1560.81 nm/192.075000 THz 3.125/6.25/12.5/75GHz spacing";
               }
               enum "1560.78" {
                 description "1560.78 nm/192.078125 THz 3.125GHz spacing";
               }
               enum "1560.76" {
                 description "1560.76 nm/192.081250 THz 3.125/6.25GHz spacing";
               }
               enum "1560.73" {
                 description "1560.73 nm/192.084375 THz 3.125GHz spacing";
               }
               enum "1560.71" {
                 description "1560.71 nm/192.087500 THz 3.125/6.25/12.5GHz spacing";
               }
               enum "1560.68" {
                 description "1560.68 nm/192.090625 THz 3.125GHz spacing";
               }
               enum "1560.66" {
                 description "1560.66 nm/192.093750 THz 3.125/6.25GHz spacing";
               }
               enum "1560.63" {
                 description "1560.63 nm/192.096875 THz 3.125GHz spacing";
               }
               enum "1560.61" {
                 description "1560.61 nm/192.100000 THz 3.125/6.25/12.5/100GHz spacing";
               }
               enum "1560.58" {
                 description "1560.58 nm/192.103125 THz 3.125GHz spacing";
               }
               enum "1560.56" {
                 description "1560.56 nm/192.106250 THz 3.125/6.25GHz spacing";
               }
               enum "1560.53" {
                 description "1560.53 nm/192.109375 THz 3.125GHz spacing";
               }
               enum "1560.50" {
                 description "1560.50 nm/192.112500 THz 3.125/6.25/12.5GHz spacing";
               }
               enum "1560.48" {
                 description "1560.48 nm/192.115625 THz 3.125GHz spacing";
               }
               enum "1560.45" {
                 description "1560.45 nm/192.118750 THz 3.125/6.25GHz spacing";
               }
               enum "1560.43" {
                 description "1560.43 nm/192.121875 THz 3.125GHz spacing";
               }
               enum "1560.40" {
                 description "1560.40 nm/192.125000 THz 3.125/6.25/12.5GHz spacing";
               }
               enum "1560.38" {
                 description "1560.38 nm/192.128125 THz 3.125GHz spacing";
               }
               enum "1560.35" {
                 description "1560.35 nm/192.131250 THz 3.125/6.25GHz spacing";
               }
               enum "1560.33" {
                 description "1560.33 nm/192.134375 THz 3.125GHz spacing";
               }
               enum "1560.30" {
                 description "1560.30 nm/192.137500 THz 3.125/6.25/12.5GHz spacing";
               }
               enum "1560.28" {
                 description "1560.28 nm/192.140625 THz 3.125GHz spacing";
               }
               enum "1560.25" {
                 description "1560.25 nm/192.143750 THz 3.125/6.25GHz spacing";
               }
               enum "1560.23" {
                 description "1560.23 nm/192.146875 THz 3.125GHz spacing";
               }
               enum "1560.20" {
                 description "1560.20 nm/192.150000 THz 3.125/6.25/12.5/50/75GHz spacing";
               }
               enum "1560.17" {
                 description "1560.17 nm/192.153125 THz 3.125GHz spacing";
               }
               enum "1560.15" {
                 description "1560.15 nm/192.156250 THz 3.125/6.25GHz spacing";
               }
               enum "1560.12" {
                 description "1560.12 nm/192.159375 THz 3.125GHz spacing";
               }
               enum "1560.10" {
                 description "1560.10 nm/192.162500 THz 3.125/6.25/12.5GHz spacing";
               }
               enum "1560.07" {
                 description "1560.07 nm/192.165625 THz 3.125GHz spacing";
               }
               enum "1560.05" {
                 description "1560.05 nm/192.168750 THz 3.125/6.25GHz spacing";
               }
               enum "1560.02" {
                 description "1560.02 nm/192.171875 THz 3.125GHz spacing";
               }
               enum "1560.00" {
                 description "1560.00 nm/192.175000 THz 3.125/6.25/12.5GHz spacing";
               }
               enum "1559.97" {
                 description "1559.97 nm/192.178125 THz 3.125GHz spacing";
               }
               enum "1559.95" {
                 description "1559.95 nm/192.181250 THz 3.125/6.25GHz spacing";
               }
               enum "1559.92" {
                 description "1559.92 nm/192.184375 THz 3.125GHz spacing";
               }
               enum "1559.90" {
                 description "1559.90 nm/192.187500 THz 3.125/6.25/12.5GHz spacing";
               }
               enum "1559.87" {
                 description "1559.87 nm/192.190625 THz 3.125GHz spacing";
               }
               enum "1559.84" {
                 description "1559.84 nm/192.193750 THz 3.125/6.25GHz spacing";
               }
               enum "1559.82" {
                 description "1559.82 nm/192.196875 THz 3.125GHz spacing";
               }
               enum "1559.79" {
                 description "1559.79 nm/192.200000 THz 3.125/6.25/12.5/100GHz spacing";
               }
               enum "1559.77" {
                 description "1559.77 nm/192.203125 THz 3.125GHz spacing";
               }
               enum "1559.74" {
                 description "1559.74 nm/192.206250 THz 3.125/6.25GHz spacing";
               }
               enum "1559.72" {
                 description "1559.72 nm/192.209375 THz 3.125GHz spacing";
               }
               enum "1559.69" {
                 description "1559.69 nm/192.212500 THz 3.125/6.25/12.5GHz spacing";
               }
               enum "1559.67" {
                 description "1559.67 nm/192.215625 THz 3.125GHz spacing";
               }
               enum "1559.64" {
                 description "1559.64 nm/192.218750 THz 3.125/6.25GHz spacing";
               }
               enum "1559.62" {
                 description "1559.62 nm/192.221875 THz 3.125GHz spacing";
               }
               enum "1559.59" {
                 description "1559.59 nm/192.225000 THz 3.125/6.25/12.5/75GHz spacing";
               }
               enum "1559.57" {
                 description "1559.57 nm/192.228125 THz 3.125GHz spacing";
               }
               enum "1559.54" {
                 description "1559.54 nm/192.231250 THz 3.125/6.25GHz spacing";
               }
               enum "1559.52" {
                 description "1559.52 nm/192.234375 THz 3.125GHz spacing";
               }
               enum "1559.49" {
                 description "1559.49 nm/192.237500 THz 3.125/6.25/12.5GHz spacing";
               }
               enum "1559.46" {
                 description "1559.46 nm/192.240625 THz 3.125GHz spacing";
               }
               enum "1559.44" {
                 description "1559.44 nm/192.243750 THz 3.125/6.25GHz spacing";
               }
               enum "1559.41" {
                 description "1559.41 nm/192.246875 THz 3.125GHz spacing";
               }
               enum "1559.39" {
                 description "1559.39 nm/192.250000 THz 3.125/6.25/12.5/50GHz spacing";
               }
               enum "1559.36" {
                 description "1559.36 nm/192.253125 THz 3.125GHz spacing";
               }
               enum "1559.34" {
                 description "1559.34 nm/192.256250 THz 3.125/6.25GHz spacing";
               }
               enum "1559.31" {
                 description "1559.31 nm/192.259375 THz 3.125GHz spacing";
               }
               enum "1559.29" {
                 description "1559.29 nm/192.262500 THz 3.125/6.25/12.5GHz spacing";
               }
               enum "1559.26" {
                 description "1559.26 nm/192.265625 THz 3.125GHz spacing";
               }
               enum "1559.24" {
                 description "1559.24 nm/192.268750 THz 3.125/6.25GHz spacing";
               }
               enum "1559.21" {
                 description "1559.21 nm/192.271875 THz 3.125GHz spacing";
               }
               enum "1559.19" {
                 description "1559.19 nm/192.275000 THz 3.125/6.25/12.5GHz spacing";
               }
               enum "1559.16" {
                 description "1559.16 nm/192.278125 THz 3.125GHz spacing";
               }
               enum "1559.14" {
                 description "1559.14 nm/192.281250 THz 3.125/6.25GHz spacing";
               }
               enum "1559.11" {
                 description "1559.11 nm/192.284375 THz 3.125GHz spacing";
               }
               enum "1559.08" {
                 description "1559.08 nm/192.287500 THz 3.125/6.25/12.5GHz spacing";
               }
               enum "1559.06" {
                 description "1559.06 nm/192.290625 THz 3.125GHz spacing";
               }
               enum "1559.03" {
                 description "1559.03 nm/192.293750 THz 3.125/6.25GHz spacing";
               }
               enum "1559.01" {
                 description "1559.01 nm/192.296875 THz 3.125GHz spacing";
               }
               enum "1558.98" {
                 description "1558.98 nm/192.300000 THz 3.125/6.25/12.5/50/75/100GHz spacing";
               }
               enum "1558.96" {
                 description "1558.96 nm/192.303125 THz 3.125GHz spacing";
               }
               enum "1558.93" {
                 description "1558.93 nm/192.306250 THz 3.125/6.25GHz spacing";
               }
               enum "1558.91" {
                 description "1558.91 nm/192.309375 THz 3.125GHz spacing";
               }
               enum "1558.88" {
                 description "1558.88 nm/192.312500 THz 3.125/6.25/12.5GHz spacing";
               }
               enum "1558.86" {
                 description "1558.86 nm/192.315625 THz 3.125GHz spacing";
               }
               enum "1558.83" {
                 description "1558.83 nm/192.318750 THz 3.125/6.25GHz spacing";
               }
               enum "1558.81" {
                 description "1558.81 nm/192.321875 THz 3.125GHz spacing";
               }
               enum "1558.78" {
                 description "1558.78 nm/192.325000 THz 3.125/6.25/12.5GHz spacing";
               }
               enum "1558.76" {
                 description "1558.76 nm/192.328125 THz 3.125GHz spacing";
               }
               enum "1558.73" {
                 description "1558.73 nm/192.331250 THz 3.125/6.25GHz spacing";
               }
               enum "1558.70" {
                 description "1558.70 nm/192.334375 THz 3.125GHz spacing";
               }
               enum "1558.68" {
                 description "1558.68 nm/192.337500 THz 3.125/6.25/12.5GHz spacing";
               }
               enum "1558.65" {
                 description "1558.65 nm/192.340625 THz 3.125GHz spacing";
               }
               enum "1558.63" {
                 description "1558.63 nm/192.343750 THz 3.125/6.25GHz spacing";
               }
               enum "1558.60" {
                 description "1558.60 nm/192.346875 THz 3.125GHz spacing";
               }
               enum "1558.58" {
                 description "1558.58 nm/192.350000 THz 3.125/6.25/12.5/50GHz spacing";
               }
               enum "1558.55" {
                 description "1558.55 nm/192.353125 THz 3.125GHz spacing";
               }
               enum "1558.53" {
                 description "1558.53 nm/192.356250 THz 3.125/6.25GHz spacing";
               }
               enum "1558.50" {
                 description "1558.50 nm/192.359375 THz 3.125GHz spacing";
               }
               enum "1558.48" {
                 description "1558.48 nm/192.362500 THz 3.125/6.25/12.5GHz spacing";
               }
               enum "1558.45" {
                 description "1558.45 nm/192.365625 THz 3.125GHz spacing";
               }
               enum "1558.43" {
                 description "1558.43 nm/192.368750 THz 3.125/6.25GHz spacing";
               }
               enum "1558.40" {
                 description "1558.40 nm/192.371875 THz 3.125GHz spacing";
               }
               enum "1558.38" {
                 description "1558.38 nm/192.375000 THz 3.125/6.25/12.5/75GHz spacing";
               }
               enum "1558.35" {
                 description "1558.35 nm/192.378125 THz 3.125GHz spacing";
               }
               enum "1558.32" {
                 description "1558.32 nm/192.381250 THz 3.125/6.25GHz spacing";
               }
               enum "1558.30" {
                 description "1558.30 nm/192.384375 THz 3.125GHz spacing";
               }
               enum "1558.27" {
                 description "1558.27 nm/192.387500 THz 3.125/6.25/12.5GHz spacing";
               }
               enum "1558.25" {
                 description "1558.25 nm/192.390625 THz 3.125GHz spacing";
               }
               enum "1558.22" {
                 description "1558.22 nm/192.393750 THz 3.125/6.25GHz spacing";
               }
               enum "1558.20" {
                 description "1558.20 nm/192.396875 THz 3.125GHz spacing";
               }
               enum "1558.17" {
                 description "1558.17 nm/192.400000 THz 3.125/6.25/12.5/100GHz spacing";
               }
               enum "1558.15" {
                 description "1558.15 nm/192.403125 THz 3.125GHz spacing";
               }
               enum "1558.12" {
                 description "1558.12 nm/192.406250 THz 3.125/6.25GHz spacing";
               }
               enum "1558.10" {
                 description "1558.10 nm/192.409375 THz 3.125GHz spacing";
               }
               enum "1558.07" {
                 description "1558.07 nm/192.412500 THz 3.125/6.25/12.5GHz spacing";
               }
               enum "1558.05" {
                 description "1558.05 nm/192.415625 THz 3.125GHz spacing";
               }
               enum "1558.02" {
                 description "1558.02 nm/192.418750 THz 3.125/6.25GHz spacing";
               }
               enum "1558.00" {
                 description "1558.00 nm/192.421875 THz 3.125GHz spacing";
               }
               enum "1557.97" {
                 description "1557.97 nm/192.425000 THz 3.125/6.25/12.5GHz spacing";
               }
               enum "1557.95" {
                 description "1557.95 nm/192.428125 THz 3.125GHz spacing";
               }
               enum "1557.92" {
                 description "1557.92 nm/192.431250 THz 3.125/6.25GHz spacing";
               }
               enum "1557.89" {
                 description "1557.89 nm/192.434375 THz 3.125GHz spacing";
               }
               enum "1557.87" {
                 description "1557.87 nm/192.437500 THz 3.125/6.25/12.5GHz spacing";
               }
               enum "1557.84" {
                 description "1557.84 nm/192.440625 THz 3.125GHz spacing";
               }
               enum "1557.82" {
                 description "1557.82 nm/192.443750 THz 3.125/6.25GHz spacing";
               }
               enum "1557.79" {
                 description "1557.79 nm/192.446875 THz 3.125GHz spacing";
               }
               enum "1557.77" {
                 description "1557.77 nm/192.450000 THz 3.125/6.25/12.5/50/75GHz spacing";
               }
               enum "1557.74" {
                 description "1557.74 nm/192.453125 THz 3.125GHz spacing";
               }
               enum "1557.72" {
                 description "1557.72 nm/192.456250 THz 3.125/6.25GHz spacing";
               }
               enum "1557.69" {
                 description "1557.69 nm/192.459375 THz 3.125GHz spacing";
               }
               enum "1557.67" {
                 description "1557.67 nm/192.462500 THz 3.125/6.25/12.5GHz spacing";
               }
               enum "1557.64" {
                 description "1557.64 nm/192.465625 THz 3.125GHz spacing";
               }
               enum "1557.62" {
                 description "1557.62 nm/192.468750 THz 3.125/6.25GHz spacing";
               }
               enum "1557.59" {
                 description "1557.59 nm/192.471875 THz 3.125GHz spacing";
               }
               enum "1557.57" {
                 description "1557.57 nm/192.475000 THz 3.125/6.25/12.5GHz spacing";
               }
               enum "1557.54" {
                 description "1557.54 nm/192.478125 THz 3.125GHz spacing";
               }
               enum "1557.52" {
                 description "1557.52 nm/192.481250 THz 3.125/6.25GHz spacing";
               }
               enum "1557.49" {
                 description "1557.49 nm/192.484375 THz 3.125GHz spacing";
               }
               enum "1557.46" {
                 description "1557.46 nm/192.487500 THz 3.125/6.25/12.5GHz spacing";
               }
               enum "1557.44" {
                 description "1557.44 nm/192.490625 THz 3.125GHz spacing";
               }
               enum "1557.41" {
                 description "1557.41 nm/192.493750 THz 3.125/6.25GHz spacing";
               }
               enum "1557.39" {
                 description "1557.39 nm/192.496875 THz 3.125GHz spacing";
               }
               enum "1557.36" {
                 description "1557.36 nm/192.500000 THz 3.125/6.25/12.5/100GHz spacing";
               }
               enum "1557.34" {
                 description "1557.34 nm/192.503125 THz 3.125GHz spacing";
               }
               enum "1557.31" {
                 description "1557.31 nm/192.506250 THz 3.125/6.25GHz spacing";
               }
               enum "1557.29" {
                 description "1557.29 nm/192.509375 THz 3.125GHz spacing";
               }
               enum "1557.26" {
                 description "1557.26 nm/192.512500 THz 3.125/6.25/12.5GHz spacing";
               }
               enum "1557.24" {
                 description "1557.24 nm/192.515625 THz 3.125GHz spacing";
               }
               enum "1557.21" {
                 description "1557.21 nm/192.518750 THz 3.125/6.25GHz spacing";
               }
               enum "1557.19" {
                 description "1557.19 nm/192.521875 THz 3.125GHz spacing";
               }
               enum "1557.16" {
                 description "1557.16 nm/192.525000 THz 3.125/6.25/12.5/75GHz spacing";
               }
               enum "1557.14" {
                 description "1557.14 nm/192.528125 THz 3.125GHz spacing";
               }
               enum "1557.11" {
                 description "1557.11 nm/192.531250 THz 3.125/6.25GHz spacing";
               }
               enum "1557.09" {
                 description "1557.09 nm/192.534375 THz 3.125GHz spacing";
               }
               enum "1557.06" {
                 description "1557.06 nm/192.537500 THz 3.125/6.25/12.5GHz spacing";
               }
               enum "1557.03" {
                 description "1557.03 nm/192.540625 THz 3.125GHz spacing";
               }
               enum "1557.01" {
                 description "1557.01 nm/192.543750 THz 3.125/6.25GHz spacing";
               }
               enum "1556.98" {
                 description "1556.98 nm/192.546875 THz 3.125GHz spacing";
               }
               enum "1556.96" {
                 description "1556.96 nm/192.550000 THz 3.125/6.25/12.5/50GHz spacing";
               }
               enum "1556.93" {
                 description "1556.93 nm/192.553125 THz 3.125GHz spacing";
               }
               enum "1556.91" {
                 description "1556.91 nm/192.556250 THz 3.125/6.25GHz spacing";
               }
               enum "1556.88" {
                 description "1556.88 nm/192.559375 THz 3.125GHz spacing";
               }
               enum "1556.86" {
                 description "1556.86 nm/192.562500 THz 3.125/6.25/12.5GHz spacing";
               }
               enum "1556.83" {
                 description "1556.83 nm/192.565625 THz 3.125GHz spacing";
               }
               enum "1556.81" {
                 description "1556.81 nm/192.568750 THz 3.125/6.25GHz spacing";
               }
               enum "1556.78" {
                 description "1556.78 nm/192.571875 THz 3.125GHz spacing";
               }
               enum "1556.76" {
                 description "1556.76 nm/192.575000 THz 3.125/6.25/12.5GHz spacing";
               }
               enum "1556.73" {
                 description "1556.73 nm/192.578125 THz 3.125GHz spacing";
               }
               enum "1556.71" {
                 description "1556.71 nm/192.581250 THz 3.125/6.25GHz spacing";
               }
               enum "1556.68" {
                 description "1556.68 nm/192.584375 THz 3.125GHz spacing";
               }
               enum "1556.66" {
                 description "1556.66 nm/192.587500 THz 3.125/6.25/12.5GHz spacing";
               }
               enum "1556.63" {
                 description "1556.63 nm/192.590625 THz 3.125GHz spacing";
               }
               enum "1556.61" {
                 description "1556.61 nm/192.593750 THz 3.125/6.25GHz spacing";
               }
               enum "1556.58" {
                 description "1556.58 nm/192.596875 THz 3.125GHz spacing";
               }
               enum "1556.55" {
                 description "1556.55 nm/192.600000 THz 3.125/6.25/12.5/50/75/100GHz spacing";
               }
               enum "1556.53" {
                 description "1556.53 nm/192.603125 THz 3.125GHz spacing";
               }
               enum "1556.50" {
                 description "1556.50 nm/192.606250 THz 3.125/6.25GHz spacing";
               }
               enum "1556.48" {
                 description "1556.48 nm/192.609375 THz 3.125GHz spacing";
               }
               enum "1556.45" {
                 description "1556.45 nm/192.612500 THz 3.125/6.25/12.5GHz spacing";
               }
               enum "1556.43" {
                 description "1556.43 nm/192.615625 THz 3.125GHz spacing";
               }
               enum "1556.40" {
                 description "1556.40 nm/192.618750 THz 3.125/6.25GHz spacing";
               }
               enum "1556.38" {
                 description "1556.38 nm/192.621875 THz 3.125GHz spacing";
               }
               enum "1556.35" {
                 description "1556.35 nm/192.625000 THz 3.125/6.25/12.5GHz spacing";
               }
               enum "1556.33" {
                 description "1556.33 nm/192.628125 THz 3.125GHz spacing";
               }
               enum "1556.30" {
                 description "1556.30 nm/192.631250 THz 3.125/6.25GHz spacing";
               }
               enum "1556.28" {
                 description "1556.28 nm/192.634375 THz 3.125GHz spacing";
               }
               enum "1556.25" {
                 description "1556.25 nm/192.637500 THz 3.125/6.25/12.5GHz spacing";
               }
               enum "1556.23" {
                 description "1556.23 nm/192.640625 THz 3.125GHz spacing";
               }
               enum "1556.20" {
                 description "1556.20 nm/192.643750 THz 3.125/6.25GHz spacing";
               }
               enum "1556.18" {
                 description "1556.18 nm/192.646875 THz 3.125GHz spacing";
               }
               enum "1556.15" {
                 description "1556.15 nm/192.650000 THz 3.125/6.25/12.5/50GHz spacing";
               }
               enum "1556.13" {
                 description "1556.13 nm/192.653125 THz 3.125GHz spacing";
               }
               enum "1556.10" {
                 description "1556.10 nm/192.656250 THz 3.125/6.25GHz spacing";
               }
               enum "1556.08" {
                 description "1556.08 nm/192.659375 THz 3.125GHz spacing";
               }
               enum "1556.05" {
                 description "1556.05 nm/192.662500 THz 3.125/6.25/12.5GHz spacing";
               }
               enum "1556.02" {
                 description "1556.02 nm/192.665625 THz 3.125GHz spacing";
               }
               enum "1556.00" {
                 description "1556.00 nm/192.668750 THz 3.125/6.25GHz spacing";
               }
               enum "1555.97" {
                 description "1555.97 nm/192.671875 THz 3.125GHz spacing";
               }
               enum "1555.95" {
                 description "1555.95 nm/192.675000 THz 3.125/6.25/12.5/75GHz spacing";
               }
               enum "1555.92" {
                 description "1555.92 nm/192.678125 THz 3.125GHz spacing";
               }
               enum "1555.90" {
                 description "1555.90 nm/192.681250 THz 3.125/6.25GHz spacing";
               }
               enum "1555.87" {
                 description "1555.87 nm/192.684375 THz 3.125GHz spacing";
               }
               enum "1555.85" {
                 description "1555.85 nm/192.687500 THz 3.125/6.25/12.5GHz spacing";
               }
               enum "1555.82" {
                 description "1555.82 nm/192.690625 THz 3.125GHz spacing";
               }
               enum "1555.80" {
                 description "1555.80 nm/192.693750 THz 3.125/6.25GHz spacing";
               }
               enum "1555.77" {
                 description "1555.77 nm/192.696875 THz 3.125GHz spacing";
               }
               enum "1555.75" {
                 description "1555.75 nm/192.700000 THz 3.125/6.25/12.5/100GHz spacing";
               }
               enum "1555.72" {
                 description "1555.72 nm/192.703125 THz 3.125GHz spacing";
               }
               enum "1555.70" {
                 description "1555.70 nm/192.706250 THz 3.125/6.25GHz spacing";
               }
               enum "1555.67" {
                 description "1555.67 nm/192.709375 THz 3.125GHz spacing";
               }
               enum "1555.65" {
                 description "1555.65 nm/192.712500 THz 3.125/6.25/12.5GHz spacing";
               }
               enum "1555.62" {
                 description "1555.62 nm/192.715625 THz 3.125GHz spacing";
               }
               enum "1555.60" {
                 description "1555.60 nm/192.718750 THz 3.125/6.25GHz spacing";
               }
               enum "1555.57" {
                 description "1555.57 nm/192.721875 THz 3.125GHz spacing";
               }
               enum "1555.55" {
                 description "1555.55 nm/192.725000 THz 3.125/6.25/12.5GHz spacing";
               }
               enum "1555.52" {
                 description "1555.52 nm/192.728125 THz 3.125GHz spacing";
               }
               enum "1555.49" {
                 description "1555.49 nm/192.731250 THz 3.125/6.25GHz spacing";
               }
               enum "1555.47" {
                 description "1555.47 nm/192.734375 THz 3.125GHz spacing";
               }
               enum "1555.44" {
                 description "1555.44 nm/192.737500 THz 3.125/6.25/12.5GHz spacing";
               }
               enum "1555.42" {
                 description "1555.42 nm/192.740625 THz 3.125GHz spacing";
               }
               enum "1555.39" {
                 description "1555.39 nm/192.743750 THz 3.125/6.25GHz spacing";
               }
               enum "1555.37" {
                 description "1555.37 nm/192.746875 THz 3.125GHz spacing";
               }
               enum "1555.34" {
                 description "1555.34 nm/192.750000 THz 3.125/6.25/12.5/50/75GHz spacing";
               }
               enum "1555.32" {
                 description "1555.32 nm/192.753125 THz 3.125GHz spacing";
               }
               enum "1555.29" {
                 description "1555.29 nm/192.756250 THz 3.125/6.25GHz spacing";
               }
               enum "1555.27" {
                 description "1555.27 nm/192.759375 THz 3.125GHz spacing";
               }
               enum "1555.24" {
                 description "1555.24 nm/192.762500 THz 3.125/6.25/12.5GHz spacing";
               }
               enum "1555.22" {
                 description "1555.22 nm/192.765625 THz 3.125GHz spacing";
               }
               enum "1555.19" {
                 description "1555.19 nm/192.768750 THz 3.125/6.25GHz spacing";
               }
               enum "1555.17" {
                 description "1555.17 nm/192.771875 THz 3.125GHz spacing";
               }
               enum "1555.14" {
                 description "1555.14 nm/192.775000 THz 3.125/6.25/12.5GHz spacing";
               }
               enum "1555.12" {
                 description "1555.12 nm/192.778125 THz 3.125GHz spacing";
               }
               enum "1555.09" {
                 description "1555.09 nm/192.781250 THz 3.125/6.25GHz spacing";
               }
               enum "1555.07" {
                 description "1555.07 nm/192.784375 THz 3.125GHz spacing";
               }
               enum "1555.04" {
                 description "1555.04 nm/192.787500 THz 3.125/6.25/12.5GHz spacing";
               }
               enum "1555.02" {
                 description "1555.02 nm/192.790625 THz 3.125GHz spacing";
               }
               enum "1554.99" {
                 description "1554.99 nm/192.793750 THz 3.125/6.25GHz spacing";
               }
               enum "1554.97" {
                 description "1554.97 nm/192.796875 THz 3.125GHz spacing";
               }
               enum "1554.94" {
                 description "1554.94 nm/192.800000 THz 3.125/6.25/12.5/100GHz spacing";
               }
               enum "1554.91" {
                 description "1554.91 nm/192.803125 THz 3.125GHz spacing";
               }
               enum "1554.89" {
                 description "1554.89 nm/192.806250 THz 3.125/6.25GHz spacing";
               }
               enum "1554.86" {
                 description "1554.86 nm/192.809375 THz 3.125GHz spacing";
               }
               enum "1554.84" {
                 description "1554.84 nm/192.812500 THz 3.125/6.25/12.5GHz spacing";
               }
               enum "1554.81" {
                 description "1554.81 nm/192.815625 THz 3.125GHz spacing";
               }
               enum "1554.79" {
                 description "1554.79 nm/192.818750 THz 3.125/6.25GHz spacing";
               }
               enum "1554.76" {
                 description "1554.76 nm/192.821875 THz 3.125GHz spacing";
               }
               enum "1554.74" {
                 description "1554.74 nm/192.825000 THz 3.125/6.25/12.5/75GHz spacing";
               }
               enum "1554.71" {
                 description "1554.71 nm/192.828125 THz 3.125GHz spacing";
               }
               enum "1554.69" {
                 description "1554.69 nm/192.831250 THz 3.125/6.25GHz spacing";
               }
               enum "1554.66" {
                 description "1554.66 nm/192.834375 THz 3.125GHz spacing";
               }
               enum "1554.64" {
                 description "1554.64 nm/192.837500 THz 3.125/6.25/12.5GHz spacing";
               }
               enum "1554.61" {
                 description "1554.61 nm/192.840625 THz 3.125GHz spacing";
               }
               enum "1554.59" {
                 description "1554.59 nm/192.843750 THz 3.125/6.25GHz spacing";
               }
               enum "1554.56" {
                 description "1554.56 nm/192.846875 THz 3.125GHz spacing";
               }
               enum "1554.54" {
                 description "1554.54 nm/192.850000 THz 3.125/6.25/12.5/50GHz spacing";
               }
               enum "1554.51" {
                 description "1554.51 nm/192.853125 THz 3.125GHz spacing";
               }
               enum "1554.49" {
                 description "1554.49 nm/192.856250 THz 3.125/6.25GHz spacing";
               }
               enum "1554.46" {
                 description "1554.46 nm/192.859375 THz 3.125GHz spacing";
               }
               enum "1554.44" {
                 description "1554.44 nm/192.862500 THz 3.125/6.25/12.5GHz spacing";
               }
               enum "1554.41" {
                 description "1554.41 nm/192.865625 THz 3.125GHz spacing";
               }
               enum "1554.39" {
                 description "1554.39 nm/192.868750 THz 3.125/6.25GHz spacing";
               }
               enum "1554.36" {
                 description "1554.36 nm/192.871875 THz 3.125GHz spacing";
               }
               enum "1554.34" {
                 description "1554.34 nm/192.875000 THz 3.125/6.25/12.5GHz spacing";
               }
               enum "1554.31" {
                 description "1554.31 nm/192.878125 THz 3.125GHz spacing";
               }
               enum "1554.29" {
                 description "1554.29 nm/192.881250 THz 3.125/6.25GHz spacing";
               }
               enum "1554.26" {
                 description "1554.26 nm/192.884375 THz 3.125GHz spacing";
               }
               enum "1554.23" {
                 description "1554.23 nm/192.887500 THz 3.125/6.25/12.5GHz spacing";
               }
               enum "1554.21" {
                 description "1554.21 nm/192.890625 THz 3.125GHz spacing";
               }
               enum "1554.18" {
                 description "1554.18 nm/192.893750 THz 3.125/6.25GHz spacing";
               }
               enum "1554.16" {
                 description "1554.16 nm/192.896875 THz 3.125GHz spacing";
               }
               enum "1554.13" {
                 description "1554.13 nm/192.900000 THz 3.125/6.25/12.5/50/75/100GHz spacing";
               }
               enum "1554.11" {
                 description "1554.11 nm/192.903125 THz 3.125GHz spacing";
               }
               enum "1554.08" {
                 description "1554.08 nm/192.906250 THz 3.125/6.25GHz spacing";
               }
               enum "1554.06" {
                 description "1554.06 nm/192.909375 THz 3.125GHz spacing";
               }
               enum "1554.03" {
                 description "1554.03 nm/192.912500 THz 3.125/6.25/12.5GHz spacing";
               }
               enum "1554.01" {
                 description "1554.01 nm/192.915625 THz 3.125GHz spacing";
               }
               enum "1553.98" {
                 description "1553.98 nm/192.918750 THz 3.125/6.25GHz spacing";
               }
               enum "1553.96" {
                 description "1553.96 nm/192.921875 THz 3.125GHz spacing";
               }
               enum "1553.93" {
                 description "1553.93 nm/192.925000 THz 3.125/6.25/12.5GHz spacing";
               }
               enum "1553.91" {
                 description "1553.91 nm/192.928125 THz 3.125GHz spacing";
               }
               enum "1553.88" {
                 description "1553.88 nm/192.931250 THz 3.125/6.25GHz spacing";
               }
               enum "1553.86" {
                 description "1553.86 nm/192.934375 THz 3.125GHz spacing";
               }
               enum "1553.83" {
                 description "1553.83 nm/192.937500 THz 3.125/6.25/12.5GHz spacing";
               }
               enum "1553.81" {
                 description "1553.81 nm/192.940625 THz 3.125GHz spacing";
               }
               enum "1553.78" {
                 description "1553.78 nm/192.943750 THz 3.125/6.25GHz spacing";
               }
               enum "1553.76" {
                 description "1553.76 nm/192.946875 THz 3.125GHz spacing";
               }
               enum "1553.73" {
                 description "1553.73 nm/192.950000 THz 3.125/6.25/12.5/50GHz spacing";
               }
               enum "1553.71" {
                 description "1553.71 nm/192.953125 THz 3.125GHz spacing";
               }
               enum "1553.68" {
                 description "1553.68 nm/192.956250 THz 3.125/6.25GHz spacing";
               }
               enum "1553.66" {
                 description "1553.66 nm/192.959375 THz 3.125GHz spacing";
               }
               enum "1553.63" {
                 description "1553.63 nm/192.962500 THz 3.125/6.25/12.5GHz spacing";
               }
               enum "1553.61" {
                 description "1553.61 nm/192.965625 THz 3.125GHz spacing";
               }
               enum "1553.58" {
                 description "1553.58 nm/192.968750 THz 3.125/6.25GHz spacing";
               }
               enum "1553.56" {
                 description "1553.56 nm/192.971875 THz 3.125GHz spacing";
               }
               enum "1553.53" {
                 description "1553.53 nm/192.975000 THz 3.125/6.25/12.5/75GHz spacing";
               }
               enum "1553.50" {
                 description "1553.50 nm/192.978125 THz 3.125GHz spacing";
               }
               enum "1553.48" {
                 description "1553.48 nm/192.981250 THz 3.125/6.25GHz spacing";
               }
               enum "1553.45" {
                 description "1553.45 nm/192.984375 THz 3.125GHz spacing";
               }
               enum "1553.43" {
                 description "1553.43 nm/192.987500 THz 3.125/6.25/12.5GHz spacing";
               }
               enum "1553.40" {
                 description "1553.40 nm/192.990625 THz 3.125GHz spacing";
               }
               enum "1553.38" {
                 description "1553.38 nm/192.993750 THz 3.125/6.25GHz spacing";
               }
               enum "1553.35" {
                 description "1553.35 nm/192.996875 THz 3.125GHz spacing";
               }
               enum "1553.33" {
                 description "1553.33 nm/193.000000 THz 3.125/6.25/12.5/100GHz spacing";
               }
               enum "1553.30" {
                 description "1553.30 nm/193.003125 THz 3.125GHz spacing";
               }
               enum "1553.28" {
                 description "1553.28 nm/193.006250 THz 3.125/6.25GHz spacing";
               }
               enum "1553.25" {
                 description "1553.25 nm/193.009375 THz 3.125GHz spacing";
               }
               enum "1553.23" {
                 description "1553.23 nm/193.012500 THz 3.125/6.25/12.5GHz spacing";
               }
               enum "1553.20" {
                 description "1553.20 nm/193.015625 THz 3.125GHz spacing";
               }
               enum "1553.18" {
                 description "1553.18 nm/193.018750 THz 3.125/6.25GHz spacing";
               }
               enum "1553.15" {
                 description "1553.15 nm/193.021875 THz 3.125GHz spacing";
               }
               enum "1553.13" {
                 description "1553.13 nm/193.025000 THz 3.125/6.25/12.5GHz spacing";
               }
               enum "1553.10" {
                 description "1553.10 nm/193.028125 THz 3.125GHz spacing";
               }
               enum "1553.08" {
                 description "1553.08 nm/193.031250 THz 3.125/6.25GHz spacing";
               }
               enum "1553.05" {
                 description "1553.05 nm/193.034375 THz 3.125GHz spacing";
               }
               enum "1553.03" {
                 description "1553.03 nm/193.037500 THz 3.125/6.25/12.5GHz spacing";
               }
               enum "1553.00" {
                 description "1553.00 nm/193.040625 THz 3.125GHz spacing";
               }
               enum "1552.98" {
                 description "1552.98 nm/193.043750 THz 3.125/6.25GHz spacing";
               }
               enum "1552.95" {
                 description "1552.95 nm/193.046875 THz 3.125GHz spacing";
               }
               enum "1552.93" {
                 description "1552.93 nm/193.050000 THz 3.125/6.25/12.5/50/75GHz spacing";
               }
               enum "1552.90" {
                 description "1552.90 nm/193.053125 THz 3.125GHz spacing";
               }
               enum "1552.88" {
                 description "1552.88 nm/193.056250 THz 3.125/6.25GHz spacing";
               }
               enum "1552.85" {
                 description "1552.85 nm/193.059375 THz 3.125GHz spacing";
               }
               enum "1552.83" {
                 description "1552.83 nm/193.062500 THz 3.125/6.25/12.5GHz spacing";
               }
               enum "1552.80" {
                 description "1552.80 nm/193.065625 THz 3.125GHz spacing";
               }
               enum "1552.78" {
                 description "1552.78 nm/193.068750 THz 3.125/6.25GHz spacing";
               }
               enum "1552.75" {
                 description "1552.75 nm/193.071875 THz 3.125GHz spacing";
               }
               enum "1552.73" {
                 description "1552.73 nm/193.075000 THz 3.125/6.25/12.5GHz spacing";
               }
               enum "1552.70" {
                 description "1552.70 nm/193.078125 THz 3.125GHz spacing";
               }
               enum "1552.68" {
                 description "1552.68 nm/193.081250 THz 3.125/6.25GHz spacing";
               }
               enum "1552.65" {
                 description "1552.65 nm/193.084375 THz 3.125GHz spacing";
               }
               enum "1552.62" {
                 description "1552.62 nm/193.087500 THz 3.125/6.25/12.5GHz spacing";
               }
               enum "1552.60" {
                 description "1552.60 nm/193.090625 THz 3.125GHz spacing";
               }
               enum "1552.57" {
                 description "1552.57 nm/193.093750 THz 3.125/6.25GHz spacing";
               }
               enum "1552.55" {
                 description "1552.55 nm/193.096875 THz 3.125GHz spacing";
               }
               enum "1552.52" {
                 description "1552.52 nm/193.100000 THz 3.125/6.25/12.5/100GHz spacing";
               }
               enum "1552.50" {
                 description "1552.50 nm/193.103125 THz 3.125GHz spacing";
               }
               enum "1552.47" {
                 description "1552.47 nm/193.106250 THz 3.125/6.25GHz spacing";
               }
               enum "1552.45" {
                 description "1552.45 nm/193.109375 THz 3.125GHz spacing";
               }
               enum "1552.42" {
                 description "1552.42 nm/193.112500 THz 3.125/6.25/12.5GHz spacing";
               }
               enum "1552.40" {
                 description "1552.40 nm/193.115625 THz 3.125GHz spacing";
               }
               enum "1552.37" {
                 description "1552.37 nm/193.118750 THz 3.125/6.25GHz spacing";
               }
               enum "1552.35" {
                 description "1552.35 nm/193.121875 THz 3.125GHz spacing";
               }
               enum "1552.32" {
                 description "1552.32 nm/193.125000 THz 3.125/6.25/12.5/75GHz spacing";
               }
               enum "1552.30" {
                 description "1552.30 nm/193.128125 THz 3.125GHz spacing";
               }
               enum "1552.27" {
                 description "1552.27 nm/193.131250 THz 3.125/6.25GHz spacing";
               }
               enum "1552.25" {
                 description "1552.25 nm/193.134375 THz 3.125GHz spacing";
               }
               enum "1552.22" {
                 description "1552.22 nm/193.137500 THz 3.125/6.25/12.5GHz spacing";
               }
               enum "1552.20" {
                 description "1552.20 nm/193.140625 THz 3.125GHz spacing";
               }
               enum "1552.17" {
                 description "1552.17 nm/193.143750 THz 3.125/6.25GHz spacing";
               }
               enum "1552.15" {
                 description "1552.15 nm/193.146875 THz 3.125GHz spacing";
               }
               enum "1552.12" {
                 description "1552.12 nm/193.150000 THz 3.125/6.25/12.5/50GHz spacing";
               }
               enum "1552.10" {
                 description "1552.10 nm/193.153125 THz 3.125GHz spacing";
               }
               enum "1552.07" {
                 description "1552.07 nm/193.156250 THz 3.125/6.25GHz spacing";
               }
               enum "1552.05" {
                 description "1552.05 nm/193.159375 THz 3.125GHz spacing";
               }
               enum "1552.02" {
                 description "1552.02 nm/193.162500 THz 3.125/6.25/12.5GHz spacing";
               }
               enum "1552.00" {
                 description "1552.00 nm/193.165625 THz 3.125GHz spacing";
               }
               enum "1551.97" {
                 description "1551.97 nm/193.168750 THz 3.125/6.25GHz spacing";
               }
               enum "1551.95" {
                 description "1551.95 nm/193.171875 THz 3.125GHz spacing";
               }
               enum "1551.92" {
                 description "1551.92 nm/193.175000 THz 3.125/6.25/12.5GHz spacing";
               }
               enum "1551.90" {
                 description "1551.90 nm/193.178125 THz 3.125GHz spacing";
               }
               enum "1551.87" {
                 description "1551.87 nm/193.181250 THz 3.125/6.25GHz spacing";
               }
               enum "1551.85" {
                 description "1551.85 nm/193.184375 THz 3.125GHz spacing";
               }
               enum "1551.82" {
                 description "1551.82 nm/193.187500 THz 3.125/6.25/12.5GHz spacing";
               }
               enum "1551.80" {
                 description "1551.80 nm/193.190625 THz 3.125GHz spacing";
               }
               enum "1551.77" {
                 description "1551.77 nm/193.193750 THz 3.125/6.25GHz spacing";
               }
               enum "1551.75" {
                 description "1551.75 nm/193.196875 THz 3.125GHz spacing";
               }
               enum "1551.72" {
                 description "1551.72 nm/193.200000 THz 3.125/6.25/12.5/50/75/100GHz spacing";
               }
               enum "1551.70" {
                 description "1551.70 nm/193.203125 THz 3.125GHz spacing";
               }
               enum "1551.67" {
                 description "1551.67 nm/193.206250 THz 3.125/6.25GHz spacing";
               }
               enum "1551.65" {
                 description "1551.65 nm/193.209375 THz 3.125GHz spacing";
               }
               enum "1551.62" {
                 description "1551.62 nm/193.212500 THz 3.125/6.25/12.5GHz spacing";
               }
               enum "1551.60" {
                 description "1551.60 nm/193.215625 THz 3.125GHz spacing";
               }
               enum "1551.57" {
                 description "1551.57 nm/193.218750 THz 3.125/6.25GHz spacing";
               }
               enum "1551.55" {
                 description "1551.55 nm/193.221875 THz 3.125GHz spacing";
               }
               enum "1551.52" {
                 description "1551.52 nm/193.225000 THz 3.125/6.25/12.5GHz spacing";
               }
               enum "1551.49" {
                 description "1551.49 nm/193.228125 THz 3.125GHz spacing";
               }
               enum "1551.47" {
                 description "1551.47 nm/193.231250 THz 3.125/6.25GHz spacing";
               }
               enum "1551.44" {
                 description "1551.44 nm/193.234375 THz 3.125GHz spacing";
               }
               enum "1551.42" {
                 description "1551.42 nm/193.237500 THz 3.125/6.25/12.5GHz spacing";
               }
               enum "1551.39" {
                 description "1551.39 nm/193.240625 THz 3.125GHz spacing";
               }
               enum "1551.37" {
                 description "1551.37 nm/193.243750 THz 3.125/6.25GHz spacing";
               }
               enum "1551.34" {
                 description "1551.34 nm/193.246875 THz 3.125GHz spacing";
               }
               enum "1551.32" {
                 description "1551.32 nm/193.250000 THz 3.125/6.25/12.5/50GHz spacing";
               }
               enum "1551.29" {
                 description "1551.29 nm/193.253125 THz 3.125GHz spacing";
               }
               enum "1551.27" {
                 description "1551.27 nm/193.256250 THz 3.125/6.25GHz spacing";
               }
               enum "1551.24" {
                 description "1551.24 nm/193.259375 THz 3.125GHz spacing";
               }
               enum "1551.22" {
                 description "1551.22 nm/193.262500 THz 3.125/6.25/12.5GHz spacing";
               }
               enum "1551.19" {
                 description "1551.19 nm/193.265625 THz 3.125GHz spacing";
               }
               enum "1551.17" {
                 description "1551.17 nm/193.268750 THz 3.125/6.25GHz spacing";
               }
               enum "1551.14" {
                 description "1551.14 nm/193.271875 THz 3.125GHz spacing";
               }
               enum "1551.12" {
                 description "1551.12 nm/193.275000 THz 3.125/6.25/12.5/75GHz spacing";
               }
               enum "1551.09" {
                 description "1551.09 nm/193.278125 THz 3.125GHz spacing";
               }
               enum "1551.07" {
                 description "1551.07 nm/193.281250 THz 3.125/6.25GHz spacing";
               }
               enum "1551.04" {
                 description "1551.04 nm/193.284375 THz 3.125GHz spacing";
               }
               enum "1551.02" {
                 description "1551.02 nm/193.287500 THz 3.125/6.25/12.5GHz spacing";
               }
               enum "1550.99" {
                 description "1550.99 nm/193.290625 THz 3.125GHz spacing";
               }
               enum "1550.97" {
                 description "1550.97 nm/193.293750 THz 3.125/6.25GHz spacing";
               }
               enum "1550.94" {
                 description "1550.94 nm/193.296875 THz 3.125GHz spacing";
               }
               enum "1550.92" {
                 description "1550.92 nm/193.300000 THz 3.125/6.25/12.5/100GHz spacing";
               }
               enum "1550.89" {
                 description "1550.89 nm/193.303125 THz 3.125GHz spacing";
               }
               enum "1550.87" {
                 description "1550.87 nm/193.306250 THz 3.125/6.25GHz spacing";
               }
               enum "1550.84" {
                 description "1550.84 nm/193.309375 THz 3.125GHz spacing";
               }
               enum "1550.82" {
                 description "1550.82 nm/193.312500 THz 3.125/6.25/12.5GHz spacing";
               }
               enum "1550.79" {
                 description "1550.79 nm/193.315625 THz 3.125GHz spacing";
               }
               enum "1550.77" {
                 description "1550.77 nm/193.318750 THz 3.125/6.25GHz spacing";
               }
               enum "1550.74" {
                 description "1550.74 nm/193.321875 THz 3.125GHz spacing";
               }
               enum "1550.72" {
                 description "1550.72 nm/193.325000 THz 3.125/6.25/12.5GHz spacing";
               }
               enum "1550.69" {
                 description "1550.69 nm/193.328125 THz 3.125GHz spacing";
               }
               enum "1550.67" {
                 description "1550.67 nm/193.331250 THz 3.125/6.25GHz spacing";
               }
               enum "1550.64" {
                 description "1550.64 nm/193.334375 THz 3.125GHz spacing";
               }
               enum "1550.62" {
                 description "1550.62 nm/193.337500 THz 3.125/6.25/12.5GHz spacing";
               }
               enum "1550.59" {
                 description "1550.59 nm/193.340625 THz 3.125GHz spacing";
               }
               enum "1550.57" {
                 description "1550.57 nm/193.343750 THz 3.125/6.25GHz spacing";
               }
               enum "1550.54" {
                 description "1550.54 nm/193.346875 THz 3.125GHz spacing";
               }
               enum "1550.52" {
                 description "1550.52 nm/193.350000 THz 3.125/6.25/12.5/50/75GHz spacing";
               }
               enum "1550.49" {
                 description "1550.49 nm/193.353125 THz 3.125GHz spacing";
               }
               enum "1550.47" {
                 description "1550.47 nm/193.356250 THz 3.125/6.25GHz spacing";
               }
               enum "1550.44" {
                 description "1550.44 nm/193.359375 THz 3.125GHz spacing";
               }
               enum "1550.42" {
                 description "1550.42 nm/193.362500 THz 3.125/6.25/12.5GHz spacing";
               }
               enum "1550.39" {
                 description "1550.39 nm/193.365625 THz 3.125GHz spacing";
               }
               enum "1550.37" {
                 description "1550.37 nm/193.368750 THz 3.125/6.25GHz spacing";
               }
               enum "1550.34" {
                 description "1550.34 nm/193.371875 THz 3.125GHz spacing";
               }
               enum "1550.32" {
                 description "1550.32 nm/193.375000 THz 3.125/6.25/12.5GHz spacing";
               }
               enum "1550.29" {
                 description "1550.29 nm/193.378125 THz 3.125GHz spacing";
               }
               enum "1550.27" {
                 description "1550.27 nm/193.381250 THz 3.125/6.25GHz spacing";
               }
               enum "1550.24" {
                 description "1550.24 nm/193.384375 THz 3.125GHz spacing";
               }
               enum "1550.22" {
                 description "1550.22 nm/193.387500 THz 3.125/6.25/12.5GHz spacing";
               }
               enum "1550.19" {
                 description "1550.19 nm/193.390625 THz 3.125GHz spacing";
               }
               enum "1550.17" {
                 description "1550.17 nm/193.393750 THz 3.125/6.25GHz spacing";
               }
               enum "1550.14" {
                 description "1550.14 nm/193.396875 THz 3.125GHz spacing";
               }
               enum "1550.12" {
                 description "1550.12 nm/193.400000 THz 3.125/6.25/12.5/100GHz spacing";
               }
               enum "1550.09" {
                 description "1550.09 nm/193.403125 THz 3.125GHz spacing";
               }
               enum "1550.07" {
                 description "1550.07 nm/193.406250 THz 3.125/6.25GHz spacing";
               }
               enum "1550.04" {
                 description "1550.04 nm/193.409375 THz 3.125GHz spacing";
               }
               enum "1550.02" {
                 description "1550.02 nm/193.412500 THz 3.125/6.25/12.5GHz spacing";
               }
               enum "1549.99" {
                 description "1549.99 nm/193.415625 THz 3.125GHz spacing";
               }
               enum "1549.97" {
                 description "1549.97 nm/193.418750 THz 3.125/6.25GHz spacing";
               }
               enum "1549.94" {
                 description "1549.94 nm/193.421875 THz 3.125GHz spacing";
               }
               enum "1549.92" {
                 description "1549.92 nm/193.425000 THz 3.125/6.25/12.5/75GHz spacing";
               }
               enum "1549.89" {
                 description "1549.89 nm/193.428125 THz 3.125GHz spacing";
               }
               enum "1549.87" {
                 description "1549.87 nm/193.431250 THz 3.125/6.25GHz spacing";
               }
               enum "1549.84" {
                 description "1549.84 nm/193.434375 THz 3.125GHz spacing";
               }
               enum "1549.82" {
                 description "1549.82 nm/193.437500 THz 3.125/6.25/12.5GHz spacing";
               }
               enum "1549.79" {
                 description "1549.79 nm/193.440625 THz 3.125GHz spacing";
               }
               enum "1549.77" {
                 description "1549.77 nm/193.443750 THz 3.125/6.25GHz spacing";
               }
               enum "1549.74" {
                 description "1549.74 nm/193.446875 THz 3.125GHz spacing";
               }
               enum "1549.72" {
                 description "1549.72 nm/193.450000 THz 3.125/6.25/12.5/50GHz spacing";
               }
               enum "1549.69" {
                 description "1549.69 nm/193.453125 THz 3.125GHz spacing";
               }
               enum "1549.67" {
                 description "1549.67 nm/193.456250 THz 3.125/6.25GHz spacing";
               }
               enum "1549.64" {
                 description "1549.64 nm/193.459375 THz 3.125GHz spacing";
               }
               enum "1549.62" {
                 description "1549.62 nm/193.462500 THz 3.125/6.25/12.5GHz spacing";
               }
               enum "1549.59" {
                 description "1549.59 nm/193.465625 THz 3.125GHz spacing";
               }
               enum "1549.57" {
                 description "1549.57 nm/193.468750 THz 3.125/6.25GHz spacing";
               }
               enum "1549.54" {
                 description "1549.54 nm/193.471875 THz 3.125GHz spacing";
               }
               enum "1549.52" {
                 description "1549.52 nm/193.475000 THz 3.125/6.25/12.5GHz spacing";
               }
               enum "1549.49" {
                 description "1549.49 nm/193.478125 THz 3.125GHz spacing";
               }
               enum "1549.47" {
                 description "1549.47 nm/193.481250 THz 3.125/6.25GHz spacing";
               }
               enum "1549.44" {
                 description "1549.44 nm/193.484375 THz 3.125GHz spacing";
               }
               enum "1549.42" {
                 description "1549.42 nm/193.487500 THz 3.125/6.25/12.5GHz spacing";
               }
               enum "1549.39" {
                 description "1549.39 nm/193.490625 THz 3.125GHz spacing";
               }
               enum "1549.37" {
                 description "1549.37 nm/193.493750 THz 3.125/6.25GHz spacing";
               }
               enum "1549.34" {
                 description "1549.34 nm/193.496875 THz 3.125GHz spacing";
               }
               enum "1549.32" {
                 description "1549.32 nm/193.500000 THz 3.125/6.25/12.5/50/75/100GHz spacing";
               }
               enum "1549.29" {
                 description "1549.29 nm/193.503125 THz 3.125GHz spacing";
               }
               enum "1549.26" {
                 description "1549.26 nm/193.506250 THz 3.125/6.25GHz spacing";
               }
               enum "1549.24" {
                 description "1549.24 nm/193.509375 THz 3.125GHz spacing";
               }
               enum "1549.21" {
                 description "1549.21 nm/193.512500 THz 3.125/6.25/12.5GHz spacing";
               }
               enum "1549.19" {
                 description "1549.19 nm/193.515625 THz 3.125GHz spacing";
               }
               enum "1549.16" {
                 description "1549.16 nm/193.518750 THz 3.125/6.25GHz spacing";
               }
               enum "1549.14" {
                 description "1549.14 nm/193.521875 THz 3.125GHz spacing";
               }
               enum "1549.11" {
                 description "1549.11 nm/193.525000 THz 3.125/6.25/12.5GHz spacing";
               }
               enum "1549.09" {
                 description "1549.09 nm/193.528125 THz 3.125GHz spacing";
               }
               enum "1549.06" {
                 description "1549.06 nm/193.531250 THz 3.125/6.25GHz spacing";
               }
               enum "1549.04" {
                 description "1549.04 nm/193.534375 THz 3.125GHz spacing";
               }
               enum "1549.01" {
                 description "1549.01 nm/193.537500 THz 3.125/6.25/12.5GHz spacing";
               }
               enum "1548.99" {
                 description "1548.99 nm/193.540625 THz 3.125GHz spacing";
               }
               enum "1548.96" {
                 description "1548.96 nm/193.543750 THz 3.125/6.25GHz spacing";
               }
               enum "1548.94" {
                 description "1548.94 nm/193.546875 THz 3.125GHz spacing";
               }
               enum "1548.91" {
                 description "1548.91 nm/193.550000 THz 3.125/6.25/12.5/50GHz spacing";
               }
               enum "1548.89" {
                 description "1548.89 nm/193.553125 THz 3.125GHz spacing";
               }
               enum "1548.86" {
                 description "1548.86 nm/193.556250 THz 3.125/6.25GHz spacing";
               }
               enum "1548.84" {
                 description "1548.84 nm/193.559375 THz 3.125GHz spacing";
               }
               enum "1548.81" {
                 description "1548.81 nm/193.562500 THz 3.125/6.25/12.5GHz spacing";
               }
               enum "1548.79" {
                 description "1548.79 nm/193.565625 THz 3.125GHz spacing";
               }
               enum "1548.76" {
                 description "1548.76 nm/193.568750 THz 3.125/6.25GHz spacing";
               }
               enum "1548.74" {
                 description "1548.74 nm/193.571875 THz 3.125GHz spacing";
               }
               enum "1548.71" {
                 description "1548.71 nm/193.575000 THz 3.125/6.25/12.5/75GHz spacing";
               }
               enum "1548.69" {
                 description "1548.69 nm/193.578125 THz 3.125GHz spacing";
               }
               enum "1548.66" {
                 description "1548.66 nm/193.581250 THz 3.125/6.25GHz spacing";
               }
               enum "1548.64" {
                 description "1548.64 nm/193.584375 THz 3.125GHz spacing";
               }
               enum "1548.61" {
                 description "1548.61 nm/193.587500 THz 3.125/6.25/12.5GHz spacing";
               }
               enum "1548.59" {
                 description "1548.59 nm/193.590625 THz 3.125GHz spacing";
               }
               enum "1548.56" {
                 description "1548.56 nm/193.593750 THz 3.125/6.25GHz spacing";
               }
               enum "1548.54" {
                 description "1548.54 nm/193.596875 THz 3.125GHz spacing";
               }
               enum "1548.51" {
                 description "1548.51 nm/193.600000 THz 3.125/6.25/12.5/100GHz spacing";
               }
               enum "1548.49" {
                 description "1548.49 nm/193.603125 THz 3.125GHz spacing";
               }
               enum "1548.46" {
                 description "1548.46 nm/193.606250 THz 3.125/6.25GHz spacing";
               }
               enum "1548.44" {
                 description "1548.44 nm/193.609375 THz 3.125GHz spacing";
               }
               enum "1548.41" {
                 description "1548.41 nm/193.612500 THz 3.125/6.25/12.5GHz spacing";
               }
               enum "1548.39" {
                 description "1548.39 nm/193.615625 THz 3.125GHz spacing";
               }
               enum "1548.36" {
                 description "1548.36 nm/193.618750 THz 3.125/6.25GHz spacing";
               }
               enum "1548.34" {
                 description "1548.34 nm/193.621875 THz 3.125GHz spacing";
               }
               enum "1548.31" {
                 description "1548.31 nm/193.625000 THz 3.125/6.25/12.5GHz spacing";
               }
               enum "1548.29" {
                 description "1548.29 nm/193.628125 THz 3.125GHz spacing";
               }
               enum "1548.26" {
                 description "1548.26 nm/193.631250 THz 3.125/6.25GHz spacing";
               }
               enum "1548.24" {
                 description "1548.24 nm/193.634375 THz 3.125GHz spacing";
               }
               enum "1548.21" {
                 description "1548.21 nm/193.637500 THz 3.125/6.25/12.5GHz spacing";
               }
               enum "1548.19" {
                 description "1548.19 nm/193.640625 THz 3.125GHz spacing";
               }
               enum "1548.16" {
                 description "1548.16 nm/193.643750 THz 3.125/6.25GHz spacing";
               }
               enum "1548.14" {
                 description "1548.14 nm/193.646875 THz 3.125GHz spacing";
               }
               enum "1548.11" {
                 description "1548.11 nm/193.650000 THz 3.125/6.25/12.5/50/75GHz spacing";
               }
               enum "1548.09" {
                 description "1548.09 nm/193.653125 THz 3.125GHz spacing";
               }
               enum "1548.06" {
                 description "1548.06 nm/193.656250 THz 3.125/6.25GHz spacing";
               }
               enum "1548.04" {
                 description "1548.04 nm/193.659375 THz 3.125GHz spacing";
               }
               enum "1548.02" {
                 description "1548.02 nm/193.662500 THz 3.125/6.25/12.5GHz spacing";
               }
               enum "1547.99" {
                 description "1547.99 nm/193.665625 THz 3.125GHz spacing";
               }
               enum "1547.97" {
                 description "1547.97 nm/193.668750 THz 3.125/6.25GHz spacing";
               }
               enum "1547.94" {
                 description "1547.94 nm/193.671875 THz 3.125GHz spacing";
               }
               enum "1547.92" {
                 description "1547.92 nm/193.675000 THz 3.125/6.25/12.5GHz spacing";
               }
               enum "1547.89" {
                 description "1547.89 nm/193.678125 THz 3.125GHz spacing";
               }
               enum "1547.87" {
                 description "1547.87 nm/193.681250 THz 3.125/6.25GHz spacing";
               }
               enum "1547.84" {
                 description "1547.84 nm/193.684375 THz 3.125GHz spacing";
               }
               enum "1547.82" {
                 description "1547.82 nm/193.687500 THz 3.125/6.25/12.5GHz spacing";
               }
               enum "1547.79" {
                 description "1547.79 nm/193.690625 THz 3.125GHz spacing";
               }
               enum "1547.77" {
                 description "1547.77 nm/193.693750 THz 3.125/6.25GHz spacing";
               }
               enum "1547.74" {
                 description "1547.74 nm/193.696875 THz 3.125GHz spacing";
               }
               enum "1547.72" {
                 description "1547.72 nm/193.700000 THz 3.125/6.25/12.5/100GHz spacing";
               }
               enum "1547.69" {
                 description "1547.69 nm/193.703125 THz 3.125GHz spacing";
               }
               enum "1547.67" {
                 description "1547.67 nm/193.706250 THz 3.125/6.25GHz spacing";
               }
               enum "1547.64" {
                 description "1547.64 nm/193.709375 THz 3.125GHz spacing";
               }
               enum "1547.62" {
                 description "1547.62 nm/193.712500 THz 3.125/6.25/12.5GHz spacing";
               }
               enum "1547.59" {
                 description "1547.59 nm/193.715625 THz 3.125GHz spacing";
               }
               enum "1547.57" {
                 description "1547.57 nm/193.718750 THz 3.125/6.25GHz spacing";
               }
               enum "1547.54" {
                 description "1547.54 nm/193.721875 THz 3.125GHz spacing";
               }
               enum "1547.52" {
                 description "1547.52 nm/193.725000 THz 3.125/6.25/12.5/75GHz spacing";
               }
               enum "1547.49" {
                 description "1547.49 nm/193.728125 THz 3.125GHz spacing";
               }
               enum "1547.47" {
                 description "1547.47 nm/193.731250 THz 3.125/6.25GHz spacing";
               }
               enum "1547.44" {
                 description "1547.44 nm/193.734375 THz 3.125GHz spacing";
               }
               enum "1547.42" {
                 description "1547.42 nm/193.737500 THz 3.125/6.25/12.5GHz spacing";
               }
               enum "1547.39" {
                 description "1547.39 nm/193.740625 THz 3.125GHz spacing";
               }
               enum "1547.37" {
                 description "1547.37 nm/193.743750 THz 3.125/6.25GHz spacing";
               }
               enum "1547.34" {
                 description "1547.34 nm/193.746875 THz 3.125GHz spacing";
               }
               enum "1547.32" {
                 description "1547.32 nm/193.750000 THz 3.125/6.25/12.5/50GHz spacing";
               }
               enum "1547.29" {
                 description "1547.29 nm/193.753125 THz 3.125GHz spacing";
               }
               enum "1547.27" {
                 description "1547.27 nm/193.756250 THz 3.125/6.25GHz spacing";
               }
               enum "1547.24" {
                 description "1547.24 nm/193.759375 THz 3.125GHz spacing";
               }
               enum "1547.22" {
                 description "1547.22 nm/193.762500 THz 3.125/6.25/12.5GHz spacing";
               }
               enum "1547.19" {
                 description "1547.19 nm/193.765625 THz 3.125GHz spacing";
               }
               enum "1547.17" {
                 description "1547.17 nm/193.768750 THz 3.125/6.25GHz spacing";
               }
               enum "1547.14" {
                 description "1547.14 nm/193.771875 THz 3.125GHz spacing";
               }
               enum "1547.12" {
                 description "1547.12 nm/193.775000 THz 3.125/6.25/12.5GHz spacing";
               }
               enum "1547.09" {
                 description "1547.09 nm/193.778125 THz 3.125GHz spacing";
               }
               enum "1547.07" {
                 description "1547.07 nm/193.781250 THz 3.125/6.25GHz spacing";
               }
               enum "1547.04" {
                 description "1547.04 nm/193.784375 THz 3.125GHz spacing";
               }
               enum "1547.02" {
                 description "1547.02 nm/193.787500 THz 3.125/6.25/12.5GHz spacing";
               }
               enum "1546.99" {
                 description "1546.99 nm/193.790625 THz 3.125GHz spacing";
               }
               enum "1546.97" {
                 description "1546.97 nm/193.793750 THz 3.125/6.25GHz spacing";
               }
               enum "1546.94" {
                 description "1546.94 nm/193.796875 THz 3.125GHz spacing";
               }
               enum "1546.92" {
                 description "1546.92 nm/193.800000 THz 3.125/6.25/12.5/50/75/100GHz spacing";
               }
               enum "1546.89" {
                 description "1546.89 nm/193.803125 THz 3.125GHz spacing";
               }
               enum "1546.87" {
                 description "1546.87 nm/193.806250 THz 3.125/6.25GHz spacing";
               }
               enum "1546.84" {
                 description "1546.84 nm/193.809375 THz 3.125GHz spacing";
               }
               enum "1546.82" {
                 description "1546.82 nm/193.812500 THz 3.125/6.25/12.5GHz spacing";
               }
               enum "1546.79" {
                 description "1546.79 nm/193.815625 THz 3.125GHz spacing";
               }
               enum "1546.77" {
                 description "1546.77 nm/193.818750 THz 3.125/6.25GHz spacing";
               }
               enum "1546.74" {
                 description "1546.74 nm/193.821875 THz 3.125GHz spacing";
               }
               enum "1546.72" {
                 description "1546.72 nm/193.825000 THz 3.125/6.25/12.5GHz spacing";
               }
               enum "1546.69" {
                 description "1546.69 nm/193.828125 THz 3.125GHz spacing";
               }
               enum "1546.67" {
                 description "1546.67 nm/193.831250 THz 3.125/6.25GHz spacing";
               }
               enum "1546.64" {
                 description "1546.64 nm/193.834375 THz 3.125GHz spacing";
               }
               enum "1546.62" {
                 description "1546.62 nm/193.837500 THz 3.125/6.25/12.5GHz spacing";
               }
               enum "1546.59" {
                 description "1546.59 nm/193.840625 THz 3.125GHz spacing";
               }
               enum "1546.57" {
                 description "1546.57 nm/193.843750 THz 3.125/6.25GHz spacing";
               }
               enum "1546.54" {
                 description "1546.54 nm/193.846875 THz 3.125GHz spacing";
               }
               enum "1546.52" {
                 description "1546.52 nm/193.850000 THz 3.125/6.25/12.5/50GHz spacing";
               }
               enum "1546.49" {
                 description "1546.49 nm/193.853125 THz 3.125GHz spacing";
               }
               enum "1546.47" {
                 description "1546.47 nm/193.856250 THz 3.125/6.25GHz spacing";
               }
               enum "1546.44" {
                 description "1546.44 nm/193.859375 THz 3.125GHz spacing";
               }
               enum "1546.42" {
                 description "1546.42 nm/193.862500 THz 3.125/6.25/12.5GHz spacing";
               }
               enum "1546.39" {
                 description "1546.39 nm/193.865625 THz 3.125GHz spacing";
               }
               enum "1546.37" {
                 description "1546.37 nm/193.868750 THz 3.125/6.25GHz spacing";
               }
               enum "1546.34" {
                 description "1546.34 nm/193.871875 THz 3.125GHz spacing";
               }
               enum "1546.32" {
                 description "1546.32 nm/193.875000 THz 3.125/6.25/12.5/75GHz spacing";
               }
               enum "1546.29" {
                 description "1546.29 nm/193.878125 THz 3.125GHz spacing";
               }
               enum "1546.27" {
                 description "1546.27 nm/193.881250 THz 3.125/6.25GHz spacing";
               }
               enum "1546.24" {
                 description "1546.24 nm/193.884375 THz 3.125GHz spacing";
               }
               enum "1546.22" {
                 description "1546.22 nm/193.887500 THz 3.125/6.25/12.5GHz spacing";
               }
               enum "1546.19" {
                 description "1546.19 nm/193.890625 THz 3.125GHz spacing";
               }
               enum "1546.17" {
                 description "1546.17 nm/193.893750 THz 3.125/6.25GHz spacing";
               }
               enum "1546.14" {
                 description "1546.14 nm/193.896875 THz 3.125GHz spacing";
               }
               enum "1546.12" {
                 description "1546.12 nm/193.900000 THz 3.125/6.25/12.5/100GHz spacing";
               }
               enum "1546.09" {
                 description "1546.09 nm/193.903125 THz 3.125GHz spacing";
               }
               enum "1546.07" {
                 description "1546.07 nm/193.906250 THz 3.125/6.25GHz spacing";
               }
               enum "1546.04" {
                 description "1546.04 nm/193.909375 THz 3.125GHz spacing";
               }
               enum "1546.02" {
                 description "1546.02 nm/193.912500 THz 3.125/6.25/12.5GHz spacing";
               }
               enum "1545.99" {
                 description "1545.99 nm/193.915625 THz 3.125GHz spacing";
               }
               enum "1545.97" {
                 description "1545.97 nm/193.918750 THz 3.125/6.25GHz spacing";
               }
               enum "1545.94" {
                 description "1545.94 nm/193.921875 THz 3.125GHz spacing";
               }
               enum "1545.92" {
                 description "1545.92 nm/193.925000 THz 3.125/6.25/12.5GHz spacing";
               }
               enum "1545.89" {
                 description "1545.89 nm/193.928125 THz 3.125GHz spacing";
               }
               enum "1545.87" {
                 description "1545.87 nm/193.931250 THz 3.125/6.25GHz spacing";
               }
               enum "1545.84" {
                 description "1545.84 nm/193.934375 THz 3.125GHz spacing";
               }
               enum "1545.82" {
                 description "1545.82 nm/193.937500 THz 3.125/6.25/12.5GHz spacing";
               }
               enum "1545.80" {
                 description "1545.80 nm/193.940625 THz 3.125GHz spacing";
               }
               enum "1545.77" {
                 description "1545.77 nm/193.943750 THz 3.125/6.25GHz spacing";
               }
               enum "1545.75" {
                 description "1545.75 nm/193.946875 THz 3.125GHz spacing";
               }
               enum "1545.72" {
                 description "1545.72 nm/193.950000 THz 3.125/6.25/12.5/50/75GHz spacing";
               }
               enum "1545.70" {
                 description "1545.70 nm/193.953125 THz 3.125GHz spacing";
               }
               enum "1545.67" {
                 description "1545.67 nm/193.956250 THz 3.125/6.25GHz spacing";
               }
               enum "1545.65" {
                 description "1545.65 nm/193.959375 THz 3.125GHz spacing";
               }
               enum "1545.62" {
                 description "1545.62 nm/193.962500 THz 3.125/6.25/12.5GHz spacing";
               }
               enum "1545.60" {
                 description "1545.60 nm/193.965625 THz 3.125GHz spacing";
               }
               enum "1545.57" {
                 description "1545.57 nm/193.968750 THz 3.125/6.25GHz spacing";
               }
               enum "1545.55" {
                 description "1545.55 nm/193.971875 THz 3.125GHz spacing";
               }
               enum "1545.52" {
                 description "1545.52 nm/193.975000 THz 3.125/6.25/12.5GHz spacing";
               }
               enum "1545.50" {
                 description "1545.50 nm/193.978125 THz 3.125GHz spacing";
               }
               enum "1545.47" {
                 description "1545.47 nm/193.981250 THz 3.125/6.25GHz spacing";
               }
               enum "1545.45" {
                 description "1545.45 nm/193.984375 THz 3.125GHz spacing";
               }
               enum "1545.42" {
                 description "1545.42 nm/193.987500 THz 3.125/6.25/12.5GHz spacing";
               }
               enum "1545.40" {
                 description "1545.40 nm/193.990625 THz 3.125GHz spacing";
               }
               enum "1545.37" {
                 description "1545.37 nm/193.993750 THz 3.125/6.25GHz spacing";
               }
               enum "1545.35" {
                 description "1545.35 nm/193.996875 THz 3.125GHz spacing";
               }
               enum "1545.32" {
                 description "1545.32 nm/194.000000 THz 3.125/6.25/12.5/100GHz spacing";
               }
               enum "1545.30" {
                 description "1545.30 nm/194.003125 THz 3.125GHz spacing";
               }
               enum "1545.27" {
                 description "1545.27 nm/194.006250 THz 3.125/6.25GHz spacing";
               }
               enum "1545.25" {
                 description "1545.25 nm/194.009375 THz 3.125GHz spacing";
               }
               enum "1545.22" {
                 description "1545.22 nm/194.012500 THz 3.125/6.25/12.5GHz spacing";
               }
               enum "1545.20" {
                 description "1545.20 nm/194.015625 THz 3.125GHz spacing";
               }
               enum "1545.17" {
                 description "1545.17 nm/194.018750 THz 3.125/6.25GHz spacing";
               }
               enum "1545.15" {
                 description "1545.15 nm/194.021875 THz 3.125GHz spacing";
               }
               enum "1545.12" {
                 description "1545.12 nm/194.025000 THz 3.125/6.25/12.5/75GHz spacing";
               }
               enum "1545.10" {
                 description "1545.10 nm/194.028125 THz 3.125GHz spacing";
               }
               enum "1545.07" {
                 description "1545.07 nm/194.031250 THz 3.125/6.25GHz spacing";
               }
               enum "1545.05" {
                 description "1545.05 nm/194.034375 THz 3.125GHz spacing";
               }
               enum "1545.02" {
                 description "1545.02 nm/194.037500 THz 3.125/6.25/12.5GHz spacing";
               }
               enum "1545.00" {
                 description "1545.00 nm/194.040625 THz 3.125GHz spacing";
               }
               enum "1544.97" {
                 description "1544.97 nm/194.043750 THz 3.125/6.25GHz spacing";
               }
               enum "1544.95" {
                 description "1544.95 nm/194.046875 THz 3.125GHz spacing";
               }
               enum "1544.92" {
                 description "1544.92 nm/194.050000 THz 3.125/6.25/12.5/50GHz spacing";
               }
               enum "1544.90" {
                 description "1544.90 nm/194.053125 THz 3.125GHz spacing";
               }
               enum "1544.87" {
                 description "1544.87 nm/194.056250 THz 3.125/6.25GHz spacing";
               }
               enum "1544.85" {
                 description "1544.85 nm/194.059375 THz 3.125GHz spacing";
               }
               enum "1544.82" {
                 description "1544.82 nm/194.062500 THz 3.125/6.25/12.5GHz spacing";
               }
               enum "1544.80" {
                 description "1544.80 nm/194.065625 THz 3.125GHz spacing";
               }
               enum "1544.77" {
                 description "1544.77 nm/194.068750 THz 3.125/6.25GHz spacing";
               }
               enum "1544.75" {
                 description "1544.75 nm/194.071875 THz 3.125GHz spacing";
               }
               enum "1544.72" {
                 description "1544.72 nm/194.075000 THz 3.125/6.25/12.5GHz spacing";
               }
               enum "1544.70" {
                 description "1544.70 nm/194.078125 THz 3.125GHz spacing";
               }
               enum "1544.68" {
                 description "1544.68 nm/194.081250 THz 3.125/6.25GHz spacing";
               }
               enum "1544.65" {
                 description "1544.65 nm/194.084375 THz 3.125GHz spacing";
               }
               enum "1544.63" {
                 description "1544.63 nm/194.087500 THz 3.125/6.25/12.5GHz spacing";
               }
               enum "1544.60" {
                 description "1544.60 nm/194.090625 THz 3.125GHz spacing";
               }
               enum "1544.58" {
                 description "1544.58 nm/194.093750 THz 3.125/6.25GHz spacing";
               }
               enum "1544.55" {
                 description "1544.55 nm/194.096875 THz 3.125GHz spacing";
               }
               enum "1544.53" {
                 description "1544.53 nm/194.100000 THz 3.125/6.25/12.5/50/75/100GHz spacing";
               }
               enum "1544.50" {
                 description "1544.50 nm/194.103125 THz 3.125GHz spacing";
               }
               enum "1544.48" {
                 description "1544.48 nm/194.106250 THz 3.125/6.25GHz spacing";
               }
               enum "1544.45" {
                 description "1544.45 nm/194.109375 THz 3.125GHz spacing";
               }
               enum "1544.43" {
                 description "1544.43 nm/194.112500 THz 3.125/6.25/12.5GHz spacing";
               }
               enum "1544.40" {
                 description "1544.40 nm/194.115625 THz 3.125GHz spacing";
               }
               enum "1544.38" {
                 description "1544.38 nm/194.118750 THz 3.125/6.25GHz spacing";
               }
               enum "1544.35" {
                 description "1544.35 nm/194.121875 THz 3.125GHz spacing";
               }
               enum "1544.33" {
                 description "1544.33 nm/194.125000 THz 3.125/6.25/12.5GHz spacing";
               }
               enum "1544.30" {
                 description "1544.30 nm/194.128125 THz 3.125GHz spacing";
               }
               enum "1544.28" {
                 description "1544.28 nm/194.131250 THz 3.125/6.25GHz spacing";
               }
               enum "1544.25" {
                 description "1544.25 nm/194.134375 THz 3.125GHz spacing";
               }
               enum "1544.23" {
                 description "1544.23 nm/194.137500 THz 3.125/6.25/12.5GHz spacing";
               }
               enum "1544.20" {
                 description "1544.20 nm/194.140625 THz 3.125GHz spacing";
               }
               enum "1544.18" {
                 description "1544.18 nm/194.143750 THz 3.125/6.25GHz spacing";
               }
               enum "1544.15" {
                 description "1544.15 nm/194.146875 THz 3.125GHz spacing";
               }
               enum "1544.13" {
                 description "1544.13 nm/194.150000 THz 3.125/6.25/12.5/50GHz spacing";
               }
               enum "1544.10" {
                 description "1544.10 nm/194.153125 THz 3.125GHz spacing";
               }
               enum "1544.08" {
                 description "1544.08 nm/194.156250 THz 3.125/6.25GHz spacing";
               }
               enum "1544.05" {
                 description "1544.05 nm/194.159375 THz 3.125GHz spacing";
               }
               enum "1544.03" {
                 description "1544.03 nm/194.162500 THz 3.125/6.25/12.5GHz spacing";
               }
               enum "1544.00" {
                 description "1544.00 nm/194.165625 THz 3.125GHz spacing";
               }
               enum "1543.98" {
                 description "1543.98 nm/194.168750 THz 3.125/6.25GHz spacing";
               }
               enum "1543.95" {
                 description "1543.95 nm/194.171875 THz 3.125GHz spacing";
               }
               enum "1543.93" {
                 description "1543.93 nm/194.175000 THz 3.125/6.25/12.5/75GHz spacing";
               }
               enum "1543.90" {
                 description "1543.90 nm/194.178125 THz 3.125GHz spacing";
               }
               enum "1543.88" {
                 description "1543.88 nm/194.181250 THz 3.125/6.25GHz spacing";
               }
               enum "1543.85" {
                 description "1543.85 nm/194.184375 THz 3.125GHz spacing";
               }
               enum "1543.83" {
                 description "1543.83 nm/194.187500 THz 3.125/6.25/12.5GHz spacing";
               }
               enum "1543.81" {
                 description "1543.81 nm/194.190625 THz 3.125GHz spacing";
               }
               enum "1543.78" {
                 description "1543.78 nm/194.193750 THz 3.125/6.25GHz spacing";
               }
               enum "1543.76" {
                 description "1543.76 nm/194.196875 THz 3.125GHz spacing";
               }
               enum "1543.73" {
                 description "1543.73 nm/194.200000 THz 3.125/6.25/12.5/100GHz spacing";
               }
               enum "1543.71" {
                 description "1543.71 nm/194.203125 THz 3.125GHz spacing";
               }
               enum "1543.68" {
                 description "1543.68 nm/194.206250 THz 3.125/6.25GHz spacing";
               }
               enum "1543.66" {
                 description "1543.66 nm/194.209375 THz 3.125GHz spacing";
               }
               enum "1543.63" {
                 description "1543.63 nm/194.212500 THz 3.125/6.25/12.5GHz spacing";
               }
               enum "1543.61" {
                 description "1543.61 nm/194.215625 THz 3.125GHz spacing";
               }
               enum "1543.58" {
                 description "1543.58 nm/194.218750 THz 3.125/6.25GHz spacing";
               }
               enum "1543.56" {
                 description "1543.56 nm/194.221875 THz 3.125GHz spacing";
               }
               enum "1543.53" {
                 description "1543.53 nm/194.225000 THz 3.125/6.25/12.5GHz spacing";
               }
               enum "1543.51" {
                 description "1543.51 nm/194.228125 THz 3.125GHz spacing";
               }
               enum "1543.48" {
                 description "1543.48 nm/194.231250 THz 3.125/6.25GHz spacing";
               }
               enum "1543.46" {
                 description "1543.46 nm/194.234375 THz 3.125GHz spacing";
               }
               enum "1543.43" {
                 description "1543.43 nm/194.237500 THz 3.125/6.25/12.5GHz spacing";
               }
               enum "1543.41" {
                 description "1543.41 nm/194.240625 THz 3.125GHz spacing";
               }
               enum "1543.38" {
                 description "1543.38 nm/194.243750 THz 3.125/6.25GHz spacing";
               }
               enum "1543.36" {
                 description "1543.36 nm/194.246875 THz 3.125GHz spacing";
               }
               enum "1543.33" {
                 description "1543.33 nm/194.250000 THz 3.125/6.25/12.5/50/75GHz spacing";
               }
               enum "1543.31" {
                 description "1543.31 nm/194.253125 THz 3.125GHz spacing";
               }
               enum "1543.28" {
                 description "1543.28 nm/194.256250 THz 3.125/6.25GHz spacing";
               }
               enum "1543.26" {
                 description "1543.26 nm/194.259375 THz 3.125GHz spacing";
               }
               enum "1543.23" {
                 description "1543.23 nm/194.262500 THz 3.125/6.25/12.5GHz spacing";
               }
               enum "1543.21" {
                 description "1543.21 nm/194.265625 THz 3.125GHz spacing";
               }
               enum "1543.18" {
                 description "1543.18 nm/194.268750 THz 3.125/6.25GHz spacing";
               }
               enum "1543.16" {
                 description "1543.16 nm/194.271875 THz 3.125GHz spacing";
               }
               enum "1543.13" {
                 description "1543.13 nm/194.275000 THz 3.125/6.25/12.5GHz spacing";
               }
               enum "1543.11" {
                 description "1543.11 nm/194.278125 THz 3.125GHz spacing";
               }
               enum "1543.08" {
                 description "1543.08 nm/194.281250 THz 3.125/6.25GHz spacing";
               }
               enum "1543.06" {
                 description "1543.06 nm/194.284375 THz 3.125GHz spacing";
               }
               enum "1543.04" {
                 description "1543.04 nm/194.287500 THz 3.125/6.25/12.5GHz spacing";
               }
               enum "1543.01" {
                 description "1543.01 nm/194.290625 THz 3.125GHz spacing";
               }
               enum "1542.99" {
                 description "1542.99 nm/194.293750 THz 3.125/6.25GHz spacing";
               }
               enum "1542.96" {
                 description "1542.96 nm/194.296875 THz 3.125GHz spacing";
               }
               enum "1542.94" {
                 description "1542.94 nm/194.300000 THz 3.125/6.25/12.5/100GHz spacing";
               }
               enum "1542.91" {
                 description "1542.91 nm/194.303125 THz 3.125GHz spacing";
               }
               enum "1542.89" {
                 description "1542.89 nm/194.306250 THz 3.125/6.25GHz spacing";
               }
               enum "1542.86" {
                 description "1542.86 nm/194.309375 THz 3.125GHz spacing";
               }
               enum "1542.84" {
                 description "1542.84 nm/194.312500 THz 3.125/6.25/12.5GHz spacing";
               }
               enum "1542.81" {
                 description "1542.81 nm/194.315625 THz 3.125GHz spacing";
               }
               enum "1542.79" {
                 description "1542.79 nm/194.318750 THz 3.125/6.25GHz spacing";
               }
               enum "1542.76" {
                 description "1542.76 nm/194.321875 THz 3.125GHz spacing";
               }
               enum "1542.74" {
                 description "1542.74 nm/194.325000 THz 3.125/6.25/12.5/75GHz spacing";
               }
               enum "1542.71" {
                 description "1542.71 nm/194.328125 THz 3.125GHz spacing";
               }
               enum "1542.69" {
                 description "1542.69 nm/194.331250 THz 3.125/6.25GHz spacing";
               }
               enum "1542.66" {
                 description "1542.66 nm/194.334375 THz 3.125GHz spacing";
               }
               enum "1542.64" {
                 description "1542.64 nm/194.337500 THz 3.125/6.25/12.5GHz spacing";
               }
               enum "1542.61" {
                 description "1542.61 nm/194.340625 THz 3.125GHz spacing";
               }
               enum "1542.59" {
                 description "1542.59 nm/194.343750 THz 3.125/6.25GHz spacing";
               }
               enum "1542.56" {
                 description "1542.56 nm/194.346875 THz 3.125GHz spacing";
               }
               enum "1542.54" {
                 description "1542.54 nm/194.350000 THz 3.125/6.25/12.5/50GHz spacing";
               }
               enum "1542.51" {
                 description "1542.51 nm/194.353125 THz 3.125GHz spacing";
               }
               enum "1542.49" {
                 description "1542.49 nm/194.356250 THz 3.125/6.25GHz spacing";
               }
               enum "1542.46" {
                 description "1542.46 nm/194.359375 THz 3.125GHz spacing";
               }
               enum "1542.44" {
                 description "1542.44 nm/194.362500 THz 3.125/6.25/12.5GHz spacing";
               }
               enum "1542.42" {
                 description "1542.42 nm/194.365625 THz 3.125GHz spacing";
               }
               enum "1542.39" {
                 description "1542.39 nm/194.368750 THz 3.125/6.25GHz spacing";
               }
               enum "1542.37" {
                 description "1542.37 nm/194.371875 THz 3.125GHz spacing";
               }
               enum "1542.34" {
                 description "1542.34 nm/194.375000 THz 3.125/6.25/12.5GHz spacing";
               }
               enum "1542.32" {
                 description "1542.32 nm/194.378125 THz 3.125GHz spacing";
               }
               enum "1542.29" {
                 description "1542.29 nm/194.381250 THz 3.125/6.25GHz spacing";
               }
               enum "1542.27" {
                 description "1542.27 nm/194.384375 THz 3.125GHz spacing";
               }
               enum "1542.24" {
                 description "1542.24 nm/194.387500 THz 3.125/6.25/12.5GHz spacing";
               }
               enum "1542.22" {
                 description "1542.22 nm/194.390625 THz 3.125GHz spacing";
               }
               enum "1542.19" {
                 description "1542.19 nm/194.393750 THz 3.125/6.25GHz spacing";
               }
               enum "1542.17" {
                 description "1542.17 nm/194.396875 THz 3.125GHz spacing";
               }
               enum "1542.14" {
                 description "1542.14 nm/194.400000 THz 3.125/6.25/12.5/50/75/100GHz spacing";
               }
               enum "1542.12" {
                 description "1542.12 nm/194.403125 THz 3.125GHz spacing";
               }
               enum "1542.09" {
                 description "1542.09 nm/194.406250 THz 3.125/6.25GHz spacing";
               }
               enum "1542.07" {
                 description "1542.07 nm/194.409375 THz 3.125GHz spacing";
               }
               enum "1542.04" {
                 description "1542.04 nm/194.412500 THz 3.125/6.25/12.5GHz spacing";
               }
               enum "1542.02" {
                 description "1542.02 nm/194.415625 THz 3.125GHz spacing";
               }
               enum "1541.99" {
                 description "1541.99 nm/194.418750 THz 3.125/6.25GHz spacing";
               }
               enum "1541.97" {
                 description "1541.97 nm/194.421875 THz 3.125GHz spacing";
               }
               enum "1541.94" {
                 description "1541.94 nm/194.425000 THz 3.125/6.25/12.5GHz spacing";
               }
               enum "1541.92" {
                 description "1541.92 nm/194.428125 THz 3.125GHz spacing";
               }
               enum "1541.89" {
                 description "1541.89 nm/194.431250 THz 3.125/6.25GHz spacing";
               }
               enum "1541.87" {
                 description "1541.87 nm/194.434375 THz 3.125GHz spacing";
               }
               enum "1541.84" {
                 description "1541.84 nm/194.437500 THz 3.125/6.25/12.5GHz spacing";
               }
               enum "1541.82" {
                 description "1541.82 nm/194.440625 THz 3.125GHz spacing";
               }
               enum "1541.80" {
                 description "1541.80 nm/194.443750 THz 3.125/6.25GHz spacing";
               }
               enum "1541.77" {
                 description "1541.77 nm/194.446875 THz 3.125GHz spacing";
               }
               enum "1541.75" {
                 description "1541.75 nm/194.450000 THz 3.125/6.25/12.5/50GHz spacing";
               }
               enum "1541.72" {
                 description "1541.72 nm/194.453125 THz 3.125GHz spacing";
               }
               enum "1541.70" {
                 description "1541.70 nm/194.456250 THz 3.125/6.25GHz spacing";
               }
               enum "1541.67" {
                 description "1541.67 nm/194.459375 THz 3.125GHz spacing";
               }
               enum "1541.65" {
                 description "1541.65 nm/194.462500 THz 3.125/6.25/12.5GHz spacing";
               }
               enum "1541.62" {
                 description "1541.62 nm/194.465625 THz 3.125GHz spacing";
               }
               enum "1541.60" {
                 description "1541.60 nm/194.468750 THz 3.125/6.25GHz spacing";
               }
               enum "1541.57" {
                 description "1541.57 nm/194.471875 THz 3.125GHz spacing";
               }
               enum "1541.55" {
                 description "1541.55 nm/194.475000 THz 3.125/6.25/12.5/75GHz spacing";
               }
               enum "1541.52" {
                 description "1541.52 nm/194.478125 THz 3.125GHz spacing";
               }
               enum "1541.50" {
                 description "1541.50 nm/194.481250 THz 3.125/6.25GHz spacing";
               }
               enum "1541.47" {
                 description "1541.47 nm/194.484375 THz 3.125GHz spacing";
               }
               enum "1541.45" {
                 description "1541.45 nm/194.487500 THz 3.125/6.25/12.5GHz spacing";
               }
               enum "1541.42" {
                 description "1541.42 nm/194.490625 THz 3.125GHz spacing";
               }
               enum "1541.40" {
                 description "1541.40 nm/194.493750 THz 3.125/6.25GHz spacing";
               }
               enum "1541.37" {
                 description "1541.37 nm/194.496875 THz 3.125GHz spacing";
               }
               enum "1541.35" {
                 description "1541.35 nm/194.500000 THz 3.125/6.25/12.5/100GHz spacing";
               }
               enum "1541.32" {
                 description "1541.32 nm/194.503125 THz 3.125GHz spacing";
               }
               enum "1541.30" {
                 description "1541.30 nm/194.506250 THz 3.125/6.25GHz spacing";
               }
               enum "1541.28" {
                 description "1541.28 nm/194.509375 THz 3.125GHz spacing";
               }
               enum "1541.25" {
                 description "1541.25 nm/194.512500 THz 3.125/6.25/12.5GHz spacing";
               }
               enum "1541.23" {
                 description "1541.23 nm/194.515625 THz 3.125GHz spacing";
               }
               enum "1541.20" {
                 description "1541.20 nm/194.518750 THz 3.125/6.25GHz spacing";
               }
               enum "1541.18" {
                 description "1541.18 nm/194.521875 THz 3.125GHz spacing";
               }
               enum "1541.15" {
                 description "1541.15 nm/194.525000 THz 3.125/6.25/12.5GHz spacing";
               }
               enum "1541.13" {
                 description "1541.13 nm/194.528125 THz 3.125GHz spacing";
               }
               enum "1541.10" {
                 description "1541.10 nm/194.531250 THz 3.125/6.25GHz spacing";
               }
               enum "1541.08" {
                 description "1541.08 nm/194.534375 THz 3.125GHz spacing";
               }
               enum "1541.05" {
                 description "1541.05 nm/194.537500 THz 3.125/6.25/12.5GHz spacing";
               }
               enum "1541.03" {
                 description "1541.03 nm/194.540625 THz 3.125GHz spacing";
               }
               enum "1541.00" {
                 description "1541.00 nm/194.543750 THz 3.125/6.25GHz spacing";
               }
               enum "1540.98" {
                 description "1540.98 nm/194.546875 THz 3.125GHz spacing";
               }
               enum "1540.95" {
                 description "1540.95 nm/194.550000 THz 3.125/6.25/12.5/50/75GHz spacing";
               }
               enum "1540.93" {
                 description "1540.93 nm/194.553125 THz 3.125GHz spacing";
               }
               enum "1540.90" {
                 description "1540.90 nm/194.556250 THz 3.125/6.25GHz spacing";
               }
               enum "1540.88" {
                 description "1540.88 nm/194.559375 THz 3.125GHz spacing";
               }
               enum "1540.85" {
                 description "1540.85 nm/194.562500 THz 3.125/6.25/12.5GHz spacing";
               }
               enum "1540.83" {
                 description "1540.83 nm/194.565625 THz 3.125GHz spacing";
               }
               enum "1540.80" {
                 description "1540.80 nm/194.568750 THz 3.125/6.25GHz spacing";
               }
               enum "1540.78" {
                 description "1540.78 nm/194.571875 THz 3.125GHz spacing";
               }
               enum "1540.76" {
                 description "1540.76 nm/194.575000 THz 3.125/6.25/12.5GHz spacing";
               }
               enum "1540.73" {
                 description "1540.73 nm/194.578125 THz 3.125GHz spacing";
               }
               enum "1540.71" {
                 description "1540.71 nm/194.581250 THz 3.125/6.25GHz spacing";
               }
               enum "1540.68" {
                 description "1540.68 nm/194.584375 THz 3.125GHz spacing";
               }
               enum "1540.66" {
                 description "1540.66 nm/194.587500 THz 3.125/6.25/12.5GHz spacing";
               }
               enum "1540.63" {
                 description "1540.63 nm/194.590625 THz 3.125GHz spacing";
               }
               enum "1540.61" {
                 description "1540.61 nm/194.593750 THz 3.125/6.25GHz spacing";
               }
               enum "1540.58" {
                 description "1540.58 nm/194.596875 THz 3.125GHz spacing";
               }
               enum "1540.56" {
                 description "1540.56 nm/194.600000 THz 3.125/6.25/12.5/100GHz spacing";
               }
               enum "1540.53" {
                 description "1540.53 nm/194.603125 THz 3.125GHz spacing";
               }
               enum "1540.51" {
                 description "1540.51 nm/194.606250 THz 3.125/6.25GHz spacing";
               }
               enum "1540.48" {
                 description "1540.48 nm/194.609375 THz 3.125GHz spacing";
               }
               enum "1540.46" {
                 description "1540.46 nm/194.612500 THz 3.125/6.25/12.5GHz spacing";
               }
               enum "1540.43" {
                 description "1540.43 nm/194.615625 THz 3.125GHz spacing";
               }
               enum "1540.41" {
                 description "1540.41 nm/194.618750 THz 3.125/6.25GHz spacing";
               }
               enum "1540.38" {
                 description "1540.38 nm/194.621875 THz 3.125GHz spacing";
               }
               enum "1540.36" {
                 description "1540.36 nm/194.625000 THz 3.125/6.25/12.5/75GHz spacing";
               }
               enum "1540.33" {
                 description "1540.33 nm/194.628125 THz 3.125GHz spacing";
               }
               enum "1540.31" {
                 description "1540.31 nm/194.631250 THz 3.125/6.25GHz spacing";
               }
               enum "1540.29" {
                 description "1540.29 nm/194.634375 THz 3.125GHz spacing";
               }
               enum "1540.26" {
                 description "1540.26 nm/194.637500 THz 3.125/6.25/12.5GHz spacing";
               }
               enum "1540.24" {
                 description "1540.24 nm/194.640625 THz 3.125GHz spacing";
               }
               enum "1540.21" {
                 description "1540.21 nm/194.643750 THz 3.125/6.25GHz spacing";
               }
               enum "1540.19" {
                 description "1540.19 nm/194.646875 THz 3.125GHz spacing";
               }
               enum "1540.16" {
                 description "1540.16 nm/194.650000 THz 3.125/6.25/12.5/50GHz spacing";
               }
               enum "1540.14" {
                 description "1540.14 nm/194.653125 THz 3.125GHz spacing";
               }
               enum "1540.11" {
                 description "1540.11 nm/194.656250 THz 3.125/6.25GHz spacing";
               }
               enum "1540.09" {
                 description "1540.09 nm/194.659375 THz 3.125GHz spacing";
               }
               enum "1540.06" {
                 description "1540.06 nm/194.662500 THz 3.125/6.25/12.5GHz spacing";
               }
               enum "1540.04" {
                 description "1540.04 nm/194.665625 THz 3.125GHz spacing";
               }
               enum "1540.01" {
                 description "1540.01 nm/194.668750 THz 3.125/6.25GHz spacing";
               }
               enum "1539.99" {
                 description "1539.99 nm/194.671875 THz 3.125GHz spacing";
               }
               enum "1539.96" {
                 description "1539.96 nm/194.675000 THz 3.125/6.25/12.5/75GHz spacing";
               }
               enum "1539.94" {
                 description "1539.94 nm/194.678125 THz 3.125GHz spacing";
               }
               enum "1539.91" {
                 description "1539.91 nm/194.681250 THz 3.125/6.25GHz spacing";
               }
               enum "1539.89" {
                 description "1539.89 nm/194.684375 THz 3.125GHz spacing";
               }
               enum "1539.86" {
                 description "1539.86 nm/194.687500 THz 3.125/6.25/12.5GHz spacing";
               }
               enum "1539.84" {
                 description "1539.84 nm/194.690625 THz 3.125GHz spacing";
               }
               enum "1539.82" {
                 description "1539.82 nm/194.693750 THz 3.125/6.25GHz spacing";
               }
               enum "1539.79" {
                 description "1539.79 nm/194.696875 THz 3.125GHz spacing";
               }
               enum "1539.77" {
                 description "1539.77 nm/194.700000 THz 3.125/6.25/12.5/50/75/100GHz spacing";
               }
               enum "1539.74" {
                 description "1539.74 nm/194.703125 THz 3.125GHz spacing";
               }
               enum "1539.72" {
                 description "1539.72 nm/194.706250 THz 3.125/6.25GHz spacing";
               }
               enum "1539.69" {
                 description "1539.69 nm/194.709375 THz 3.125GHz spacing";
               }
               enum "1539.67" {
                 description "1539.67 nm/194.712500 THz 3.125/6.25/12.5GHz spacing";
               }
               enum "1539.64" {
                 description "1539.64 nm/194.715625 THz 3.125GHz spacing";
               }
               enum "1539.62" {
                 description "1539.62 nm/194.718750 THz 3.125/6.25GHz spacing";
               }
               enum "1539.59" {
                 description "1539.59 nm/194.721875 THz 3.125GHz spacing";
               }
               enum "1539.57" {
                 description "1539.57 nm/194.725000 THz 3.125/6.25/12.5GHz spacing";
               }
               enum "1539.54" {
                 description "1539.54 nm/194.728125 THz 3.125GHz spacing";
               }
               enum "1539.52" {
                 description "1539.52 nm/194.731250 THz 3.125/6.25GHz spacing";
               }
               enum "1539.49" {
                 description "1539.49 nm/194.734375 THz 3.125GHz spacing";
               }
               enum "1539.47" {
                 description "1539.47 nm/194.737500 THz 3.125/6.25/12.5GHz spacing";
               }
               enum "1539.44" {
                 description "1539.44 nm/194.740625 THz 3.125GHz spacing";
               }
               enum "1539.42" {
                 description "1539.42 nm/194.743750 THz 3.125/6.25GHz spacing";
               }
               enum "1539.40" {
                 description "1539.40 nm/194.746875 THz 3.125GHz spacing";
               }
               enum "1539.37" {
                 description "1539.37 nm/194.750000 THz 3.125/6.25/12.5/50GHz spacing";
               }
               enum "1539.35" {
                 description "1539.35 nm/194.753125 THz 3.125GHz spacing";
               }
               enum "1539.32" {
                 description "1539.32 nm/194.756250 THz 3.125/6.25GHz spacing";
               }
               enum "1539.30" {
                 description "1539.30 nm/194.759375 THz 3.125GHz spacing";
               }
               enum "1539.27" {
                 description "1539.27 nm/194.762500 THz 3.125/6.25/12.5GHz spacing";
               }
               enum "1539.25" {
                 description "1539.25 nm/194.765625 THz 3.125GHz spacing";
               }
               enum "1539.22" {
                 description "1539.22 nm/194.768750 THz 3.125/6.25GHz spacing";
               }
               enum "1539.20" {
                 description "1539.20 nm/194.771875 THz 3.125GHz spacing";
               }
               enum "1539.17" {
                 description "1539.17 nm/194.775000 THz 3.125/6.25/12.5/75GHz spacing";
               }
               enum "1539.15" {
                 description "1539.15 nm/194.778125 THz 3.125GHz spacing";
               }
               enum "1539.12" {
                 description "1539.12 nm/194.781250 THz 3.125/6.25GHz spacing";
               }
               enum "1539.10" {
                 description "1539.10 nm/194.784375 THz 3.125GHz spacing";
               }
               enum "1539.07" {
                 description "1539.07 nm/194.787500 THz 3.125/6.25/12.5GHz spacing";
               }
               enum "1539.05" {
                 description "1539.05 nm/194.790625 THz 3.125GHz spacing";
               }
               enum "1539.03" {
                 description "1539.03 nm/194.793750 THz 3.125/6.25GHz spacing";
               }
               enum "1539.00" {
                 description "1539.00 nm/194.796875 THz 3.125GHz spacing";
               }
               enum "1538.98" {
                 description "1538.98 nm/194.800000 THz 3.125/6.25/12.5/100GHz spacing";
               }
               enum "1538.95" {
                 description "1538.95 nm/194.803125 THz 3.125GHz spacing";
               }
               enum "1538.93" {
                 description "1538.93 nm/194.806250 THz 3.125/6.25GHz spacing";
               }
               enum "1538.90" {
                 description "1538.90 nm/194.809375 THz 3.125GHz spacing";
               }
               enum "1538.88" {
                 description "1538.88 nm/194.812500 THz 3.125/6.25/12.5GHz spacing";
               }
               enum "1538.85" {
                 description "1538.85 nm/194.815625 THz 3.125GHz spacing";
               }
               enum "1538.83" {
                 description "1538.83 nm/194.818750 THz 3.125/6.25GHz spacing";
               }
               enum "1538.80" {
                 description "1538.80 nm/194.821875 THz 3.125GHz spacing";
               }
               enum "1538.78" {
                 description "1538.78 nm/194.825000 THz 3.125/6.25/12.5GHz spacing";
               }
               enum "1538.75" {
                 description "1538.75 nm/194.828125 THz 3.125GHz spacing";
               }
               enum "1538.73" {
                 description "1538.73 nm/194.831250 THz 3.125/6.25GHz spacing";
               }
               enum "1538.70" {
                 description "1538.70 nm/194.834375 THz 3.125GHz spacing";
               }
               enum "1538.68" {
                 description "1538.68 nm/194.837500 THz 3.125/6.25/12.5GHz spacing";
               }
               enum "1538.65" {
                 description "1538.65 nm/194.840625 THz 3.125GHz spacing";
               }
               enum "1538.63" {
                 description "1538.63 nm/194.843750 THz 3.125/6.25GHz spacing";
               }
               enum "1538.61" {
                 description "1538.61 nm/194.846875 THz 3.125GHz spacing";
               }
               enum "1538.58" {
                 description "1538.58 nm/194.850000 THz 3.125/6.25/12.5/50/75GHz spacing";
               }
               enum "1538.56" {
                 description "1538.56 nm/194.853125 THz 3.125GHz spacing";
               }
               enum "1538.53" {
                 description "1538.53 nm/194.856250 THz 3.125/6.25GHz spacing";
               }
               enum "1538.51" {
                 description "1538.51 nm/194.859375 THz 3.125GHz spacing";
               }
               enum "1538.48" {
                 description "1538.48 nm/194.862500 THz 3.125/6.25/12.5GHz spacing";
               }
               enum "1538.46" {
                 description "1538.46 nm/194.865625 THz 3.125GHz spacing";
               }
               enum "1538.43" {
                 description "1538.43 nm/194.868750 THz 3.125/6.25GHz spacing";
               }
               enum "1538.41" {
                 description "1538.41 nm/194.871875 THz 3.125GHz spacing";
               }
               enum "1538.38" {
                 description "1538.38 nm/194.875000 THz 3.125/6.25/12.5GHz spacing";
               }
               enum "1538.36" {
                 description "1538.36 nm/194.878125 THz 3.125GHz spacing";
               }
               enum "1538.33" {
                 description "1538.33 nm/194.881250 THz 3.125/6.25GHz spacing";
               }
               enum "1538.31" {
                 description "1538.31 nm/194.884375 THz 3.125GHz spacing";
               }
               enum "1538.28" {
                 description "1538.28 nm/194.887500 THz 3.125/6.25/12.5GHz spacing";
               }
               enum "1538.26" {
                 description "1538.26 nm/194.890625 THz 3.125GHz spacing";
               }
               enum "1538.24" {
                 description "1538.24 nm/194.893750 THz 3.125/6.25GHz spacing";
               }
               enum "1538.21" {
                 description "1538.21 nm/194.896875 THz 3.125GHz spacing";
               }
               enum "1538.19" {
                 description "1538.19 nm/194.900000 THz 3.125/6.25/12.5/100GHz spacing";
               }
               enum "1538.16" {
                 description "1538.16 nm/194.903125 THz 3.125GHz spacing";
               }
               enum "1538.14" {
                 description "1538.14 nm/194.906250 THz 3.125/6.25GHz spacing";
               }
               enum "1538.11" {
                 description "1538.11 nm/194.909375 THz 3.125GHz spacing";
               }
               enum "1538.09" {
                 description "1538.09 nm/194.912500 THz 3.125/6.25/12.5GHz spacing";
               }
               enum "1538.06" {
                 description "1538.06 nm/194.915625 THz 3.125GHz spacing";
               }
               enum "1538.04" {
                 description "1538.04 nm/194.918750 THz 3.125/6.25GHz spacing";
               }
               enum "1538.01" {
                 description "1538.01 nm/194.921875 THz 3.125GHz spacing";
               }
               enum "1537.99" {
                 description "1537.99 nm/194.925000 THz 3.125/6.25/12.5/75GHz spacing";
               }
               enum "1537.96" {
                 description "1537.96 nm/194.928125 THz 3.125GHz spacing";
               }
               enum "1537.94" {
                 description "1537.94 nm/194.931250 THz 3.125/6.25GHz spacing";
               }
               enum "1537.91" {
                 description "1537.91 nm/194.934375 THz 3.125GHz spacing";
               }
               enum "1537.89" {
                 description "1537.89 nm/194.937500 THz 3.125/6.25/12.5GHz spacing";
               }
               enum "1537.87" {
                 description "1537.87 nm/194.940625 THz 3.125GHz spacing";
               }
               enum "1537.84" {
                 description "1537.84 nm/194.943750 THz 3.125/6.25GHz spacing";
               }
               enum "1537.82" {
                 description "1537.82 nm/194.946875 THz 3.125GHz spacing";
               }
               enum "1537.79" {
                 description "1537.79 nm/194.950000 THz 3.125/6.25/12.5/50GHz spacing";
               }
               enum "1537.77" {
                 description "1537.77 nm/194.953125 THz 3.125GHz spacing";
               }
               enum "1537.74" {
                 description "1537.74 nm/194.956250 THz 3.125/6.25GHz spacing";
               }
               enum "1537.72" {
                 description "1537.72 nm/194.959375 THz 3.125GHz spacing";
               }
               enum "1537.69" {
                 description "1537.69 nm/194.962500 THz 3.125/6.25/12.5GHz spacing";
               }
               enum "1537.67" {
                 description "1537.67 nm/194.965625 THz 3.125GHz spacing";
               }
               enum "1537.64" {
                 description "1537.64 nm/194.968750 THz 3.125/6.25GHz spacing";
               }
               enum "1537.62" {
                 description "1537.62 nm/194.971875 THz 3.125GHz spacing";
               }
               enum "1537.59" {
                 description "1537.59 nm/194.975000 THz 3.125/6.25/12.5GHz spacing";
               }
               enum "1537.57" {
                 description "1537.57 nm/194.978125 THz 3.125GHz spacing";
               }
               enum "1537.55" {
                 description "1537.55 nm/194.981250 THz 3.125/6.25GHz spacing";
               }
               enum "1537.52" {
                 description "1537.52 nm/194.984375 THz 3.125GHz spacing";
               }
               enum "1537.50" {
                 description "1537.50 nm/194.987500 THz 3.125/6.25/12.5GHz spacing";
               }
               enum "1537.47" {
                 description "1537.47 nm/194.990625 THz 3.125GHz spacing";
               }
               enum "1537.45" {
                 description "1537.45 nm/194.993750 THz 3.125/6.25GHz spacing";
               }
               enum "1537.42" {
                 description "1537.42 nm/194.996875 THz 3.125GHz spacing";
               }
               enum "1537.40" {
                 description "1537.40 nm/195.000000 THz 3.125/6.25/12.5/50/75/100GHz spacing";
               }
               enum "1537.37" {
                 description "1537.37 nm/195.003125 THz 3.125GHz spacing";
               }
               enum "1537.35" {
                 description "1537.35 nm/195.006250 THz 3.125/6.25GHz spacing";
               }
               enum "1537.32" {
                 description "1537.32 nm/195.009375 THz 3.125GHz spacing";
               }
               enum "1537.30" {
                 description "1537.30 nm/195.012500 THz 3.125/6.25/12.5GHz spacing";
               }
               enum "1537.27" {
                 description "1537.27 nm/195.015625 THz 3.125GHz spacing";
               }
               enum "1537.25" {
                 description "1537.25 nm/195.018750 THz 3.125/6.25GHz spacing";
               }
               enum "1537.22" {
                 description "1537.22 nm/195.021875 THz 3.125GHz spacing";
               }
               enum "1537.20" {
                 description "1537.20 nm/195.025000 THz 3.125/6.25/12.5GHz spacing";
               }
               enum "1537.18" {
                 description "1537.18 nm/195.028125 THz 3.125GHz spacing";
               }
               enum "1537.15" {
                 description "1537.15 nm/195.031250 THz 3.125/6.25GHz spacing";
               }
               enum "1537.13" {
                 description "1537.13 nm/195.034375 THz 3.125GHz spacing";
               }
               enum "1537.10" {
                 description "1537.10 nm/195.037500 THz 3.125/6.25/12.5GHz spacing";
               }
               enum "1537.08" {
                 description "1537.08 nm/195.040625 THz 3.125GHz spacing";
               }
               enum "1537.05" {
                 description "1537.05 nm/195.043750 THz 3.125/6.25GHz spacing";
               }
               enum "1537.03" {
                 description "1537.03 nm/195.046875 THz 3.125GHz spacing";
               }
               enum "1537.00" {
                 description "1537.00 nm/195.050000 THz 3.125/6.25/12.5/50GHz spacing";
               }
               enum "1536.98" {
                 description "1536.98 nm/195.053125 THz 3.125GHz spacing";
               }
               enum "1536.95" {
                 description "1536.95 nm/195.056250 THz 3.125/6.25GHz spacing";
               }
               enum "1536.93" {
                 description "1536.93 nm/195.059375 THz 3.125GHz spacing";
               }
               enum "1536.90" {
                 description "1536.90 nm/195.062500 THz 3.125/6.25/12.5GHz spacing";
               }
               enum "1536.88" {
                 description "1536.88 nm/195.065625 THz 3.125GHz spacing";
               }
               enum "1536.86" {
                 description "1536.86 nm/195.068750 THz 3.125/6.25GHz spacing";
               }
               enum "1536.83" {
                 description "1536.83 nm/195.071875 THz 3.125GHz spacing";
               }
               enum "1536.81" {
                 description "1536.81 nm/195.075000 THz 3.125/6.25/12.5/75GHz spacing";
               }
               enum "1536.78" {
                 description "1536.78 nm/195.078125 THz 3.125GHz spacing";
               }
               enum "1536.76" {
                 description "1536.76 nm/195.081250 THz 3.125/6.25GHz spacing";
               }
               enum "1536.73" {
                 description "1536.73 nm/195.084375 THz 3.125GHz spacing";
               }
               enum "1536.71" {
                 description "1536.71 nm/195.087500 THz 3.125/6.25/12.5GHz spacing";
               }
               enum "1536.68" {
                 description "1536.68 nm/195.090625 THz 3.125GHz spacing";
               }
               enum "1536.66" {
                 description "1536.66 nm/195.093750 THz 3.125/6.25GHz spacing";
               }
               enum "1536.63" {
                 description "1536.63 nm/195.096875 THz 3.125GHz spacing";
               }
               enum "1536.61" {
                 description "1536.61 nm/195.100000 THz 3.125/6.25/12.5/100GHz spacing";
               }
               enum "1536.58" {
                 description "1536.58 nm/195.103125 THz 3.125GHz spacing";
               }
               enum "1536.56" {
                 description "1536.56 nm/195.106250 THz 3.125/6.25GHz spacing";
               }
               enum "1536.54" {
                 description "1536.54 nm/195.109375 THz 3.125GHz spacing";
               }
               enum "1536.51" {
                 description "1536.51 nm/195.112500 THz 3.125/6.25/12.5GHz spacing";
               }
               enum "1536.49" {
                 description "1536.49 nm/195.115625 THz 3.125GHz spacing";
               }
               enum "1536.46" {
                 description "1536.46 nm/195.118750 THz 3.125/6.25GHz spacing";
               }
               enum "1536.44" {
                 description "1536.44 nm/195.121875 THz 3.125GHz spacing";
               }
               enum "1536.41" {
                 description "1536.41 nm/195.125000 THz 3.125/6.25/12.5GHz spacing";
               }
               enum "1536.39" {
                 description "1536.39 nm/195.128125 THz 3.125GHz spacing";
               }
               enum "1536.36" {
                 description "1536.36 nm/195.131250 THz 3.125/6.25GHz spacing";
               }
               enum "1536.34" {
                 description "1536.34 nm/195.134375 THz 3.125GHz spacing";
               }
               enum "1536.31" {
                 description "1536.31 nm/195.137500 THz 3.125/6.25/12.5GHz spacing";
               }
               enum "1536.29" {
                 description "1536.29 nm/195.140625 THz 3.125GHz spacing";
               }
               enum "1536.26" {
                 description "1536.26 nm/195.143750 THz 3.125/6.25GHz spacing";
               }
               enum "1536.24" {
                 description "1536.24 nm/195.146875 THz 3.125GHz spacing";
               }
               enum "1536.22" {
                 description "1536.22 nm/195.150000 THz 3.125/6.25/12.5/50/75GHz spacing";
               }
               enum "1536.19" {
                 description "1536.19 nm/195.153125 THz 3.125GHz spacing";
               }
               enum "1536.17" {
                 description "1536.17 nm/195.156250 THz 3.125/6.25GHz spacing";
               }
               enum "1536.14" {
                 description "1536.14 nm/195.159375 THz 3.125GHz spacing";
               }
               enum "1536.12" {
                 description "1536.12 nm/195.162500 THz 3.125/6.25/12.5GHz spacing";
               }
               enum "1536.09" {
                 description "1536.09 nm/195.165625 THz 3.125GHz spacing";
               }
               enum "1536.07" {
                 description "1536.07 nm/195.168750 THz 3.125/6.25GHz spacing";
               }
               enum "1536.04" {
                 description "1536.04 nm/195.171875 THz 3.125GHz spacing";
               }
               enum "1536.02" {
                 description "1536.02 nm/195.175000 THz 3.125/6.25/12.5GHz spacing";
               }
               enum "1535.99" {
                 description "1535.99 nm/195.178125 THz 3.125GHz spacing";
               }
               enum "1535.97" {
                 description "1535.97 nm/195.181250 THz 3.125/6.25GHz spacing";
               }
               enum "1535.94" {
                 description "1535.94 nm/195.184375 THz 3.125GHz spacing";
               }
               enum "1535.92" {
                 description "1535.92 nm/195.187500 THz 3.125/6.25/12.5GHz spacing";
               }
               enum "1535.90" {
                 description "1535.90 nm/195.190625 THz 3.125GHz spacing";
               }
               enum "1535.87" {
                 description "1535.87 nm/195.193750 THz 3.125/6.25GHz spacing";
               }
               enum "1535.85" {
                 description "1535.85 nm/195.196875 THz 3.125GHz spacing";
               }
               enum "1535.82" {
                 description "1535.82 nm/195.200000 THz 3.125/6.25/12.5/100GHz spacing";
               }
               enum "1535.80" {
                 description "1535.80 nm/195.203125 THz 3.125GHz spacing";
               }
               enum "1535.77" {
                 description "1535.77 nm/195.206250 THz 3.125/6.25GHz spacing";
               }
               enum "1535.75" {
                 description "1535.75 nm/195.209375 THz 3.125GHz spacing";
               }
               enum "1535.72" {
                 description "1535.72 nm/195.212500 THz 3.125/6.25/12.5GHz spacing";
               }
               enum "1535.70" {
                 description "1535.70 nm/195.215625 THz 3.125GHz spacing";
               }
               enum "1535.67" {
                 description "1535.67 nm/195.218750 THz 3.125/6.25GHz spacing";
               }
               enum "1535.65" {
                 description "1535.65 nm/195.221875 THz 3.125GHz spacing";
               }
               enum "1535.63" {
                 description "1535.63 nm/195.225000 THz 3.125/6.25/12.5/75GHz spacing";
               }
               enum "1535.60" {
                 description "1535.60 nm/195.228125 THz 3.125GHz spacing";
               }
               enum "1535.58" {
                 description "1535.58 nm/195.231250 THz 3.125/6.25GHz spacing";
               }
               enum "1535.55" {
                 description "1535.55 nm/195.234375 THz 3.125GHz spacing";
               }
               enum "1535.53" {
                 description "1535.53 nm/195.237500 THz 3.125/6.25/12.5GHz spacing";
               }
               enum "1535.50" {
                 description "1535.50 nm/195.240625 THz 3.125GHz spacing";
               }
               enum "1535.48" {
                 description "1535.48 nm/195.243750 THz 3.125/6.25GHz spacing";
               }
               enum "1535.45" {
                 description "1535.45 nm/195.246875 THz 3.125GHz spacing";
               }
               enum "1535.43" {
                 description "1535.43 nm/195.250000 THz 3.125/6.25/12.5/50GHz spacing";
               }
               enum "1535.40" {
                 description "1535.40 nm/195.253125 THz 3.125GHz spacing";
               }
               enum "1535.38" {
                 description "1535.38 nm/195.256250 THz 3.125/6.25GHz spacing";
               }
               enum "1535.36" {
                 description "1535.36 nm/195.259375 THz 3.125GHz spacing";
               }
               enum "1535.33" {
                 description "1535.33 nm/195.262500 THz 3.125/6.25/12.5GHz spacing";
               }
               enum "1535.31" {
                 description "1535.31 nm/195.265625 THz 3.125GHz spacing";
               }
               enum "1535.28" {
                 description "1535.28 nm/195.268750 THz 3.125/6.25GHz spacing";
               }
               enum "1535.26" {
                 description "1535.26 nm/195.271875 THz 3.125GHz spacing";
               }
               enum "1535.23" {
                 description "1535.23 nm/195.275000 THz 3.125/6.25/12.5GHz spacing";
               }
               enum "1535.21" {
                 description "1535.21 nm/195.278125 THz 3.125GHz spacing";
               }
               enum "1535.18" {
                 description "1535.18 nm/195.281250 THz 3.125/6.25GHz spacing";
               }
               enum "1535.16" {
                 description "1535.16 nm/195.284375 THz 3.125GHz spacing";
               }
               enum "1535.13" {
                 description "1535.13 nm/195.287500 THz 3.125/6.25/12.5GHz spacing";
               }
               enum "1535.11" {
                 description "1535.11 nm/195.290625 THz 3.125GHz spacing";
               }
               enum "1535.08" {
                 description "1535.08 nm/195.293750 THz 3.125/6.25GHz spacing";
               }
               enum "1535.06" {
                 description "1535.06 nm/195.296875 THz 3.125GHz spacing";
               }
               enum "1535.04" {
                 description "1535.04 nm/195.300000 THz 3.125/6.25/12.5/50/75/100GHz spacing";
               }
               enum "1535.01" {
                 description "1535.01 nm/195.303125 THz 3.125GHz spacing";
               }
               enum "1534.99" {
                 description "1534.99 nm/195.306250 THz 3.125/6.25GHz spacing";
               }
               enum "1534.96" {
                 description "1534.96 nm/195.309375 THz 3.125GHz spacing";
               }
               enum "1534.94" {
                 description "1534.94 nm/195.312500 THz 3.125/6.25/12.5GHz spacing";
               }
               enum "1534.91" {
                 description "1534.91 nm/195.315625 THz 3.125GHz spacing";
               }
               enum "1534.89" {
                 description "1534.89 nm/195.318750 THz 3.125/6.25GHz spacing";
               }
               enum "1534.86" {
                 description "1534.86 nm/195.321875 THz 3.125GHz spacing";
               }
               enum "1534.84" {
                 description "1534.84 nm/195.325000 THz 3.125/6.25/12.5GHz spacing";
               }
               enum "1534.81" {
                 description "1534.81 nm/195.328125 THz 3.125GHz spacing";
               }
               enum "1534.79" {
                 description "1534.79 nm/195.331250 THz 3.125/6.25GHz spacing";
               }
               enum "1534.77" {
                 description "1534.77 nm/195.334375 THz 3.125GHz spacing";
               }
               enum "1534.74" {
                 description "1534.74 nm/195.337500 THz 3.125/6.25/12.5GHz spacing";
               }
               enum "1534.72" {
                 description "1534.72 nm/195.340625 THz 3.125GHz spacing";
               }
               enum "1534.69" {
                 description "1534.69 nm/195.343750 THz 3.125/6.25GHz spacing";
               }
               enum "1534.67" {
                 description "1534.67 nm/195.346875 THz 3.125GHz spacing";
               }
               enum "1534.64" {
                 description "1534.64 nm/195.350000 THz 3.125/6.25/12.5/50GHz spacing";
               }
               enum "1534.62" {
                 description "1534.62 nm/195.353125 THz 3.125GHz spacing";
               }
               enum "1534.59" {
                 description "1534.59 nm/195.356250 THz 3.125/6.25GHz spacing";
               }
               enum "1534.57" {
                 description "1534.57 nm/195.359375 THz 3.125GHz spacing";
               }
               enum "1534.54" {
                 description "1534.54 nm/195.362500 THz 3.125/6.25/12.5GHz spacing";
               }
               enum "1534.52" {
                 description "1534.52 nm/195.365625 THz 3.125GHz spacing";
               }
               enum "1534.50" {
                 description "1534.50 nm/195.368750 THz 3.125/6.25GHz spacing";
               }
               enum "1534.47" {
                 description "1534.47 nm/195.371875 THz 3.125GHz spacing";
               }
               enum "1534.45" {
                 description "1534.45 nm/195.375000 THz 3.125/6.25/12.5/75GHz spacing";
               }
               enum "1534.42" {
                 description "1534.42 nm/195.378125 THz 3.125GHz spacing";
               }
               enum "1534.40" {
                 description "1534.40 nm/195.381250 THz 3.125/6.25GHz spacing";
               }
               enum "1534.37" {
                 description "1534.37 nm/195.384375 THz 3.125GHz spacing";
               }
               enum "1534.35" {
                 description "1534.35 nm/195.387500 THz 3.125/6.25/12.5GHz spacing";
               }
               enum "1534.32" {
                 description "1534.32 nm/195.390625 THz 3.125GHz spacing";
               }
               enum "1534.30" {
                 description "1534.30 nm/195.393750 THz 3.125/6.25GHz spacing";
               }
               enum "1534.27" {
                 description "1534.27 nm/195.396875 THz 3.125GHz spacing";
               }
               enum "1534.25" {
                 description "1534.25 nm/195.400000 THz 3.125/6.25/12.5/100GHz spacing";
               }
               enum "1534.23" {
                 description "1534.23 nm/195.403125 THz 3.125GHz spacing";
               }
               enum "1534.20" {
                 description "1534.20 nm/195.406250 THz 3.125/6.25GHz spacing";
               }
               enum "1534.18" {
                 description "1534.18 nm/195.409375 THz 3.125GHz spacing";
               }
               enum "1534.15" {
                 description "1534.15 nm/195.412500 THz 3.125/6.25/12.5GHz spacing";
               }
               enum "1534.13" {
                 description "1534.13 nm/195.415625 THz 3.125GHz spacing";
               }
               enum "1534.10" {
                 description "1534.10 nm/195.418750 THz 3.125/6.25GHz spacing";
               }
               enum "1534.08" {
                 description "1534.08 nm/195.421875 THz 3.125GHz spacing";
               }
               enum "1534.05" {
                 description "1534.05 nm/195.425000 THz 3.125/6.25/12.5GHz spacing";
               }
               enum "1534.03" {
                 description "1534.03 nm/195.428125 THz 3.125GHz spacing";
               }
               enum "1534.00" {
                 description "1534.00 nm/195.431250 THz 3.125/6.25GHz spacing";
               }
               enum "1533.98" {
                 description "1533.98 nm/195.434375 THz 3.125GHz spacing";
               }
               enum "1533.96" {
                 description "1533.96 nm/195.437500 THz 3.125/6.25/12.5GHz spacing";
               }
               enum "1533.93" {
                 description "1533.93 nm/195.440625 THz 3.125GHz spacing";
               }
               enum "1533.91" {
                 description "1533.91 nm/195.443750 THz 3.125/6.25GHz spacing";
               }
               enum "1533.88" {
                 description "1533.88 nm/195.446875 THz 3.125GHz spacing";
               }
               enum "1533.86" {
                 description "1533.86 nm/195.450000 THz 3.125/6.25/12.5/50/75GHz spacing";
               }
               enum "1533.83" {
                 description "1533.83 nm/195.453125 THz 3.125GHz spacing";
               }
               enum "1533.81" {
                 description "1533.81 nm/195.456250 THz 3.125/6.25GHz spacing";
               }
               enum "1533.78" {
                 description "1533.78 nm/195.459375 THz 3.125GHz spacing";
               }
               enum "1533.76" {
                 description "1533.76 nm/195.462500 THz 3.125/6.25/12.5GHz spacing";
               }
               enum "1533.73" {
                 description "1533.73 nm/195.465625 THz 3.125GHz spacing";
               }
               enum "1533.71" {
                 description "1533.71 nm/195.468750 THz 3.125/6.25GHz spacing";
               }
               enum "1533.69" {
                 description "1533.69 nm/195.471875 THz 3.125GHz spacing";
               }
               enum "1533.66" {
                 description "1533.66 nm/195.475000 THz 3.125/6.25/12.5GHz spacing";
               }
               enum "1533.64" {
                 description "1533.64 nm/195.478125 THz 3.125GHz spacing";
               }
               enum "1533.61" {
                 description "1533.61 nm/195.481250 THz 3.125/6.25GHz spacing";
               }
               enum "1533.59" {
                 description "1533.59 nm/195.484375 THz 3.125GHz spacing";
               }
               enum "1533.56" {
                 description "1533.56 nm/195.487500 THz 3.125/6.25/12.5GHz spacing";
               }
               enum "1533.54" {
                 description "1533.54 nm/195.490625 THz 3.125GHz spacing";
               }
               enum "1533.51" {
                 description "1533.51 nm/195.493750 THz 3.125/6.25GHz spacing";
               }
               enum "1533.49" {
                 description "1533.49 nm/195.496875 THz 3.125GHz spacing";
               }
               enum "1533.47" {
                 description "1533.47 nm/195.500000 THz 3.125/6.25/12.5/100GHz spacing";
               }
               enum "1533.44" {
                 description "1533.44 nm/195.503125 THz 3.125GHz spacing";
               }
               enum "1533.42" {
                 description "1533.42 nm/195.506250 THz 3.125/6.25GHz spacing";
               }
               enum "1533.39" {
                 description "1533.39 nm/195.509375 THz 3.125GHz spacing";
               }
               enum "1533.37" {
                 description "1533.37 nm/195.512500 THz 3.125/6.25/12.5GHz spacing";
               }
               enum "1533.34" {
                 description "1533.34 nm/195.515625 THz 3.125GHz spacing";
               }
               enum "1533.32" {
                 description "1533.32 nm/195.518750 THz 3.125/6.25GHz spacing";
               }
               enum "1533.29" {
                 description "1533.29 nm/195.521875 THz 3.125GHz spacing";
               }
               enum "1533.27" {
                 description "1533.27 nm/195.525000 THz 3.125/6.25/12.5/75GHz spacing";
               }
               enum "1533.24" {
                 description "1533.24 nm/195.528125 THz 3.125GHz spacing";
               }
               enum "1533.22" {
                 description "1533.22 nm/195.531250 THz 3.125/6.25GHz spacing";
               }
               enum "1533.20" {
                 description "1533.20 nm/195.534375 THz 3.125GHz spacing";
               }
               enum "1533.17" {
                 description "1533.17 nm/195.537500 THz 3.125/6.25/12.5GHz spacing";
               }
               enum "1533.15" {
                 description "1533.15 nm/195.540625 THz 3.125GHz spacing";
               }
               enum "1533.12" {
                 description "1533.12 nm/195.543750 THz 3.125/6.25GHz spacing";
               }
               enum "1533.10" {
                 description "1533.10 nm/195.546875 THz 3.125GHz spacing";
               }
               enum "1533.07" {
                 description "1533.07 nm/195.550000 THz 3.125/6.25/12.5/50GHz spacing";
               }
               enum "1533.05" {
                 description "1533.05 nm/195.553125 THz 3.125GHz spacing";
               }
               enum "1533.02" {
                 description "1533.02 nm/195.556250 THz 3.125/6.25GHz spacing";
               }
               enum "1533.00" {
                 description "1533.00 nm/195.559375 THz 3.125GHz spacing";
               }
               enum "1532.98" {
                 description "1532.98 nm/195.562500 THz 3.125/6.25/12.5GHz spacing";
               }
               enum "1532.95" {
                 description "1532.95 nm/195.565625 THz 3.125GHz spacing";
               }
               enum "1532.93" {
                 description "1532.93 nm/195.568750 THz 3.125/6.25GHz spacing";
               }
               enum "1532.90" {
                 description "1532.90 nm/195.571875 THz 3.125GHz spacing";
               }
               enum "1532.88" {
                 description "1532.88 nm/195.575000 THz 3.125/6.25/12.5GHz spacing";
               }
               enum "1532.85" {
                 description "1532.85 nm/195.578125 THz 3.125GHz spacing";
               }
               enum "1532.83" {
                 description "1532.83 nm/195.581250 THz 3.125/6.25GHz spacing";
               }
               enum "1532.80" {
                 description "1532.80 nm/195.584375 THz 3.125GHz spacing";
               }
               enum "1532.78" {
                 description "1532.78 nm/195.587500 THz 3.125/6.25/12.5GHz spacing";
               }
               enum "1532.75" {
                 description "1532.75 nm/195.590625 THz 3.125GHz spacing";
               }
               enum "1532.73" {
                 description "1532.73 nm/195.593750 THz 3.125/6.25GHz spacing";
               }
               enum "1532.71" {
                 description "1532.71 nm/195.596875 THz 3.125GHz spacing";
               }
               enum "1532.68" {
                 description "1532.68 nm/195.600000 THz 3.125/6.25/12.5/50/75/100GHz spacing";
               }
               enum "1532.66" {
                 description "1532.66 nm/195.603125 THz 3.125GHz spacing";
               }
               enum "1532.63" {
                 description "1532.63 nm/195.606250 THz 3.125/6.25GHz spacing";
               }
               enum "1532.61" {
                 description "1532.61 nm/195.609375 THz 3.125GHz spacing";
               }
               enum "1532.58" {
                 description "1532.58 nm/195.612500 THz 3.125/6.25/12.5GHz spacing";
               }
               enum "1532.56" {
                 description "1532.56 nm/195.615625 THz 3.125GHz spacing";
               }
               enum "1532.53" {
                 description "1532.53 nm/195.618750 THz 3.125/6.25GHz spacing";
               }
               enum "1532.51" {
                 description "1532.51 nm/195.621875 THz 3.125GHz spacing";
               }
               enum "1532.49" {
                 description "1532.49 nm/195.625000 THz 3.125/6.25/12.5GHz spacing";
               }
               enum "1532.46" {
                 description "1532.46 nm/195.628125 THz 3.125GHz spacing";
               }
               enum "1532.44" {
                 description "1532.44 nm/195.631250 THz 3.125/6.25GHz spacing";
               }
               enum "1532.41" {
                 description "1532.41 nm/195.634375 THz 3.125GHz spacing";
               }
               enum "1532.39" {
                 description "1532.39 nm/195.637500 THz 3.125/6.25/12.5GHz spacing";
               }
               enum "1532.36" {
                 description "1532.36 nm/195.640625 THz 3.125GHz spacing";
               }
               enum "1532.34" {
                 description "1532.34 nm/195.643750 THz 3.125/6.25GHz spacing";
               }
               enum "1532.31" {
                 description "1532.31 nm/195.646875 THz 3.125GHz spacing";
               }
               enum "1532.29" {
                 description "1532.29 nm/195.650000 THz 3.125/6.25/12.5/50GHz spacing";
               }
               enum "1532.27" {
                 description "1532.27 nm/195.653125 THz 3.125GHz spacing";
               }
               enum "1532.24" {
                 description "1532.24 nm/195.656250 THz 3.125/6.25GHz spacing";
               }
               enum "1532.22" {
                 description "1532.22 nm/195.659375 THz 3.125GHz spacing";
               }
               enum "1532.19" {
                 description "1532.19 nm/195.662500 THz 3.125/6.25/12.5GHz spacing";
               }
               enum "1532.17" {
                 description "1532.17 nm/195.665625 THz 3.125GHz spacing";
               }
               enum "1532.14" {
                 description "1532.14 nm/195.668750 THz 3.125/6.25GHz spacing";
               }
               enum "1532.12" {
                 description "1532.12 nm/195.671875 THz 3.125GHz spacing";
               }
               enum "1532.09" {
                 description "1532.09 nm/195.675000 THz 3.125/6.25/12.5/75GHz spacing";
               }
               enum "1532.07" {
                 description "1532.07 nm/195.678125 THz 3.125GHz spacing";
               }
               enum "1532.04" {
                 description "1532.04 nm/195.681250 THz 3.125/6.25GHz spacing";
               }
               enum "1532.02" {
                 description "1532.02 nm/195.684375 THz 3.125GHz spacing";
               }
               enum "1532.00" {
                 description "1532.00 nm/195.687500 THz 3.125/6.25/12.5GHz spacing";
               }
               enum "1531.97" {
                 description "1531.97 nm/195.690625 THz 3.125GHz spacing";
               }
               enum "1531.95" {
                 description "1531.95 nm/195.693750 THz 3.125/6.25GHz spacing";
               }
               enum "1531.92" {
                 description "1531.92 nm/195.696875 THz 3.125GHz spacing";
               }
               enum "1531.90" {
                 description "1531.90 nm/195.700000 THz 3.125/6.25/12.5/100GHz spacing";
               }
               enum "1531.87" {
                 description "1531.87 nm/195.703125 THz 3.125GHz spacing";
               }
               enum "1531.85" {
                 description "1531.85 nm/195.706250 THz 3.125/6.25GHz spacing";
               }
               enum "1531.82" {
                 description "1531.82 nm/195.709375 THz 3.125GHz spacing";
               }
               enum "1531.80" {
                 description "1531.80 nm/195.712500 THz 3.125/6.25/12.5GHz spacing";
               }
               enum "1531.78" {
                 description "1531.78 nm/195.715625 THz 3.125GHz spacing";
               }
               enum "1531.75" {
                 description "1531.75 nm/195.718750 THz 3.125/6.25GHz spacing";
               }
               enum "1531.73" {
                 description "1531.73 nm/195.721875 THz 3.125GHz spacing";
               }
               enum "1531.70" {
                 description "1531.70 nm/195.725000 THz 3.125/6.25/12.5GHz spacing";
               }
               enum "1531.68" {
                 description "1531.68 nm/195.728125 THz 3.125GHz spacing";
               }
               enum "1531.65" {
                 description "1531.65 nm/195.731250 THz 3.125/6.25GHz spacing";
               }
               enum "1531.63" {
                 description "1531.63 nm/195.734375 THz 3.125GHz spacing";
               }
               enum "1531.60" {
                 description "1531.60 nm/195.737500 THz 3.125/6.25/12.5GHz spacing";
               }
               enum "1531.58" {
                 description "1531.58 nm/195.740625 THz 3.125GHz spacing";
               }
               enum "1531.56" {
                 description "1531.56 nm/195.743750 THz 3.125/6.25GHz spacing";
               }
               enum "1531.53" {
                 description "1531.53 nm/195.746875 THz 3.125GHz spacing";
               }
               enum "1531.51" {
                 description "1531.51 nm/195.750000 THz 3.125/6.25/12.5/50/75GHz spacing";
               }
               enum "1531.48" {
                 description "1531.48 nm/195.753125 THz 3.125GHz spacing";
               }
               enum "1531.46" {
                 description "1531.46 nm/195.756250 THz 3.125/6.25GHz spacing";
               }
               enum "1531.43" {
                 description "1531.43 nm/195.759375 THz 3.125GHz spacing";
               }
               enum "1531.41" {
                 description "1531.41 nm/195.762500 THz 3.125/6.25/12.5GHz spacing";
               }
               enum "1531.38" {
                 description "1531.38 nm/195.765625 THz 3.125GHz spacing";
               }
               enum "1531.36" {
                 description "1531.36 nm/195.768750 THz 3.125/6.25GHz spacing";
               }
               enum "1531.34" {
                 description "1531.34 nm/195.771875 THz 3.125GHz spacing";
               }
               enum "1531.31" {
                 description "1531.31 nm/195.775000 THz 3.125/6.25/12.5GHz spacing";
               }
               enum "1531.29" {
                 description "1531.29 nm/195.778125 THz 3.125GHz spacing";
               }
               enum "1531.26" {
                 description "1531.26 nm/195.781250 THz 3.125/6.25GHz spacing";
               }
               enum "1531.24" {
                 description "1531.24 nm/195.784375 THz 3.125GHz spacing";
               }
               enum "1531.21" {
                 description "1531.21 nm/195.787500 THz 3.125/6.25/12.5GHz spacing";
               }
               enum "1531.19" {
                 description "1531.19 nm/195.790625 THz 3.125GHz spacing";
               }
               enum "1531.16" {
                 description "1531.16 nm/195.793750 THz 3.125/6.25GHz spacing";
               }
               enum "1531.14" {
                 description "1531.14 nm/195.796875 THz 3.125GHz spacing";
               }
               enum "1531.12" {
                 description "1531.12 nm/195.800000 THz 3.125/6.25/12.5/100GHz spacing";
               }
               enum "1531.09" {
                 description "1531.09 nm/195.803125 THz 3.125GHz spacing";
               }
               enum "1531.07" {
                 description "1531.07 nm/195.806250 THz 3.125/6.25GHz spacing";
               }
               enum "1531.04" {
                 description "1531.04 nm/195.809375 THz 3.125GHz spacing";
               }
               enum "1531.02" {
                 description "1531.02 nm/195.812500 THz 3.125/6.25/12.5GHz spacing";
               }
               enum "1530.99" {
                 description "1530.99 nm/195.815625 THz 3.125GHz spacing";
               }
               enum "1530.97" {
                 description "1530.97 nm/195.818750 THz 3.125/6.25GHz spacing";
               }
               enum "1530.94" {
                 description "1530.94 nm/195.821875 THz 3.125GHz spacing";
               }
               enum "1530.92" {
                 description "1530.92 nm/195.825000 THz 3.125/6.25/12.5/75GHz spacing";
               }
               enum "1530.90" {
                 description "1530.90 nm/195.828125 THz 3.125GHz spacing";
               }
               enum "1530.87" {
                 description "1530.87 nm/195.831250 THz 3.125/6.25GHz spacing";
               }
               enum "1530.85" {
                 description "1530.85 nm/195.834375 THz 3.125GHz spacing";
               }
               enum "1530.82" {
                 description "1530.82 nm/195.837500 THz 3.125/6.25/12.5GHz spacing";
               }
               enum "1530.80" {
                 description "1530.80 nm/195.840625 THz 3.125GHz spacing";
               }
               enum "1530.77" {
                 description "1530.77 nm/195.843750 THz 3.125/6.25GHz spacing";
               }
               enum "1530.75" {
                 description "1530.75 nm/195.846875 THz 3.125GHz spacing";
               }
               enum "1530.72" {
                 description "1530.72 nm/195.850000 THz 3.125/6.25/12.5/50GHz spacing";
               }
               enum "1530.70" {
                 description "1530.70 nm/195.853125 THz 3.125GHz spacing";
               }
               enum "1530.68" {
                 description "1530.68 nm/195.856250 THz 3.125/6.25GHz spacing";
               }
               enum "1530.65" {
                 description "1530.65 nm/195.859375 THz 3.125GHz spacing";
               }
               enum "1530.63" {
                 description "1530.63 nm/195.862500 THz 3.125/6.25/12.5GHz spacing";
               }
               enum "1530.60" {
                 description "1530.60 nm/195.865625 THz 3.125GHz spacing";
               }
               enum "1530.58" {
                 description "1530.58 nm/195.868750 THz 3.125/6.25GHz spacing";
               }
               enum "1530.55" {
                 description "1530.55 nm/195.871875 THz 3.125GHz spacing";
               }
               enum "1530.53" {
                 description "1530.53 nm/195.875000 THz 3.125/6.25/12.5GHz spacing";
               }
               enum "1530.51" {
                 description "1530.51 nm/195.878125 THz 3.125GHz spacing";
               }
               enum "1530.48" {
                 description "1530.48 nm/195.881250 THz 3.125/6.25GHz spacing";
               }
               enum "1530.46" {
                 description "1530.46 nm/195.884375 THz 3.125GHz spacing";
               }
               enum "1530.43" {
                 description "1530.43 nm/195.887500 THz 3.125/6.25/12.5GHz spacing";
               }
               enum "1530.41" {
                 description "1530.41 nm/195.890625 THz 3.125GHz spacing";
               }
               enum "1530.38" {
                 description "1530.38 nm/195.893750 THz 3.125/6.25GHz spacing";
               }
               enum "1530.36" {
                 description "1530.36 nm/195.896875 THz 3.125GHz spacing";
               }
               enum "1530.33" {
                 description "1530.33 nm/195.900000 THz 3.125/6.25/12.5/50/75/100GHz spacing";
               }
               enum "1530.31" {
                 description "1530.31 nm/195.903125 THz 3.125GHz spacing";
               }
               enum "1530.29" {
                 description "1530.29 nm/195.906250 THz 3.125/6.25GHz spacing";
               }
               enum "1530.26" {
                 description "1530.26 nm/195.909375 THz 3.125GHz spacing";
               }
               enum "1530.24" {
                 description "1530.24 nm/195.912500 THz 3.125/6.25/12.5GHz spacing";
               }
               enum "1530.21" {
                 description "1530.21 nm/195.915625 THz 3.125GHz spacing";
               }
               enum "1530.19" {
                 description "1530.19 nm/195.918750 THz 3.125/6.25GHz spacing";
               }
               enum "1530.16" {
                 description "1530.16 nm/195.921875 THz 3.125GHz spacing";
               }
               enum "1530.14" {
                 description "1530.14 nm/195.925000 THz 3.125/6.25/12.5GHz spacing";
               }
               enum "1530.11" {
                 description "1530.11 nm/195.928125 THz 3.125GHz spacing";
               }
               enum "1530.09" {
                 description "1530.09 nm/195.931250 THz 3.125/6.25GHz spacing";
               }
               enum "1530.07" {
                 description "1530.07 nm/195.934375 THz 3.125GHz spacing";
               }
               enum "1530.04" {
                 description "1530.04 nm/195.937500 THz 3.125/6.25/12.5GHz spacing";
               }
               enum "1530.02" {
                 description "1530.02 nm/195.940625 THz 3.125GHz spacing";
               }
               enum "1529.99" {
                 description "1529.99 nm/195.943750 THz 3.125/6.25GHz spacing";
               }
               enum "1529.97" {
                 description "1529.97 nm/195.946875 THz 3.125GHz spacing";
               }
               enum "1529.94" {
                 description "1529.94 nm/195.950000 THz 3.125/6.25/12.5/50GHz spacing";
               }
               enum "1529.92" {
                 description "1529.92 nm/195.953125 THz 3.125GHz spacing";
               }
               enum "1529.89" {
                 description "1529.89 nm/195.956250 THz 3.125/6.25GHz spacing";
               }
               enum "1529.87" {
                 description "1529.87 nm/195.959375 THz 3.125GHz spacing";
               }
               enum "1529.85" {
                 description "1529.85 nm/195.962500 THz 3.125/6.25/12.5GHz spacing";
               }
               enum "1529.82" {
                 description "1529.82 nm/195.965625 THz 3.125GHz spacing";
               }
               enum "1529.80" {
                 description "1529.80 nm/195.968750 THz 3.125/6.25GHz spacing";
               }
               enum "1529.77" {
                 description "1529.77 nm/195.971875 THz 3.125GHz spacing";
               }
               enum "1529.75" {
                 description "1529.75 nm/195.975000 THz 3.125/6.25/12.5/75GHz spacing";
               }
               enum "1529.72" {
                 description "1529.72 nm/195.978125 THz 3.125GHz spacing";
               }
               enum "1529.70" {
                 description "1529.70 nm/195.981250 THz 3.125/6.25GHz spacing";
               }
               enum "1529.68" {
                 description "1529.68 nm/195.984375 THz 3.125GHz spacing";
               }
               enum "1529.65" {
                 description "1529.65 nm/195.987500 THz 3.125/6.25/12.5GHz spacing";
               }
               enum "1529.63" {
                 description "1529.63 nm/195.990625 THz 3.125GHz spacing";
               }
               enum "1529.60" {
                 description "1529.60 nm/195.993750 THz 3.125/6.25GHz spacing";
               }
               enum "1529.58" {
                 description "1529.58 nm/195.996875 THz 3.125GHz spacing";
               }
               enum "1529.55" {
                 description "1529.55 nm/196.000000 THz 3.125/6.25/12.5/100GHz spacing";
               }
               enum "1529.53" {
                 description "1529.53 nm/196.003125 THz 3.125GHz spacing";
               }
               enum "1529.50" {
                 description "1529.50 nm/196.006250 THz 3.125/6.25GHz spacing";
               }
               enum "1529.48" {
                 description "1529.48 nm/196.009375 THz 3.125GHz spacing";
               }
               enum "1529.46" {
                 description "1529.46 nm/196.012500 THz 3.125/6.25/12.5GHz spacing";
               }
               enum "1529.43" {
                 description "1529.43 nm/196.015625 THz 3.125GHz spacing";
               }
               enum "1529.41" {
                 description "1529.41 nm/196.018750 THz 3.125/6.25GHz spacing";
               }
               enum "1529.38" {
                 description "1529.38 nm/196.021875 THz 3.125GHz spacing";
               }
               enum "1529.36" {
                 description "1529.36 nm/196.025000 THz 3.125/6.25/12.5GHz spacing";
               }
               enum "1529.33" {
                 description "1529.33 nm/196.028125 THz 3.125GHz spacing";
               }
               enum "1529.31" {
                 description "1529.31 nm/196.031250 THz 3.125/6.25GHz spacing";
               }
               enum "1529.29" {
                 description "1529.29 nm/196.034375 THz 3.125GHz spacing";
               }
               enum "1529.26" {
                 description "1529.26 nm/196.037500 THz 3.125/6.25/12.5GHz spacing";
               }
               enum "1529.24" {
                 description "1529.24 nm/196.040625 THz 3.125GHz spacing";
               }
               enum "1529.21" {
                 description "1529.21 nm/196.043750 THz 3.125/6.25GHz spacing";
               }
               enum "1529.19" {
                 description "1529.19 nm/196.046875 THz 3.125GHz spacing";
               }
               enum "1529.16" {
                 description "1529.16 nm/196.050000 THz 3.125/6.25/12.5/50/75GHz spacing";
               }
               enum "1529.14" {
                 description "1529.14 nm/196.053125 THz 3.125GHz spacing";
               }
               enum "1529.11" {
                 description "1529.11 nm/196.056250 THz 3.125/6.25GHz spacing";
               }
               enum "1529.09" {
                 description "1529.09 nm/196.059375 THz 3.125GHz spacing";
               }
               enum "1529.07" {
                 description "1529.07 nm/196.062500 THz 3.125/6.25/12.5GHz spacing";
               }
               enum "1529.04" {
                 description "1529.04 nm/196.065625 THz 3.125GHz spacing";
               }
               enum "1529.02" {
                 description "1529.02 nm/196.068750 THz 3.125/6.25GHz spacing";
               }
               enum "1528.99" {
                 description "1528.99 nm/196.071875 THz 3.125GHz spacing";
               }
               enum "1528.97" {
                 description "1528.97 nm/196.075000 THz 3.125/6.25/12.5GHz spacing";
               }
               enum "1528.94" {
                 description "1528.94 nm/196.078125 THz 3.125GHz spacing";
               }
               enum "1528.92" {
                 description "1528.92 nm/196.081250 THz 3.125/6.25GHz spacing";
               }
               enum "1528.90" {
                 description "1528.90 nm/196.084375 THz 3.125GHz spacing";
               }
               enum "1528.87" {
                 description "1528.87 nm/196.087500 THz 3.125/6.25/12.5GHz spacing";
               }
               enum "1528.85" {
                 description "1528.85 nm/196.090625 THz 3.125GHz spacing";
               }
               enum "1528.82" {
                 description "1528.82 nm/196.093750 THz 3.125/6.25GHz spacing";
               }
               enum "1528.80" {
                 description "1528.80 nm/196.096875 THz 3.125GHz spacing";
               }
               enum "1528.77" {
                 description "1528.77 nm/196.100000 THz 3.125/6.25/12.5/50/75/100GHz spacing";
               }
               enum "1528.75" {
                 description "1528.75 nm/196.103125 THz 3.125GHz spacing";
               }
               enum "1528.72" {
                 description "1528.72 nm/196.106250 THz 3.125/6.25GHz spacing";
               }
               enum "1528.70" {
                 description "1528.70 nm/196.109375 THz 3.125GHz spacing";
               }
               enum "1528.68" {
                 description "1528.68 nm/196.112500 THz 3.125/6.25/12.5GHz spacing";
               }
               enum "1528.65" {
                 description "1528.65 nm/196.115625 THz 3.125GHz spacing";
               }
               enum "1528.63" {
                 description "1528.63 nm/196.118750 THz 3.125/6.25GHz spacing";
               }
               enum "1528.60" {
                 description "1528.60 nm/196.121875 THz 3.125GHz spacing";
               }
               enum "1528.58" {
                 description "1528.58 nm/196.125000 THz 3.125/6.25/12.5/75GHz spacing";
               }
               enum "1528.55" {
                 description "1528.55 nm/196.128125 THz 3.125GHz spacing";
               }
               enum "1528.53" {
                 description "1528.53 nm/196.131250 THz 3.125/6.25GHz spacing";
               }
               enum "1528.51" {
                 description "1528.51 nm/196.134375 THz 3.125GHz spacing";
               }
               enum "1528.48" {
                 description "1528.48 nm/196.137500 THz 3.125/6.25/12.5GHz spacing";
               }
               enum "1528.46" {
                 description "1528.46 nm/196.140625 THz 3.125GHz spacing";
               }
               enum "1528.43" {
                 description "1528.43 nm/196.143750 THz 3.125/6.25GHz spacing";
               }
               enum "1528.41" {
                 description "1528.41 nm/196.146875 THz 3.125GHz spacing";
               }
               enum "1528.38" {
                 description "1528.38 nm/196.15040 THz 50Ghz spacing";
               }
             }
           }
           leaf tx-power {
             description "Transmit laser output power";
             units "dBm";
             type string {
               junos:posix-pattern "^[+-]?[0-9]+(\\.[0-9]+)?$";
               junos:pattern-message "numerical value must be specified with optional leading sign and optional decimal point";
             }
           }
           container loopback {
             presence "enable loopback";
             description "Put the optics in loopback mode";
             uses apply-advanced;
             leaf loopbacktype {
               description "Set loopback type";
               type enumeration {
                 enum "media-side-out" {
                   description "Loop media side output back to input";
                 }
                 enum "media-side-in" {
                   description "Loop media side input back to output";
                 }
                 enum "host-side-out" {
                   description "Loop host side output back to input";
                 }
                 enum "host-side-in" {
                   description "Loop host side input back to output";
                 }
               }
             }
           }
           leaf los-warning-threshold {
             description "LOS warning threshold";
             units "dBm";
             type string;
           }
           leaf los-alarm-threshold {
             description "LOS alarm threshold";
             units "dBm";
             type string;
           }
           leaf modulation-format {
             description "Type of Modulation Format";
             type enumeration {
               enum "16qam" {
                 description "16-QAM Modulation Format";
               }
               enum "8qam" {
                 description "8-QAM MOdulation Format";
               }
               enum "qpsk" {
                 description "QPSK Modulation Format";
               }
             }
           }
           choice laser-enable-choice {
             leaf laser-enable {
               description "Enable Laser";
               type empty;
             }
             leaf no-laser-enable {
               description "Don't enable Laser";
               type empty;
             }
           }
           choice is-ma-choice {
             leaf is-ma {
               description "Link is enabled with alarms masked";
               type empty;
             }
             leaf no-is-ma {
               description "Don't link is enabled with alarms masked";
               type empty;
             }
           }
           leaf encoding {
             description "Line encoding";
             type enumeration {
               enum "differential" {
                 description "Differential phase line encoding";
               }
               enum "non-differential" {
                 description "Non-differential phase line encoding";
               }
             }
           }
           leaf fec {
             description "Forward Error Correction mode";
             type enumeration {
               enum "sdfec" {
                 description "Sky-Compatible Soft Decision Forward Error Correction";
               }
               enum "sdfec25" {
                 description "Denali-Compatible Soft Decision Forward Error Correction with 25 percent overhead";
               }
               enum "hgfec" {
                 description "High Gain Forward Error Correction";
               }
               enum "sdfec15" {
                 description "Soft Decision Forward Error Correction with 15 percent overhead";
               }
             }
           }
           leaf high-polarization {
             description "High polarization tracking mode";
             type empty;
           }
           container application {
             description "Config Host and Media Code";
             uses apply-advanced;
             leaf hostid {
               description "Enter Host Code";
               type union {
                 type string {
                   pattern "<.*>|$.*";
                 }
                 type uint32 {
                   range "1 .. 255";
                 }
               }
             }
             leaf mediaid {
               description "Enter Media Code";
               type union {
                 type string {
                   pattern "<.*>|$.*";
                 }
                 type uint32 {
                   range "1 .. 255";
                 }
               }
             }
             leaf domainid {
               description "Enter Domain ID";
               type union {
                 type string {
                   pattern "<.*>|$.*";
                 }
                 type uint32 {
                   range "0 .. 255";
                 }
               }
             }
           }
           container cd {
             description "Config CD value mapped with media-id";
             uses apply-advanced;
             leaf cd-val {
               description "Enter cd value";
               type decimal64 {
                 fraction-digits 9;
               }
             }
           }
           container appselid {
             description "Config AppSel ID";
             uses apply-advanced;
             leaf id {
               type union {
                 type string {
                   pattern "<.*>|$.*";
                 }
                 type uint32 {
                   range "1 .. 240";
                 }
               }
             }
           }
           container signal-degrade {
             description "Signal degrade thresholds";
             uses apply-advanced;
             leaf interval {
               description "Time interval";
               default "10";
               units "milliseconds";
               type union {
                 type string {
                   pattern "<.*>|$.*";
                 }
                 type uint32 {
                   range "1 .. 1000";
                 }
               }
             }
             leaf ber-threshold-clear {
               description "Ber threshold for signal degrade clear (format: xe-n, example: 4.5e-3)";
               type string {
                 junos:posix-pattern "^[0-9]+(.[0-9]+)?e-[0-9]$";
                 junos:pattern-message "Ber threshold value in format: xe-n, x is an integer or decimal number, n = 0..9";
               }
             }
             leaf ber-threshold-signal-degrade {
               description "Ber threshold for signal-degrade (format: xe-n, example: 4.5e-3)";
               type string {
                 junos:posix-pattern "^[0-9]+(.[0-9]+)?e-[0-9]$";
                 junos:pattern-message "Ber threshold value in format: xe-n, x is an integer or decimal number, n = 0..9";
               }
             }
             leaf q-threshold-signal-degrade-clear {
               description "Q threshold for signal-degrade clear (e.g. 14.26)";
               units "dB";
               type string;
             }
             leaf q-threshold-signal-degrade {
               description "Q threshold for signal-degrade (e.g. 9.26)";
               units "dB";
               type string;
             }
           }
           list alarm {
             key name;
             ordered-by user;
             description "Set optic alarms";
             leaf name {
               junos:cli-feature "nokeyword";
               type enumeration {
                 enum "low-light-alarm" {
                   description "Enable low light alarm";
                 }
               }
             }
             uses apply-advanced;
             choice actiontype {
               case case_1 {
                 leaf syslog {
                   type empty;
                 }
               }
               case case_2 {
                 leaf link-down {
                   type empty;
                 }
               }
             }
           }
           container tca {
             description "Set tca for optic alarms";
             uses apply-advanced;
             container tx-power-high-tca {
               description "Tx power high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                   junos:posix-pattern "^[+-]?[0-9]+(\\.[0-9]+)?$";
                   junos:pattern-message "numerical value must be specified with optional leading sign and optional decimal point";
                 }
               }
               leaf threshold-24hrs {
                 description "TCA Threshold for 24-hour interval in dBm";
                 type string {
                   junos:posix-pattern "^[+-]?[0-9]+(\\.[0-9]+)?$";
                   junos:pattern-message "numerical value must be specified with optional leading sign and optional decimal point";
                 }
               }
             }
             container tx-power-low-tca {
               description "Tx power low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                   junos:posix-pattern "^[+-]?[0-9]+(\\.[0-9]+)?$";
                   junos:pattern-message "numerical value must be specified with optional leading sign and optional decimal point";
                 }
               }
               leaf threshold-24hrs {
                 description "TCA Threshold for 24-hour interval in dBm";
                 type string {
                   junos:posix-pattern "^[+-]?[0-9]+(\\.[0-9]+)?$";
                   junos:pattern-message "numerical value must be specified with optional leading sign and optional decimal point";
                 }
               }
             }
             container rx-power-high-tca {
               description "Rx power high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                   junos:posix-pattern "^[+-]?[0-9]+(\\.[0-9]+)?$";
                   junos:pattern-message "numerical value must be specified with optional leading sign and optional decimal point";
                 }
               }
               leaf threshold-24hrs {
                 description "TCA Threshold for 24-hour interval in dBm";
                 type string {
                   junos:posix-pattern "^[+-]?[0-9]+(\\.[0-9]+)?$";
                   junos:pattern-message "numerical value must be specified with optional leading sign and optional decimal point";
                 }
               }
             }
             container rx-power-low-tca {
               description "Rx power low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                   junos:posix-pattern "^[+-]?[0-9]+(\\.[0-9]+)?$";
                   junos:pattern-message "numerical value must be specified with optional leading sign and optional decimal point";
                 }
               }
               leaf threshold-24hrs {
                 description "TCA Threshold for 24-hour interval in dBm";
                 type string {
                   junos:posix-pattern "^[+-]?[0-9]+(\\.[0-9]+)?$";
                   junos:pattern-message "numerical value must be specified with optional leading sign and optional decimal point";
                 }
               }
             }
             container rx-signal-power-high-tca {
               description "Rx signal power high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                   junos:posix-pattern "^[+-]?[0-9]+(\\.[0-9]+)?$";
                   junos:pattern-message "numerical value must be specified with optional leading sign and optional decimal point";
                 }
               }
               leaf threshold-24hrs {
                 description "TCA Threshold for 24-hour interval in dBm";
                 type string {
                   junos:posix-pattern "^[+-]?[0-9]+(\\.[0-9]+)?$";
                   junos:pattern-message "numerical value must be specified with optional leading sign and optional decimal point";
                 }
               }
             }
             container rx-signal-power-low-tca {
               description "Rx signal power low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                   junos:posix-pattern "^[+-]?[0-9]+(\\.[0-9]+)?$";
                   junos:pattern-message "numerical value must be specified with optional leading sign and optional decimal point";
                 }
               }
               leaf threshold-24hrs {
                 description "TCA Threshold for 24-hour interval in dBm";
                 type string {
                   junos:posix-pattern "^[+-]?[0-9]+(\\.[0-9]+)?$";
                   junos:pattern-message "numerical value must be specified with optional leading sign and optional decimal point";
                 }
               }
             }
             container temperature-high-tca {
               description "Temperature high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in celsius";
                 type string {
                   junos:posix-pattern "^[+-]?[0-9]+(\\.[0-9]+)?$";
                   junos:pattern-message "numerical value must be specified with optional leading sign and optional decimal point";
                 }
               }
               leaf threshold-24hrs {
                 description "TCA Threshold for 24-hour interval in celsius";
                 type string {
                   junos:posix-pattern "^[+-]?[0-9]+(\\.[0-9]+)?$";
                   junos:pattern-message "numerical value must be specified with optional leading sign and optional decimal point";
                 }
               }
             }
             container temperature-low-tca {
               description "Temperature low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in celsius";
                 type string {
                   junos:posix-pattern "^[+-]?[0-9]+(\\.[0-9]+)?$";
                   junos:pattern-message "numerical value must be specified with optional leading sign and optional decimal point";
                 }
               }
               leaf threshold-24hrs {
                 description "TCA Threshold for 24-hour interval in celsius";
                 type string {
                   junos:posix-pattern "^[+-]?[0-9]+(\\.[0-9]+)?$";
                   junos:pattern-message "numerical value must be specified with optional leading sign and optional decimal point";
                 }
               }
             }
             container carrier-frequency-offset-high-tca {
               description "Carrier frequency offset high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                   junos:posix-pattern "^[+-]?[0-9]+(\\.[0-9]+)?$";
                   junos:pattern-message "numerical value must be specified with optional leading sign and optional decimal point";
                 }
               }
               leaf threshold-24hrs {
                 description "TCA Threshold for 24-hour interval in MHz";
                 type string {
                   junos:posix-pattern "^[+-]?[0-9]+(\\.[0-9]+)?$";
                   junos:pattern-message "numerical value must be specified with optional leading sign and optional decimal point";
                 }
               }
             }
             container carrier-frequency-offset-low-tca {
               description "Carrier frequency offset low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                   junos:posix-pattern "^[+-]?[0-9]+(\\.[0-9]+)?$";
                   junos:pattern-message "numerical value must be specified with optional leading sign and optional decimal point";
                 }
               }
               leaf threshold-24hrs {
                 description "TCA Threshold for 24-hour interval in MHz";
                 type string {
                   junos:posix-pattern "^[+-]?[0-9]+(\\.[0-9]+)?$";
                   junos:pattern-message "numerical value must be specified with optional leading sign and optional decimal point";
                 }
               }
             }
             container fec-ber {
               junos:cli-feature "oneliner";
               description "Optics Errored Seconds Threshold crossing defect trigger";
               choice enable-tca-choice {
                 leaf enable-tca {
                   description "Enable the Optics errored seconds threshold crossing alert";
                   type empty;
                 }
                 leaf no-enable-tca {
                   description "Don't enable the Optics errored seconds threshold crossing alert";
                   type empty;
                 }
               }
               leaf threshold {
                 description "TCA Threshold for user-configurable interval (default 15-minutes) in exponential format";
                 default "10e-3";
                 type string {
                   junos:posix-pattern "^[0-9]+(\\.[0-9]+)?e-[0-9]$";
                   junos:pattern-message "exponential value must be in format xe-n, x is a decimal number, n = 0..9";
                 }
               }
               leaf threshold-24hrs {
                 description "TCA Threshold for 24-hour interval in exponential format";
                 default "10e-3";
                 type string {
                   junos:posix-pattern "^[0-9]+(\\.[0-9]+)?e-[0-9]$";
                   junos:pattern-message "exponential value must be in format xe-n, x is a decimal number, n = 0..9";
                 }
               }
             }
             container tec-current-high-tca {
               description "TEC Current high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in mA";
                 type string {
                   junos:posix-pattern "^[+-]?[0-9]+(\\.[0-9]+)?$";
                   junos:pattern-message "numerical value must be specified with optional leading sign and optional decimal point";
                 }
               }
               leaf threshold-24hrs {
                 description "TCA Threshold for 24-hour interval in mA";
                 type string {
                   junos:posix-pattern "^[+-]?[0-9]+(\\.[0-9]+)?$";
                   junos:pattern-message "numerical value must be specified with optional leading sign and optional decimal point";
                 }
               }
             }
             container tec-current-low-tca {
               description "TEC Current low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in mA";
                 type string {
                   junos:posix-pattern "^[+-]?[0-9]+(\\.[0-9]+)?$";
                   junos:pattern-message "numerical value must be specified with optional leading sign and optional decimal point";
                 }
               }
               leaf threshold-24hrs {
                 description "TCA Threshold for 24-hour interval in mA";
                 type string {
                   junos:posix-pattern "^[+-]?[0-9]+(\\.[0-9]+)?$";
                   junos:pattern-message "numerical value must be specified with optional leading sign and optional decimal point";
                 }
               }
             }
             container residual-isi-high-tca {
               description "Residual ISI high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in ps/nm";
                 type string {
                   junos:posix-pattern "^[+-]?[0-9]+(\\.[0-9]+)?$";
                   junos:pattern-message "numerical value must be specified with optional leading sign and optional decimal point";
                 }
               }
               leaf threshold-24hrs {
                 description "TCA Threshold for 24-hour interval in ps/nm";
                 type string {
                   junos:posix-pattern "^[+-]?[0-9]+(\\.[0-9]+)?$";
                   junos:pattern-message "numerical value must be specified with optional leading sign and optional decimal point";
                 }
               }
             }
             container residual-isi-low-tca {
               description "Residual ISI low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in ps/nm";
                 type string {
                   junos:posix-pattern "^[+-]?[0-9]+(\\.[0-9]+)?$";
                   junos:pattern-message "numerical value must be specified with optional leading sign and optional decimal point";
                 }
               }
               leaf threshold-24hrs {
                 description "TCA Threshold for 24-hour interval in ps/nm";
                 type string {
                   junos:posix-pattern "^[+-]?[0-9]+(\\.[0-9]+)?$";
                   junos:pattern-message "numerical value must be specified with optional leading sign and optional decimal point";
                 }
               }
             }
             container pam-histogram-high-tca {
               description "PAM Histogram high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes)";
                 type string {
                   junos:posix-pattern "^[0-9]+$";
                   junos:pattern-message "must be an unsigned integer";
                 }
               }
               leaf threshold-24hrs {
                 description "TCA Threshold for 24-hour interval";
                 type string {
                   junos:posix-pattern "^[0-9]+$";
                   junos:pattern-message "must be an unsigned integer";
                 }
               }
             }
             container snr-low-tca {
               description "SNR low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm ";
                 type string {
                   junos:posix-pattern "^[+-]?[0-9]+(\\.[0-9]+)?$";
                   junos:pattern-message "numerical value must be specified with optional leading sign and optional decimal point";
                 }
               }
               leaf threshold-24hrs {
                 description "TCA Threshold for 24-hour interval in dBm";
                 type string {
                   junos:posix-pattern "^[+-]?[0-9]+(\\.[0-9]+)?$";
                   junos:pattern-message "numerical value must be specified with optional leading sign and optional decimal point";
                 }
               }
             }
             container fec-corrected-errors-high-tca {
               description "FEC Corrected Error High Threshold crossing defect trigger";
               uses apply-advanced;
               choice enable-tca-choice {
                 leaf enable-tca {
                   description "Enable the FEC Corrected Errors threshold crossing alert";
                   type empty;
                 }
                 leaf no-enable-tca {
                   description "Don't enable the FEC Corrected Errors threshold crossing alert";
                   type empty;
                 }
               }
               leaf threshold {
                 description "TCA Threshold for user-configurable interval (default 15-minutes) in exponential format";
                 default "10e-3";
                 type string {
                   junos:posix-pattern "^[0-9]+(\\.[0-9]+)?e-[0-9]$";
                   junos:pattern-message "exponential value must be in format xe-n, x is a decimal number, n = 0..9";
                 }
               }
               leaf threshold-24hrs {
                 description "TCA Threshold for 24-hour interval in exponential format";
                 default "10e-3";
                 type string {
                   junos:posix-pattern "^[0-9]+(\\.[0-9]+)?e-[0-9]$";
                   junos:pattern-message "exponential value must be in format xe-n, x is a decimal number, n = 0..9";
                 }
               }
             }
             container fec-ucorrected-words-high-tca {
               description "FEC UCorrected Words High Threshold crossing defect trigger";
               uses apply-advanced;
               choice enable-tca-choice {
                 leaf enable-tca {
                   description "Enable the FEC UCorrected Words threshold crossing alert";
                   type empty;
                 }
                 leaf no-enable-tca {
                   description "Don't enable the FEC UCorrected Words threshold crossing alert";
                   type empty;
                 }
               }
               leaf threshold {
                 description "TCA Threshold for user-configurable interval (default 15-minutes) in exponential format";
                 default "10e-3";
                 type string {
                   junos:posix-pattern "^[0-9]+(\\.[0-9]+)?e-[0-9]$";
                   junos:pattern-message "exponential value must be in format xe-n, x is a decimal number, n = 0..9";
                 }
               }
               leaf threshold-24hrs {
                 description "TCA Threshold for 24-hour interval in exponential format";
                 default "10e-3";
                 type string {
                   junos:posix-pattern "^[0-9]+(\\.[0-9]+)?e-[0-9]$";
                   junos:pattern-message "exponential value must be in format xe-n, x is a decimal number, n = 0..9";
                 }
               }
             }
             container laser-frequency-error-high-tca {
               description "Laser frequency error high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                   junos:posix-pattern "^[+-]?[0-9]+(\\.[0-9]+)?$";
                   junos:pattern-message "numerical value must be specified with optional leading sign and optional decimal point";
                 }
               }
               leaf threshold-24hrs {
                 description "TCA Threshold for 24-hour interval in MHz";
                 type string {
                   junos:posix-pattern "^[+-]?[0-9]+(\\.[0-9]+)?$";
                   junos:pattern-message "numerical value must be specified with optional leading sign and optional decimal point";
                 }
               }
             }
             container laser-frequency-error-low-tca {
               description "Laser frequency error low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                   junos:posix-pattern "^[+-]?[0-9]+(\\.[0-9]+)?$";
                   junos:pattern-message "numerical value must be specified with optional leading sign and optional decimal point";
                 }
               }
               leaf threshold-24hrs {
                 description "TCA Threshold for 24-hour interval in MHz";
                 type string {
                   junos:posix-pattern "^[+-]?[0-9]+(\\.[0-9]+)?$";
                   junos:pattern-message "numerical value must be specified with optional leading sign and optional decimal point";
                 }
               }
             }
           }
           list warning {
             key name;
             ordered-by user;
             description "Set optic warnings";
             leaf name {
               junos:cli-feature "nokeyword";
               type enumeration {
                 enum "low-light-warning" {
                   description "Enable low light warning";
                 }
               }
             }
             uses apply-advanced;
             choice actiontype {
               case case_1 {
                 leaf syslog {
                   description "Set action as syslog";
                   type empty;
                 }
               }
               case case_2 {
                 leaf link-down {
                   description "Set action as link-down";
                   type empty;
                 }
               }
             }
           }
           leaf low-power-mode {
             description "Force optics to low power mode";
             type empty;
           }
           leaf high-power-mode {
             description "High power optic mode";
             type empty;
           }
           leaf host-side-fec {
             description "Host side optics FEC ON/OFF";
             type enumeration {
               enum "off" {
                 description "Host side FEC OFF for optics";
               }
               enum "on" {
                 description "Host side FEC ON for optics";
               }
             }
           }
           leaf media-side-fec {
             description "Media side FEC ON/OFF";
             type enumeration {
               enum "off" {
                 description "Media side FEC OFF for optics";
               }
               enum "on" {
                 description "Media side FEC ON for optics";
               }
             }
           }
           choice lane-info {
             case case_1 {
               list lane {
                 key name;
                 description "Media lane number";
                 leaf name {
                   description "Lane number";
                   junos:cli-feature "nokeyword";
                   type union {
                     type string {
                       pattern "<.*>|$.*";
                     }
                     type uint32 {
                       range "0 .. 7";
                     }
                   }
                 }
                 uses apply-advanced;
                 leaf tx-laser {
                   description "Transmit Laser ON/OFF";
                   junos:must "(!(\"interfaces ${interface} disable\"))";
                   junos:must-message "tx-laser cannot be applied when interface is disabled";
                   type enumeration {
                     enum "off" {
                       description "Transmit laser OFF for optics";
                     }
                     enum "on" {
                       description "Transmit laser ON for optics";
                     }
                   }
                 }
                 leaf rx-output {
                   description "Receive output ON/OFF";
                   type enumeration {
                     enum "off" {
                       description "Receive output OFF for optics";
                     }
                     enum "on" {
                       description "Receive output ON for optics";
                     }
                   }
                 }
                 leaf tx-cdr {
                   description "Transmit Clock and Data Recovery ON/OFF";
                   type enumeration {
                     enum "off" {
                       description "Transmit Clock and Data Recovery OFF for optics";
                     }
                     enum "on" {
                       description "Transmit Clock and Data Recovery ON for optics";
                     }
                   }
                 }
                 leaf rx-cdr {
                   description "Receive Clock and Data Recovery ON/OFF";
                   type enumeration {
                     enum "off" {
                       description "Receive Clock and Data Recovery OFF for optics";
                     }
                     enum "on" {
                       description "Receive Clock and Data Recovery ON for optics";
                     }
                   }
                 }
                 leaf tx-input-equalization-adaptive {
                   description "Transmit adaptive equalization ON/OFF";
                   type enumeration {
                     enum "off" {
                       description "Transmit adaptive equalization OFF for optics";
                     }
                     enum "on" {
                       description "Transmit adaptive equalization ON for optics";
                     }
                   }
                 }
                 leaf tx-input-equalization-manual {
                   description "Transmit manual equalization for optics";
                   units "dB";
                   junos:must "(!(\".. tx-input-equalization-adaptive on\"))";
                   junos:must-message "Manual equalization not possible when adaptive is enabled";
                   type union {
                     type string {
                       pattern "<.*>|$.*";
                     }
                     type int32 {
                       range "0 .. 15";
                     }
                   }
                 }
                 leaf rx-output-emphasis {
                   description "Receive output emphasis for optics";
                   units "dB";
                   type union {
                     type string {
                       pattern "<.*>|$.*";
                     }
                     type int32 {
                       range "0 .. 15";
                     }
                   }
                 }
                 leaf rx-output-amplitude {
                   description "Receive output amplitude setting";
                   type enumeration {
                     enum "400mV" {
                       description "No equalization for 100mV - 400mV amplitude";
                     }
                     enum "600mV" {
                       description "No equalization for 300mV - 600mV amplitude";
                     }
                     enum "800mV" {
                       description "No equalization for 400mV - 800mV amplitude";
                     }
                     enum "1200mV" {
                       description "No equalization for 600mV - 1200mV amplitude";
                     }
                   }
                 }
                 leaf tx-squelch {
                   description "Transmit squelch ON/OFF";
                   type enumeration {
                     enum "off" {
                       description "Transmit squelch OFF for optics";
                     }
                     enum "on" {
                       description "Transmit squelch ON for optics";
                     }
                   }
                 }
                 leaf rx-squelch {
                   description "Receive squelch ON/OFF";
                   type enumeration {
                     enum "off" {
                       description "Receive squelch OFF for optics";
                     }
                     enum "on" {
                       description "Receive squelch ON for optics";
                     }
                   }
                 }
                 leaf tx-rate-select {
                   description "Transmit rate select for optics";
                   type union {
                     type string {
                       pattern "<.*>|$.*";
                     }
                     type int32 {
                       range "0 .. 3";
                     }
                   }
                 }
                 leaf rx-rate-select {
                   description "Receive rate select for optics";
                   type union {
                     type string {
                       pattern "<.*>|$.*";
                     }
                     type int32 {
                       range "0 .. 3";
                     }
                   }
                 }
               }
             }
             case case_2 {
               container lane-all {
                 presence "enable lane-all";
                 description "Apply settings to all lane";
                 uses apply-advanced;
                 leaf tx-laser {
                   description "Transmit Laser ON/OFF";
                   junos:must "(!(\"interfaces ${interface} disable\"))";
                   junos:must-message "tx-laser cannot be applied when interface is disabled";
                   type enumeration {
                     enum "off" {
                       description "Transmit laser OFF for optics";
                     }
                     enum "on" {
                       description "Transmit laser ON for optics";
                     }
                   }
                 }
                 leaf rx-output {
                   description "Receive output ON/OFF";
                   type enumeration {
                     enum "off" {
                       description "Receive output OFF for optics";
                     }
                     enum "on" {
                       description "Receive output ON for optics";
                     }
                   }
                 }
                 leaf tx-cdr {
                   description "Transmit Clock and Data Recovery ON/OFF";
                   type enumeration {
                     enum "off" {
                       description "Transmit Clock and Data Recovery OFF for optics";
                     }
                     enum "on" {
                       description "Transmit Clock and Data Recovery ON for optics";
                     }
                   }
                 }
                 leaf rx-cdr {
                   description "Receive Clock and Data Recovery ON/OFF";
                   type enumeration {
                     enum "off" {
                       description "Receive Clock and Data Recovery OFF for optics";
                     }
                     enum "on" {
                       description "Receive Clock and Data Recovery ON for optics";
                     }
                   }
                 }
                 leaf tx-input-equalization-adaptive {
                   description "Transmit adaptive equalization ON/OFF";
                   type enumeration {
                     enum "off" {
                       description "Transmit adaptive equalization OFF for optics";
                     }
                     enum "on" {
                       description "Transmit adaptive equalization ON for optics";
                     }
                   }
                 }
                 leaf tx-input-equalization-manual {
                   description "Transmit manual equalization for optics";
                   units "dB";
                   junos:must "(!(\".. tx-input-equalization-adaptive on\"))";
                   junos:must-message "Manual equalization not possible when adaptive is enabled";
                   type union {
                     type string {
                       pattern "<.*>|$.*";
                     }
                     type int32 {
                       range "0 .. 15";
                     }
                   }
                 }
                 leaf rx-output-emphasis {
                   description "Receive output emphasis for optics";
                   units "dB";
                   type union {
                     type string {
                       pattern "<.*>|$.*";
                     }
                     type int32 {
                       range "0 .. 15";
                     }
                   }
                 }
                 leaf rx-output-amplitude {
                   description "Receive output amplitude setting";
                   type enumeration {
                     enum "400mV" {
                       description "No equalization for 100mV - 400mV amplitude";
                     }
                     enum "600mV" {
                       description "No equalization for 300mV - 600mV amplitude";
                     }
                     enum "800mV" {
                       description "No equalization for 400mV - 800mV amplitude";
                     }
                     enum "1200mV" {
                       description "No equalization for 600mV - 1200mV amplitude";
                     }
                   }
                 }
                 leaf tx-squelch {
                   description "Transmit squelch ON/OFF";
                   type enumeration {
                     enum "off" {
                       description "Transmit squelch OFF for optics";
                     }
                     enum "on" {
                       description "Transmit squelch ON for optics";
                     }
                   }
                 }
                 leaf rx-squelch {
                   description "Receive squelch ON/OFF";
                   type enumeration {
                     enum "off" {
                       description "Receive squelch OFF for optics";
                     }
                     enum "on" {
                       description "Receive squelch ON for optics";
                     }
                   }
                 }
                 leaf tx-rate-select {
                   description "Transmit rate select for optics";
                   type union {
                     type string {
                       pattern "<.*>|$.*";
                     }
                     type int32 {
                       range "0 .. 3";
                     }
                   }
                 }
                 leaf rx-rate-select {
                   description "Receive rate select for optics";
                   type union {
                     type string {
                       pattern "<.*>|$.*";
                     }
                     type int32 {
                       range "0 .. 3";
                     }
                   }
                 }
               }
             }
           }
         }
         container otn-options {
           description "Optical Transmission Network interface-specific options";
           uses otn_options_type;
         }
         container och-options {
           description "Optical channel configuration options";
           uses och-attributes;
         }
         container otu-options {
           description "Optical transmission unit configuration options";
           uses otu-attributes;
         }
         container odu-options {
           description "Optical data unit configuration options";
           uses odu-attributes;
         }
         container ett-options {
           description "Transport ethernet client configuration options";
           uses ett-attributes;
         }
         container fastether-options {
           description "Fast Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           leaf ingress-rate-limit {
             description "Ingress rate at port";
             units "megabits per second";
             type union {
               type string {
                 pattern "<.*>|$.*";
               }
               type uint32 {
                 range "1 .. 100";
               }
             }
           }
           list source-address-filter {
             key name;
             ordered-by user;
             junos:cli-feature "homogeneous";
             junos:cli-feature "oneliner";
             description "Source address filters";
             leaf name {
               description "Remote MAC address";
               junos:cli-feature "nokeyword";
               type jt:mac-addr;
             }
           }
           container ieee-802.3ad {
             junos:must "(!(\"system autoinstallation\"))";
             junos:must-message "incompatible with 'system autoinstallation'";
             junos:cli-feature "oneliner-plus";
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               junos:cli-feature "nokeyword";
               junos:must "(!(any \"class-of-service interfaces ${interface} unit <*> rewrite-rules\"))";
               junos:must-message "rewrite config can not be applied on ae child";
               junos:must "(!(any \"class-of-service interfaces ${interface} unit <*> classifiers\"))";
               junos:must-message "classifier config can not be applied on ae child";
               junos:must "(!(any \"class-of-service interfaces ${interface} unit <*> output-traffic-control-profile\"))";
               junos:must-message "output-traffic-control-profile config can not be applied on ae child";
               junos:must "(!(\"class-of-service interfaces ${interface} output-traffic-control-profile\"))";
               junos:must-message "output-traffic-control-profile config can not be applied on ae child";
               junos:must "(!(\"class-of-service interfaces ${interface} shaping-rate\"))";
               junos:must-message "shaping-rate config can not be applied on ae child";
               junos:must "(!(\"class-of-service interfaces ${interface} scheduler-map\"))";
               junos:must-message "scheduler-map config can not be applied on ae child";
               junos:must "(!(\".. .. .. vlan-offload\"))";
               junos:must-message "ae child device vlan-offload is not allowed";
               junos:must "(!(\".. .. .. flow-control\"))";
               junos:must-message "Setting flow-control on ae child device is not allowed";
               junos:must "(!(\".. .. .. mtu\"))";
               junos:must-message "Setting mtu on ae child device is not allowed";
               junos:must "(!(\".. .. .. vlan-vci-tagging\"))";
               junos:must-message "ae child device vlan-vci-tagging is not allowed";
               junos:must "(!(\".. .. .. stacked-vlan-tagging\"))";
               junos:must-message "ae child device stacked-vlan-tagging is not allowed";
               junos:must "(!(\".. .. .. flexible-vlan-tagging\"))";
               junos:must-message "ae child device flexible-vlan-tagging is not allowed";
               junos:must "(!(\".. .. .. vlan-tagging\"))";
               junos:must-message "ae child device vlan-tagging is not allowed";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           container mpls {
             description "MPLS options";
             uses mpls_ifd_options;
           }
           leaf ignore-l3-incompletes {
             description "Ignore L3 incomplete errors";
             type empty;
           }
         }
         container aggregated-ether-options {
           description "Aggregated Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           leaf autostate-exclude {
             description "Interface will not contribute to IRB state";
             type empty;
           }
           container link-protection {
             presence "enable link-protection";
             description "Enable link protection mode";
             uses apply-advanced;
             leaf revertive {
               description "Revert back from active backup link to primary, if primary is UP";
               junos:must "(!(\"interfaces ${interface} aggregated-ether-options link-protection non-revertive\"))";
               junos:must-message "link-protection revertive and non-revertive are mutually exclusive";
               junos:must "(!(\"chassis aggregated-devices ethernet lacp\"))";
               junos:must-message "link-protection revertive and LACP are mutually exclusive";
               junos:must "(!(\"interfaces ${interface} aggregated-ether-options lacp\"))";
               junos:must-message "link-protection revertive and LACP are mutually exclusive";
               type empty;
             }
             leaf non-revertive {
               description "Do not revert back (default mode) from active backup link to primary, if primary is UP";
               junos:must "(!(\"interfaces ${interface} aggregated-ether-options link-protection revertive\"))";
               junos:must-message "link-protection revertive and non-revertive are mutually exclusive";
               junos:must "(!(\"chassis aggregated-devices ethernet lacp\"))";
               junos:must-message "link-protection revertive and LACP are mutually exclusive";
               junos:must "(!(\"interfaces ${interface} aggregated-ether-options lacp\"))";
               junos:must-message "link-protection revertive and LACP are mutually exclusive";
               type empty;
             }
             leaf backup-state {
               description "Link protection backup link state";
               default "accept-data";
               type enumeration {
                 enum "accept-data" {
                   description "Accept data on receive channel of backup link";
                 }
                 enum "discard-data" {
                   description "Discard data on receive channel of backup link";
                 }
                 enum "down" {
                   description "Backup link is marked down";
                   junos:must "(!(\"chassis aggregated-devices ethernet lacp\"))";
                   junos:must-message "backup-state down and LACP are mutually exclusive";
                   junos:must "(!(\"interfaces ${interface} aggregated-ether-options lacp\"))";
                   junos:must-message "backup-state down and LACP are mutually exclusive";
                 }
               }
             }
             container rtg-config {
               presence "enable rtg-config";
               description "RTG enable on AE";
               uses apply-advanced;
               leaf preempt-cutover-timer {
                 description "RTG preempt-cutover-timer in seconds";
                 default "1";
                 type union {
                   type string {
                     pattern "<.*>|$.*";
                   }
                   type uint32 {
                     range "0 .. 255";
                   }
                 }
               }
             }
           }
           choice fcoe-lag-choice {
             leaf fcoe-lag {
               description "Enable FIP/FCoE LAG";
               type empty;
             }
             leaf no-fcoe-lag {
               description "Don't enable FIP/FCoE LAG";
               type empty;
             }
           }
           list source-address-filter {
             key name;
             ordered-by user;
             junos:cli-feature "homogeneous";
             junos:cli-feature "oneliner";
             description "Source address filters";
             leaf name {
               description "Remote MAC address";
               junos:cli-feature "nokeyword";
               type jt:mac-addr;
             }
           }
           container configured-flow-control {
             presence "enable configured-flow-control";
             junos:must "(!((\".. flow-control\" || \".. no-flow-control\")))";
             junos:must-message "flow-control and configured-flow-control are not allowed together";
             description "Enable flow control";
             uses apply-advanced;
             leaf rx-buffers {
               description "Enable/Disable Rx buffers";
               type enumeration {
                 enum "on" {
                   description "Enable Rx buffers";
                 }
                 enum "off" {
                   description "Disable Rx buffers";
                 }
               }
             }
             leaf tx-buffers {
               description "Enable/Disable Tx buffers";
               type enumeration {
                 enum "on" {
                   description "Enable Tx buffers";
                 }
                 enum "off" {
                   description "Disable Tx buffers";
                 }
               }
             }
           }
           container load-balance {
             uses aggregate-load-balance;
           }
           container bfd-liveness-detection {
             junos:must "(!(\".. lacp fast-failover\"))";
             junos:must-message "BFD not supported with lacp with fast-failover mode";
             junos:must "(!(\".. lacp link-protection\"))";
             junos:must-message "BFD not supported with lacp link protection";
             junos:must "(!(\".. link-protection\"))";
             junos:must-message "BFD not supported with link protection";
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container damping {
               description "BFD flap damping parameters";
               uses apply-advanced;
               leaf suppress {
                 description "Suppress threshold for figure-of-merit value";
                 default "5000";
                 type union {
                   type string {
                     pattern "<.*>|$.*";
                   }
                   type uint32 {
                     range "1000 .. 200000";
                   }
                 }
               }
               leaf reuse {
                 description "Reuse threshold for figure-of-merit value";
                 default "1000";
                 type union {
                   type string {
                     pattern "<.*>|$.*";
                   }
                   type uint32 {
                     range "1000 .. 200000";
                   }
                 }
               }
               leaf max-suppress-time {
                 description "Maximum hold-down time";
                 default "600";
                 units "seconds";
                 type union {
                   type string {
                     pattern "<.*>|$.*";
                   }
                   type uint32 {
                     range "1 .. 20000";
                   }
                 }
               }
               leaf half-life-interval {
                 description "Decay half life interval";
                 default "30";
                 units "seconds";
                 type union {
                   type string {
                     pattern "<.*>|$.*";
                   }
                   type uint32 {
                     range "1 .. 600";
                   }
                 }
               }
               leaf increment {
                 description "Increments applied to figure-of-merit value for every flap";
                 default "1000";
                 type union {
                   type string {
                     pattern "<.*>|$.*";
                   }
                   type uint32 {
                     range "1000 .. 20000";
                   }
                 }
               }
             }
             leaf neighbor {
               description "BFD neighbor address";
               type jt:ipaddr;
             }
             leaf local-address {
               description "BFD local address";
               type jt:ipaddr;
             }
             leaf holddown-interval {
               description "Time to hold the session-UP notification to the client";
               units "milliseconds";
               type union {
                 type string {
                   pattern "<.*>|$.*";
                 }
                 type uint32 {
                   range "0 .. 255000";
                 }
               }
             }
           }
           leaf minimum-links {
             description "Minimum number of aggregated links";
             junos:must "(!(\"interfaces ${interface} aggregated-ether-options link-speed mixed\"))";
             junos:must-message "Minimum-links option is not compatible with link-speed mixed";
             type union {
               type string {
                 pattern "<.*>|$.*";
               }
               type uint16;
             }
           }
           leaf no-unsecure-links {
             description "Don't allow MACSEC unsecure links under AE";
             type empty;
           }
           container minimum-bandwidth {
             presence "enable minimum-bandwidth";
             junos:must "(!(\"interfaces ${interface}  aggregated-ether-options optimize-aggregate-frr\"))";
             junos:must-message "Minimum-bandwidth and optimize-aggregate-frr are mutually exclusive";
             junos:must "(!(\"interfaces ${interface}  aggregated-ether-options minimum-links\"))";
             junos:must-message "Minimum-bandwidth and minimum-links are mutually exclusive";
             description "Minimum bandwidth configured for aggregated bundle";
             uses apply-advanced;
             leaf bw-value {
               description "Bandwidth value";
               default "1";
               type union {
                 type uint64;
                 type string {
                   pattern "<.*>|$.*";
                 }
               }
             }
             leaf bw-unit {
               description "Bandwidth unit";
               type enumeration {
                 enum "bps" {
                   description "Links are in bits per sec";
                 }
                 enum "kbps" {
                   description "Links are in kilo bits per sec";
                 }
                 enum "mbps" {
                   description "Links are in mega bits per sec";
                 }
                 enum "gbps" {
                   description "Links are in giga bits per sec ";
                 }
               }
             }
           }
           choice redundancy_choice {
             case case_1 {
             }
             case case_2 {
             }
           }
           container rebalance-periodic {
             uses apply-advanced;
           }
           leaf link-speed {
             description "Link speed of individual interface that joins the AE";
             type enumeration {
               enum "10m" {
                 description "Links are 10M";
               }
               enum "100m" {
                 description "Links are 100M";
               }
               enum "1g" {
                 description "Links are 1G";
               }
               enum "2.5g" {
                 description "Links are 2.5G";
               }
               enum "5g" {
                 description "Links are 5G";
               }
               enum "8g" {
                 description "Links are 8G";
               }
               enum "10g" {
                 description "Links are 10G";
               }
               enum "25g" {
                 description "Links are 25G";
               }
               enum "40g" {
                 description "Links are 40G";
               }
               enum "50g" {
                 description "Links are 50G";
               }
               enum "80g" {
                 description "Links are 80G";
               }
               enum "100g" {
                 description "Links are 100G";
               }
               enum "200g" {
                 description "Links are 200G";
               }
               enum "400g" {
                 description "Links are 400G";
               }
               enum "800g" {
                 description "Links are 800G";
               }
               enum "oc192" {
                 description "Links are OC-192";
               }
               enum "mixed" {
                 description "Links are various speeds";
                 junos:must "(!(\"interfaces ${interface} per-unit-scheduler\"))";
                 junos:must-message "per-unit-scheduler is incompatible with link-speed mixed";
                 junos:must "(!(\".. resilient-hash\"))";
                 junos:must-message "Mixed-rate AE is not supported along with Resilient Hashing  mode";
                 junos:must "(!(\".. load-balance adaptive\"))";
                 junos:must-message "Mixed-rate AE is not supported along with Adaptive Load balance mode";
               }
             }
           }
           container local-bias {
             presence "enable local-bias";
             description "Turn on local bias functionality";
             uses apply-advanced;
             leaf disable {
               description "Disable local-bias";
               type empty;
             }
           }
           leaf local-minimum-links-threshold {
             description "Specify threshold for minimum links per VC/VCF member";
             type union {
               type string {
                 pattern "<.*>|$.*";
               }
               type uint16 {
                 range "1 .. 100";
               }
             }
           }
           leaf resilient-hash {
             description "Turn on resilient-hash";
             junos:must "(!(\".. dlb\"))";
             junos:must-message "Resilient-hash AE is not supported along with Dynamic Load Balancing AE";
             junos:must "(!(\"link-speed mixed\"))";
             junos:must-message "Resilient-hash AE is not supported along with Mixed-rate mode";
             junos:must "(!(\"load-balance per-packet\"))";
             junos:must-message "Resilient-hash AE is not supported along with Per-Packet Load balance mode";
             junos:must "(!(\"load-balance adaptive\"))";
             junos:must-message "Resilient-hash AE is not supported along with Adaptive Load balance mode";
             type empty;
           }
           container dlb {
             junos:must "(!(\"virtual-chassis\"))";
             junos:must-message "DLB not supported on VC";
             junos:must "(!(\".. resilient-hash\"))";
             junos:must-message "Dynamic Load Balancing AE is not supported along with resilient hash";
             description "Enable DLB on LAG";
             uses apply-advanced;
             choice mode {
               case case_1 {
                 leaf per-packet {
                   description "Per-packet link assignment";
                   type empty;
                 }
               }
               case case_2 {
                 leaf assigned-flow {
                   description "Fixed link assignment";
                   type empty;
                 }
               }
               case case_3 {
                 container flowlet {
                   presence "enable flowlet";
                   description "Inactivity-based link assignment";
                   uses apply-advanced;
                   leaf inactivity-interval {
                     description " Minimum inactivity interval in micro-seconds for link re-assignment";
                     default "256";
                     type union {
                       type string {
                         pattern "<.*>|$.*";
                       }
                       type uint32;
                     }
                   }
                 }
               }
             }
           }
           container lacp {
             description "Link Aggregation Control Protocol configuration";
             uses apply-advanced;
             choice mode {
               case case_1 {
                 leaf active {
                   description "Initiate transmission of LACP packets";
                   type empty;
                 }
               }
               case case_2 {
                 leaf passive {
                   description "Respond to LACP packets";
                   type empty;
                 }
               }
             }
             leaf periodic {
               description "Timer interval for periodic transmission of LACP packets";
               type enumeration {
                 enum "fast" {
                   description "Receive packets every second";
                 }
                 enum "slow" {
                   description "Receive packets every 30 seconds";
                 }
               }
             }
             leaf multiplier {
               description "LACP timeout detection multiplier";
               type union {
                 type string {
                   pattern "<.*>|$.*";
                 }
                 type uint32 {
                   range "3 .. 30";
                 }
               }
             }
             leaf fast-failover {
               description "To turn on LACP fast-failover";
               type empty;
             }
             container link-protection {
               presence "enable link-protection";
               junos:must "(!(\".. .. link-protection\"))";
               junos:must-message "LACP and non LACP based link-protection not allowed together";
               uses apply-advanced;
               leaf disable {
                 description "To turn off LACP link-protection";
                 type empty;
               }
               choice mode {
                 case case_1 {
                   leaf revertive {
                     description "Switch links when better priority link comes up";
                     type empty;
                   }
                 }
                 case case_2 {
                   leaf non-revertive {
                     description "Do not switch links when better priority link comes up";
                     type empty;
                   }
                 }
               }
               container rtg-config {
                 presence "enable rtg-config";
                 description "RTG Feature enable on AE";
                 uses apply-advanced;
                 leaf preempt-cutover-timer {
                   description "RTG preempt-cutover-timer in seconds";
                   default "1";
                   type union {
                     type string {
                       pattern "<.*>|$.*";
                     }
                     type uint32 {
                       range "0 .. 255";
                     }
                   }
                 }
               }
             }
             leaf sync-reset {
               description "On minimum-link failure notify out of sync to peer";
               type enumeration {
                 enum "disable" {
                   description "To disable minimum-link failure handling at LACP level";
                 }
                 enum "enable" {
                   description "To enable minimum-link failure handling at LACP level";
                 }
               }
             }
             leaf system-priority {
               description "Priority of the system (0 ... 65535)";
               type string;
             }
             leaf system-id {
               description "Node's System ID, encoded as a MAC address";
               type jt:mac-addr;
             }
             leaf admin-key {
               description "Node's administrative key";
               type union {
                 type uint16;
                 type string {
                   pattern "<.*>|$.*";
                 }
               }
             }
             container hold-time {
               junos:cli-feature "oneliner";
               description "Hold time for link up and link down for AE link members";
               leaf up {
                 description "Link up hold time for the AE link members";
                 units "seconds";
                 type union {
                   type string {
                     pattern "<.*>|$.*";
                   }
                   type uint16 {
                     range "1 .. 6000";
                   }
                 }
               }
             }
             leaf aggregate-wait-time {
               description "Aggregate wait time for the AE";
               units "seconds";
               type union {
                 type string {
                   pattern "<.*>|$.*";
                 }
                 type uint16 {
                   range "0 .. 1800";
                 }
               }
             }
             leaf force-up {
               description "Forceup AE interface with LACP";
               type empty;
             }
             leaf no-peer-loopback-validation {
               description "Skip MCLAG peer loop back validation for LACP PDUs on Forceup AE interface";
               junos:must "(\".. force-up\")";
               junos:must-message "LACP force-up must be configured for no-peer-loopback-validation";
               junos:must "(\".. .. mc-ae\")";
               junos:must-message "MC-AE must be configured for no-peer-loopback-validation";
               type empty;
             }
           }
           list link-protection-sub-group {
             key name;
             ordered-by user;
             description "Link Protection subgroup configuration";
             leaf name {
               description "Name of the subgroup";
               junos:cli-feature "nokeyword";
               type string {
                 length "2 .. 64";
               }
             }
             uses apply-advanced;
             choice type {
               case case_1 {
                 leaf primary {
                   description "Primary subgroup for N:N link-protection mode";
                   type empty;
                 }
               }
               case case_2 {
                 leaf backup {
                   description "Backup subgroup for N:N link-protection mode";
                   type empty;
                 }
               }
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             container storm-control {
               junos:cli-feature "oneliner-plus";
               description "Storm control profile name to bind";
               uses apply-advanced;
               leaf profile-name {
                 description "Profile name";
                 junos:cli-feature "nokeyword";
                 junos:must "(\"forwarding-options storm-control-profiles $$\")";
                 junos:must-message "Storm profile name must be defined in the [edit forwarding-options storm-control-profiles] hierarchy";
                 type string;
               }
             }
             container recovery-timeout {
               junos:cli-feature "oneliner";
               description "Recovery timeout for this interface";
               leaf time-in-seconds {
                 junos:cli-feature "nokeyword";
                 units "seconds";
                 type union {
                   type string {
                     pattern "<.*>|$.*";
                   }
                   type uint32 {
                     range "10 .. 3600";
                   }
                 }
               }
             }
             leaf mac-learn-enable {
               description "Learn MAC addresses dynamically";
               type empty;
             }
           }
           container mc-ae {
             junos:must "(!((\".. link-protection\" || \".. lacp link-protection\")))";
             junos:must-message "MC-AE and link-protection on AE can not co-exist";
             junos:must "(\".. lacp admin-key\")";
             junos:must-message "LACP admin-key must be configured for MC-AE";
             junos:must "(\".. lacp system-id\")";
             junos:must-message "LACP system-id must be configured for MC-AE";
             junos:must "(!(\".. .. encapsulation vlan-ccc\"))";
             junos:must-message "Encapsulation vlan-ccc is not supported with MC-AE";
             description "Multi-chassis aggregation (MC-AE) network device configuration";
             uses apply-advanced;
             leaf mc-ae-id {
               description "MC-AE group id";
               junos:must "(unique \"interfaces <*>  aggregated-ether-options mc-ae mc-ae-id $$\")";
               junos:must-message "MC-AE id alredy being used";
               type union {
                 type string {
                   pattern "<.*>|$.*";
                 }
                 type uint16 {
                   range "1 .. 65535";
                 }
               }
             }
             leaf redundancy-group {
               description "Redundancy group id";
               default "1";
               junos:must "((any \"protocols iccp peer <*> redundancy-group-id-list $$\" || any \"logical-systems <*> protocols iccp peer <*> redundancy-group-id-list $$\"))";
               junos:must-message "The redundancy group must match with one defined at <protocols iccp peer redundancy-group-id-list>";
               type union {
                 type string {
                   pattern "<.*>|$.*";
                 }
                 type uint32 {
                   range "1 .. 4294967294";
                 }
               }
             }
             leaf chassis-id {
               description "Chassis id of MC-AE network device";
               type union {
                 type string {
                   pattern "<.*>|$.*";
                 }
                 type uint16 {
                   range "0 .. 1";
                 }
               }
             }
             leaf mode {
               description "Mode of the MC-AE";
               type enumeration {
                 enum "active-active" {
                   description "MC-AE in active-active mode";
                   junos:must "(!(any \"interfaces ${interface} unit <*> family inet6\"))";
                   junos:must-message "family inet6 is not supported with MC-AE active-active";
                   junos:must "(!(any \"interfaces ${interface} unit <*> family inet\"))";
                   junos:must-message "family inet is not supported with MC-AE active-active";
                 }
               }
             }
             leaf status-control {
               description "Status of the MC-AE chassis";
               type enumeration {
                 enum "active" {
                   description "Chassis is Active";
                 }
                 enum "standby" {
                   description "Chassis is Standby";
                 }
               }
             }
             leaf switchover-mode {
               description "Switchover mode";
               type enumeration {
                 enum "revertive" {
                   description "Switch mcae node when preferred link comes up";
                   junos:must "(\".. .. mc-ae mode active-standby\")";
                   junos:must-message "Only Supported in Active-Standby mode.";
                   junos:must "(!(\".. .. mc-ae status-control standby\"))";
                   junos:must-message "Supported only when status control is Active";
                 }
                 enum "non-revertive" {
                   description "Do not switch mcae node when preferred link comes up";
                   junos:must "(\".. .. mc-ae mode active-standby\")";
                   junos:must-message "Only Supported in Active-Standby mode.";
                   junos:must "(\".. .. mc-ae status-control active\")";
                   junos:must-message "Supported only when status control is Active";
                 }
               }
             }
             leaf revert-time {
               description "Wait interval before performing switchover";
               default "3";
               units "minute";
               junos:must "(\".. .. mc-ae mode active-standby\")";
               junos:must-message "Only Supported in Active-Standby mode.";
               junos:must "(\".. .. mc-ae status-control active\")";
               junos:must-message "Supported only when status control is Active";
               type union {
                 type string {
                   pattern "<.*>|$.*";
                 }
                 type uint32 {
                   range "1 .. 10";
                 }
               }
             }
             leaf init-delay-time {
               description "Init delay timer for mcae sm for min traffic loss";
               units "seconds";
               type union {
                 type string {
                   pattern "<.*>|$.*";
                 }
                 type uint16 {
                   range "1 .. 6000";
                 }
               }
             }
             leaf recovery-delay-time {
               description "Delay timer for bringing up ICL, ICCP";
               units "seconds";
               type union {
                 type string {
                   pattern "<.*>|$.*";
                 }
                 type uint16 {
                   range "1 .. 6000";
                 }
               }
             }
             leaf enhanced-convergence {
               description "Optimized convergence time for mcae";
               junos:must "(\".. .. mc-ae mode active-active\")";
               junos:must-message "Only Supported in MCAE active-active mode.";
               type empty;
             }
             container events {
               presence "enable events";
               description "MCAE related events";
               uses apply-advanced;
               container iccp-peer-down {
                 presence "enable iccp-peer-down";
                 description "Define behavior in the event of ICCP peer down";
                 uses apply-advanced;
                 leaf force-icl-down {
                   description "Bring down ICL logical interface";
                   type empty;
                 }
                 leaf prefer-status-control-active {
                   description "Keep this node up (recommended only on status-control active)";
                   type empty;
                 }
               }
             }
           }
         }
         container es-options {
           description "ES PIC interface-specific options";
           uses apply-advanced;
           leaf backup-interface {
             description "Name of backup interface";
             type union {
               type jt:interface-device;
               type string {
                 pattern "<.*>|$.*";
               }
             }
           }
         }
         container vdsl-options {
           description "VDSL interface-specific options";
           uses apply-advanced;
           leaf vdsl-profile {
             description "VDSL profile";
             type enumeration {
               enum "auto" {
                 description "Auto";
               }
               enum "8a" {
                 description "Profile 8a";
               }
               enum "8b" {
                 description "Profile 8b";
               }
               enum "8c" {
                 description "Profile 8c";
               }
               enum "8d" {
                 description "Profile 8d";
               }
               enum "12a" {
                 description "Profile 12a";
               }
               enum "12b" {
                 description "Profile 12b";
               }
               enum "17a" {
                 description "Profile 17a";
               }
             }
           }
           leaf sra {
             description "DSL SRA";
             default "disable";
             type enumeration {
               enum "enable" {
                 description "Enable SRA";
               }
               enum "disable" {
                 description "Disable SRA";
               }
             }
           }
           leaf v43 {
             description "DSL V43 tones";
             default "enable";
             type enumeration {
               enum "enable" {
                 description "Enable V43";
               }
               enum "disable" {
                 description "Disable V43";
               }
             }
           }
           leaf sos {
             description "Enable SOS";
             type empty;
           }
         }
         container dsl-sfp-options {
           description "DSL SFP options";
           uses apply-advanced;
           container adsl-options {
             description "ADSL options";
             uses apply-advanced;
             leaf vpi {
               description "Virtual path identifier";
               junos:must "(\".. vci\")";
               junos:must-message "vci must be specified";
               type union {
                 type string {
                   pattern "<.*>|$.*";
                 }
                 type uint32 {
                   range "0 .. 255";
                 }
               }
             }
             leaf vci {
               description "Virtual circuit identifier";
               junos:must "(\".. vpi\")";
               junos:must-message "vpi must be specified";
               type union {
                 type string {
                   pattern "<.*>|$.*";
                 }
                 type uint32 {
                   range "32 .. 65535";
                 }
               }
             }
             leaf encap {
               description "Encapsulation";
               junos:must "((\".. vci\" && \".. vpi\"))";
               junos:must-message "vci and vpi must be specified";
               type enumeration {
                 enum "bypass" {
                   description "Bypass";
                 }
                 enum "llcsnap-bridged-802dot1q" {
                   description "LLCSNAP bridged 802.1q";
                 }
                 enum "llcsnap-routed-ip" {
                   description "LLCSNAP routed ip";
                 }
                 enum "vc-mux-bridged" {
                   description "VC MUX bridged";
                 }
                 enum "vc-mux-routed-ip" {
                   description "VC MUX routed ip";
                 }
                 enum "generic" {
                   description "Generic";
                 }
               }
             }
             leaf annex {
               description "Annex type";
               junos:must "((\".. vci\" && \".. vpi\"))";
               junos:must-message "vci and vpi must be specified";
               type enumeration {
                 enum "auto" {
                   description "Annex type auto";
                 }
                 enum "annexj-off" {
                   description "Annex type annexj turn off";
                 }
               }
             }
           }
           container vdsl-options {
             description "VDSL options";
             uses apply-advanced;
             leaf profile {
               description "VDSL profile";
               type enumeration {
                 enum "auto" {
                   description "Automatic";
                 }
                 enum "8a" {
                   description "Profile 8a";
                 }
                 enum "8b" {
                   description "Profile 8b";
                 }
                 enum "8c" {
                   description "Profile 8c";
                 }
                 enum "8d" {
                   description "Profile 8d";
                 }
                 enum "12a" {
                   description "Profile 12a";
                 }
                 enum "12b" {
                   description "Profile 12b";
                 }
                 enum "17a" {
                   description "Profile 17a";
                 }
                 enum "30a" {
                   description "Profile 30a";
                 }
               }
             }
             leaf carrier {
               description "Carrier setting";
               type enumeration {
                 enum "auto" {
                   description "Automatic";
                 }
                 enum "a43" {
                   description "Carrier A43";
                 }
                 enum "b43" {
                   description "Carrier B43";
                 }
               }
             }
           }
           container gfast-options {
             description "G.fast options";
             uses apply-advanced;
             leaf carrier {
               description "Carrier setting";
               type enumeration {
                 enum "a43" {
                   description "Carrier A43";
                 }
                 enum "a43c" {
                   description "Carrier A43C";
                 }
                 enum "b43" {
                   description "Carrier B43";
                 }
                 enum "b43c" {
                   description "Carrier B43C";
                 }
               }
             }
           }
         }
         container shdsl-options {
           junos:must "(!(\"interfaces ${interface} vdsl-options\"))";
           junos:must-message "VDSL options cannot co-exist with SHDSL options on the same interface";
           junos:must "(!(\"interfaces ${interface} dsl-options\"))";
           junos:must-message "DSL options cannot co-exist with SHDSL options on the same interface";
           description "SHDSL interface-specific options";
           uses apply-advanced;
           leaf annex {
             description "Type of SHDSL annex";
             default "annex-b";
             type enumeration {
               enum "annex-a" {
                 description "Annex-a PIC";
               }
               enum "annex-b" {
                 description "Annex-b PIC";
               }
               enum "annex-f" {
                 description "Annex-f PIC";
               }
               enum "annex-g" {
                 description "Annex-g PIC";
               }
               enum "annex-auto" {
                 description "Annex-auto PIC";
               }
             }
           }
           leaf line-rate {
             description "SHDSL line rate";
             type string;
           }
           leaf loopback {
             description "Loopback mode";
             type enumeration {
               enum "local" {
                 description "Local loopback";
               }
               enum "remote" {
                 description "Remote loopback";
               }
             }
           }
           container snr-margin {
             presence "enable snr-margin";
             description "Signal to noise ratio margin";
             uses apply-advanced;
             leaf current {
               description "Current signal to noise ratio margin";
               units "dB";
               type string;
             }
             leaf snext {
               description "SNEXT signal to noise ratio margin";
               units "dB";
               type string;
             }
           }
         }
         container container-options {
           description "Container interface specific options";
           uses apply-advanced;
           container container-type {
             presence "enable container-type";
             description "Protocol type of the container interface";
             uses apply-advanced;
             choice container-type-choice {
               case case_1 {
                 container aps {
                   description "APS options on the container";
                   presence "enable aps";
                   junos:must "((\".. .. member-interface-type sonet\" || (\".. .. member-interface-type atm\" || (\".. .. member-interface-type channelized-sonet\" || \".. .. member-interface-type channelized-sdh\"))))";
                   junos:must-message "APS can be enabled on Sonet, Channelized-Sonet, Channelized-SDH  or ATM interfaces only";
                   uses aps_type;
                 }
               }
             }
           }
           container member-interface-type {
             description "Link type of members of container";
             uses apply-advanced;
             choice member_interface_type_choice {
               case case_1 {
                 container sonet {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                       enum "oc192" {
                         description "Links are OC-192";
                       }
                       enum "oc768" {
                         description "Links are OC-768";
                       }
                       enum "mixed" {
                         description "Links are of different speeds";
                       }
                     }
                   }
                 }
               }
               case case_2 {
                 container atm {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                     }
                   }
                 }
               }
               case case_3 {
                 container channelized-sonet {
                   uses apply-advanced;
                   leaf member-interface-speed {
                     description "Link speed of members of container";
                     type enumeration {
                       enum "coc3" {
                         description "Links are COC-3";
                       }
                       enum "coc12" {
                         description "Links are COC-12";
                       }
                       enum "coc48" {
                         description "Links are COC-48";
                       }
                       enum "coc192" {
                         description "Links are COC-192";
                       }
                       enum "coc768" {
                         description "Links are COC-768";
                       }
                     }
                   }
                 }
               }
               case case_4 {
                 container channelized-sdh {
                   uses apply-advanced;
                   leaf member-interface-speed {
                     description "Link speed of members of container";
                     type enumeration {
                       enum "cstm1" {
                         description "Links are cstm-1";
                       }
                       enum "cstm4" {
                         description "Links are cstm-4";
                       }
                       enum "cstm16" {
                         description "Links are cstm-16";
                       }
                       enum "coc64" {
                         description "Links are cstm-64";
                       }
                       enum "cstm256" {
                         description "Links are cstm256";
                       }
                     }
                   }
                 }
               }
             }
           }
           container redundancy {
             description "Container interface redundancy options";
             uses apply-advanced;
             container hold-time {
               junos:cli-feature "oneliner";
               description "Hold time for link up and link down";
               leaf up {
                 description "Link up hold time";
                 units "milliseconds";
                 type union {
                   type string {
                     pattern "<.*>|$.*";
                   }
                   type uint32 {
                     range "0 .. 65534";
                   }
                 }
               }
               leaf down {
                 description "Link down hold time";
                 units "milliseconds";
                 type union {
                   type string {
                     pattern "<.*>|$.*";
                   }
                   type uint32 {
                     range "0 .. 65534";
                   }
                 }
               }
             }
           }
           leaf-list container-list {
             ordered-by user;
             description "List of container interfaces this member link is associated to";
             type union {
               type jt:interface-device;
               type string {
                 pattern "<.*>|$.*";
               }
             }
           }
           choice redundancy-type {
             case case_1 {
               choice aps-redundancy {
                 case case_1 {
                   leaf primary {
                     description "This member link is primary interface of the container";
                     type empty;
                   }
                 }
                 case case_2 {
                   leaf standby {
                     description "This member link is standby interface of the container";
                     type empty;
                   }
                 }
               }
             }
           }
           leaf fast-aps {
             description "Fast APS switch";
             type empty;
           }
           leaf allow-configuration-override {
             description "Allow physical configuration of member link to override container configuration";
             type empty;
           }
         }
         container layer2-policer {
           description "Layer2 policing for interface";
           uses apply-advanced;
           choice layer2-input-policer-choice {
             case case_1 {
               leaf input-policer {
                 description "Two-color policer for received packets";
                 junos:must "(!(\"firewall policer $$ then forwarding-class\"))";
                 junos:must-message "Forwarding class cannot be modified for Layer 2 policer";
                 junos:must "(!(\"firewall policer $$ then loss-priority medium-low\"))";
                 junos:must-message "Loss priority 'medium-low' is not valid for Layer 2 policer";
                 junos:must "(!(\"firewall policer $$ then loss-priority low\"))";
                 junos:must-message "Loss priority 'low' is not valid for Layer 2 policer";
                 junos:must "(\"firewall policer $$ physical-interface-policer\")";
                 junos:must-message "Layer 2 policer must be a physical interface policer";
                 type string;
               }
             }
             case case_2 {
               leaf input-hierarchical-policer {
                 description "Hierarchical policer for received packets";
                 type string;
               }
             }
           }
         }
         list unit {
           key name;
           description "Logical interface";
           leaf name {
             junos:cli-feature "nokeyword";
             type string;
           }
           uses apply-advanced;
           leaf interface-tag {
             description "Interface tag name";
             type string {
               length "1 .. 64";
               junos:posix-pattern "^[A-Za-z0-9][_0-9A-Za-z-]*$";
               junos:pattern-message "Must be a non-reserved string of 64 characters or less";
             }
           }
           container policer-overhead {
             description "Policer overhead adjustment for this unit";
             uses apply-advanced;
             leaf policer-overhead-value {
               description "Policer overhead bytes to be accounted in ingress and egress";
               junos:cli-feature "nokeyword";
               units "bytes";
               junos:must "((!(\".. ingress\") && !(\".. egress\")))";
               junos:must-message "Do not use the options ingress or egress when adjust values are specified";
               type union {
                 type string {
                   pattern "<.*>|$.*";
                 }
                 type int32;
               }
             }
             leaf ingress {
               description "Ingress value in bytes";
               units "bytes";
               type union {
                 type string {
                   pattern "<.*>|$.*";
                 }
                 type int32 {
                   range "-64 .. 64";
                 }
               }
             }
             leaf egress {
               description "Egress value in bytes";
               units "bytes";
               type union {
                 type string {
                   pattern "<.*>|$.*";
                 }
                 type int32 {
                   range "-64 .. 64";
                 }
               }
             }
           }
           leaf alias {
             description "Interface alias";
             junos:must "(!(\"interfaces interface-range $$\"))";
             junos:must-message "Interface alias cannot be an existing interface range name";
             type string;
           }
           leaf enhanced-convergence {
             description "Optimize convergence time for L3";
             type empty;
           }
           leaf proxy-macip-advertisement {
             description "Proxy advertisement of type 2 MAC+IP route for EVPN";
             type empty;
           }
           leaf virtual-gateway-accept-data {
             description "Accept packets destined for virtual gateway address";
             type empty;
           }
           container peer-psd {
             presence "enable peer-psd";
             junos:cli-feature "oneliner";
             description "Peer psd";
             leaf psd-name {
               description "Peer psd name";
               junos:cli-feature "nokeyword";
               junos:must "(\".. .. peer-interface\")";
               junos:must-message "peer-interface must be configured on this interface";
               type string;
             }
           }
           container peer-interface {
             presence "enable peer-interface";
             junos:cli-feature "oneliner-plus";
             description "Peer interface";
             uses apply-advanced;
             leaf interface-name {
               description "Peer interface name";
               junos:cli-feature "nokeyword";
               junos:must "((\".. .. peer-psd\" || \"interfaces $$-IFL peer-interface\"))";
               junos:must-message "Peer interface or peer psd must be configured";
               type union {
                 type jt:interface-unit;
                 type string {
                   pattern "<.*>|$.*";
                 }
               }
             }
           }
           container interface-shared-with {
             presence "enable interface-shared-with";
             junos:must "(\"chassis system-domains\")";
             junos:must-message "Chassis system-domains must be configured";
             junos:cli-feature "oneliner-plus";
             description "Specify which PSD owns this logical interface";
             uses apply-advanced;
             leaf psd-name {
               description "Name of protected system domain (psd[1-31], ex. psd2)";
               junos:cli-feature "nokeyword";
               type string {
                 junos:posix-pattern "^psd([1-9]|[1-2][0-9]|[3][0-1])$";
                 junos:pattern-message "Protected system domain name is a string consisting of \'psd\' follows by the PSD ID (1-31), ex. psd2";
               }
             }
           }
           choice enable-disable {
             case case_1 {
               leaf disable {
                 description "Disable this logical interface";
                 type empty;
               }
             }
           }
           leaf extended-telemetry {
             description "Enable extended telemetry";
             type empty;
           }
           leaf passive-monitor-mode {
             description "Use interface to tap packets from another router";
             type empty;
           }
           container account-layer2-overhead {
             presence "enable account-layer2-overhead";
             description "Account layer2 overhead in IFL byte statistics";
             uses apply-advanced;
             leaf overhead-value {
               description "Layer2 overhead bytes to be accounted in ingress and egress";
               junos:cli-feature "nokeyword";
               units "bytes";
               junos:must "((!(\".. ingress\") && !(\".. egress\")))";
               junos:must-message "Do not use the options ingress or egress when adjust values are specified";
               type union {
                 type string {
                   pattern "<.*>|$.*";
                 }
                 type int8 {
                   range "-128 .. 127";
                 }
               }
             }
             leaf ingress {
               description "Layer2 overhead bytes to be accounted in ingress";
               units "bytes";
               type union {
                 type string {
                   pattern "<.*>|$.*";
                 }
                 type int8 {
                   range "-128 .. 127";
                 }
               }
             }
             leaf egress {
               description "Layer2 overhead bytes to be accounted in egress";
               units "bytes";
               type union {
                 type string {
                   pattern "<.*>|$.*";
                 }
                 type int8 {
                   range "-128 .. 127";
                 }
               }
             }
           }
           leaf clear-dont-fragment-bit {
             description "Clear DF bit in packet (AS PIC and J-series only as well as MIF)";
             type empty;
           }
           leaf description {
             description "Text description of interface";
             type string;
           }
           leaf metadata {
             description "Text metadata attached to interface";
             type string;
           }
           leaf encapsulation {
             description "Logical link-layer encapsulation";
             type enumeration {
               enum "atm-nlpid" {
                 description "ATM NLPID encapsulation";
               }
               enum "atm-cisco-nlpid" {
                 description "Cisco-compatible ATM NLPID encapsulation";
               }
               enum "atm-snap" {
                 description "ATM LLC/SNAP encapsulation";
               }
               enum "atm-vc-mux" {
                 description "ATM VC multiplexing";
               }
               enum "atm-ccc-vc-mux" {
                 description "ATM VC for CCC";
               }
               enum "atm-tcc-vc-mux" {
                 description "ATM VC for translational cross-connect";
               }
               enum "atm-tcc-snap" {
                 description "ATM LLC/SNAP for translational cross-connect";
               }
               enum "atm-ccc-cell-relay" {
                 description "ATM cell relay for CCC";
               }
               enum "vlan-vci-ccc" {
                 description "CCC for VLAN Q-in-Q and ATM VPI/VCI interworking";
               }
               enum "ether-over-atm-llc" {
                 description "Ethernet over ATM (LLC/SNAP) encapsulation";
               }
               enum "ether-vpls-over-atm-llc" {
                 description "Ethernet VPLS over ATM (bridging) encapsulation";
               }
               enum "ppp-over-ether-over-atm-llc" {
                 description "PPPoE over ATM (LLC/SNAP) encapsulation";
               }
               enum "ppp-over-ether" {
                 description "PPPoE encapsulation";
                 junos:must "(!(\".. family\"))";
                 junos:must-message "Can't configure protocol family with encapsulation ppp-over-ether";
               }
               enum "atm-ppp-vc-mux" {
                 description "ATM PPP over raw AAL5";
               }
               enum "atm-ppp-llc" {
                 description "ATM PPP over AAL5/LLC";
               }
               enum "atm-ppp-funi" {
                 description "ATM PPP over FUNI";
               }
               enum "atm-mlppp-llc" {
                 description "ATM MLPPP over AAL5/LLC";
               }
               enum "frame-relay-ppp" {
                 description "PPP over Frame Relay";
                 junos:must "(!(\".. family inet6\"))";
                 junos:must-message "family inet6 is not supported on encapsulation frame-relay-ppp";
                 junos:must "(!(\".. family inet\"))";
                 junos:must-message "family inet is not supported on encapsulation frame-relay-ppp";
                 junos:must "(\".. .. encapsulation frame-relay\")";
                 junos:must-message "Physical link-layer encapsulation must be frame-relay";
               }
               enum "frame-relay-ccc" {
                 description "Frame Relay DLCI for CCC";
               }
               enum "frame-relay" {
                 description "Frame Relay DLCI";
               }
               enum "frame-relay-tcc" {
                 description "Frame Relay DLCI for translational cross-connect";
               }
               enum "frame-relay-ether-type" {
                 description "Cisco-compatible Frame Relay Encapsulation DLCI";
                 junos:must "((\".. .. encapsulation flexible-frame-relay\" || (\".. .. encapsulation frame-relay-ether-type\" || \".. .. encapsulation frame-relay-ether-type-tcc\")))";
                 junos:must-message "Interface encapsulation must be cisco-compatible or flexible frame relay";
               }
               enum "frame-relay-ether-type-tcc" {
                 description "Cisco-compatible Frame Relay Encapsulation DLCI for TCC";
               }
               enum "ether-vpls-fr" {
                 description "Ethernet VPLS over Frame Relay (bridging) encapsulation";
               }
               enum "vlan-ccc" {
                 description "802.1q tagging for a cross-connect";
               }
               enum "ethernet-ccc" {
                 description "Ethernet for a cross-connect";
               }
               enum "vlan-vpls" {
                 description "VLAN virtual private LAN service";
               }
               enum "vlan-bridge" {
                 description "VLAN layer-2 bridging";
               }
               enum "ethernet-tcc" {
                 description "Ethernet translational cross-connect";
               }
               enum "dix" {
                 description "Ethernet DIXv2 (RFC 894)";
               }
               enum "ethernet" {
                 description "Ethernet II (RFC 894)";
               }
               enum "ethernet-vpls" {
                 description "Ethernet II virtual private LAN service";
               }
               enum "ethernet-bridge" {
                 description "Ethernet II bridging";
               }
               enum "vlan" {
                 description "802.1q-tagged Ethernet";
               }
               enum "vlan-tcc" {
                 description "802.1q tagging for a translational cross-connect";
               }
               enum "multilink-ppp" {
                 description "Multilink PPP";
               }
               enum "multilink-frame-relay-end-to-end" {
                 description "Multilink Frame Relay end-to-end (FRF.15)";
               }
               enum "ppp-ccc" {
                 description "Serial PPP device for a cross-connect";
               }
             }
           }
           leaf mtu {
             description "Maximum transmission unit packet size";
             type union {
               type string {
                 pattern "<.*>|$.*";
               }
               type uint32;
             }
           }
           choice pointedness {
             case case_1 {
               leaf point-to-point {
                 description "Point-to-point connection";
                 type empty;
               }
             }
             case case_2 {
               leaf multipoint {
                 description "Multipoint connection";
                 type empty;
               }
             }
           }
           leaf bandwidth {
             description "Logical unit bandwidth (informational only)";
             type string;
           }
           leaf global-layer2-domainid {
             description "Global Layer-2 Identifier for this interface";
             type union {
               type string {
                 pattern "<.*>|$.*";
               }
               type uint32 {
                 range "5 .. 4094";
               }
             }
           }
           choice traps-choice {
             leaf traps {
               description "Enable SNMP notifications on state changes";
               type empty;
             }
             leaf no-traps {
               description "Don't enable SNMP notifications on state changes";
               type empty;
             }
           }
           choice routing-services-choice {
             leaf routing-services {
               description "Enable routing services";
               status deprecated;
               type empty;
             }
             leaf no-routing-services {
               description "Don't enable routing services";
               status deprecated;
               type empty;
             }
           }
           container routing-service {
             description "Routing Services on this interface";
             uses apply-advanced;
             choice enable-disable {
               case case_1 {
                 leaf enable {
                   description "Enable Routing Service";
                   type empty;
                 }
               }
               case case_2 {
                 leaf disable {
                   description "Disable Routing Service";
                   type empty;
                 }
               }
             }
           }
           container arp-resp {
             presence "enable arp-resp";
             junos:cli-feature "oneliner";
             description "Knob to control ARP response on the interface, default is restricted";
             choice arp-response-options {
               case case_1 {
                 leaf unrestricted {
                   description "Enable unrestricted ARP respone on the interface";
                   type empty;
                 }
               }
               case case_2 {
                 leaf restricted {
                   description "Enable restricted proxy ARP response on the interface";
                   type empty;
                 }
               }
             }
           }
           container proxy-arp {
             presence "enable proxy-arp";
             junos:must "(!(\"switch-options no-arp-trap \"))";
             junos:must-message "Cannot enable proxy ARP with no-arp-trap";
             junos:cli-feature "oneliner";
             description "Enable proxy ARP on the interface, default is unrestricted";
             choice proxyarp-options {
               case case_1 {
                 leaf unrestricted {
                   description "Enable unrestricted proxy ARP on the interface";
                   type empty;
                 }
               }
               case case_2 {
                 leaf restricted {
                   description "Enable restricted proxy ARP on the interface";
                   type empty;
                 }
               }
             }
           }
           choice vlan_choice {
             case case_1 {
               leaf vlan-id {
                 description "Virtual LAN identifier value for 802.1q VLAN tags";
                 junos:must "(!(\"interfaces ${interface} stacked-vlan-tagging\"))";
                 junos:must-message "vlan-id is not supported on stacked-vlan-tagging mode";
                 type string;
               }
             }
             case case_2 {
               leaf vlan-id-range {
                 description "Virtual LAN identifier range of form vid1-vid2";
                 junos:must "((\"interfaces ${interface} vlan-tagging\" || \"interfaces ${interface} flexible-vlan-tagging\"))";
                 junos:must-message "valid only with vlan-tagging or flexible-vlan-tagging mode";
                 type jt:vlan-range;
               }
             }
             case case_3 {
               leaf-list inner-vlan-id-swap-ranges {
                 description "Inner vlan-id swap range(s) of form vid1-vid2 for dynamic L2 VLANs";
                 type jt:vlan-range;
               }
             }
             case case_4 {
               leaf-list vlan-id-list {
                 description "List of VLAN identifiers";
                 junos:must "((\" .. encapsulation vlan-ccc\" || (\"interfaces ${interface} encapsulation extended-vlan-ccc\" || (\" .. encapsulation vlan-vpls\" || (\"interfaces ${interface} encapsulation extended-vlan-vpls\" || (\" .. encapsulation vlan-bridge\" || \"interfaces ${interface} encapsulation extended-vlan-bridge\"))))))";
                 junos:must-message "valid only with ccc/vpls/bridge encapsulation";
                 junos:must "((\"interfaces ${interface} vlan-tagging\" || \"interfaces ${interface} flexible-vlan-tagging\"))";
                 junos:must-message "valid only with vlan-tagging or flexible-vlan-tagging mode";
                 type jt:vlan-range;
               }
             }
             case case_5 {
               leaf-list vlan-tag {
                 ordered-by user;
                 description "IEEE 802.1q tag list for VLAN tagged frames";
                 status deprecated;
                 type string;
               }
             }
             case case_6 {
               container vlan-tags {
                 presence "enable vlan-tags";
                 junos:must "((!(\"interfaces ${interface} vlan-tagging\") || !((\". inner\" || (\". inner-range\" || \". inner-list\")))))";
                 junos:must-message "inner/inner-range/inner-list is valid only on stacked-vlan-tagging and flexible-vlan-tagging mode";
                 junos:must "((!(\"interfaces ${interface} stacked-vlan-tagging\") || (\". inner\" || (\". inner-range\" || \". inner-list\"))))";
                 junos:must-message "inner/inner-range/inner-list must be defined for stacked-vlan-tagging mode";
                 junos:must "((\".. demux-options\" || (\"interfaces ${interface} vlan-tagging\" || (\"interfaces ${interface} stacked-vlan-tagging\" || \"interfaces ${interface} flexible-vlan-tagging\"))))";
                 junos:must-message "valid only with vlan-tagging, stacked-vlan-tagging or flexible-vlan-tagging mode";
                 junos:cli-feature "oneliner";
                 description "IEEE 802.1q tags";
                 leaf outer {
                   description "[tpid.]vlan-id, tpid format is 0xNNNN and is optional";
                   type string;
                 }
                 choice inner_choice {
                   case case_1 {
                     leaf inner {
                       description "[tpid.]vlan-id, tpid format is 0xNNNN and is optional";
                       type string;
                     }
                   }
                   case case_2 {
                     leaf inner-range {
                       description "[tpid.]vid1-vid2, tpid format is 0xNNNN and is optional";
                       type string {
                         junos:posix-pattern "^((0[Xx][0-9A-Fa-f]{4}.){0,1}([1-9][0-9]{0,2}|[1-3][0-9]{3}|40[0-8][0-9]|409[0-4])-([1-9][0-9]{0,2}|[1-3][0-9]{3}|40[0-8][0-9]|409[0-4]))$";
                         junos:pattern-message "vid in vlan-tag ([0xNNNN.]vid1-vid2) must be 1 to 4094";
                       }
                     }
                   }
                   case case_3 {
                     leaf-list inner-list {
                       description "List of VLAN identifiers";
                       junos:must "((\" .. .. encapsulation vlan-ccc\" || (\"interfaces ${interface} encapsulation extended-vlan-ccc\" || (\" .. .. encapsulation vlan-vpls\" || (\"interfaces ${interface} encapsulation extended-vlan-vpls\" || (\" .. .. encapsulation vlan-bridge\" || \"interfaces ${interface} encapsulation extended-vlan-bridge\"))))))";
                       junos:must-message "valid only with ccc/vpls/bridge encapsulation";
                       type jt:vlan-range;
                     }
                   }
                 }
               }
             }
           }
           leaf native-inner-vlan-id {
             description "Native virtual LAN identifier for singly tagged frames";
             junos:must "((\".. vlan-tags\" || \".. family bridge inner-vlan-id-list\"))";
             junos:must-message "native-inner-vlan-id can be specified only on a dual vlan tagged unit";
             junos:must "(\"interfaces ${interface} flexible-vlan-tagging\")";
             junos:must-message "native-inner-vlan-id can be specified only with flexible-vlan-tagging mode";
             type union {
               type string {
                 pattern "<.*>|$.*";
               }
               type uint32 {
                 range "0 .. 4094";
               }
             }
           }
           container accept-source-mac {
             junos:must "(\".. family ethernet-switching\")";
             junos:must-message "source mac filters are allowed only on interfaces with family ethernet-switching";
             description "Remote media access control address to/from which to accept traffic";
             uses apply-advanced;
             list mac-address {
               key name;
               description "Remote MAC address";
               uses mac_list;
             }
           }
           container input-vlan-map {
             description "VLAN map operation on input";
             junos:cli-feature "oneliner-plus";
             uses vlan_map;
           }
           container output-vlan-map {
             description "VLAN map operation on output";
             junos:cli-feature "oneliner-plus";
             uses vlan_map;
           }
           leaf swap-by-poppush {
             description "Pop original vlan tag and then push a new vlan tag";
             type empty;
           }
           leaf receive-lsp {
             description "Name of incoming label-switched path";
             type string;
           }
           leaf transmit-lsp {
             description "Name of outgoing label-switched path";
             type string;
           }
           leaf dlci {
             description "Frame Relay data-link control identifier";
             type union {
               type string {
                 pattern "<.*>|$.*";
               }
               type uint32 {
                 range "1 .. 1022";
               }
             }
           }
           leaf multicast-dlci {
             description "Frame Relay data-link control identifier for multicast packets";
             type union {
               type string {
                 pattern "<.*>|$.*";
               }
               type uint32 {
                 range "1 .. 1022";
               }
             }
           }
           choice vci_type {
             case case_1 {
               leaf vci {
                 description "ATM point-to-point virtual circuit identifier ([vpi.]vci)";
                 junos:must "(!(\".. encapsulation vlan-vci-ccc\"))";
                 junos:must-message "'vci-range' must be used with encapsulation vlan-vci-ccc";
                 type jt:atm-vci;
               }
             }
             case case_2 {
               leaf allow-any-vci {
                 description "Allow all VCIs to open in atm-ccc-cell-relay mode";
                 type empty;
               }
             }
             case case_3 {
               leaf vpi {
                 description "ATM point-to-point virtual path identifier (vpi)";
                 type union {
                   type string {
                     pattern "<.*>|$.*";
                   }
                   type uint32 {
                     range "0 .. 255";
                   }
                 }
               }
             }
             case case_4 {
               leaf trunk-id {
                 description "ATM trunk identifier";
                 type union {
                   type string {
                     pattern "<.*>|$.*";
                   }
                   type uint32 {
                     range "0 .. 31";
                   }
                 }
               }
             }
           }
           leaf no-vpivci-swapping {
             description "Do not swap VPI/VCI for Cell Relay";
             junos:must "(\".. encapsulation atm-ccc-cell-relay\")";
             junos:must-message "encapsulation must be atm-ccc-cell-relay";
             type empty;
           }
           choice psn_vci_type {
             case case_1 {
               leaf psn-vci {
                 description "PSN VCI";
                 junos:must "(\".. encapsulation atm-ccc-cell-relay\")";
                 junos:must-message "encapsulation must be atm-ccc-cell-relay";
                 junos:must "(!(\".. no-vpivci-swapping\"))";
                 junos:must-message "no-vpivci-swapping must not be configured";
                 type jt:atm-vci;
               }
             }
             case case_2 {
               leaf psn-vpi {
                 description "PSN VPI";
                 junos:must "(\".. encapsulation atm-ccc-cell-relay\")";
                 junos:must-message "encapsulation must be atm-ccc-cell-relay";
                 junos:must "(!(\".. no-vpivci-swapping\"))";
                 junos:must-message "no-vpivci-swapping must not be configured";
                 type union {
                   type string {
                     pattern "<.*>|$.*";
                   }
                   type uint32 {
                     range "0 .. 255";
                   }
                 }
               }
             }
           }
           container atm-l2circuit-mode {
             junos:cli-feature "oneliner";
             description "Select ATM Layer 2 circuit transport mode";
             choice mode_choice {
               case case_1 {
                 leaf cell {
                   description "ATM Layer 2 circuit cell mode";
                   type empty;
                 }
               }
               case case_2 {
                 leaf aal5 {
                   description "ATM Layer 2 circuit AAL5 mode";
                   type empty;
                 }
               }
             }
           }
           container vci-range {
             junos:must "(!(\".. vci\"))";
             junos:must-message "'vci-range' and 'vci' statements cannot co-exist";
             junos:cli-feature "oneliner";
             description "ATM VCI range start <start-vci> end <end-vci>";
             leaf start {
               description "ATM VCI range's start value";
               type union {
                 type string {
                   pattern "<.*>|$.*";
                 }
                 type uint16 {
                   range "32 .. 4094";
                 }
               }
             }
             leaf end {
               description "ATM VCI range's end value";
               type union {
                 type string {
                   pattern "<.*>|$.*";
                 }
                 type uint16 {
                   range "32 .. 4094";
                 }
               }
             }
           }
           leaf trunk-bandwidth {
             description "ATM trunk bandwidth";
             units "bits per second";
             type string;
           }
           leaf multicast-vci {
             description "ATM virtual circuit identifier for multicast packets";
             type jt:atm-vci;
           }
           container shaping {
             description "Virtual circuit traffic-shaping options";
             uses dcd_shaping_config;
           }
           container oam-period {
             junos:cli-feature "oneliner";
             description "OAM cell period";
             choice oam_period_choices {
               case case_1 {
                 leaf oam-period {
                   description "OAM cell period";
                   junos:cli-feature "nokeyword";
                   units "seconds";
                   type union {
                     type string {
                       pattern "<.*>|$.*";
                     }
                     type uint32 {
                       range "1 .. 900";
                     }
                   }
                 }
               }
               case case_2 {
                 container disable {
                   presence "enable disable";
                   junos:cli-feature "oneliner";
                   description "Disable F5 OAM loopback";
                 }
               }
             }
           }
           container oam-liveness {
             description "OAM virtual circuit liveness parameters";
             uses apply-advanced;
             leaf up-count {
               description "Number of OAM cells to consider VC up";
               type union {
                 type string {
                   pattern "<.*>|$.*";
                 }
                 type uint32 {
                   range "1 .. 255";
                 }
               }
             }
             leaf down-count {
               description "Number of OAM cells to consider VC down";
               type union {
                 type string {
                   pattern "<.*>|$.*";
                 }
                 type uint32 {
                   range "1 .. 255";
                 }
               }
             }
           }
           container ppp-options {
             description "Point-to-Point Protocol interface-specific options";
             uses ppp_options_type;
           }
           container pppoe-options {
             description "PPP over Ethernet interface-specific options";
             uses pppoe_options_type;
           }
           choice keepalive_choices {
             case case_1 {
               container keepalives {
                 description "Send or demand keepalive messages";
                 presence "enable keepalives";
                 junos:cli-feature "oneliner";
                 uses keepalives_type;
               }
             }
             case case_2 {
               leaf no-keepalives {
                 description "Do not send or demand keepalive messages";
                 type empty;
               }
             }
           }
           leaf inverse-arp {
             description "Enable inverse ARP";
             type empty;
           }
           leaf transmit-weight {
             description "ATM2 transmit weight for VC under VP tunnel";
             type union {
               type string {
                 pattern "<.*>|$.*";
               }
               type uint16 {
                 range "1 .. 32767";
               }
             }
           }
           container epd-threshold {
             description "Early packet discard threshold for ATM2";
             junos:cli-feature "oneliner";
             uses epd_threshold_config;
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf atm-scheduler-map {
             description "Assign ATM2 CoS scheduling map";
             type union {
               type string {
                 pattern "default";
               }
               type string;
             }
           }
           leaf mrru {
             description "Maximum received reconstructed unit";
             units "bytes";
             type union {
               type string {
                 pattern "<.*>|$.*";
               }
               type uint16 {
                 range "1500 .. 4500";
               }
             }
           }
           leaf short-sequence {
             description "Short sequence number header format (MLPPP only)";
             type empty;
           }
           leaf fragment-threshold {
             description "Fragmentation threshold";
             units "bytes";
             type union {
               type string {
                 pattern "<.*>|$.*";
               }
               type uint32 {
                 range "64 .. 4500";
               }
             }
           }
           leaf drop-timeout {
             description "Drop timeout";
             units "milliseconds";
             type union {
               type string {
                 pattern "<.*>|$.*";
               }
               type uint16 {
                 range "0 .. 2000";
               }
             }
           }
           leaf disable-mlppp-inner-ppp-pfc {
             description "Disable compression for inner PPP header in MLPPP payload";
             type empty;
           }
           leaf minimum-links {
             description "Minimum number of links to sustain the bundle";
             type union {
               type string {
                 pattern "<.*>|$.*";
               }
               type uint16;
             }
           }
           leaf multilink-max-classes {
             description "Number of multilink classes";
             type union {
               type string {
                 pattern "<.*>|$.*";
               }
               type uint16;
             }
           }
           leaf interleave-fragments {
             description "Interleave long packets with high priority ones";
             type empty;
           }
           leaf link-layer-overhead {
             description "Link layer bit stuffing overhead (0.0 .. 50.0 percent)";
             type jt:unsigned-float;
           }
           leaf accounting-profile {
             description "Accounting profile name";
             junos:must "((\"accounting-options interface-profile $$\" || \"accounting-options flat-file-profile $$\"))";
             junos:must-message "referenced accounting profile must be defined";
             type string;
           }
           leaf peer-unit {
             description "Peer unit number";
             type union {
               type string {
                 pattern "<.*>|$.*";
               }
               type uint32 {
                 range "0 .. 16385";
               }
             }
           }
           container tunnel {
             description "Tunnel parameters";
             uses apply-advanced;
             container encapsulation {
               presence "enable encapsulation";
               junos:cli-feature "homogeneous";
               description "Encapsulation over tunnel";
               container vxlan-gpe {
                 presence "enable vxlan-gpe";
                 junos:must "((!(\".. udp\") && !(\".. ipip\")))";
                 junos:must-message "Only one encapsulation can  be set per IFL";
                 uses apply-advanced;
                 container source {
                   uses apply-advanced;
                   leaf address {
                     description "Interface address prefix";
                     junos:must "(!(\".. interface\"))";
                     junos:must-message "To configure address interface must be not set";
                     type jt:ipv4addr;
                   }
                   leaf mac-address {
                     description "Interface source mac address";
                     junos:must "((\".. interface\" || \".. address\"))";
                     junos:must-message "Either address or interface must be set";
                     type jt:mac-addr;
                   }
                   leaf interface {
                     description "Name of the interface";
                     type union {
                       type jt:interface-name;
                       type string {
                         pattern "<.*>|$.*";
                       }
                     }
                   }
                 }
                 container destination {
                   uses apply-advanced;
                   leaf address {
                     description "Interface address prefix";
                     type jt:ipv4addr;
                   }
                   leaf mac-address {
                     description "Interface destination mac address";
                     junos:must "(\".. address\")";
                     junos:must-message "destination address must be set";
                     type jt:mac-addr;
                   }
                 }
                 leaf tunnel-endpoint {
                   description "Tunnel end point type";
                   type enumeration {
                     enum "vxlan" {
                       description "To configure vxlan tunnel-end-point";
                     }
                   }
                 }
                 container source-udp-port-range {
                   junos:cli-feature "oneliner";
                   description "Value range for source-udp-port";
                   leaf min {
                     description "Minimum range value";
                     type union {
                       type string {
                         pattern "<.*>|$.*";
                       }
                       type uint32 {
                         range "1 .. 65535";
                       }
                     }
                   }
                   leaf max {
                     description "Maximum range value";
                     type union {
                       type string {
                         pattern "<.*>|$.*";
                       }
                       type uint32 {
                         range "1 .. 65535";
                       }
                     }
                   }
                 }
                 leaf destination-udp-port {
                   description "Value to write to the destination-udp-port field";
                   type union {
                     type string {
                       pattern "<.*>|$.*";
                     }
                     type uint32 {
                       range "1 .. 65535";
                     }
                   }
                 }
                 leaf vni {
                   description "Value to write to the vni field";
                   type union {
                     type string {
                       pattern "<.*>|$.*";
                     }
                     type uint32 {
                       range "0 .. 16777214";
                     }
                   }
                 }
               }
               container udp {
                 presence "enable udp";
                 junos:must "((!(\".. .. .. family ccc\") && !(\".. .. .. family tcc\")))";
                 junos:must-message "Only inet, inet6, mpls, iso families allowed for udp tunnel in encap mode";
                 junos:must "((!(\".. vxlan-gpe\") && (!(\".. ipip\") && !(\"..gre\"))))";
                 junos:must-message "Only one encapsulation can  be set per IFL";
                 description "Family for tunnel encapsulation udp";
                 uses apply-advanced;
                 container source {
                   uses apply-advanced;
                   leaf address {
                     description "Interface address prefix";
                     junos:must "(!(\".. interface\"))";
                     junos:must-message "To configure address interface must be not set";
                     type jt:ipv4addr;
                   }
                   leaf interface {
                     description "Name of the interface";
                     type union {
                       type jt:interface-name;
                       type string {
                         pattern "<.*>|$.*";
                       }
                     }
                   }
                 }
                 container destination {
                   uses apply-advanced;
                   leaf address {
                     description "Interface address prefix";
                     type jt:ipv4addr;
                   }
                 }
               }
               container ipip {
                 presence "enable ipip";
                 junos:must "((!(\".. .. .. family ccc\") && (!(\".. .. .. family tcc\") && !(\".. .. .. family iso\"))))";
                 junos:must-message "Only inet, inet6, mpls families allowed for ipip tunnel in decap/encap mode";
                 junos:must "((!(\".. udp\") && (!(\".. vxlan-gpe\") && !(\".. gre\"))))";
                 junos:must-message "Only one encapsulation can  be set per IFL";
                 description "Family for tunnel encapsulation ipip";
                 uses apply-advanced;
                 container source {
                   uses apply-advanced;
                   leaf address {
                     description "Interface address prefix";
                     junos:must "(!(\".. interface\"))";
                     junos:must-message "To configure address interface must be not set";
                     type jt:ipv4addr;
                   }
                   leaf interface {
                     description "Name of the interface";
                     type union {
                       type jt:interface-name;
                       type string {
                         pattern "<.*>|$.*";
                       }
                     }
                   }
                 }
                 container destination {
                   uses apply-advanced;
                   leaf address {
                     description "Interface address prefix";
                     type jt:ipv4addr;
                   }
                 }
               }
               container virtual-loop {
                 presence "enable virtual-loop";
                 junos:must "((!(\".. .. .. family ccc\") && (!(\".. .. .. family tcc\") && (!(\".. .. .. family mpls\") && !(\".. .. .. family iso\")))))";
                 junos:must-message "Only inet, and inet6 families allowed for virtual-loop tunnel encapsulation mode";
                 junos:must "((!(\".. vxlan-gpe\") && (!(\".. ipip\") && (!(\"..gre\") && !(\"..udp\")))))";
                 junos:must-message "Only one encapsulation is allowed per IFL";
                 description "Family for tunnel encapsulation virtual-loop";
               }
             }
             choice source_type {
               case case_1 {
                 leaf source {
                   description "Tunnel source address";
                   type jt:ipaddr;
                 }
               }
               case case_2 {
               }
               case case_3 {
               }
             }
             choice destination_type {
               case case_1 {
                 leaf destination {
                   description "Tunnel destination address";
                   type jt:ipaddr;
                 }
               }
               case case_2 {
               }
             }
             leaf backup-destination {
               description "Backup tunnel destination";
               junos:must "(!(\".. destination $$\"))";
               junos:must-message "Backup and primary tunnel destinations must be different";
               type jt:ipaddr;
             }
             choice fragmentation {
               case case_1 {
                 leaf allow-fragmentation {
                   description "Do not set DF bit on packets";
                   type empty;
                 }
               }
               case case_2 {
                 leaf do-not-fragment {
                   description "Set DF bit on packets";
                   type empty;
                 }
               }
             }
             leaf ttl {
               description "Time to live";
               type union {
                 type string {
                   pattern "<.*>|$.*";
                 }
                 type uint32 {
                   range "1 .. 255";
                 }
               }
             }
             leaf traffic-class {
               description "TOS/Traffic class field of IP-header";
               type union {
                 type string {
                   pattern "<.*>|$.*";
                 }
                 type uint32 {
                   range "0 .. 255";
                 }
               }
             }
             leaf flow-label {
               description "Flow label field of IP6-header";
               type union {
                 type string {
                   pattern "<.*>|$.*";
                 }
                 type uint32 {
                   range "0 .. 1048575";
                 }
               }
             }
             choice path-mtu-discovery-choice {
               leaf path-mtu-discovery {
                 description "Enable path MTU discovery for tunnels";
                 type empty;
               }
               leaf no-path-mtu-discovery {
                 description "Don't enable path MTU discovery for tunnels";
                 type empty;
               }
             }
             container routing-instance {
               description "Routing instance to which tunnel ends belong";
               uses apply-advanced;
               leaf destination {
                 description "Routing instance of tunnel destination";
                 junos:must "((\"routing-instances $$\" || any \"tenants <*> routing-instances $$\"))";
                 junos:must-message "referenced routing-instance must be defined";
                 type string {
                   junos:posix-pattern "!^((__.*__)|(all)|(.*[ ].*)|(\"\")|(.{129,}))$";
                   junos:pattern-message "Must be a non-reserved string of 128 characters or less with no spaces.";
                 }
               }
             }
           }
           leaf compression-device {
             description "Logical interface used for compression";
             type union {
               type jt:interface-unit;
               type string {
                 pattern "<.*>|$.*";
               }
             }
           }
           container atm-policer {
             junos:must "(\".. family\")";
             junos:must-message "Family must be defined for a unit with atm-policer";
             description "ATM policing for logical interface";
             uses apply-advanced;
             leaf input-atm-policer {
               description "Input atm policer";
               type string;
             }
           }
           container layer2-policer {
             junos:must "(\".. family\")";
             junos:must-message "Family must be defined for a unit with layer2-policer";
             description "Layer2 policing for logical interface";
             uses apply-advanced;
             choice layer2-input-policer-choice {
               case case_1 {
                 leaf input-policer {
                   description "Two-color policer for received packets";
                   type string;
                 }
               }
               case case_2 {
               }
               case case_3 {
                 leaf input-three-color {
                   description "Color-blind three-color policer for received packets";
                   type string;
                 }
               }
             }
             choice layer2-output-policer-choice {
               case case_1 {
                 leaf output-policer {
                   description "Two-color policer for transmitted packets";
                   type string;
                 }
               }
               case case_2 {
                 leaf output-three-color {
                   description "Three-color policer for transmitted packets";
                   type string;
                 }
               }
             }
           }
           container filter {
             description "Filters to apply to all families configured under this logical interface";
             uses apply-advanced;
             choice chain_choice {
               case case_1 {
               }
             }
             choice input_choice {
               case case_1 {
                 container input {
                   junos:cli-feature "oneliner";
                   description "Name of filter to be applied to received packets";
                   leaf filter-name {
                     description "Name of the filter";
                     junos:cli-feature "nokeyword";
                     junos:must "((!(any \"firewall family any filter $$ term <*> from gbp-dst-tag\") || !(any \"firewall family any filter $$ term <*> then next-ip6\")))";
                     junos:must-message "GBP enforcement filter with next-ip6 action not supported on interface input.";
                     junos:must "((!(any \"firewall family any filter $$ term <*> from gbp-src-tag\") || !(any \"firewall family any filter $$ term <*> then next-ip6\")))";
                     junos:must-message "GBP enforcement filter with next-ip6 action not supported on interface input.";
                     junos:must "((!(any \"firewall family any filter $$ term <*> from gbp-dst-tag\") || !(any \"firewall family any filter $$ term <*> then next-ip\")))";
                     junos:must-message "GBP enforcement filter with next-ip action not supported on interface input.";
                     junos:must "((!(any \"firewall family any filter $$ term <*> from gbp-src-tag\") || !(any \"firewall family any filter $$ term <*> then next-ip\")))";
                     junos:must-message "GBP enforcement filter with next-ip action not supported on interface input.";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
             }
             choice output_choice {
               case case_1 {
                 container output {
                   junos:cli-feature "oneliner";
                   description "Name of filter to be applied to transmitted packets";
                   leaf filter-name {
                     description "Name of the filter";
                     junos:cli-feature "nokeyword";
                     junos:must "((!(any \"firewall family any filter $$ term <*> from gbp-dst-tag\") || !(any \"firewall family any filter $$ term <*> then next-ip6\")))";
                     junos:must-message "GBP enforcement filter with next-ip6 action not supported on interface output.";
                     junos:must "((!(any \"firewall family any filter $$ term <*> from gbp-src-tag\") || !(any \"firewall family any filter $$ term <*> then next-ip6\")))";
                     junos:must-message "GBP enforcement filter with next-ip6 action not supported on interface output.";
                     junos:must "((!(any \"firewall family any filter $$ term <*> from gbp-dst-tag\") || !(any \"firewall family any filter $$ term <*> then next-ip\")))";
                     junos:must-message "GBP enforcement filter with next-ip action not supported on interface output.";
                     junos:must "((!(any \"firewall family any filter $$ term <*> from gbp-src-tag\") || !(any \"firewall family any filter $$ term <*> then next-ip\")))";
                     junos:must-message "GBP enforcement filter with next-ip action not supported on interface output.";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
             }
           }
           list multi-chassis-protection {
             key name;
             description "Inter-Chassis protection configuration";
             junos:must "(\"interfaces ${interface} aggregated-ether-options mc-ae mode active-active\")";
             junos:must-message "multi-chassis-protection is only supported for MC-AE active-active mode";
             uses multi-chassis-protection-group-ifl;
           }
           leaf statistics {
             description "Enable statistics collection in PFE";
             type empty;
           }
           choice virtual-gateway {
             case case_1 {
               leaf no-auto-virtual-gateway-esi {
                 description "Disable auto ESI generation for virtual gateway address";
                 junos:must "((any \".. family inet address <*> virtual-gateway-address\" || any \".. family inet6 address <*> virtual-gateway-address\"))";
                 junos:must-message "Only when virtual gateway address is configured";
                 type empty;
               }
             }
             case case_2 {
               container virtual-gateway-esi {
                 description "ESI configuration of virtual gateway";
                 uses apply-advanced;
                 leaf identifier {
                   description "ESI value for the interface";
                   junos:cli-feature "nokeyword";
                   junos:must "(unique \"interfaces <*> unit <*> virtual-gateway-esi $$\")";
                   junos:must-message "virtual-gateway-esi value must be unique under all IFDs and IFLs";
                   junos:must "(unique \"interfaces <*> esi $$\")";
                   junos:must-message "ESI value must be unique under all IFDs and IFLs";
                   type jt:esi;
                 }
                 choice mode {
                   case case_1 {
                     leaf single-active {
                       description "Single-active mode";
                       type empty;
                     }
                   }
                   case case_2 {
                     leaf all-active {
                       description "All-active mode";
                       type empty;
                     }
                   }
                 }
               }
             }
           }
           container service {
             description "Service operations";
             uses apply-advanced;
             list pcef {
               key name;
               ordered-by user;
               description "PCEF configuration";
               leaf name {
                 description "PCEF Profile name";
                 junos:cli-feature "nokeyword";
                 junos:must "((\".. family inet service\" || \".. family inet6 service\"))";
                 junos:must-message "Must be configured along with a family inet/inet6 service.";
                 type string;
               }
               uses apply-advanced;
               leaf activate-all {
                 description "Activate all rules and rulebases in the pcef profile";
                 junos:must "(!(\"activate\"))";
                 junos:must-message "Can't be configured with activate-rule or activate- rulebase.";
                 type empty;
               }
               list activate {
                 key name;
                 ordered-by user;
                 description "Name of pcef profile rule or rulebase to activate";
                 leaf name {
                   description "Name of pcef profile rule or rulebase to activate";
                   junos:cli-feature "nokeyword";
                   type string;
                 }
                 uses apply-advanced;
               }
             }
           }
           choice generate-eui64-choice {
             leaf generate-eui64 {
               description "To generate Link Local EUI-64 addresses";
               junos:must "(\".. family inet6 unnumbered-address\")";
               junos:must-message "generate-eui64 attribute must be set when unnumbered-address is configured under family inet6";
               type empty;
             }
             leaf no-generate-eui64 {
               description "Don't to generate Link Local EUI-64 addresses";
               junos:must "(\".. family inet6 unnumbered-address\")";
               junos:must-message "generate-eui64 attribute must be set when unnumbered-address is configured under family inet6";
               type empty;
             }
           }
           container mode {
             description "Add an interface to a tap or tool group";
             uses apply-advanced;
             list tap {
               key name;
               ordered-by user;
               description "Add an interface to a tap group";
               leaf name {
                 description "Tap group name";
                 junos:cli-feature "nokeyword";
                 type string;
               }
               uses apply-advanced;
             }
             list tool {
               key name;
               ordered-by user;
               description "Add an interface to a tool group";
               leaf name {
                 description "Tool group name";
                 junos:cli-feature "nokeyword";
                 type string;
               }
               uses apply-advanced;
             }
           }
           container family {
             junos:must "(!(\".. encapsulation ppp-over-ether\"))";
             junos:must-message "Can't configure protocol family with encapsulation ppp-over-ether";
             junos:cli-feature "homogeneous";
             description "Protocol family";
             container inet {
               presence "enable inet";
               junos:must "(!(\".. .. .. encapsulation vlan-vpls\"))";
               junos:must-message "Can't configure protocol family inet with encapsulation vpls";
               description "IPv4 parameters";
               uses apply-advanced;
               leaf source-lookup {
                 description "Set source lookup flag";
                 junos:must "(!(\".. accouting source-class-usage\"))";
                 junos:must-message " Source lookup is not allowed with source-class-usage";
                 type empty;
               }
               container class-based-filtering {
                 description "Enable class based filter on interface";
                 uses apply-advanced;
               }
               container dhcp {
                 presence "enable dhcp";
                 junos:must "(!(any \"forwarding-options dhcp-relay group <*> interface ${interface}.${unit}\"))";
                 junos:must-message "Incompatible with the interface configured under 'forwarding-options dhcp-relay group'";
                 junos:must "(!(\"system services dhcp\"))";
                 junos:must-message "Incompatible with the dhcp server configured under 'system services dhcp'";
                 junos:must "(!(\"system autoinstallation interfaces\"))";
                 junos:must-message "Incompatible with 'system autoinstallation interfaces'";
                 junos:must "(!(\".. address\"))";
                 junos:must-message "Incompatible with interface assigned with address";
                 junos:must "(!(\"system autoinstallation\"))";
                 junos:must-message "Incompatible with 'system autoinstallation'";
                 description "Configure DHCP Client";
                 uses apply-advanced;
                 container client-identifier {
                   junos:cli-feature "oneliner";
                   description "DHCP Server identifies a client by client-identifier value ";
                   choice client-identifier-choice {
                     case case_1 {
                       leaf ascii {
                         description "Client identifier as an ASCII string";
                         type string;
                       }
                     }
                     case case_2 {
                       leaf hexadecimal {
                         description "Client identifier as a hexadecimal string";
                         type string {
                           junos:posix-pattern "^[[:xdigit:]]+$";
                           junos:pattern-message "Must be hexadecimal digits (0-9, a-f, A-F)";
                         }
                       }
                     }
                   }
                 }
                 leaf lease-time {
                   description "Default lease time requested in ";
                   units "seconds";
                   type string;
                 }
                 leaf retransmission-attempt {
                   description "Number of attempts to retransmit the DHCP client protocol packet";
                   default "4";
                   type union {
                     type string {
                       pattern "<.*>|$.*";
                     }
                     type uint32 {
                       range "0 .. 6";
                     }
                   }
                 }
                 leaf retransmission-interval {
                   description "Number of seconds between successive retransmission";
                   default "4";
                   units "seconds";
                   type union {
                     type string {
                       pattern "<.*>|$.*";
                     }
                     type uint32 {
                       range "4 .. 64";
                     }
                   }
                 }
                 leaf server-address {
                   description "DHCP Server-address";
                   type jt:ipv4addr;
                 }
                 leaf update-server {
                   description "Propagate TCP/IP settings to DHCP server ";
                   type empty;
                 }
                 leaf vendor-id {
                   description "Vendor class id for the DHCP Client";
                   type string;
                 }
               }
               container targeted-broadcast {
                 presence "enable targeted-broadcast";
                 description "Directed broadcast";
                 uses apply-advanced;
                 choice targeted-bcast-choice {
                   case case_1 {
                     leaf forward-and-send-to-re {
                       description "Allow packets to be forwarded and sent to re";
                       type empty;
                     }
                   }
                   case case_2 {
                     leaf forward-only {
                       description "Allow packets only to be forwarded";
                       type empty;
                     }
                   }
                 }
               }
               leaf destination-class-usage {
                 description "Enable destination class usage on this interface";
                 status deprecated;
                 type empty;
               }
               leaf transit-options-packets {
                 description "Transit IP options packets (don't send to Routing Engine)";
                 status deprecated;
                 type empty;
               }
               leaf transit-ttl-exceeded {
                 description "Transit IP TTL-exceeded packets (don't send to Routing Engine)";
                 status deprecated;
                 type empty;
               }
               leaf receive-options-packets {
                 description "Receive IP options packets (don't send to Routing Engine)";
                 type empty;
               }
               leaf receive-ttl-exceeded {
                 description "Receive IP TTL-exceeded packets (don't send to Routing Engine)";
                 type empty;
               }
               container accounting {
                 description "Configure interface-based accounting options";
                 uses apply-advanced;
                 container source-class-usage {
                   junos:must "(!(\".. .. class-based-filtering source-class-usage\"))";
                   junos:must-message "source-class-usage is not allowed with class-based-filtering source-class-usage";
                   junos:must "(!(\".. .. source-lookup\"))";
                   junos:must-message " source-class-usage is not allowed with source-lookup";
                   description "Enable source class usage on this interface";
                   uses apply-advanced;
                   leaf input {
                     description "Specify this interface for source-class-usage input";
                     type empty;
                   }
                   leaf output {
                     description "Specify this interface for source-class-usage output";
                     type empty;
                   }
                 }
                 leaf destination-class-usage {
                   description "Enable destination class usage on this interface";
                   junos:must "(!(\".. .. class-based-filtering destination-class-usage\"))";
                   junos:must-message "destination-class-usage is not allowed with class-based-filtering destination-class-usage";
                   type empty;
                 }
               }
               leaf mac-validate {
                 description "Validate source MAC address";
                 type enumeration {
                   enum "strict" {
                     description "Strict mac-validation";
                   }
                   enum "loose" {
                     description "Loose mac-validation";
                   }
                 }
               }
               container rpf-check {
                 presence "enable rpf-check";
                 junos:cli-feature "oneliner-plus";
                 description "Enable reverse-path-forwarding checks on this interface";
                 uses apply-advanced;
                 leaf fail-filter {
                   description "Name of filter applied to packets failing RPF check";
                   type string;
                 }
                 container mode {
                   junos:cli-feature "oneliner";
                   description "Mode for reverse path forwarding";
                   leaf loose {
                     description "Reverse-path-forwarding loose mode";
                     type empty;
                   }
                 }
               }
               leaf mtu {
                 description "Protocol family maximum transmission unit";
                 type union {
                   type uint32;
                   type string {
                     pattern "<.*>|$.*";
                   }
                 }
               }
               leaf arp-max-cache {
                 description "Max interface ARP nexthop cache size";
                 type union {
                   type string {
                     pattern "<.*>|$.*";
                   }
                   type uint32 {
                     range "1 .. 2000000";
                   }
                 }
               }
               leaf arp-new-hold-limit {
                 description "Max no. of new unresolved nexthops";
                 junos:must "(\".. arp-max-cache\")";
                 junos:must-message "Interface max ARP cache size must be configured";
                 type union {
                   type string {
                     pattern "<.*>|$.*";
                   }
                   type uint32 {
                     range "1 .. 2000000";
                   }
                 }
               }
               leaf no-redirects {
                 description "Do not redirect traffic";
                 type empty;
               }
               leaf nat-outside-interface {
                 description "Public interface used for NAT";
                 junos:must "(!(\"interfaces ${interface} unit ${unit} family inet6\"))";
                 junos:must-message "family inet6 is not supported with nat-outside-interface";
                 type empty;
               }
               leaf no-neighbor-learn {
                 description "Disable neighbor address learning on interface";
                 type empty;
               }
               leaf unconditional-src-learn {
                 description "Glean from arp packets even when source cannot be validated";
                 type empty;
               }
               leaf multicast-only {
                 description "Allow only multicast traffic (tunnels only)";
                 type empty;
               }
               leaf primary {
                 description "Candidate for primary interface in system";
                 type empty;
               }
               leaf ipsec-sa {
                 description "Name of security association";
                 type string {
                   length "1 .. 32";
                 }
               }
               container filter {
                 description "Packet filtering";
                 uses apply-advanced;
                 choice input_choice {
                   case case_1 {
                     container input {
                       junos:cli-feature "oneliner";
                       description "Filter to be applied to received packets";
                       leaf filter-name {
                         description "Name of the filter";
                         junos:cli-feature "nokeyword";
                         junos:must "((!(\".. .. .. rpf-check\") || (!(any \"firewall family inet filter $$ term <*> from first-byte-of-payload\") && !(any \"firewall family inet filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 leaf-list output-chain {
                   ordered-by user;
                   description "List of filter modules applied to transmitted packets ";
                   type string;
                 }
                 choice output_choice {
                   case case_1 {
                     container output {
                       junos:cli-feature "oneliner";
                       description "Filter to be applied to transmitted packets";
                       leaf filter-name {
                         description "Name of the filter";
                         junos:cli-feature "nokeyword";
                         junos:must "((!(\".. .. .. rpf-check\") || (!(any \"firewall family inet filter $$ term <*> from first-byte-of-payload\") && !(any \"firewall family inet filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       junos:cli-feature "nokeyword";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32;
                   }
                 }
               }
               container simple-filter {
                 description "Filter for doing multifield classification";
                 uses apply-advanced;
                 leaf input {
                   description "Name of simple filter applied to received packets";
                   type string;
                 }
               }
               container policer {
                 description "Interface policing";
                 uses apply-advanced;
                 leaf arp {
                   description "Name of policer applied to received ARP packets";
                   junos:must "(!(\".. disable-arp-policer\"))";
                   junos:must-message "Interface configuration can have either disable-arp-policer or arp policer configured";
                   junos:must "((!(\".. .. .. .. peer-unit\") || (\".. .. .. .. encapsulation ethernet\" || \".. .. .. .. encapsulation vlan\")))";
                   junos:must-message "Interface encapsulation must be ethernet or vlan";
                   type string;
                 }
                 leaf input {
                   description "Name of policer applied to received packets";
                   junos:must "(!(\".. .. input-hierarchical-policer\"))";
                   junos:must-message "Both input policer and input hierarchical policer can not be applied on the same family";
                   type string;
                 }
                 leaf output {
                   description "Name of policer applied to transmitted packets";
                   type string;
                 }
               }
               container sampling {
                 junos:must "((\"forwarding-options sampling family inet\" || (\"forwarding-options packet-capture\" || any \"forwarding-options sampling instance <*> family inet\")))";
                 junos:must-message "Requires forwarding-options sampling or packet-capture config";
                 description "Interface sampling";
                 uses apply-advanced;
                 leaf input {
                   description "Sample all packets input on this interface";
                   type empty;
                 }
                 leaf output {
                   description "Sample all packets output on this interface";
                   type empty;
                 }
               }
               list next-hop-tunnel {
                 key name;
                 ordered-by user;
                 junos:cli-feature "oneliner-plus";
                 description "One or more next-hop tunnel tables";
                 leaf name {
                   description "Next-hop tunnel gateway address";
                   junos:cli-feature "nokeyword";
                   type string;
                 }
                 uses apply-advanced;
                 leaf ipsec-vpn {
                   description "Name of IPSec VPN";
                   junos:must "(\"security ipsec vpn $$\")";
                   junos:must-message "Referenced IPSec vpn must be defined under [edit security ipsec vpn] hierarchy level";
                   junos:must "(unique \"interfaces st0 unit <*> family inet next-hop-tunnel <*> ipsec-vpn $$\")";
                   junos:must-message "Referenced IPSec vpn must be unique";
                   type string;
                 }
               }
               choice tunnel-termination-status {
                 case case_1 {
                   leaf tunnel-termination {
                     description "Tunnel termination";
                     type empty;
                   }
                 }
                 case case_2 {
                   leaf no-tunnel-termination {
                     description "No Tunnel termination";
                     type empty;
                   }
                 }
               }
               leaf tunnel-loopback {
                 description "Allows tunnel packet processing on IRB underlay using the loopback path";
                 type empty;
               }
               list address {
                 key name;
                 ordered-by user;
                 description "Interface address/destination prefix";
                 junos:must "((!(\".. unnumbered-address\") && !(\".. location-pool-address\")))";
                 junos:must-message "address cannot be defined with unnumbered-address or location-pool-address simultaneously";
                 leaf name {
                   description "Interface address/destination prefix";
                   junos:cli-feature "nokeyword";
                   type jt:ipv4prefix;
                 }
                 uses apply-advanced;
                 leaf destination {
                   description "Destination address";
                   type jt:ipv4addr;
                 }
                 leaf destination-profile {
                   description "Profile to use for destination address";
                   junos:must "(\"access group-profile $$ ppp\")";
                   junos:must-message "referenced group-profile must be defined and must contain ppp statement";
                   type string;
                 }
                 leaf broadcast {
                   description "Broadcast address";
                   type jt:ipv4addr;
                 }
                 leaf primary {
                   description "Candidate for primary address in system";
                   type empty;
                 }
                 leaf preferred {
                   description "Preferred address on interface";
                   type empty;
                 }
                 leaf master-only {
                   description "Master management IP address for router";
                   type empty;
                 }
                 container tag {
                   description "Tag used for route/local";
                   uses apply-advanced;
                   leaf tag-value {
                     description "The tag value on the address";
                     junos:cli-feature "nokeyword";
                     type union {
                       type string {
                         pattern "<.*>|$.*";
                       }
                       type uint32 {
                         range "1 .. 4294967295";
                       }
                     }
                   }
                   leaf type {
                     description "Tag type must be [1-16]";
                     type union {
                       type string {
                         pattern "<.*>|$.*";
                       }
                       type uint32 {
                         range "1 .. 16";
                       }
                     }
                   }
                 }
                 container tag2 {
                   description "Tag2 used for route/local";
                   uses apply-advanced;
                   leaf tag2-value {
                     description "The tag value on the address";
                     junos:cli-feature "nokeyword";
                     type union {
                       type string {
                         pattern "<.*>|$.*";
                       }
                       type uint32 {
                         range "1 .. 4294967295";
                       }
                     }
                   }
                   leaf type {
                     description "Tag type must be [1-16]";
                     type union {
                       type string {
                         pattern "<.*>|$.*";
                       }
                       type uint32 {
                         range "1 .. 16";
                       }
                     }
                   }
                 }
                 list multipoint-destination {
                   key name;
                   ordered-by user;
                   junos:cli-feature "oneliner-plus";
                   description "Multipoint NBMA destination";
                   leaf name {
                     description "Destination address";
                     junos:cli-feature "nokeyword";
                     type jt:ipv4addr;
                   }
                   uses apply-advanced;
                   choice link-address {
                     case case_1 {
                       leaf dlci {
                         description "Frame Relay data-link control identifier";
                         type union {
                           type string {
                             pattern "<.*>|$.*";
                           }
                           type uint32 {
                             range "1 .. 1022";
                           }
                         }
                       }
                     }
                     case case_2 {
                       leaf vci {
                         description "ATM virtual circuit identifier ([vpi.]vci)";
                         type jt:atm-vci;
                       }
                     }
                   }
                   container shaping {
                     description "Virtual circuit traffic-shaping options";
                     uses dcd_shaping_config;
                   }
                   container oam-period {
                     junos:cli-feature "oneliner";
                     description "OAM cell period";
                     choice oam_period_choices {
                       case case_1 {
                         leaf oam_period {
                           description "OAM cell period";
                           junos:cli-feature "nokeyword";
                           units "seconds";
                           type union {
                             type string {
                               pattern "<.*>|$.*";
                             }
                             type uint32 {
                               range "1 .. 900";
                             }
                           }
                         }
                       }
                       case case_2 {
                         container disable {
                           presence "enable disable";
                           junos:cli-feature "oneliner";
                           description "Disable OAM loopback";
                         }
                       }
                     }
                   }
                   container oam-liveness {
                     description "OAM virtual circuit liveness parameters";
                     uses apply-advanced;
                     leaf up-count {
                       description "Number of OAM cells to consider VC up";
                       type union {
                         type string {
                           pattern "<.*>|$.*";
                         }
                         type uint32 {
                           range "1 .. 255";
                         }
                       }
                     }
                     leaf down-count {
                       description "Number of OAM cells to consider VC down";
                       type union {
                         type string {
                           pattern "<.*>|$.*";
                         }
                         type uint32 {
                           range "1 .. 255";
                         }
                       }
                     }
                   }
                   leaf inverse-arp {
                     description "Enable inverse ARP reply messages";
                     type empty;
                   }
                   leaf transmit-weight {
                     description "ATM2 transmit weight for VC under VP tunnel";
                     type union {
                       type string {
                         pattern "<.*>|$.*";
                       }
                       type uint16 {
                         range "1 .. 32767";
                       }
                     }
                   }
                   container epd-threshold {
                     description "Early packet discard threshold for ATM2";
                     junos:cli-feature "oneliner";
                     uses epd_threshold_config;
                   }
                 }
                 list arp {
                   key name;
                   ordered-by user;
                   junos:cli-feature "oneliner";
                   description "Static Address Resolution Protocol entries";
                   leaf name {
                     description "Destination IP address";
                     junos:cli-feature "nokeyword";
                     type jt:ipv4addr;
                   }
                   leaf l2-interface {
                     description "Layer 2 interface name for ARP entry";
                     type union {
                       type jt:interface-name;
                       type string {
                         pattern "<.*>|$.*";
                       }
                     }
                   }
                   choice mac_address_type {
                     case case_1 {
                       leaf mac {
                         description "MAC address";
                         type jt:mac-unicast;
                       }
                     }
                     case case_2 {
                       leaf multicast-mac {
                         description "Multicast MAC address";
                         type jt:mac-multicast;
                       }
                     }
                   }
                   leaf publish {
                     description "Reply to ARP requests for this entry";
                     junos:must "((\".. mac\" || \".. multicast-mac\"))";
                     junos:must-message "mac or multicast-mac must be configured to publish";
                     type empty;
                   }
                   leaf flood-as-unknown-unicast {
                     description "Broadcast the packet with unicast MAC";
                     junos:must "(!(\".. l2-interface\"))";
                     junos:must-message "l2-interface cannot be configured with flood-as-unknown-unicast";
                     junos:must "(\".. mac\")";
                     junos:must-message "mac must be configured to flood-as-unknown-unicast";
                     type empty;
                   }
                 }
                 list host-discovery {
                   key name;
                   ordered-by user;
                   junos:cli-feature "oneliner";
                   description "Discover servers IP based on subnet range";
                   junos:must "(\"system arp proactive-arp-detection \")";
                   junos:must-message "Proactive ARP Detection feature should be enabled";
                   max-elements 8;
                   leaf name {
                     description "IP address subnet range";
                     junos:cli-feature "nokeyword";
                     type jt:ipv4prefix;
                   }
                   leaf aging-timer {
                     description "ARP aging timer";
                     type union {
                       type string {
                         pattern "<.*>|$.*";
                       }
                       type uint32 {
                         range "10 .. 1200";
                       }
                     }
                   }
                   leaf discovery-interval {
                     description "ARP proactive discovery time";
                     type union {
                       type string {
                         pattern "<.*>|$.*";
                       }
                       type uint32 {
                         range "3 .. 300";
                       }
                     }
                   }
                 }
                 list vrrp-group {
                   key name;
                   ordered-by user;
                   description "VRRP group";
                   uses vrrp-group;
                 }
                 leaf virtual-gateway-address {
                   description "Virtual Gateway IP address";
                   junos:must "(!(\".. vrrp-group\"))";
                   junos:must-message "vrrp configuration incompatible with virtual gateway address";
                   type jt:ipv4addr;
                 }
               }
               container unnumbered-address {
                 junos:cli-feature "oneliner";
                 description "Unnumbered interface address/destination prefix";
                 leaf source {
                   description "Interface from which to take local address";
                   junos:cli-feature "nokeyword";
                   junos:must "(\"interfaces $$-IFL family inet address\")";
                   junos:must-message "referred interface must have address configured under family inet";
                   type union {
                     type jt:interface-unit;
                     type string {
                       pattern "<.*>|$.*";
                     }
                   }
                 }
                 leaf preferred-source-address {
                   description "Preferred address on the donor interface";
                   type string;
                 }
                 leaf destination {
                   description "Destination address";
                   type jt:ipv4addr;
                 }
                 leaf destination-profile {
                   description "Profile to use for destination address";
                   junos:must "(\"access group-profile $$ ppp\")";
                   junos:must-message "referenced group-profile must be defined and must contain ppp statement";
                   type string;
                 }
               }
               leaf negotiate-address {
                 description "Negotiate address with remote";
                 junos:must "(!(\".. .. .. .. encapsulation multilink-frame-relay-uni-nni\"))";
                 junos:must-message "negotiate-address is not supported with family mlfr-uni-nni ";
                 junos:must "(!(\".. .. .. encapsulation multilink-frame-relay-end-to-end\"))";
                 junos:must-message "negotiate-address is not supported with family mlfr-end-to-end ";
                 junos:must "(!(\".. location-pool-address\"))";
                 junos:must-message "negotiate-address and location-pool-address must not be defined simultaneously";
                 junos:must "(!(\".. unnumbered-address\"))";
                 junos:must-message "negotiate-address and unnumbered-address must not be defined simultaneously";
                 junos:must "(!(\".. address\"))";
                 junos:must-message "negotiate-address and address must not be defined simultaneously";
                 type empty;
               }
               leaf destination-udp-port {
                 description "Choose destination UDP port number";
                 junos:must "(\".. .. .. tunnel encapsulation udp\")";
                 junos:must-message "destination-udp-port can be configured only for encapsulation udp on fti interface";
                 type union {
                   type string {
                     pattern "<.*>|$.*";
                   }
                   type uint32 {
                     range "10000 .. 10009";
                   }
                 }
               }
               container auto-configure {
                 description "Auto configuration";
                 uses dynamic_ipv4_type;
               }
             }
             container iso {
               presence "enable iso";
               junos:must "(!(\".. .. encapsulation frame-relay-ppp\"))";
               junos:must-message "family iso is not supported on encapsulation frame-relay-ppp";
               description "OSI ISO protocol parameters";
               uses apply-advanced;
               list address {
                 key name;
                 ordered-by user;
                 description "Interface address";
                 leaf name {
                   description "Interface address";
                   junos:cli-feature "nokeyword";
                   type jt:isoaddr;
                 }
                 uses apply-advanced;
               }
               leaf mtu {
                 description "Protocol family maximum transmission unit";
                 type union {
                   type uint32;
                   type string {
                     pattern "<.*>|$.*";
                   }
                 }
               }
               leaf destination-udp-port {
                 description "Choose destination UDP port number";
                 junos:must "(\".. .. .. tunnel encapsulation udp\")";
                 junos:must-message "destination-udp-port can be configured only for encapsulation udp on fti interface";
                 type union {
                   type string {
                     pattern "<.*>|$.*";
                   }
                   type uint32 {
                     range "10030 .. 10039";
                   }
                 }
               }
             }
             container inet6 {
               presence "enable inet6";
               description "IPv6 protocol parameters";
               uses apply-advanced;
               leaf source-lookup {
                 description "Set source lookup flag";
                 junos:must "(!(\".. accouting source-class-usage\"))";
                 junos:must-message " Source lookup is not allowed with source-class-usage";
                 type empty;
               }
               container class-based-filtering {
                 description "Enable class based filter on interface";
                 uses apply-advanced;
               }
               container dhcpv6-client {
                 junos:must "(!(\"system services dhcp\"))";
                 junos:must-message "Incompatible with the dhcp server configured under 'system services dhcp'";
                 junos:must "(!(\"system autoinstallation\"))";
                 junos:must-message "Incompatible with 'system autoinstallation'";
                 junos:must "(!(\".. address\"))";
                 junos:must-message "Incompatible with interface assigned with address";
                 junos:must "(!(any \"forwarding-options dhcp-relay dhcpv6  group <*> interface ${interface}.${unit}\"))";
                 junos:must-message "DHCPv6 client and relay cannot be configured on the same interface ";
                 junos:must "(!(any \"system services dhcp-local-server dhcpv6 group <*> interface ${interface}.${unit}\"))";
                 junos:must-message "DHCPv6 client and server cannot be configured on the same interface ";
                 description "Dynamic Host Configuration Protocol DHCPv6 client configuration";
                 uses apply-advanced;
                 leaf client-type {
                   description "DHCPv6 client type";
                   type enumeration {
                     enum "stateful" {
                       description "Stateful client type for address assignment.";
                     }
                     enum "autoconfig" {
                       description "Autoconfig  client type for router-advertisement";
                       junos:must "(\"protocols router-advertisement interface ${interface}.${unit}\")";
                       junos:must-message "Interface for ra messages is must for auto mode";
                       junos:must "(!(\"interfaces ${interface} unit ${unit} family inet6 dhcpv6-client update-router-advertisement\"))";
                       junos:must-message "Incompatible with 'dhcpv6-client update-router-advertisement'";
                       junos:must "(!(\"interfaces ${interface} unit ${unit} family inet6 dhcpv6-client client-ia-type ia-pd\"))";
                       junos:must-message "Incompatible with 'client-ia-type ia-pd'";
                     }
                   }
                 }
                 list client-ia-type {
                   key name;
                   ordered-by user;
                   description "DHCPv6 client identity association type";
                   leaf name {
                     junos:cli-feature "nokeyword";
                     type enumeration {
                       enum "ia-na" {
                         description "Identity Association-Non-temporary Address";
                       }
                       enum "ia-pd" {
                         description "Identity Association-Prefix Address";
                       }
                     }
                   }
                   uses apply-advanced;
                 }
                 container rapid-commit {
                   presence "enable rapid-commit";
                   description "Option is used to signal the use of the two message exchange for address assignment";
                 }
                 leaf interface-identifier {
                   description "Identifier for this interface";
                   type jt:ipv6addr;
                 }
                 leaf use-ra-prefix {
                   description "Assign interface IP from RA prefix when ia-na address not received";
                   junos:must "(\"interfaces ${interface} unit ${unit} family inet6 dhcpv6-client client-ia-type ia-na\")";
                   junos:must-message "Incompatible with out 'client-ia-type ia-na'";
                   junos:must "(\"interfaces ${interface} unit ${unit} family inet6 dhcpv6-client client-type stateful\")";
                   junos:must-message "Incompatible with out 'client-type stateful'";
                   type empty;
                 }
                 container prefix-delegating {
                   junos:must "(\"interfaces ${interface} unit ${unit} family inet6 dhcpv6-client client-ia-type ia-pd\")";
                   junos:must-message "Incompatible with out 'client-ia-type ia-pd'";
                   description "Prefix delegating parameters";
                   uses apply-advanced;
                   leaf preferred-prefix-length {
                     description "Client preferred prefix length";
                     type union {
                       type string {
                         pattern "<.*>|$.*";
                       }
                       type uint32 {
                         range "0 .. 64";
                       }
                     }
                   }
                   leaf sub-prefix-length {
                     description "The sub prefix length for LAN interfaces";
                     type union {
                       type string {
                         pattern "<.*>|$.*";
                       }
                       type uint32 {
                         range "1 .. 127";
                       }
                     }
                   }
                 }
                 container client-identifier {
                   junos:cli-feature "oneliner";
                   description "DHCP Server identifies a client by client-identifier value ";
                   leaf duid-type {
                     description "DUID identifying a client";
                     type enumeration {
                       enum "duid-llt" {
                         description "Link-layer address plus time";
                       }
                       enum "vendor" {
                         description "Vendor-assigned unique ID based on Enterprise Number";
                       }
                       enum "duid-ll" {
                         description "Link-layer address";
                       }
                     }
                   }
                 }
                 leaf vendor-id {
                   description "Vendor class id for the dhcpv6 client";
                   type string {
                     length "1 .. 60";
                   }
                 }
                 list req-option {
                   key name;
                   ordered-by user;
                   description "DHCPV6 client requested option configuration";
                   leaf name {
                     junos:cli-feature "nokeyword";
                     type enumeration {
                       enum "dns-server" {
                         description "Dns-server option";
                       }
                       enum "domain" {
                         description "Dns-server option";
                       }
                       enum "ntp-server" {
                         description "Ntp-server option";
                       }
                       enum "time-zone" {
                         description "Time-zone option";
                       }
                       enum "sip-server" {
                         description "Sip-server option";
                       }
                       enum "sip-domain" {
                         description "Sip-domain option";
                       }
                       enum "nis-server" {
                         description "Nis-server option";
                       }
                       enum "nis-domain" {
                         description "Nis-domain option";
                       }
                       enum "fqdn" {
                         description "Fully-qualified-domain option";
                       }
                       enum "vendor-spec" {
                         description "Vendor-spec option";
                       }
                       enum "zero-touch-redirect" {
                         description "Zero-touch-redirect";
                       }
                       enum "bootfile-url" {
                         description "Bootfile url";
                       }
                       enum "bootfile-param" {
                         description "Bootfile param";
                       }
                     }
                   }
                   uses apply-advanced;
                 }
                 container options {
                   description "DHCP options";
                   uses apply-advanced;
                   list number {
                     key name;
                     junos:cli-feature "oneliner";
                     description "DHCP option code";
                     leaf name {
                       description "DHCP option identifier code";
                       junos:cli-feature "nokeyword";
                       type union {
                         type string {
                           pattern "<.*>|$.*";
                         }
                         type uint32 {
                           range "1 .. 254";
                         }
                       }
                     }
                     choice option-type-choice {
                       case case_1 {
                         leaf hex-string {
                           description "Hexadecimal string";
                           type string {
                             length "1 .. 510";
                             junos:posix-pattern "^[[:xdigit:]]+$";
                             junos:pattern-message "Must be hexadecimal digits (0-9, a-f, A-F)";
                           }
                         }
                       }
                     }
                   }
                 }
                 leaf retransmission-attempt {
                   description "Number of attempts to retransmit the DHCPV6 client protocol packet";
                   default "9";
                   type union {
                     type string {
                       pattern "<.*>|$.*";
                     }
                     type uint32 {
                       range "0 .. 50000";
                     }
                   }
                 }
                 container update-router-advertisement {
                   junos:must "(\"interfaces ${interface} unit ${unit} family inet6 dhcpv6-client client-ia-type $$={2}\")";
                   junos:must-message "Incompatible without 'client-ia-type ia-pd'";
                   description "Dhcpv6 client update rpd for prefix delegation";
                   uses apply-advanced;
                   list interface {
                     key name;
                     ordered-by user;
                     description "Interfaces on which to delegate prefix";
                     max-elements 3;
                     leaf name {
                       description "Interfaces-name on which to delegate prefix";
                       junos:cli-feature "nokeyword";
                       junos:must "(unique \"interfaces <*> unit 0 family inet6 dhcpv6-client update-router-advertisement interface $$\")";
                       junos:must-message "This interface is already updated by a dhcpv6-client";
                       junos:must "(!(\"protocols router-advertisement interface $$\"))";
                       junos:must-message "Incompatible with the interface configured under 'protocols router-advertisement interface'";
                       type union {
                         type jt:interface-name;
                         type string {
                           pattern "<.*>|$.*";
                         }
                       }
                     }
                     uses apply-advanced;
                     leaf interface-identifier {
                       description "Identifier for this interface";
                       type jt:ipv6addr;
                     }
                     leaf prefix-identifier {
                       description "Prefix identifier for prefix used in this interface";
                       type jt:ipv6addr;
                     }
                     choice managed-configuration-choice {
                       leaf managed-configuration {
                         description "Set managed address configuration";
                         type empty;
                       }
                       leaf no-managed-configuration {
                         description "Don't set managed address configuration";
                         type empty;
                       }
                     }
                     choice other-stateful-configuration-choice {
                       leaf other-stateful-configuration {
                         description "Set other stateful configuration";
                         type empty;
                       }
                       leaf no-other-stateful-configuration {
                         description "Don't set other stateful configuration";
                         type empty;
                       }
                     }
                     leaf max-advertisement-interval {
                       description "Maximum advertisement interval";
                       units "seconds";
                       type union {
                         type string {
                           pattern "<.*>|$.*";
                         }
                         type uint32 {
                           range "4 .. 1800";
                         }
                       }
                     }
                     leaf min-advertisement-interval {
                       description "Minimum advertisement interval";
                       units "seconds";
                       type union {
                         type string {
                           pattern "<.*>|$.*";
                         }
                         type uint32 {
                           range "3 .. 1350";
                         }
                       }
                     }
                     choice enable-recursive-dns-server-option-choice {
                       leaf enable-recursive-dns-server-option {
                         description "Enables the recursive DNS server option";
                         type empty;
                       }
                       leaf no-enable-recursive-dns-server-option {
                         description "Don't enables the recursive DNS server option";
                         type empty;
                       }
                     }
                   }
                 }
               }
               leaf mac-validate {
                 description "Validate source MAC address";
                 type enumeration {
                   enum "strict" {
                     description "Strict mac-validation";
                   }
                   enum "loose" {
                     description "Loose mac-validation";
                   }
                 }
               }
               container rpf-check {
                 presence "enable rpf-check";
                 junos:cli-feature "oneliner-plus";
                 description "Enable reverse-path-forwarding checks on this interface";
                 uses apply-advanced;
                 leaf fail-filter {
                   description "Name of filter applied to packets failing RPF check";
                   type string;
                 }
                 container mode {
                   junos:cli-feature "oneliner";
                   description "Mode for reverse path forwarding";
                   leaf loose {
                     description "Reverse-path-forwarding loose mode";
                     type empty;
                   }
                 }
               }
               container accounting {
                 description "Interface-based accounting options";
                 uses apply-advanced;
                 container source-class-usage {
                   junos:must "(!(\".. .. class-based-filtering source-class-usage\"))";
                   junos:must-message "source-class-usage is not allowed with class-based-filtering source-class-usage";
                   junos:must "(!(\".. .. source-lookup\"))";
                   junos:must-message " source-class-usage is not allowed with source-lookup";
                   uses apply-advanced;
                   leaf input {
                     description "Interface for source-class-usage input";
                     type empty;
                   }
                   leaf output {
                     description "Interface for source-class-usage output";
                     type empty;
                   }
                 }
                 leaf destination-class-usage {
                   description "Enable destination class usage on this interface";
                   junos:must "(!(\".. .. class-based-filtering destination-class-usage\"))";
                   junos:must-message "destination-class-usage is not allowed with class-based-filtering destination-class-usage";
                   type empty;
                 }
               }
               leaf mtu {
                 description "Protocol family maximum transmission unit";
                 type union {
                   type uint32;
                   type string {
                     pattern "<.*>|$.*";
                   }
                 }
               }
               leaf nd6-stale-time {
                 description "Stale time to reconfirm reachability with inet6 neighbour";
                 units "seconds";
                 type union {
                   type string {
                     pattern "<.*>|$.*";
                   }
                   type uint32 {
                     range "1 .. 18000";
                   }
                 }
               }
               leaf no-neighbor-learn {
                 description "Disable neighbor address learning on interface";
                 type empty;
               }
               container ndp-proxy {
                 description "Enable ndp proxy on interface";
                 uses apply-advanced;
                 leaf interface-restricted {
                   description "Enable ndp interface proxy restricted to interface";
                   junos:must "(!(\".. interface-unrestricted\"))";
                   junos:must-message "interface-restricted and interface-unrestricted are not allowed together";
                   type empty;
                 }
                 leaf interface-unrestricted {
                   description "Enable ndp interface proxy unrestricted to interface";
                   junos:must "(!(\".. interface-restricted\"))";
                   junos:must-message "interface-restricted and interface-unrestricted are not allowed together";
                   type empty;
                 }
               }
               container dad-proxy {
                 junos:must "(\".. ndp-proxy\")";
                 junos:must-message "ndp-proxy must be configured";
                 description "DAD proxy on interface";
                 uses apply-advanced;
                 leaf interface-restricted {
                   description "Enable DAD interface proxy restricted to interface";
                   junos:must "(!(\".. interface-unrestricted\"))";
                   junos:must-message "interface-restricted and interface-unrestricted are not allowed together";
                   junos:must "(\".. .. ndp-proxy interface-restricted\")";
                   junos:must-message "ndp-proxy interface-restricted must be configured to set this";
                   type empty;
                 }
                 leaf interface-unrestricted {
                   description "Enable DAD interface proxy unrestricted to interface";
                   junos:must "(!(\".. interface-restricted\"))";
                   junos:must-message "interface-restricted and interface-unrestricted are not allowed together";
                   junos:must "(\".. .. ndp-proxy interface-unrestricted\")";
                   junos:must-message "ndp-proxy interface-unrestricted must be configured to set this";
                   type empty;
                 }
               }
               leaf nd6-max-cache {
                 description "Max interface ND nexthop cache size";
                 type union {
                   type string {
                     pattern "<.*>|$.*";
                   }
                   type uint32 {
                     range "1 .. 2000000";
                   }
                 }
               }
               leaf nd6-new-hold-limit {
                 description "Max no. of new unresolved nexthops";
                 junos:must "(\".. nd6-max-cache\")";
                 junos:must-message "Interface max ND cache size must be configured";
                 type union {
                   type string {
                     pattern "<.*>|$.*";
                   }
                   type uint32 {
                     range "1 .. 2000000";
                   }
                 }
               }
               leaf no-redirects {
                 description "Do not redirect traffic";
                 type empty;
               }
               container filter {
                 description "Packet filtering";
                 uses apply-advanced;
                 choice input_choice {
                   case case_1 {
                     container input {
                       junos:cli-feature "oneliner";
                       description "Filter to be applied to received packets";
                       leaf filter-name {
                         description "Name of the filter";
                         junos:cli-feature "nokeyword";
                         junos:must "((!(\".. .. .. rpf-check\") || (!(any \"firewall family inet6 filter $$ term <*> from first-byte-of-payload\") && !(any \"firewall family inet6 filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 choice output_choice {
                   case case_1 {
                     container output {
                       junos:cli-feature "oneliner";
                       description "Filter to be applied to transmitted packets";
                       leaf filter-name {
                         description "Name of the filter";
                         junos:cli-feature "nokeyword";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 leaf-list input-chain {
                   ordered-by user;
                   description "List of filter modules applied to received packets ";
                   type string;
                 }
                 leaf-list output-chain {
                   ordered-by user;
                   description "List of filter modules applied to transmitted packets ";
                   type string;
                 }
                 container adf {
                   description "Ascend Data Filter definition";
                   uses apply-advanced;
                   list rule {
                     key name;
                     ordered-by user;
                     description "Set of ADF rules";
                     leaf name {
                       description "Value for a single rule";
                       junos:cli-feature "nokeyword";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32;
                   }
                 }
               }
               container policer {
                 description "Interface policing";
                 uses apply-advanced;
                 leaf input {
                   description "Name of policer applied to received packets";
                   type string;
                 }
                 leaf output {
                   description "Name of policer applied to transmitted packets";
                   type string;
                 }
               }
               container sampling {
                 junos:must "((\"forwarding-options sampling family inet6\" || (\"forwarding-options packet-capture\" || any \"forwarding-options sampling instance <*> family inet6\")))";
                 junos:must-message "Requires forwarding-options sampling or packet-capture config";
                 description "Interface sampling";
                 uses apply-advanced;
                 leaf input {
                   description "Sample all packets input on this interface";
                   type empty;
                 }
                 leaf output {
                   description "Sample all packets output on this interface";
                   type empty;
                 }
               }
               choice tunnel-termination-status {
                 case case_1 {
                   leaf tunnel-termination {
                     description "Tunnel termination";
                     type empty;
                   }
                 }
                 case case_2 {
                   leaf no-tunnel-termination {
                     description "No Tunnel termination";
                     type empty;
                   }
                 }
               }
               list address {
                 key name;
                 ordered-by user;
                 description "Interface address or destination prefix";
                 junos:must "(!(\".. unnumbered-address\"))";
                 junos:must-message "ipv6 unnumbered-address and ipv6 address must not be defined simultaneously";
                 leaf name {
                   description "Interface address or destination prefix";
                   junos:cli-feature "nokeyword";
                   type jt:ipv6prefix;
                 }
                 uses apply-advanced;
                 leaf destination {
                   description "Destination address";
                   type jt:ipv6addr;
                 }
                 leaf eui-64 {
                   description "Generate EUI-64 interface ID";
                   type empty;
                 }
                 leaf primary {
                   description "Candidate for primary address in system";
                   type empty;
                 }
                 leaf preferred {
                   description "Preferred address on interface";
                   type empty;
                 }
                 leaf master-only {
                   description "Master management IP address for router";
                   type empty;
                 }
                 container tag {
                   description "Tag used for route/local";
                   uses apply-advanced;
                   leaf tag-value {
                     description "The tag value on the address";
                     junos:cli-feature "nokeyword";
                     type union {
                       type string {
                         pattern "<.*>|$.*";
                       }
                       type uint32 {
                         range "1 .. 4294967295";
                       }
                     }
                   }
                   leaf type {
                     description "Tag type must be [1-16]";
                     type union {
                       type string {
                         pattern "<.*>|$.*";
                       }
                       type uint32 {
                         range "1 .. 16";
                       }
                     }
                   }
                 }
                 container tag2 {
                   description "Tag2 used for route/local";
                   uses apply-advanced;
                   leaf tag2-value {
                     description "The tag value on the address";
                     junos:cli-feature "nokeyword";
                     type union {
                       type string {
                         pattern "<.*>|$.*";
                       }
                       type uint32 {
                         range "1 .. 4294967295";
                       }
                     }
                   }
                   leaf type {
                     description "Tag type must be [1-16]";
                     type union {
                       type string {
                         pattern "<.*>|$.*";
                       }
                       type uint32 {
                         range "1 .. 16";
                       }
                     }
                   }
                 }
                 list ndp {
                   key name;
                   ordered-by user;
                   junos:cli-feature "oneliner";
                   description "Static Neighbor Discovery Protocol  entries";
                   leaf name {
                     description "Destination IP address";
                     junos:cli-feature "nokeyword";
                     type jt:ipv6addr;
                   }
                   leaf l2-interface {
                     description "Layer 2 interface name for NDP entry";
                     type union {
                       type jt:interface-name;
                       type string {
                         pattern "<.*>|$.*";
                       }
                     }
                   }
                   choice mac_address_type {
                     case case_1 {
                       leaf mac {
                         description "MAC address";
                         type jt:mac-unicast;
                       }
                     }
                     case case_2 {
                       leaf multicast-mac {
                         description "Multicast MAC address";
                         type jt:mac-multicast;
                       }
                     }
                   }
                   leaf publish {
                     description "Reply to NDP requests for this entry";
                     junos:must "((\".. mac\" || \".. multicast-mac\"))";
                     junos:must-message "either 'mac' or 'multicast-mac' must be configured along with 'publish' statment";
                     type empty;
                   }
                 }
                 list host-discovery {
                   key name;
                   ordered-by user;
                   junos:cli-feature "oneliner";
                   description "Discover servers IP based on subnet range";
                   junos:must "(\"system arp proactive-arp-detection\")";
                   junos:must-message "Proactive ARP detection feature should be enabled";
                   max-elements 8;
                   leaf name {
                     description "IPv6 address subnet range";
                     junos:cli-feature "nokeyword";
                     type jt:ipv6prefix;
                   }
                   leaf aging-timer {
                     description "Neighbor solicitation stale timer";
                     type union {
                       type string {
                         pattern "<.*>|$.*";
                       }
                       type uint32 {
                         range "100 .. 1200";
                       }
                     }
                   }
                   leaf discovery-interval {
                     description "Neighbor proactive discovery time";
                     type union {
                       type string {
                         pattern "<.*>|$.*";
                       }
                       type uint32 {
                         range "3 .. 300";
                       }
                     }
                   }
                 }
                 list vrrp-inet6-group {
                   key name;
                   ordered-by user;
                   description "VRRP group";
                   junos:must "(!(\".. eui-64\"))";
                   junos:must-message "'vrrp-inet6-group' is not supported when 'eui-64' is configured";
                   uses vrrp-group;
                 }
                 leaf virtual-gateway-address {
                   description "Virtual Gateway IP address";
                   junos:must "(!(\".. vrrp-inet6-group\"))";
                   junos:must-message "vrrp configuration incompatible with virtual gateway address";
                   type jt:ipv6addr;
                 }
                 leaf subnet-router-anycast {
                   description "Create a subnet roter anycast address for this address.";
                   type empty;
                 }
               }
               container unnumbered-address {
                 junos:cli-feature "oneliner";
                 description "Unnumbered interface address/destination prefix";
                 leaf source {
                   description "Interface from which to take local address";
                   junos:cli-feature "nokeyword";
                   junos:must "(\"interfaces $$-IFL family inet6 address\")";
                   junos:must-message "referred interface must have address configured under family inet6";
                   type union {
                     type jt:interface-unit;
                     type string {
                       pattern "<.*>|$.*";
                     }
                   }
                 }
                 leaf preferred-source-address {
                   description "Preferred address on the donor interface";
                   type string;
                 }
               }
               choice dad-disable-choice {
                 leaf dad-disable {
                   description "Disable duplicate-address-detection";
                   type empty;
                 }
                 leaf no-dad-disable {
                   description "Don't disable duplicate-address-detection";
                   type empty;
                 }
               }
               leaf destination-udp-port {
                 description "Choose destination UDP port number";
                 junos:must "(\".. .. .. tunnel encapsulation udp\")";
                 junos:must-message "destination-udp-port can be configured only for encapsulation udp on fti interface";
                 type union {
                   type string {
                     pattern "<.*>|$.*";
                   }
                   type uint32 {
                     range "10010 .. 10019";
                   }
                 }
               }
               leaf enhanced-dad-disable {
                 description "Disable Enhanced DAD while send NS with Nonce option";
                 type empty;
               }
               container auto-configure {
                 description "Auto configuration";
                 uses dynamic_ipv6_type;
               }
             }
             container mpls {
               presence "enable mpls";
               junos:must "(!(\".. .. encapsulation frame-relay-ppp\"))";
               junos:must-message "family mpls is not supported on encapsulation frame-relay-ppp";
               description "MPLS protocol parameters";
               uses apply-advanced;
               leaf mtu {
                 description "Protocol family maximum transmission unit";
                 type union {
                   type uint32;
                   type string {
                     pattern "<.*>|$.*";
                   }
                 }
               }
               leaf maximum-labels {
                 description "Protocol family maximum number of labels";
                 type union {
                   type string {
                     pattern "<.*>|$.*";
                   }
                   type uint32;
                 }
               }
               container filter {
                 description "Packet filtering";
                 uses apply-advanced;
                 choice input_choice {
                   case case_1 {
                     leaf input {
                       description "Name of filter applied to received packets";
                       type string;
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 choice output_choice {
                   case case_1 {
                     leaf output {
                       description "Name of filter applied to transmitted packets";
                       type string;
                     }
                   }
                   case case_2 {
                     leaf-list output-list {
                       ordered-by user;
                       description "List of filter modules applied to transmitted packets ";
                       type string;
                     }
                   }
                 }
                 leaf-list output-chain {
                   ordered-by user;
                   description "List of filter modules applied to transmitted packets ";
                   type string;
                 }
                 leaf group {
                   description "Interface group to which interface belongs";
                   type union {
                     type string {
                       pattern "<.*>|$.*";
                     }
                     type uint32 {
                       range "1 .. 255";
                     }
                   }
                 }
               }
               container ingress-queuing-filter {
                 junos:cli-feature "oneliner";
                 description "Protocol family ingress-queuing-filter";
                 leaf filter-name {
                   description "Name of the ingress-queuing-filter";
                   junos:cli-feature "nokeyword";
                   type string;
                 }
               }
               container policer {
                 description "Interface policing";
                 uses apply-advanced;
                 leaf input {
                   description "Name of policer applied to received packets";
                   type string;
                 }
                 leaf output {
                   description "Name of policer applied to transmitted packets";
                   type string;
                 }
               }
               leaf destination-udp-port {
                 description "Choose destination UDP port number";
                 junos:must "(\".. .. .. tunnel encapsulation udp\")";
                 junos:must-message "destination-udp-port can be configured only for encapsulation udp on fti interface";
                 type union {
                   type string {
                     pattern "<.*>|$.*";
                   }
                   type uint32 {
                     range "10020 .. 10029";
                   }
                 }
               }
             }
             container mlppp {
               junos:must "(!(\"interfaces ${interface} container-options\"))";
               junos:must-message "mlppp is not supported for container interfaces";
               description "Multilink PPP protocol parameters";
               uses apply-advanced;
               leaf bundle {
                 description "Logical interface name this link will join";
                 junos:must "((!(\".. .. .. dial-options\") || \"interfaces $$-IFL encapsulation multilink-ppp\"))";
                 junos:must-message "Bundle interface must be configured";
                 junos:must "((!(\".. .. .. pppoe-options\") || \"interfaces $$-IFL encapsulation multilink-ppp\"))";
                 junos:must-message "Bundle interface must be configured";
                 type string;
               }
               choice anchor-points {
                 case case_1 {
                 }
                 case case_2 {
                 }
               }
               leaf dynamic-profile {
                 description " dynamic profile for interface to use";
                 junos:must "(\"dynamic-profiles $$\")";
                 junos:must-message "referenced dynamic-profile must be defined";
                 type string {
                   length "1 .. 80";
                 }
               }
             }
             container mlfr-end-to-end {
               presence "enable mlfr-end-to-end";
               junos:must "(!(\".. .. encapsulation frame-relay-ppp\"))";
               junos:must-message "family mlfr-end-to-end is not supported on encapsulation frame-relay-ppp";
               description "Multilink Frame Relay end-to-end protocol parameters";
               uses apply-advanced;
               leaf bundle {
                 description "Logical interface name this link will join";
                 type union {
                   type jt:interface-unit;
                   type string {
                     pattern "<.*>|$.*";
                   }
                 }
               }
             }
             container mlfr-uni-nni {
               presence "enable mlfr-uni-nni";
               junos:must "(!(\".. .. encapsulation frame-relay-ppp\"))";
               junos:must-message "family mlfr-uni-uni is not supported on encapsulation frame-relay-ppp";
               description "Multilink Frame Relay UNI NNI protocol parameters";
               uses apply-advanced;
               leaf bundle {
                 description "Logical interface name this link will join";
                 type union {
                   type jt:interface-unit;
                   type string {
                     pattern "<.*>|$.*";
                   }
                 }
               }
             }
             container ccc {
               presence "enable ccc";
               junos:must "(!(\".. .. encapsulation frame-relay-ppp\"))";
               junos:must-message "family ccc is not supported on encapsulation frame-relay-ppp";
               description "Circuit cross-connect parameters";
               uses apply-advanced;
               container filter {
                 description "Packet filtering";
                 uses apply-advanced;
                 choice input_choice {
                   case case_1 {
                     leaf input {
                       description "Name of filter applied to received packets";
                       type string;
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 choice output_choice {
                   case case_1 {
                     leaf output {
                       description "Name of filter applied to transmitted packets";
                       type string;
                     }
                   }
                   case case_2 {
                     leaf-list output-list {
                       ordered-by user;
                       description "List of filter modules applied to transmitted packets ";
                       type string;
                     }
                   }
                 }
                 leaf-list output-chain {
                   ordered-by user;
                   description "List of filter modules applied to transmitted packets ";
                   type string;
                 }
                 leaf group {
                   description "Interface group to which interface belongs";
                   type union {
                     type string {
                       pattern "<.*>|$.*";
                     }
                     type uint32 {
                       range "1 .. 255";
                     }
                   }
                 }
               }
               container policer {
                 description "Interface policing";
                 uses apply-advanced;
                 leaf input {
                   description "Name of policer applied to received packets";
                   type string;
                 }
                 leaf output {
                   description "Name of policer applied to transmitted packets";
                   type string;
                 }
               }
               leaf translate-fecn-and-becn {
                 description "Translate FECN and BECN bits";
                 type empty;
               }
               choice de-or-plp {
                 case case_1 {
                   leaf translate-discard-eligible {
                     description "Translate DE bit";
                     type empty;
                   }
                 }
                 case case_2 {
                 }
               }
               leaf keep-address-and-control {
                 description "Don't strip PPP address and control bytes";
                 type empty;
               }
             }
             container tcc {
               presence "enable tcc";
               junos:must "(!(\".. .. encapsulation frame-relay-ppp\"))";
               junos:must-message "family tcc is not supported on encapsulation frame-relay-ppp";
               description "Translational cross-connect parameters";
               uses apply-advanced;
               container policer {
                 description "Interface policing";
                 uses apply-advanced;
                 leaf input {
                   description "Name of policer applied to received packets";
                   type string;
                 }
                 leaf output {
                   description "Name of policer applied to transmitted packets";
                   type string;
                 }
               }
               container proxy {
                 presence "enable proxy";
                 uses apply-advanced;
                 leaf inet-address {
                   description "Remote host address on non-Ethernet side of Ethernet TCC";
                   type jt:ipv4addr;
                 }
               }
               container remote {
                 presence "enable remote";
                 uses apply-advanced;
                 leaf inet-address {
                   description "Remote host address on Ethernet side of Ethernet TCC";
                   type jt:ipv4addr;
                 }
                 leaf mac-address {
                   description "Remote host MAC address on Ethernet side of Ethernet TCC";
                   type jt:mac-addr;
                 }
               }
               leaf-list protocols {
                 ordered-by user;
                 description "Protocols supported on TCC interface";
                 type enumeration {
                   enum "mpls" {
                     description "Multiprotocol Label Switching";
                   }
                   enum "inet" {
                     description "IP version 4";
                   }
                   enum "iso" {
                     description "International Organization for Standardization";
                   }
                   enum "inet6" {
                     description "IP version 6";
                   }
                 }
               }
             }
             container vpls {
               presence "enable vpls";
               description "Virtual private LAN service parameters";
               uses apply-advanced;
               leaf core-facing {
                 description "Interface is core facing";
                 type empty;
               }
               container filter {
                 description "Packet filtering";
                 uses apply-advanced;
                 choice input_choice {
                   case case_1 {
                     container input {
                       junos:cli-feature "oneliner";
                       description "Filter to be applied to received packets";
                       leaf filter-name {
                         description "Name of the filter";
                         junos:cli-feature "nokeyword";
                         junos:must "((!(\".. .. .. rpf-check\") || (!(any \"firewall family inet filter $$ term <*> from first-byte-of-payload\") && !(any \"firewall family inet filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 leaf-list output-chain {
                   ordered-by user;
                   description "List of filter modules applied to transmitted packets ";
                   type string;
                 }
                 choice output_choice {
                   case case_1 {
                     container output {
                       junos:cli-feature "oneliner";
                       description "Filter to be applied to transmitted packets";
                       leaf filter-name {
                         description "Name of the filter";
                         junos:cli-feature "nokeyword";
                         junos:must "((!(\".. .. .. rpf-check\") || (!(any \"firewall family inet filter $$ term <*> from first-byte-of-payload\") && !(any \"firewall family inet filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       junos:cli-feature "nokeyword";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32 {
                       range "1 .. 255";
                     }
                   }
                 }
               }
               container policer {
                 description "Interface policing";
                 uses apply-advanced;
                 leaf input {
                   description "Name of policer applied to received packets";
                   type string;
                 }
                 leaf output {
                   description "Name of policer applied to transmitted packets";
                   type string;
                 }
               }
             }
             container ethernet-switching {
               description "Ethernet switching parameters";
               presence "enable ethernet-switching";
               junos:must "((!(\".. vpls\") && (!(\".. inet\") && (!(\".. inet6\") && (!(\".. bridge\") && (!(\".. ccc\") && (!(\".. iso\") && (!(\".. llc2\") && (!(\".. mpls\") && (!(\".. tcc\") && (!(\".. pppoe\") && !(\".. gre\"))))))))))))";
               junos:must-message "Family ethernet-switching and rest of the families are mutually exclusive";
               uses ethernet-switching-type;
             }
             container fibre-channel {
               description "Fibre channel switching parameters";
               presence "enable fibre-channel";
               uses fibre-channel-type;
             }
             container any {
               presence "enable any";
               description "Parameters for 'any' family";
               uses apply-advanced;
               container filter {
                 description "Layer 2 packet filtering";
                 uses apply-advanced;
                 leaf input {
                   description "Name of filter applied to received packets";
                   junos:must "((\"firewall family any filter $$\" || (!(\"firewall\") && \".. .. .. .. .. .. firewall family any filter $$\")))";
                   junos:must-message "referenced filter must be defined under firewall family any";
                   type string {
                     junos:posix-pattern "!^((__.*)|(.{65,}))$";
                     junos:pattern-message "Must be a non-reserved string of 64 characters or less";
                   }
                 }
                 leaf group {
                   description "Group to which interface belongs";
                   type union {
                     type string {
                       pattern "<.*>|$.*";
                     }
                     type uint32 {
                       range "1 .. 255";
                     }
                   }
                 }
               }
             }
             uses apply-advanced;
           }
           leaf service-domain {
             description "Service domain to which interface belongs";
             type enumeration {
               enum "inside" {
                 description "Inside network";
               }
               enum "outside" {
                 description "Outside network";
               }
             }
           }
           leaf copy-tos-to-outer-ip-header {
             description "Copy IP payload header's ToS field to GRE delivery header";
             type empty;
           }
           container load-balancing-options {
             junos:must "(!(\".. .. load-balancing-options high-availability-options one-to-one\"))";
             junos:must-message "load-balancing-options are used when number of active members is more than one";
             description "AMS subunit load balancing options";
             uses apply-advanced;
             leaf preferred-active {
               description "Preferred active Interface name";
               junos:must "((\".. .. .. load-balancing-options member-interface $$\" && !(\".. .. .. load-balancing-options high-availability-options many-to-one preferred-backup $$\")))";
               junos:must-message "Active should be one of member-interfaces excluding preferred-backup";
               type union {
                 type jt:interface-device;
                 type string {
                   pattern "<.*>|$.*";
                 }
               }
             }
             leaf disable-hash {
               description "Hash based distribution is not needed for this subunit";
               junos:must "(\".. .. service-domain\")";
               junos:must-message "service-domain must be configured if disable-hash is enabled";
               junos:must "(!(\".. hash-keys\"))";
               junos:must-message "hash-keys must not be configured if disable-hash is enabled";
               type empty;
             }
             leaf modulo-key {
               description "Modulo based distribution";
               junos:must "(!(\".. .. .. load-balancing-options member-failure-options redistribute-all-traffic\"))";
               junos:must-message "redistribute-all-traffic can not be configured with modulo-key";
               junos:must "(!(\".. disable-hash\"))";
               junos:must-message "disable-hash can not be configured with modulo-key";
               junos:must "(\".. .. service-domain\")";
               junos:must-message "service-domain must be configured with modulo-key";
               junos:must "(!(\".. hash-keys\"))";
               junos:must-message "hash-keys can not be configured with modulo-key";
               type enumeration {
                 enum "source-ip" {
                   description "Source Ip Address";
                 }
                 enum "destination-ip" {
                   description "Destination Ip Address";
                 }
               }
             }
             container hash-keys {
               uses apply-advanced;
               leaf-list ingress-key {
                 ordered-by user;
                 description "Hash Key for the ingress direction";
                 type enumeration {
                   enum "source-ip" {
                     description "Source Ip Address";
                   }
                   enum "destination-ip" {
                     description "Destination Ip Address";
                   }
                   enum "protocol" {
                     description "Protocol";
                   }
                   enum "iif" {
                     description "Incoming Interface";
                   }
                 }
               }
               leaf-list egress-key {
                 ordered-by user;
                 description "Hash Key for the egress direction";
                 status deprecated;
                 type enumeration {
                   enum "source-ip" {
                     description "Source Ip Address";
                     status deprecated;
                   }
                   enum "destination-ip" {
                     description "Destination Ip Address";
                     status deprecated;
                   }
                   enum "protocol" {
                     description "Protocol";
                     status deprecated;
                   }
                   enum "oif" {
                     description "Outgoing Interface";
                     status deprecated;
                   }
                 }
               }
               leaf ipv6-source-prefix-length {
                 description "IPv6 source prefix length for hash computation";
                 type enumeration {
                   enum "56" {
                     description "56 bit IPv6 address prefix";
                   }
                   enum "64" {
                     description "64 bit IPv6 address prefix";
                   }
                   enum "96" {
                     description "96 bit IPv6 address prefix";
                   }
                   enum "128" {
                     description "Complete 128 bit IPv6 address";
                   }
                 }
               }
             }
           }
           container interface-state {
             description "IRB interface state computation";
             uses apply-advanced;
             choice state {
               case case_1 {
                 leaf local {
                   description "IRB State computation based on local interface state";
                   type empty;
                 }
               }
               case case_2 {
                 leaf remote {
                   description "IRB State computation based on remote reachability";
                   type empty;
                 }
               }
               case case_3 {
                 leaf local-remote {
                   description "IRB State computation based on local or remote reachability";
                   type empty;
                 }
               }
               case case_4 {
                 leaf local-interface {
                   description "IRB State computation based on loopback AE port state";
                   type union {
                     type jt:interface-name;
                     type string {
                       pattern "<.*>|$.*";
                     }
                   }
                 }
               }
             }
             leaf local-count {
               description "Minimum number of local layer2 link in up state to consider IRB up";
               junos:must "(!(\".. remote\"))";
               junos:must-message "Must configure local, local-remote or keep default";
               type union {
                 type uint16;
                 type string {
                   pattern "<.*>|$.*";
                 }
               }
             }
             leaf vtep-count {
               description "Minimum number of VTEP link in up state to consider IRB up";
               junos:must "(!(\".. local\"))";
               junos:must-message "Must configure remote,local-remote or keep default";
               type union {
                 type uint16;
                 type string {
                   pattern "<.*>|$.*";
                 }
               }
             }
             container hold-time {
               description "Delay before marking interface up or down for defect";
               uses apply-advanced;
               leaf up {
                 description "Delay in seconds before marking IRB interface up";
                 units "seconds";
                 type union {
                   type uint32;
                   type string {
                     pattern "<.*>|$.*";
                   }
                 }
               }
               leaf down {
                 description "Delay in seconds before marking IRB interface down";
                 units "seconds";
                 type union {
                   type uint32;
                   type string {
                     pattern "<.*>|$.*";
                   }
                 }
               }
             }
           }
           leaf mac {
             description "Configure logical interface MAC address";
             type jt:mac-unicast;
           }
           leaf virtual-gateway-v4-mac {
             description "Configure virtual gateway IPV4 virtual MAC address";
             type jt:mac-unicast;
           }
           leaf virtual-gateway-v6-mac {
             description "Configure virtual gateway IPV6 virtual MAC address";
             type jt:mac-unicast;
           }
           leaf no-dhcp-flood {
             description "Disable dhcp flooding";
             type empty;
           }
           leaf etree-ac-role {
             description "ETREE attachment circuit role";
             type enumeration {
               enum "root" {
                 description "ETREE root interface";
               }
               enum "leaf" {
                 description "ETREE leaf interface";
               }
             }
           }
         }
         container no-partition {
           junos:cli-feature "oneliner";
           description "Use channelizable interface as clear channel";
           leaf interface-type {
             description "Interface type";
             type enumeration {
               enum "e1" {
                 description "E1 interface";
               }
               enum "t1" {
                 description "T1 interface";
               }
               enum "at" {
                 description "ATM interface";
               }
               enum "t3" {
                 description "T3 interface";
               }
               enum "e3" {
                 description "E3 interface";
               }
               enum "ct3" {
                 description "Channelized T3 interface";
               }
               enum "so" {
                 description "SONET interface";
               }
               enum "cau4" {
                 description "CAU4 interface";
               }
             }
           }
         }
         list partition {
           key name;
           ordered-by user;
           junos:cli-feature "oneliner";
           description "Channelized interface partition";
           junos:must "(!(\".. no-partition\"))";
           junos:must-message "cannot set partitions with no-partition attribute turned on";
           leaf name {
             description "Sublevel interface partition index (for example, 1, 3-4)";
             junos:cli-feature "nokeyword";
             type string;
           }
           leaf oc-slice {
             description "Range of SONET/SDH slices (for example, 1, 7-9)";
             type string;
           }
           leaf timeslots {
             description "Timeslots [(1..24) for T1, (1..31) for E1]; for example, 1-3,4,9,22-24 (no spaces)";
             type string;
           }
           leaf interface-type {
             description "Sublevel interface type";
             type enumeration {
               enum "ds" {
                 description "DS0 interface";
               }
               enum "e1" {
                 description "E1 interface";
               }
               enum "t1" {
                 description "T1 interface";
               }
               enum "at" {
                 description "ATM interface";
               }
               enum "ct1" {
                 description "Channelized T1 interface";
               }
               enum "ce1" {
                 description "Channelized E1 interface";
               }
               enum "t3" {
                 description "T3 interface";
               }
               enum "ct3" {
                 description "Channelized T3 interface";
               }
               enum "e3" {
                 description "E3 interface";
               }
               enum "so" {
                 description "SONET interface";
               }
               enum "coc1" {
                 description "Channelized OC1 interface";
               }
               enum "cau4" {
                 description "Channelized AU4 interface";
               }
               enum "dc" {
                 description "D channel interface";
                 junos:must "(any \".. .. partition <*> interface-type bc\")";
                 junos:must-message "BC partition must be defined for PRI";
               }
               enum "bc" {
                 description "B channel interface";
                 junos:must "(any \".. .. partition <*> interface-type dc\")";
                 junos:must-message "DC partition must be defined for PRI";
               }
             }
           }
         }
       }
       list interface {
         key name;
         uses interfaces_type;
         junos:cli-feature "nokeyword";
         junos:cli-feature "homogeneous";
       }
     }
     container protocols {
       description "Routing protocol configuration";
       uses apply-advanced;
       container igmp {
         presence "enable igmp";
         description "IGMP options";
         uses apply-advanced;
         leaf protocol-instance-name {
           description "Name of protocol instance under routing instance";
           type string;
         }
         container traceoptions {
           description "Trace options for IGMP";
           uses apply-advanced;
           container file {
             junos:cli-feature "oneliner";
             description "Trace file options";
             leaf filename {
               description "Name of file in which to write trace information";
               junos:cli-feature "nokeyword";
               type string {
                 length "1 .. 1024";
                 junos:posix-pattern "![/ %]";
                 junos:pattern-message "Must not contain \'/\', % or a space";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             junos:cli-feature "oneliner";
             description "Tracing parameters";
             leaf name {
               junos:cli-feature "nokeyword";
               type enumeration {
                 enum "packets" {
                   description "Trace all IGMP packets";
                 }
                 enum "query" {
                   description "Trace IGMP membership query messages";
                 }
                 enum "report" {
                   description "Trace membership report messages";
                 }
                 enum "leave" {
                   description "Trace leave group messages (IGMPv2 only)";
                 }
                 enum "mtrace" {
                   description "Trace mtrace packets";
                 }
                 enum "group" {
                   description "Trace group operations";
                 }
                 enum "client-notification" {
                   description "Trace notifications";
                 }
                 enum "host-notification" {
                   description "Trace host notifications";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
             junos:posix-pattern "^[0-9]{1,4}(.[0-9])?$";
             junos:pattern-message "Up to 1 digit to right of decimal point";
           }
         }
         leaf query-last-member-interval {
           description "When to send group query messages";
           units "seconds";
           type string {
             junos:posix-pattern "^[0-9]{1,4}(.[0-9])?$";
             junos:pattern-message "Up to 1 digit to right of decimal point";
           }
         }
         leaf robust-count {
           description "Expected packet loss on a subnet";
           type union {
             type string {
               pattern "<.*>|$.*";
             }
             type uint32 {
               range "2 .. 10";
             }
           }
         }
         leaf maximum-transmit-rate {
           description "Maximum transmission rate (packets per second)";
           type union {
             type string {
               pattern "<.*>|$.*";
             }
             type uint32 {
               range "1 .. 10000";
             }
           }
         }
         leaf accounting {
           description "Enable join and leave event notification";
           type empty;
         }
         list interface {
           key name;
           ordered-by user;
           description "Interface options for IGMP";
           leaf name {
             junos:cli-feature "nokeyword";
             type string;
           }
           uses apply-advanced;
           choice enable-disable {
             case case_1 {
               leaf disable {
                 description "Disable IGMP on this interface";
                 type empty;
               }
             }
           }
           leaf version {
             description "Set IGMP version number on this interface";
             type union {
               type string {
                 pattern "<.*>|$.*";
               }
               type uint8 {
                 range "1 .. 3";
               }
             }
           }
           container static {
             description "Static group or source membership";
             uses apply-advanced;
             list group {
               key name;
               ordered-by user;
               description "IP multicast group address";
               leaf name {
                 description "IP multicast group address";
                 junos:cli-feature "nokeyword";
                 type jt:ipv4addr;
               }
               uses apply-advanced;
               leaf group-increment {
                 description "Mask for the incrementing group IP address";
                 type jt:ipv4addr;
               }
               leaf group-count {
                 description "Number of groups";
                 type union {
                   type string {
                     pattern "<.*>|$.*";
                   }
                   type uint32 {
                     range "1 .. 512";
                   }
                 }
               }
               leaf exclude {
                 description "Exclude sources";
                 type empty;
               }
               list source {
                 key name;
                 ordered-by user;
                 description "IP multicast source address";
                 leaf name {
                   description "Source address of IP multicast data";
                   junos:cli-feature "nokeyword";
                   type jt:ipv4addr;
                 }
                 uses apply-advanced;
                 leaf source-increment {
                   description "Mask for the incrementing source IP address";
                   type jt:ipv4addr;
                 }
                 leaf source-count {
                   description "Number of sources";
                   type union {
                     type string {
                       pattern "<.*>|$.*";
                     }
                     type uint32 {
                       range "1 .. 1024";
                     }
                   }
                 }
               }
             }
           }
           leaf ssm-map {
             description "Map for SSM translation of IGMPv1 or IGMPv2 messages";
             type string;
           }
           leaf-list ssm-map-policy {
             ordered-by user;
             description "SSM map policy name";
             type jt:policy-algebra;
           }
           leaf immediate-leave {
             description "Group removed immediately, last membership query not sent";
             type empty;
           }
           leaf promiscuous-mode {
             description "Accept igmp messages coming from different subnet";
             type empty;
           }
           choice accounting-choice {
             leaf accounting {
               description "Enable join and leave event notification";
               type empty;
             }
             leaf no-accounting {
               description "Don't enable join and leave event notification";
               type empty;
             }
           }
           leaf-list group-policy {
             ordered-by user;
             description "Group filter applied to incoming IGMP report messages";
             type jt:policy-algebra;
           }
           leaf group-limit {
             description "Maximum number of (source,group) per interface";
             type union {
               type string {
                 pattern "<.*>|$.*";
               }
               type uint16 {
                 range "1 .. 32767";
               }
             }
           }
           leaf group-threshold {
             description "Percentage of limit at which to generate warnings";
             junos:must "(\" .. group-limit\")";
             junos:must-message "To configure group-threshold, group-limit must be set";
             type union {
               type string {
                 pattern "<.*>|$.*";
               }
               type uint32 {
                 range "1 .. 100";
               }
             }
           }
           leaf log-interval {
             description "Time between consecutive log messages";
             junos:must "(\" .. group-limit\")";
             junos:must-message "To configure log-interval, group-limit must be set";
             type union {
               type string {
                 pattern "<.*>|$.*";
               }
               type uint32 {
                 range "6 .. 32767";
               }
             }
           }
           container passive {
             presence "enable passive";
             junos:cli-feature "oneliner";
             description "Suppress sending and receiving IGMP messages";
             leaf allow-receive {
               description "Allow receiving IGMP messages";
               type empty;
             }
             leaf send-general-query {
               description "Send IGMP general query messages";
               type empty;
             }
             leaf send-group-query {
               description "Send IGMP group query messages";
               type empty;
             }
           }
           leaf-list oif-map {
             ordered-by user;
             description "Output interface map";
             type jt:policy-algebra;
           }
           leaf distributed {
             description "Distributed IGMP interface";
             junos:must "(\"chassis network-services enhanced-ip\")";
             junos:must-message "distributed is supported only in enhanced-ip mode";
             type empty;
           }
         }
         container amt {
           description "Automatic Multicast Tunnel options for IGMP";
           uses apply-advanced;
           container relay {
             description "AMT relay options for IGMP";
             uses apply-advanced;
             container defaults {
               presence "enable defaults";
               description "Default AMT relay options for IGMP";
               uses apply-advanced;
               leaf version {
                 description "Set IGMP version number on AMT interfaces";
                 type union {
                   type string {
                     pattern "<.*>|$.*";
                   }
                   type uint8 {
                     range "1 .. 3";
                   }
                 }
               }
               leaf ssm-map {
                 description "Map for SSM translation of IGMPv1 or IGMPv2 messages";
                 type string;
               }
               leaf-list ssm-map-policy {
                 ordered-by user;
                 description "SSM map policy name";
                 type jt:policy-algebra;
               }
               choice accounting-choice {
                 leaf accounting {
                   description "Enable join and leave event notification";
                   type empty;
                 }
                 leaf no-accounting {
                   description "Don't enable join and leave event notification";
                   type empty;
                 }
               }
               leaf-list group-policy {
                 ordered-by user;
                 description "Group filter applied to incoming IGMP report messages";
                 type jt:policy-algebra;
               }
               leaf group-limit {
                 description "Maximum number of (source,group) per interface";
                 type union {
                   type string {
                     pattern "<.*>|$.*";
                   }
                   type uint16 {
                     range "1 .. 32767";
                   }
                 }
               }
               leaf group-threshold {
                 description "Percentage of limit at which to generate warnings";
                 junos:must "(\" .. group-limit\")";
                 junos:must-message "To configure group-threshold, group-limit must be set";
                 type union {
                   type string {
                     pattern "<.*>|$.*";
                   }
                   type uint32 {
                     range "1 .. 100";
                   }
                 }
               }
               leaf log-interval {
                 description "Time between consecutive log messages";
                 junos:must "(\" .. group-limit\")";
                 junos:must-message "To configure log-interval, group-limit must be set";
                 type union {
                   type string {
                     pattern "<.*>|$.*";
                   }
                   type uint32 {
                     range "6 .. 32767";
                   }
                 }
               }
               leaf robust-count {
                 description "Expected packet loss on a subnet";
                 type union {
                   type string {
                     pattern "<.*>|$.*";
                   }
                   type uint32 {
                     range "2 .. 10";
                   }
                 }
               }
               leaf query-interval {
                 description "When to send host query messages";
                 units "seconds";
                 type union {
                   type string {
                     pattern "<.*>|$.*";
                   }
                   type uint32 {
                     range "1 .. 1024";
                   }
                 }
               }
               leaf query-response-interval {
                 description "How long to wait for a host query response";
                 units "seconds";
                 type string {
                   junos:posix-pattern "^[0-9]{1,4}(.[0-9])?$";
                   junos:pattern-message "Up to 1 digit to right of decimal point";
                 }
               }
             }
           }
         }
       }
       container oam {
         description "Operation, Administration, and Management configuration";
         uses apply-advanced;
         container ethernet {
           description "OAM configuration for Ethernet";
           uses apply-advanced;
           container link-fault-management {
             description "802.3ah Ethernet OAM configuration";
             uses apply-advanced;
             container traceoptions {
               description "Trace options for link-fault management";
               uses apply-advanced;
               leaf no-remote-trace {
                 description "Disable remote tracing";
                 junos:must "(\"system tracing\")";
                 junos:must-message "'no-remote-trace' is valid only when [system tracing] is configured";
                 type empty;
               }
               container file {
                 junos:cli-feature "oneliner";
                 description "Trace file information";
                 leaf filename {
                   description "Name of file in which to write trace information";
                   junos:cli-feature "nokeyword";
                   type string {
                     length "1 .. 1024";
                     junos:posix-pattern "![/ %]";
                     junos:pattern-message "Must not contain \'/\', % or a space";
                   }
                 }
                 leaf size {
                   description "Maximum trace file size";
                   units "bytes";
                   type string;
                 }
                 leaf files {
                   description "Maximum number of trace files";
                   default "3";
                   type union {
                     type string {
                       pattern "<.*>|$.*";
                     }
                     type uint32 {
                       range "2 .. 1000";
                     }
                   }
                 }
                 choice world-readable-choice {
                   leaf world-readable {
                     description "Allow any user to read the log file";
                     type empty;
                   }
                   leaf no-world-readable {
                     description "Don't allow any user to read the log file";
                     type empty;
                   }
                 }
                 leaf match {
                   description "Regular expression for lines to be logged";
                   type jt:regular-expression;
                 }
               }
               list flag {
                 key name;
                 ordered-by user;
                 junos:cli-feature "oneliner";
                 description "Tracing parameters";
                 leaf name {
                   junos:cli-feature "nokeyword";
                   type enumeration {
                     enum "configuration" {
                       description "Trace configuration events";
                     }
                     enum "routing-socket" {
                       description "Trace routing socket events";
                     }
                     enum "protocol" {
                       description "Trace protocol processing events";
                     }
                     enum "action-profile" {
                       description "Trace action profile invocation events";
                     }
                     enum "all" {
                       description "Trace everything";
                     }
                   }
                 }
               }
             }
             list action-profile {
               key name;
               ordered-by user;
               description "Define an action profile";
               leaf name {
                 description "Name of action profile";
                 junos:cli-feature "nokeyword";
                 type string {
                   length "1 .. 32";
                 }
               }
               uses apply-advanced;
               container event {
                 description "Events this action profile will check";
                 uses apply-advanced;
                 leaf link-adjacency-loss {
                   description "Loss of adjacency with OAM peer";
                   type empty;
                 }
                 leaf protocol-down {
                   description "Upper layer indication on protocol down";
                   type empty;
                 }
                 container link-event-rate {
                   uses apply-advanced;
                   leaf symbol-period {
                     description "Rate of receiving symbol period events";
                     units "error(s) per 100 symbol";
                     type union {
                       type string {
                         pattern "<.*>|$.*";
                       }
                       type int32 {
                         range "1 .. 100";
                       }
                     }
                   }
                   leaf frame-error {
                     description "Rate of receiving frame error events";
                     units "error(s) per 100 milli-second";
                     type union {
                       type string {
                         pattern "<.*>|$.*";
                       }
                       type int32 {
                         range "1 .. 1000";
                       }
                     }
                   }
                   leaf frame-period {
                     description "Rate of receiving frame period events";
                     units "error(s) per 100 frames";
                     type union {
                       type string {
                         pattern "<.*>|$.*";
                       }
                       type int32 {
                         range "1 .. 100";
                       }
                     }
                   }
                   leaf frame-period-summary {
                     description "Rate of receiving frame period summary events";
                     units "error(s) per second";
                     type union {
                       type string {
                         pattern "<.*>|$.*";
                       }
                       type int32 {
                         range "1 .. 1000";
                       }
                     }
                   }
                 }
               }
               container action {
                 description "Action to take on specified events";
                 uses apply-advanced;
                 leaf syslog {
                   description "Generate syslog message";
                   type empty;
                 }
                 leaf link-down {
                   description "Mark the interface down for transit traffic";
                   type empty;
                 }
                 leaf send-critical-event {
                   description "Start sending OAM PDUs with critical event bit set";
                   junos:must "(\".. .. event protocol-down\")";
                   junos:must-message "send-critical-event action can be configured only with protocol-down event";
                   type empty;
                 }
               }
             }
             list interface {
               key name;
               ordered-by user;
               description "Interface on which to set Ethernet OAM parameters";
               leaf name {
                 description "Interface name";
                 junos:cli-feature "nokeyword";
                 type union {
                   type jt:interface-device;
                   type string {
                     pattern "<.*>|$.*";
                   }
                 }
               }
               uses apply-advanced;
               leaf-list apply-action-profile {
                 ordered-by user;
                 description "Apply the specified action profile on the interface";
                 type string;
               }
               leaf pdu-interval {
                 description "Periodic OAM protocol data unit interval";
                 default "1000";
                 units "milliseconds";
                 type union {
                   type string {
                     pattern "<.*>|$.*";
                   }
                   type int32 {
                     range "100 .. 1000";
                   }
                 }
               }
               leaf loopback-tracking {
                 description "Enable link down on loopback detection";
                 type empty;
               }
               leaf detect-loc {
                 description "Detects initial lack of adjacency formation";
                 type empty;
               }
               leaf link-discovery {
                 description "Mode of discovery";
                 default "active";
                 type enumeration {
                   enum "active" {
                   }
                   enum "passive" {
                   }
                 }
               }
               leaf pdu-threshold {
                 description "Number of PDUs missed before declaring peer lost";
                 default "3";
                 type union {
                   type string {
                     pattern "<.*>|$.*";
                   }
                   type int32;
                 }
               }
               leaf remote-loopback {
                 description "Put remote DTE into remote-loopback mode";
                 junos:must "(!(\".. link-discovery passive\"))";
                 junos:must-message "remote-loopback request not allowed in passive mode";
                 type empty;
               }
               container negotiation-options {
                 description "802.3ah features supported on the interface";
                 uses apply-advanced;
                 leaf no-allow-link-events {
                   description "Do not emit periodic PDUs detailing framing and symbol errors";
                   type empty;
                 }
                 leaf allow-remote-loopback {
                   description "Allow local port to be put into loopback mode";
                   type empty;
                 }
               }
               container event-thresholds {
                 junos:must "(!(\".. negotiation-options no-allow-link-events\"))";
                 junos:must-message "'event-thresholds' statement cannot be included along with 'no-allow-link-events' statement";
                 description "Thresholds for sending 802.3ah events";
                 uses apply-advanced;
                 leaf symbol-period {
                   description "Threshold for sending symbol period events";
                   default "1";
                   type union {
                     type string {
                       pattern "<.*>|$.*";
                     }
                     type int32 {
                       range "0 .. 100";
                     }
                   }
                 }
                 leaf frame-error {
                   description "Threshold for sending frame error events";
                   default "1";
                   type union {
                     type string {
                       pattern "<.*>|$.*";
                     }
                     type int32 {
                       range "0 .. 100";
                     }
                   }
                 }
                 leaf frame-period {
                   description "Threshold for sending frame period error events";
                   default "1";
                   type union {
                     type string {
                       pattern "<.*>|$.*";
                     }
                     type int32 {
                       range "0 .. 100";
                     }
                   }
                 }
                 leaf frame-period-summary {
                   description "Threshold for sending frame period summary error events";
                   default "1";
                   type union {
                     type string {
                       pattern "<.*>|$.*";
                     }
                     type int32 {
                       range "0 .. 100";
                     }
                   }
                 }
               }
             }
           }
           container connectivity-fault-management {
             description "Configurations related to 802.1ag ethernet oam";
             uses apply-advanced;
             container performance-monitoring {
               description "Configurations related to ethernet performance monitoring";
               uses apply-advanced;
               leaf hardware-assisted-timestamping {
                 description "Enable timestamping feature in hardware";
                 type empty;
               }
               leaf delegate-server-processing {
                 description "Delegate performance measurement request handling to PFE";
                 type empty;
               }
               leaf hardware-assisted-keepalives {
                 description "Enable/Disable delegating keepalives to hardware";
                 type enumeration {
                   enum "enable" {
                     description "Enable delegate keepalives handling to Hardware";
                   }
                   enum "disable" {
                     description "Disable delegate keepalives handling to Hardware (default)";
                   }
                 }
               }
               leaf hardware-assisted-pm {
                 description "Enable inline support for performance monitoring";
                 junos:must "(\"protocols oam ethernet connectivity-fault-management enhanced-cfm-mode\")";
                 junos:must-message "enhanced-cfm-mode needs to be configured for inline pm support";
                 type empty;
               }
               leaf enhanced-sla-iterator {
                 description "Enable Enhanced SLA Iterator Cycle-time";
                 type empty;
               }
               leaf measurement-interval {
                 description "Enables measurement-interval based PM (MEF 36 mode). Default 15 min in enhanced-cfm-mode";
                 units "minutes";
                 junos:must "(\".. enhanced-sla-iterator\")";
                 junos:must-message "enhanced-sla-iterator needs to be configured for MEF36 mode";
                 type enumeration {
                   enum "2" {
                     description "2 minutes measurement interval";
                   }
                   enum "5" {
                     description "5 minutes measurement interval";
                   }
                   enum "15" {
                     description "15 minutes measurement interval";
                   }
                   enum "30" {
                     description "30 minutes measurement interval";
                   }
                   enum "60" {
                     description "1 hour measurement interval";
                   }
                 }
               }
               leaf legacy-pm-display {
                 description "Display Legacy PM output (for DM) in MEF mode.";
                 junos:must "((\".. measurement-interval\" || \".. .. enhanced-cfm-mode\"))";
                 junos:must-message "measurement-interval or enhanced-cfm-mode needs to be configured for legacy PM output in MEF mode.";
                 type empty;
               }
               list sla-iterator-profiles {
                 key name;
                 ordered-by user;
                 junos:cli-feature "homogeneous";
                 description "Configuration related to an sla monitoring iterator";
                 leaf name {
                   junos:cli-feature "nokeyword";
                   type string;
                 }
                 uses apply-advanced;
                 leaf disable {
                   description "Disable the iterator profile";
                   type empty;
                 }
                 leaf measurement-type {
                   description "Choice of the type of Y.1731(SLA measurement) frame to be sent";
                   type enumeration {
                     enum "two-way-delay" {
                       description "Y.1731 2-way DM frames are sent for this profile";
                       junos:must "(!(\"routing-options ppm no-delegate-processing\"))";
                       junos:must-message "Iterator two-way-delay measurement is not supported with ppm no-delegate-processing";
                     }
                     enum "loss" {
                       description "Y.1731 LM frames are sent for this profile";
                     }
                     enum "slm" {
                       description "Y.1731 SLM frames are sent for this profile";
                     }
                     enum "statistical-frame-loss" {
                       description "Y.1731 2-way DM frames for statistical frame loss are sent for this profile";
                       junos:must "(!(\"routing-options ppm no-delegate-processing\"))";
                       junos:must-message "Iterator statistical-frame-loss measurement is not supported with ppm no-delegate-processing";
                     }
                   }
                 }
                 leaf flap-trap-monitor {
                   description "Configurable timer value 1-360";
                   units "seconds";
                   type union {
                     type string {
                       pattern "<.*>|$.*";
                     }
                     type uint32 {
                       range "1 .. 360";
                     }
                   }
                 }
                 leaf cycle-time {
                   description "Time period of an iterator profile";
                   default "1000";
                   units "milliseconds";
                   type union {
                     type string {
                       pattern "<.*>|$.*";
                     }
                     type uint32;
                   }
                 }
                 leaf iteration-period {
                   description "Maximum services under this iterator profile";
                   default "2000";
                   units "connections";
                   type union {
                     type string {
                       pattern "<.*>|$.*";
                     }
                     type uint32 {
                       range "1 .. 2000";
                     }
                   }
                 }
                 container calculation-weight {
                   presence "enable calculation-weight";
                   junos:must "(\".. measurement-type two-way-delay\")";
                   junos:must-message "The measurement type must be two-way-delay";
                   description "Configure delay and delay variation calculation weight";
                   uses apply-advanced;
                   leaf delay {
                     description "Weight used in delay calculation";
                     default "1";
                     type union {
                       type string {
                         pattern "<.*>|$.*";
                       }
                       type uint32 {
                         range "1 .. 65535";
                       }
                     }
                   }
                   leaf delay-variation {
                     description "Weight used in delay-variation calculation";
                     default "1";
                     type union {
                       type string {
                         pattern "<.*>|$.*";
                       }
                       type uint32 {
                         range "1 .. 65535";
                       }
                     }
                   }
                 }
                 container avg-flr-forward-threshold {
                   presence "enable avg-flr-forward-threshold";
                   junos:must "((\".. measurement-type loss\" || \" .. measurement-type slm\"))";
                   junos:must-message " The measurement type must be either loss or slm";
                   description "Avg forward flr threshold";
                   uses apply-advanced;
                   leaf avg-flr-forward {
                     description "Avg forward flr threshold value in mili-percent";
                     junos:cli-feature "nokeyword";
                     type union {
                       type string {
                         pattern "<.*>|$.*";
                       }
                       type uint32 {
                         range "1 .. 100000";
                       }
                     }
                   }
                   leaf flap-trap-monitor {
                     description "Configurable timer value 1-360";
                     units "seconds";
                     type union {
                       type string {
                         pattern "<.*>|$.*";
                       }
                       type uint32 {
                         range "1 .. 360";
                       }
                     }
                   }
                 }
                 container avg-flr-backward-threshold {
                   presence "enable avg-flr-backward-threshold";
                   junos:must "((\".. measurement-type loss\" || \" .. measurement-type slm\"))";
                   junos:must-message " The measurement type must be either loss or slm";
                   description "Avg backward flr threshold";
                   uses apply-advanced;
                   leaf avg-flr-backward {
                     description "Avg backward flr threshold value in mili-percent";
                     junos:cli-feature "nokeyword";
                     type union {
                       type string {
                         pattern "<.*>|$.*";
                       }
                       type uint32 {
                         range "1 .. 100000";
                       }
                     }
                   }
                   leaf flap-trap-monitor {
                     description "Configurable timer value 1-360";
                     units "seconds";
                     type union {
                       type string {
                         pattern "<.*>|$.*";
                       }
                       type uint32 {
                         range "1 .. 360";
                       }
                     }
                   }
                 }
                 container avg-fd-twoway-threshold {
                   presence "enable avg-fd-twoway-threshold";
                   junos:must "(\".. measurement-type two-way-delay\")";
                   junos:must-message " The measurement type must be two-way-delay";
                   description "Avg frame delay threshold value";
                   uses apply-advanced;
                   leaf avg-fd-twoway {
                     description "Avg frame delay threshold value in mili-percent";
                     junos:cli-feature "nokeyword";
                     units "microseconds";
                     type union {
                       type string {
                         pattern "<.*>|$.*";
                       }
                       type uint32 {
                         range "1 .. 4294967295";
                       }
                     }
                   }
                   leaf flap-trap-monitor {
                     description "Configurable timer value 1-360";
                     units "seconds";
                     type union {
                       type string {
                         pattern "<.*>|$.*";
                       }
                       type uint32 {
                         range "1 .. 360";
                       }
                     }
                   }
                 }
                 container avg-fdv-twoway-threshold {
                   presence "enable avg-fdv-twoway-threshold";
                   junos:must "(\".. measurement-type two-way-delay\")";
                   junos:must-message " The measurement type must be two-way-delay";
                   description "Avg frame delay variance threshold";
                   uses apply-advanced;
                   leaf avg-fdv-twoway {
                     description "Avg frame delay variance threshold value in mili-percent";
                     junos:cli-feature "nokeyword";
                     units "microseconds";
                     type union {
                       type string {
                         pattern "<.*>|$.*";
                       }
                       type uint32 {
                         range "1 .. 4294967295";
                       }
                     }
                   }
                   leaf flap-trap-monitor {
                     description "Configurable timer value 1-360";
                     units "seconds";
                     type union {
                       type string {
                         pattern "<.*>|$.*";
                       }
                       type uint32 {
                         range "1 .. 360";
                       }
                     }
                   }
                 }
                 container frame-delay {
                   description "Bin configuration for frame delay";
                   uses apply-advanced;
                   leaf num-bins {
                     description "Max number of bins";
                     type union {
                       type string {
                         pattern "<.*>|$.*";
                       }
                       type uint32 {
                         range "2 .. 5";
                       }
                     }
                   }
                   container two-way {
                     presence "enable two-way";
                     description "Bin configuration for 2way frame delay";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container forward {
                     presence "enable forward";
                     description "Bin configuration for forward frame delay";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container backward {
                     presence "enable backward";
                     description "Bin configuration for backward frame delay";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                 }
                 container frame-delay-range {
                   description "Bin configuration for frame delay range";
                   uses apply-advanced;
                   leaf num-bins {
                     description "Max number of bins";
                     type union {
                       type string {
                         pattern "<.*>|$.*";
                       }
                       type uint32 {
                         range "2 .. 5";
                       }
                     }
                   }
                   container two-way {
                     presence "enable two-way";
                     description "Bin configuration for 2way frame delay range";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container forward {
                     presence "enable forward";
                     description "Bin configuration for forward frame delay range";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container backward {
                     presence "enable backward";
                     description "Bin configuration for backward frame delay range";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                 }
                 container ifdv {
                   description "Bin configuration for IFDV";
                   uses apply-advanced;
                   leaf num-bins {
                     description "Max number of bins";
                     type union {
                       type string {
                         pattern "<.*>|$.*";
                       }
                       type uint32 {
                         range "2 .. 5";
                       }
                     }
                   }
                   container two-way {
                     presence "enable two-way";
                     description "Bin configuration for 2way IFDV";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container forward {
                     presence "enable forward";
                     description "Bin configuration for forward IFDV";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container backward {
                     presence "enable backward";
                     description "Bin configuration for backward IFDV";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                 }
                 container availability {
                   junos:must "((\".. measurement-type loss\" || \" .. measurement-type slm\"))";
                   junos:must-message " The measurement type must be either loss or slm";
                   junos:must "(\"protocols oam ethernet connectivity-fault-management performance-monitoring measurement-interval\")";
                   junos:must-message "missing mandatory statement 'measurement-interval' at pm level";
                   description "Configuration of availabilty related parameters (MEF 36 mode)";
                   uses apply-advanced;
                   leaf num-consecutive-pdus {
                     description "Number of consecutive LM/SLM PDUs to be used in availability measurement";
                     type union {
                       type string {
                         pattern "<.*>|$.*";
                       }
                       type uint32 {
                         range "1 .. 100";
                       }
                     }
                   }
                   leaf flr-threshold {
                     description "FLR threshold in milli-percent to be used for evaluating availability";
                     type union {
                       type string {
                         pattern "<.*>|$.*";
                       }
                       type uint32 {
                         range "0 .. 100000";
                       }
                     }
                   }
                   leaf num-consecutive-intervals {
                     description "Number of consecutive availability indicators to detect change in availability";
                     type union {
                       type string {
                         pattern "<.*>|$.*";
                       }
                       type uint32 {
                         range "1 .. 10";
                       }
                     }
                   }
                   leaf num-consecutive-highflr {
                     description "Number of consecutive availability indicators to access CHLI";
                     type union {
                       type string {
                         pattern "<.*>|$.*";
                       }
                       type uint32 {
                         range "1 .. 9";
                       }
                     }
                   }
                 }
               }
               list interface {
                 key name;
                 ordered-by user;
                 junos:cli-feature "oneliner";
                 description "Name of interface for the performance monitoring";
                 leaf name {
                   description "Interface name";
                   junos:cli-feature "nokeyword";
                   type union {
                     type jt:interface-unit;
                     type string {
                       pattern "<.*>|$.*";
                     }
                   }
                 }
                 leaf enable-multiclass-loss-measurement {
                   description "Disable multiclass loss measurement in hardware";
                   junos:must "((!(\".. code-point-based-lm-accounting\") && !(\".. priority-based-lm-accounting\")))";
                   junos:must-message "loss measurement modes are exclusive with each other";
                   type empty;
                 }
                 leaf code-point-based-lm-accounting {
                   description "Enable code point based loss measurement in hardware";
                   junos:must "((!(\".. enable-multiclass-loss-measurement\") && (!(\".. colorless-loss-measurement\") && !(\".. priority-based-lm-accounting\"))))";
                   junos:must-message "loss measurement modes are exclusive with each other";
                   type empty;
                 }
                 leaf priority-based-lm-accounting {
                   description "Enable priority based loss measurement in hardware";
                   junos:must "((!(\".. enable-multiclass-loss-measurement\") && (!(\".. colorless-loss-measurement\") && !(\".. code-point-based-lm-accounting\"))))";
                   junos:must-message "loss measurement modes are exclusive with each other";
                   type empty;
                 }
               }
               leaf enable-multiclass-loss-measurement {
                 description "Disable multiclass loss measurement in hardware";
                 junos:must "((!(\".. code-point-based-lm-accounting\") && !(\".. priority-based-lm-accounting\")))";
                 junos:must-message "loss measurement modes are exclusive with each other";
                 type empty;
               }
               leaf code-point-based-lm-accounting {
                 description "Enable code point based loss measurement in hardware";
                 junos:must "((!(\".. enable-multiclass-loss-measurement\") && (!(\".. colorless-loss-measurement\") && !(\".. priority-based-lm-accounting\"))))";
                 junos:must-message "loss measurement modes are exclusive with each other";
                 type empty;
               }
               leaf priority-based-lm-accounting {
                 description "Enable priority based loss measurement in hardware";
                 junos:must "((!(\".. enable-multiclass-loss-measurement\") && (!(\".. colorless-loss-measurement\") && !(\".. code-point-based-lm-accounting\"))))";
                 junos:must-message "loss measurement modes are exclusive with each other";
                 type empty;
               }
               leaf colorless-loss-measurement {
                 description "Enable colorless loss measurement in hardware";
                 junos:must "((!(\".. code-point-based-lm-accounting\") && !(\".. priority-based-lm-accounting\")))";
                 junos:must-message "loss measurement modes are exclusive with each other";
                 type empty;
               }
             }
             leaf no-aggregate-delegate-processing {
               description "Do not distribute aggregate session to pfe";
               type empty;
             }
             leaf enhanced-cfm-mode {
               description "Enables Enhanced CFM Mode";
               type empty;
             }
             container traceoptions {
               description "Trace options for connectivity fault management";
               presence "enable traceoptions";
               uses cfm-traceoptions;
             }
             list action-profile {
               key name;
               ordered-by user;
               description "Action profiles to use when one or more remote maintenance association endpoints are down";
               leaf name {
                 description "Name of action profile";
                 junos:cli-feature "nokeyword";
                 type string;
               }
               uses apply-advanced;
               container event {
                 junos:must "(\".. action\")";
                 junos:must-message "Cannot configure event without action";
                 description "Events that need to be monitored";
                 uses apply-advanced;
                 leaf-list interface-status-tlv {
                   ordered-by user;
                   description "Values that need to be monitored in interface status TLV";
                   type enumeration {
                     enum "down" {
                       description "Interface is administratively down";
                     }
                     enum "lower-layer-down" {
                       description "Interface is physically down";
                     }
                   }
                 }
                 leaf-list port-status-tlv {
                   ordered-by user;
                   description "Values that need to be monitored in port status TLV";
                   type enumeration {
                     enum "blocked" {
                       description "Port is blocked";
                     }
                   }
                 }
                 leaf adjacency-loss {
                   description "Connectivity is lost";
                   type empty;
                 }
                 leaf rdi {
                   description "RDI received from some MEP";
                   type empty;
                 }
                 leaf connection-protection-tlv {
                   description "Values that need to be monitored in connection protection TLV";
                   type enumeration {
                     enum "using-working-path" {
                       description "Service traffic is using working path";
                     }
                     enum "using-protection-path" {
                       description "Service traffic is using protection path";
                     }
                   }
                 }
                 leaf server-mep-defects {
                   description "Defects which are monitored by Server MEP";
                   type enumeration {
                     enum "link-loss-defect" {
                       description "Detect link loss defects for the ethernet interface";
                     }
                     enum "l2circuit-defect" {
                       description "Detect l2circuit down defects";
                     }
                     enum "l2vpn-defect" {
                       description "Detect l2vpn down defects";
                     }
                   }
                 }
                 leaf-list ais-trigger-condition {
                   ordered-by user;
                   description "Defect condition that generates alarm indication signal";
                   type enumeration {
                     enum "all-defects" {
                       description "All defects";
                     }
                     enum "adjacency-loss" {
                       description "Loss of connectivity defects";
                     }
                     enum "cross-connect-ccm" {
                       description "Cross connect CCMs";
                     }
                     enum "erroneous-ccm" {
                       description "Erroneous CCMs";
                     }
                     enum "receive-ais" {
                       description "AIS message received";
                     }
                   }
                 }
               }
               container action {
                 junos:must "(\".. event\")";
                 junos:must-message "Cannot configure action without event";
                 uses apply-advanced;
                 leaf interface-down {
                   description "Mark the interface as down";
                   type empty;
                 }
                 leaf revertive-interface-down {
                   description "Wait for CC loss-threshold to bring back the interface up";
                   junos:must "(!(\".. non-revertive-interface-down\"))";
                   junos:must-message "Cannot configure action along with revertive-interface-down";
                   type empty;
                 }
                 leaf non-revertive-interface-down {
                   description "Interface will not be brought up when CC is received";
                   junos:must "(!(\".. revertive-interface-down\"))";
                   junos:must-message "Cannot configure action along with non-revertive-interface-down";
                   type empty;
                 }
                 leaf propagate-remote-mac-flush {
                   description "Remote mac-flush";
                   type empty;
                 }
                 leaf interface-group-down {
                   description "Mark the interface group as down";
                   junos:must "((!(\".. .. event interface-status-tlv\") && (!(\".. .. event port-status-tlv\") && (!(\".. .. event connection-protection-tlv\") && (!(\".. .. event server-mep-defects\") && !(\".. .. event ais-trigger-condition\"))))))";
                   junos:must-message "Cannot configure events other that adjacency-loss or rdi with this action";
                   junos:must "((!(\".. interface-down\") && (!(\".. revertive-interface-down\") && !(\".. non-revertive-interface-down\"))))";
                   junos:must-message "Cannot configure action along with other interface down actions";
                   type empty;
                 }
                 leaf asynchronous-notification {
                   description "Generate asynchronous notification (Laser-off for optical phys)";
                   junos:must "((!(\".. .. event port-status-tlv\") && (!(\".. .. event rdi\") && (!(\".. .. event connection-protection-tlv\") && (!(\".. .. event server-mep-defects\") && !(\".. .. event ais-trigger-condition\"))))))";
                   junos:must-message "Cannot configure events other that adjacency-loss or interface-status-tlv with this action";
                   junos:must "((!(\".. interface-down\") && (!(\".. revertive-interface-down\") && (!(\".. non-revertive-interface-down\") && !(\".. interface-group-down\")))))";
                   junos:must-message "Cannot configure action along with other interface down actions";
                   type empty;
                 }
                 container log-and-generate-ais {
                   uses apply-advanced;
                   leaf-list level {
                     description "Server maintenance domain levels range";
                     type union {
                       type string {
                         pattern "<.*>|$.*";
                       }
                       type uint32 {
                         range "1 .. 7";
                       }
                     }
                   }
                   leaf interval {
                     description "Interval between AIS messages";
                     default "1s";
                     type enumeration {
                       enum "1s" {
                       }
                       enum "1m" {
                       }
                     }
                   }
                   leaf priority {
                     description "802.1p priority of AIS packet";
                     default "0";
                     type union {
                       type string {
                         pattern "<.*>|$.*";
                       }
                       type uint32 {
                         range "0 .. 7";
                       }
                     }
                   }
                 }
               }
               container clear-action {
                 junos:must "(\".. event\")";
                 junos:must-message "Cannot configure action without event";
                 uses apply-advanced;
                 container interface-down {
                   junos:cli-feature "oneliner";
                   description "Mark the interface as down";
                   leaf peer-interface {
                     description "Mark the interface as down";
                     type empty;
                   }
                 }
                 leaf propagate-remote-mac-flush {
                   description "Remote  mac flush";
                   type empty;
                 }
               }
               container default-actions {
                 junos:must "(!(\".. event\"))";
                 junos:must-message "Cannot configure default-actions if event is set";
                 description "Action that needs to be taken";
                 uses apply-advanced;
                 leaf interface-down {
                   description "Bring the interface down";
                   type empty;
                 }
               }
             }
             list server-mep {
               key name;
               ordered-by user;
               description "Server MEP to use when generation of AIS is required to monitor different services";
               leaf name {
                 description "Identifier for Server MEP";
                 junos:cli-feature "nokeyword";
                 type union {
                   type string {
                     pattern "<.*>|$.*";
                   }
                   type uint16 {
                     range "1 .. 8191";
                   }
                 }
               }
               uses apply-advanced;
               container protocol {
                 presence "enable protocol";
                 junos:must "(\".. action-profile\")";
                 junos:must-message "Cannot configure protocol without action-profile";
                 description "Protocol that needs to be monitored by Server MEP";
                 uses apply-advanced;
                 choice protocol {
                   case case_1 {
                     container l2circuit {
                       presence "enable l2circuit";
                       junos:cli-feature "oneliner";
                       description "Protocol that need to be monitored is l2circuit protocol";
                       container interface {
                         presence "enable interface";
                         junos:cli-feature "oneliner";
                         description "Interface which is participating in l2circuit service";
                         leaf interface-name {
                           description "Interface name";
                           junos:cli-feature "nokeyword";
                           junos:must "(any \"protocols l2circuit neighbor <*> interface $$\")";
                           junos:must-message "Referenced interface must be defined in l2circuit configuration";
                           type union {
                             type jt:interface-name;
                             type string {
                               pattern "<.*>|$.*";
                             }
                           }
                         }
                       }
                     }
                   }
                   case case_2 {
                     container l2vpn {
                       presence "enable l2vpn";
                       junos:cli-feature "oneliner";
                       description "Protocol that need to be monitored is l2vpn protocol";
                       container interface {
                         presence "enable interface";
                         junos:cli-feature "oneliner";
                         description "Interface which is participating in l2vpn service";
                         leaf interface-name {
                           description "Interface name";
                           junos:cli-feature "nokeyword";
                           junos:must "(any \"routing-instances <*> protocols l2vpn site <*> interface $$\")";
                           junos:must-message "Referenced interface must be defined in l2vpn configuration";
                           type union {
                             type jt:interface-name;
                             type string {
                               pattern "<.*>|$.*";
                             }
                           }
                         }
                       }
                     }
                   }
                   case case_3 {
                     container ethernet {
                       presence "enable ethernet";
                       junos:cli-feature "oneliner";
                       description "Protocol that need to be monitored is physical ethernet service";
                       container interface {
                         presence "enable interface";
                         junos:cli-feature "oneliner";
                         description "Interface which is going to be monitored";
                         leaf interface-name {
                           description "Interface name";
                           junos:cli-feature "nokeyword";
                           junos:must "(!(\"interfaces $$ gigether-options 802.3ad\"))";
                           junos:must-message "Referenced interface should not be part of AE";
                           junos:must "(\"interfaces $$\")";
                           junos:must-message "Referenced interface must be defined";
                           type union {
                             type jt:interface-device;
                             type string {
                               pattern "<.*>|$.*";
                             }
                           }
                         }
                       }
                     }
                   }
                 }
               }
               container action-profile {
                 presence "enable action-profile";
                 description "Attached action profile for this Server MEP";
                 uses apply-advanced;
                 leaf action-profile-name {
                   description "Name of the action profile";
                   junos:cli-feature "nokeyword";
                   junos:must "(\"protocols oam ethernet connectivity-fault-management action-profile $$ action log-and-generate-ais\")";
                   junos:must-message "AIS actions are not defined for Server MEP defects";
                   junos:must "(\"protocols oam ethernet connectivity-fault-management action-profile $$ event server-mep-defects\")";
                   junos:must-message "Server MEP defects are not configured";
                   junos:must "(\"protocols oam ethernet connectivity-fault-management action-profile $$\")";
                   junos:must-message "Action profile not configured";
                   type string;
                 }
               }
             }
             container policer {
               description "Rate limit Ethernet OAM packets for all sessions";
               uses apply-advanced;
               leaf continuity-check {
                 description "Policer to rate limit Continuity Check Ethernet OAM messages";
                 junos:must "(\"firewall policer $$\")";
                 junos:must-message "referenced policer must be defined";
                 type string;
               }
               leaf other {
                 description "Policer to rate limit non Continuity Check Ethernet OAM messages";
                 junos:must "(\"firewall policer $$\")";
                 junos:must-message "referenced policer must be defined";
                 type string;
               }
               leaf all {
                 description "Policer to rate limit all Ethernet OAM messages";
                 junos:must "(\"firewall policer $$\")";
                 junos:must-message "referenced policer must be defined";
                 type string;
               }
             }
             container linktrace {
               presence "enable linktrace";
               description "Linktrace protocol global options";
               uses apply-advanced;
               leaf path-database-size {
                 description "Number of linktrace reply entries to be stored per linktrace request";
                 default "100";
                 type union {
                   type string {
                     pattern "<.*>|$.*";
                   }
                   type uint32 {
                     range "1 .. 255";
                   }
                 }
               }
               leaf age {
                 description "Time after which a stale request-response entry is deleted";
                 default "10m";
                 type enumeration {
                   enum "10s" {
                   }
                   enum "30s" {
                   }
                   enum "1m" {
                   }
                   enum "10m" {
                   }
                   enum "30m" {
                   }
                 }
               }
             }
             container context-history {
               presence "enable context-history";
               description "Context history limit (0..5000000)";
               uses apply-advanced;
               leaf ctxt-limit {
                 description "Context history limit [...] ";
                 type union {
                   type string {
                     pattern "<.*>|$.*";
                   }
                   type uint32 {
                     range "0 .. 5000000";
                   }
                 }
               }
             }
             list maintenance-domain {
               key name;
               description "Maintenance domain configuration";
               leaf name {
                 junos:cli-feature "nokeyword";
                 type string;
               }
               uses apply-advanced;
               list bridge-domain {
                 key name;
                 ordered-by user;
                 junos:cli-feature "oneliner";
                 description "Bridge-domain information for the default maintenance domain";
                 leaf name {
                   description "Bridge domain name";
                   junos:cli-feature "nokeyword";
                   type string;
                 }
                 leaf-list vlan-id {
                   ordered-by user;
                   description "VLAN id";
                   type string;
                 }
               }
               list vlan {
                 key name;
                 ordered-by user;
                 junos:cli-feature "oneliner";
                 description "VLAN information for the default maintenance domain";
                 leaf name {
                   description "VLAN name";
                   junos:cli-feature "nokeyword";
                   type string;
                 }
               }
               list virtual-switch {
                 key name;
                 ordered-by user;
                 description "Virtual switch Bridge-domain information for the default maintenance domain";
                 leaf name {
                   description "Routing instance of type virtual switch";
                   junos:cli-feature "nokeyword";
                   type string;
                 }
                 uses apply-advanced;
                 list bridge-domain {
                   key name;
                   ordered-by user;
                   junos:cli-feature "oneliner";
                   leaf name {
                     description "Bridge domain name";
                     junos:cli-feature "nokeyword";
                     type string;
                   }
                   leaf-list vlan-id {
                     ordered-by user;
                     description "VLAN id";
                     type string;
                   }
                 }
               }
               list instance {
                 key name;
                 ordered-by user;
                 junos:cli-feature "oneliner";
                 description "VPLS instance name for the default maintenance domain";
                 leaf name {
                   description "VPLS routing instance name";
                   junos:cli-feature "nokeyword";
                   junos:must "(!(\"routing-instances $$ vlan-id inner-all\"))";
                   junos:must-message "MIPs are not allowed for VPLS with vlan-id inner-all";
                   junos:must "(!(\"routing-instances $$ vlan-id all\"))";
                   junos:must-message "MIPs are not allowed for VPLS with vlan-id all";
                   junos:must "((\"routing-instances $$ vlan-id\" || \"routing-instances $$ vlan-tags\"))";
                   junos:must-message "MIPs are allowed only for VPLS with vlan-id/vlan-tags";
                   junos:must "(\"routing-instances $$ instance-type vpls\")";
                   junos:must-message "Only VPLS routing-instances are allowed under default maintenance-domains";
                   type string;
                 }
               }
               list interface {
                 key name;
                 ordered-by user;
                 junos:cli-feature "oneliner";
                 description "Name of interface for the default maintenance domain";
                 leaf name {
                   description "Interface name";
                   junos:cli-feature "nokeyword";
                   junos:must "(!(\"protocols loop-detect enhanced interface $$\"))";
                   junos:must-message "Connectivtiy and loop-detect protocols cannot be enabled on same interface";
                   junos:must "(!(\"protocols oam ethernet link-fault-management interface $$\"))";
                   junos:must-message "Connectivtiy and link fault management protocols cannot be enabled on same interface";
                   junos:must "((!(any \"interfaces $$ unit <*> vlan-id 0\") && !(any \"logical-systems <*> interfaces $$ unit <*> vlan-id 0\")))";
                   junos:must-message "Default maintenance domain cannot be configured with a physical interface which has a logical interface configured with vlan-id 0";
                   type union {
                     type jt:interface-unit;
                     type string {
                       pattern "<.*>|$.*";
                     }
                   }
                 }
               }
               leaf level {
                 description "Level value for maintenance domain";
                 type union {
                   type string {
                     pattern "<.*>|$.*";
                   }
                   type uint8 {
                     range "0 .. 7";
                   }
                 }
               }
               leaf name-format {
                 description "Format of maintenance domain name";
                 type enumeration {
                   enum "none" {
                     description "No format specified";
                   }
                   enum "dns" {
                     description "Character string similar to Domain Name System name";
                   }
                   enum "mac+2oct" {
                     description "MAC address with 2 octet integer (xx:xx:xx:xx:xx:xx.Y format)";
                   }
                   enum "character-string" {
                     description "Character string";
                   }
                 }
               }
               leaf mip-half-function {
                 description "Half function to be implemented by MIP";
                 default "none";
                 type enumeration {
                   enum "none" {
                     description "No MHFs should be created";
                   }
                   enum "default" {
                     description "Create MHF as per IEEE 802.1ag specifications for defMHFDefault";
                   }
                   enum "explicit" {
                     description "Create MHF as per IEEE 802.1ag specifications for defMHFExplicit";
                   }
                 }
               }
               list maintenance-association {
                 key name;
                 description "Maintenance association configuration";
                 leaf name {
                   description "Name of maintenance association in IEEE compliant format";
                   junos:cli-feature "nokeyword";
                   type string {
                     length "1 .. 45";
                   }
                 }
                 uses apply-advanced;
                 leaf debug-session {
                   description "Debug the CFM session";
                   type empty;
                 }
                 leaf short-name-format {
                   description "Format of Maintenance Association Name";
                   type enumeration {
                     enum "2octet" {
                       description "An integer in the range 0..65535";
                     }
                     enum "rfc-2685-vpn-id" {
                       description "VPN identifier that complies with RFC 2685";
                     }
                     enum "vlan" {
                       description "Primary VLAN identifier";
                     }
                     enum "character-string" {
                       description "Character string";
                     }
                     enum "icc" {
                       description "ITU Carrier Code";
                     }
                   }
                 }
                 container protect-maintenance-association {
                   junos:cli-feature "oneliner";
                   description "Maintenance association used for connection protection";
                   leaf ma-name {
                     description "Name of the protect maintenance association";
                     junos:cli-feature "nokeyword";
                     junos:must "(!(\".. .. .. maintenance-association $$ protect-maintenance-association\"))";
                     junos:must-message "Maintenance-association can either be working or protect";
                     junos:must "(\".. .. .. maintenance-association $$\")";
                     junos:must-message "Protect maintenance-association is not configured";
                     type string {
                       length "1 .. 45";
                     }
                   }
                   leaf aps-profile {
                     description "Name of the automatic-protection-switching profile";
                     junos:must "(\"protocols protection-group ethernet-aps $$ \")";
                     junos:must-message "APS profile not found";
                     type string;
                   }
                   leaf detect-path-type {
                     description "Enable detection of working and protect paths";
                     type empty;
                   }
                 }
                 leaf primary-vid {
                   description "VLAN id";
                   type string;
                 }
                 container continuity-check {
                   presence "enable continuity-check";
                   description "Continuity check configuration";
                   uses apply-advanced;
                   leaf interval {
                     description "Interval between continuity-check messages";
                     default "1m";
                     type enumeration {
                       enum "10ms" {
                         junos:must "(!(\"routing-options ppm no-delegate-processing\"))";
                         junos:must-message "10ms interval for continuity-check is not supported with no-delegate-processing";
                       }
                       enum "100ms" {
                       }
                       enum "1s" {
                       }
                       enum "10s" {
                       }
                       enum "1m" {
                       }
                       enum "10m" {
                       }
                       enum "3.3ms" {
                         junos:must "(!(\"routing-options ppm no-delegate-processing\"))";
                         junos:must-message "3.3ms interval for continuity-check is not supported with no-delegate-processing";
                       }
                     }
                   }
                   leaf loss-threshold {
                     description "Number of continuity-check messages lost before marking endpoint as down";
                     default "3";
                     type union {
                       type string {
                         pattern "<.*>|$.*";
                       }
                       type uint32 {
                         range "3 .. 256";
                       }
                     }
                   }
                   leaf hold-interval {
                     description "Time before flushing MEP database if no updates occur";
                     default "10";
                     units "minutes";
                     type union {
                       type string {
                         pattern "<.*>|$.*";
                       }
                       type uint32 {
                         range "1 .. 30240";
                       }
                     }
                   }
                   leaf port-status-tlv {
                     description "Include port status TLV in CCM";
                     type empty;
                   }
                   leaf interface-status-tlv {
                     description "Include interface status TLV in CCM";
                     type empty;
                   }
                   leaf connection-protection-tlv {
                     description "Include connection protection OUI TLV in CCM";
                     type empty;
                   }
                   leaf convey-loss-threshold {
                     description "Include Loss Threshold OUI TLV in CCM";
                     type empty;
                   }
                   leaf interface-status-send-rdi {
                     description "Send RDI on interface operation status down in CCM";
                     type empty;
                   }
                   leaf ignore-cfm-interface-status-ap {
                     description "Ignore AP cfm interface status";
                     type empty;
                   }
                   container sendid-tlv {
                     description "Include sendid-tlv in CCM/LBM/LTM";
                     uses apply-advanced;
                     leaf send-chassis-tlv {
                       description "Attach Chassis ID & Mgmt Addr to CCM/LBM/LTM";
                       type empty;
                     }
                   }
                 }
                 leaf mip-half-function {
                   description "Half function to be implemented by MIP";
                   default "defer";
                   type enumeration {
                     enum "none" {
                       description "No MHFs should be created";
                     }
                     enum "default" {
                       description "Create MHF as per IEEE 802.1ag specifications for defMHFDefault";
                     }
                     enum "explicit" {
                       description "Create MHF as per IEEE 802.1ag specifications for defMHFExplicit";
                     }
                     enum "defer" {
                       description "Create MHF as per IEEE 802.1ag specifications for defMHFDefer";
                     }
                   }
                 }
                 list mep {
                   key name;
                   ordered-by user;
                   description "Maintenance association endpoint configuration";
                   leaf name {
                     description "Identifier for maintenance association endpoint";
                     junos:cli-feature "nokeyword";
                     type union {
                       type string {
                         pattern "<.*>|$.*";
                       }
                       type uint16 {
                         range "1 .. 8191";
                       }
                     }
                   }
                   uses apply-advanced;
                   container interface {
                     presence "enable interface";
                     junos:cli-feature "oneliner";
                     description "Name of interface";
                     leaf interface-name {
                       junos:cli-feature "nokeyword";
                       junos:must "(!(\"protocols oam ethernet link-fault-management interface $$\"))";
                       junos:must-message "Connectivtiy and link fault management protocols cannot be enabled on same interface";
                       junos:must "((!(any \"interfaces $$ unit <*> vlan-id 0\") && !(any \"logical-systems <*> interfaces $$ unit <*> vlan-id 0\")))";
                       junos:must-message "Cannot create a MEP on a physical interface which has a logical interface configured with vlan-id 0";
                       type union {
                         type jt:interface-unit;
                         type string {
                           pattern "<.*>|$.*";
                         }
                       }
                     }
                     leaf vlan {
                       description "Trunk port interface VLAN identifier";
                       type union {
                         type string {
                           pattern "<.*>|$.*";
                         }
                         type uint32 {
                           range "1 .. 4094";
                         }
                       }
                     }
                     choice connection-type {
                       case case_1 {
                         leaf working {
                           description "Monitory the primary path";
                           type empty;
                         }
                       }
                       case case_2 {
                         leaf protect {
                           description "Monitory the protect path";
                           type empty;
                         }
                       }
                     }
                   }
                   leaf direction {
                     description "Direction of maintenance endpoint";
                     default "down";
                     type enumeration {
                       enum "up" {
                       }
                       enum "down" {
                         junos:must "(!(\".. .. mip-half-function\"))";
                         junos:must-message "Cannot specify MA MHF with down MEP";
                         junos:must "(!(\".. .. .. mip-half-function\"))";
                         junos:must-message "Cannot specify MD MHF with down MEP";
                       }
                     }
                   }
                   leaf priority {
                     description "802.1p priority of continuity-check and link-trace packet";
                     default "0";
                     type union {
                       type string {
                         pattern "<.*>|$.*";
                       }
                       type uint32 {
                         range "0 .. 7";
                       }
                     }
                   }
                   leaf auto-discovery {
                     description "Accept continuity-check messages from all remote MEPs";
                     type empty;
                   }
                   leaf action-profile {
                     description "Name of the action profile";
                     junos:must "(!(\"protocols oam ethernet connectivity-fault-management action-profile $$ action asynchronous-notification\"))";
                     junos:must-message "Action asynchronous-notificaiton can not be configured at mep level";
                     junos:must "(\"protocols oam ethernet connectivity-fault-management action-profile $$\")";
                     junos:must-message "Action profile not configured";
                     type string;
                   }
                   list remote-mep {
                     key name;
                     ordered-by user;
                     description "Remote maintenance association endpoint configuration";
                     leaf name {
                       description "Identifier for remote maintenance association endpoint";
                       junos:cli-feature "nokeyword";
                       type union {
                         type string {
                           pattern "<.*>|$.*";
                         }
                         type uint16 {
                           range "1 .. 8191";
                         }
                       }
                     }
                     uses apply-advanced;
                     leaf action-profile {
                       description "Name of the action profile";
                       junos:must "(\"protocols oam ethernet connectivity-fault-management action-profile $$\")";
                       junos:must-message "Action profile not configured";
                       type string;
                     }
                     container interface-group {
                       presence "enable interface-group";
                       description "Mark this interface group down Profile configured with action interface-group-down";
                       uses apply-advanced;
                       leaf interface-device-name {
                         description "Interface device name";
                         junos:cli-feature "nokeyword";
                         type union {
                           type jt:interface-device;
                           type string {
                             pattern "<.*>|$.*";
                           }
                         }
                       }
                       leaf-list unit-list {
                         description "One or more logical interface unit numbers";
                         type jt:range;
                       }
                     }
                     list sla-iterator-profile {
                       key name;
                       ordered-by user;
                       description "Name of the iterator profile";
                       leaf name {
                         junos:cli-feature "nokeyword";
                         junos:must "((!(\".. .. .. no-delegate-processing\") || (\"protocols oam ethernet connectivity-fault-management performance-monitoring sla-iterator-profiles ${sla-iterator-profile} measurement-type loss\" || \"protocols oam ethernet connectivity-fault-management performance-monitoring sla-iterator-profiles ${sla-iterator-profile} measurement-type slm\")))";
                         junos:must-message "Iterator two-way-delay or statistical-frame-loss measurement is not supported with mep level no-delegate-processing";
                         junos:must "(\"protocols oam ethernet connectivity-fault-management performance-monitoring sla-iterator-profiles $$\")";
                         junos:must-message "The SLA iterator profile must be configured";
                         type string;
                       }
                       uses apply-advanced;
                       leaf iteration-count {
                         description "Iterations to partake for acquiring SLA measurements";
                         units "frames";
                         junos:must "(!(\"protocols oam ethernet connectivity-fault-management performance-monitoring measurement-interval\"))";
                         junos:must-message "Iteration-count not supported with measurement-interval";
                         type union {
                           type string {
                             pattern "<.*>|$.*";
                           }
                           type uint32 {
                             range "1 .. 65535";
                           }
                         }
                       }
                       leaf priority {
                         description "The vlan pcp value to be sent in the Y.1731 frame";
                         type union {
                           type string {
                             pattern "<.*>|$.*";
                           }
                           type uint32 {
                             range "0 .. 7";
                           }
                         }
                       }
                       leaf data-tlv-size {
                         description "Size of the data-tlv portion of Y.1731 frame";
                         units "bytes";
                         junos:must "((\"protocols oam ethernet connectivity-fault-management performance-monitoring sla-iterator-profiles ${sla-iterator-profile} measurement-type two-way-delay\" || (\"protocols oam ethernet connectivity-fault-management performance-monitoring sla-iterator-profiles ${sla-iterator-profile} measurement-type statistical-frame-loss\" || \"protocols oam ethernet connectivity-fault-management performance-monitoring sla-iterator-profiles ${sla-iterator-profile} measurement-type slm\")))";
                         junos:must-message "The measurement type must be two-way-delay or statistical-frame-loss or slm";
                         type union {
                           type string {
                             pattern "<.*>|$.*";
                           }
                           type uint32 {
                             range "1 .. 1400";
                           }
                         }
                       }
                     }
                     leaf detect-loc {
                       description "Detects initial loss of connectivity with remote mep";
                       type empty;
                     }
                   }
                   leaf lowest-priority-defect {
                     description "Lowest priority defect that is allowed to generate a fault alarm";
                     type enumeration {
                       enum "all-defects" {
                         description "Allows all defects";
                       }
                       enum "mac-rem-err-xcon" {
                         description "Allows only MAC, not receiving CCM, erroneous CCM and cross connect defects";
                       }
                       enum "rem-err-xcon" {
                         description "Allows only not receiving CCM, erroneous CCM and cross connect CCM defects";
                       }
                       enum "err-xcon" {
                         description "Allows only erroneous CCM and cross connect CCM defects";
                       }
                       enum "xcon" {
                         description "Allows only cross connect CCM defect";
                       }
                       enum "no-defect" {
                         description "Allows no defect";
                       }
                     }
                   }
                 }
                 container policer {
                   description "Rate limit Ethernet OAM packets for this session";
                   uses apply-advanced;
                   leaf continuity-check {
                     description "Policer to rate limit Continuity Check Ethernet OAM messages";
                     junos:must "(\"firewall policer $$\")";
                     junos:must-message "referenced policer must be defined";
                     type string;
                   }
                   leaf other {
                     description "Policer to rate limit non Continuity Check Ethernet OAM messages";
                     junos:must "(\"firewall policer $$\")";
                     junos:must-message "referenced policer must be defined";
                     type string;
                   }
                   leaf all {
                     description "Policer to rate limit all Ethernet OAM messages";
                     junos:must "(\"firewall policer $$\")";
                     junos:must-message "referenced policer must be defined";
                     type string;
                   }
                 }
               }
             }
             container sendid-tlv {
               description "Include sendid-tlv in CCM/LBM/LTM";
               uses apply-advanced;
               leaf send-chassis-tlv {
                 description "Attach Chassis ID & Mgmt Addr to CCM/LBM/LTM";
                 type empty;
               }
             }
           }
           list evcs {
             key name;
             junos:cli-feature "homogeneous";
             description "Ethernet virtual circuits configuration";
             leaf name {
               description "EVC id";
               junos:cli-feature "nokeyword";
               type string {
                 length "1 .. 100";
                 junos:posix-pattern "!^((__.*__)|(.{100,})|(.*[+].*))$";
                 junos:pattern-message "Must be a non-reserved string of 100 characters or less";
               }
             }
             uses apply-advanced;
             container evc-protocol {
               junos:cli-feature "oneliner";
               description "Signaling protocol to monitor EVC status";
               choice protocol {
                 case case_1 {
                   container cfm {
                     presence "enable cfm";
                     junos:cli-feature "oneliner";
                     description "Connectivity fault management";
                     leaf maintenance-domain {
                       description "Maintenance domain name";
                       junos:must "(\"protocols oam ethernet connectivity-fault-management maintenance-domain $$\")";
                       junos:must-message "referenced maintenance-domain must be defined";
                       type string;
                     }
                     leaf maintenance-association {
                       description "Maintenance association name";
                       junos:must "(any \"protocols oam ethernet connectivity-fault-management maintenance-domain <*> maintenance-association $$\")";
                       junos:must-message "referenced maintenance-association must be defined";
                       type string;
                     }
                     leaf mep {
                       description "Identifier for maintenance association endpoint";
                       junos:must "(any \"protocols oam ethernet connectivity-fault-management maintenance-domain <*> maintenance-association <*> mep $$\")";
                       junos:must-message "referenced maintenance association endpoint must be defined";
                       type union {
                         type string {
                           pattern "<.*>|$.*";
                         }
                         type uint16 {
                           range "1 .. 8191";
                         }
                       }
                     }
                     container faults {
                       description "CFM faults to trigger ELMI";
                       uses apply-advanced;
                       leaf rdi {
                         description "RDI received from some MEP";
                         type empty;
                       }
                     }
                   }
                 }
                 case case_2 {
                   container vpls {
                     presence "enable vpls";
                     junos:cli-feature "oneliner";
                     description "Virtual private LAN service (BGP/LDP)";
                     leaf routing-instance {
                       description "Routing instance name";
                       junos:must "((\"routing-instances $$ instance-type vpls\" || (\"routing-instances $$ instance-type virtual-switch\" && \"routing-instances $$ protocols vpls\")))";
                       junos:must-message "referenced routing-instnace must be of instance-type vpls or instance-type virtual-swicth with protocols vpls configured";
                       junos:must "((\"routing-instances $$\" || any \"tenants <*> routing-instances $$\"))";
                       junos:must-message "referenced routing-instance must be defined";
                       type string;
                     }
                   }
                 }
                 case case_3 {
                   container l2circuit {
                     description "L2circuit";
                     uses apply-advanced;
                     container interface {
                       junos:cli-feature "oneliner";
                       description "Name of interface forming the Layer 2 circuit";
                       leaf interface-name {
                         junos:cli-feature "nokeyword";
                         junos:must "(any \"protocols l2circuit neighbor <*> interface $$\")";
                         junos:must-message "referenced interface must be defined in l2circuit configuration";
                         type union {
                           type jt:interface-name;
                           type string {
                             pattern "<.*>|$.*";
                           }
                         }
                       }
                     }
                   }
                 }
                 case case_4 {
                   container l2vpn {
                     description "L2vpn";
                     uses apply-advanced;
                     container interface {
                       junos:cli-feature "oneliner";
                       description "Name of interface forming the Layer 2 VPN";
                       leaf interface-name {
                         junos:cli-feature "nokeyword";
                         junos:must "(any \"routing-instances <*> protocols l2vpn site <*> interface $$\")";
                         junos:must-message "referenced interface must be defined in l2vpn configuration";
                         type union {
                           type jt:interface-name;
                           type string {
                             pattern "<.*>|$.*";
                           }
                         }
                       }
                     }
                   }
                 }
               }
             }
             leaf remote-uni-count {
               description "Number of remote UNIs in the EVC";
               default "1";
               type union {
                 type string {
                   pattern "<.*>|$.*";
                 }
                 type uint8 {
                   range "1 .. 255";
                 }
               }
             }
             leaf async-status-msg-transmit-interval {
               description "Time interval between E-LMI async status messages per EVC";
               default "10";
               units "milliseconds";
               type union {
                 type string {
                   pattern "<.*>|$.*";
                 }
                 type int32 {
                   range "1 .. 10000";
                 }
               }
             }
             leaf multipoint-to-multipoint {
               description "Multipoint to Multipoint EVC";
               type empty;
             }
           }
           container lmi {
             presence "enable lmi";
             description "Ethernet local management interface configuration";
             uses apply-advanced;
             container traceoptions {
               description "Trace options for ethernet local management interface";
               uses apply-advanced;
               leaf no-remote-trace {
                 description "Disable remote tracing";
                 junos:must "(\"system tracing\")";
                 junos:must-message "'no-remote-trace' is valid only when [system tracing] is configured";
                 type empty;
               }
               container file {
                 junos:cli-feature "oneliner";
                 description "Trace file information";
                 leaf filename {
                   description "Name of file in which to write trace information";
                   junos:cli-feature "nokeyword";
                   type string {
                     length "1 .. 1024";
                     junos:posix-pattern "![/ %]";
                     junos:pattern-message "Must not contain \'/\', % or a space";
                   }
                 }
                 leaf size {
                   description "Maximum trace file size";
                   units "bytes";
                   type string;
                 }
                 leaf files {
                   description "Maximum number of trace files";
                   default "3";
                   type union {
                     type string {
                       pattern "<.*>|$.*";
                     }
                     type uint32 {
                       range "2 .. 1000";
                     }
                   }
                 }
                 choice world-readable-choice {
                   leaf world-readable {
                     description "Allow any user to read the log file";
                     type empty;
                   }
                   leaf no-world-readable {
                     description "Don't allow any user to read the log file";
                     type empty;
                   }
                 }
                 leaf match {
                   description "Regular expression for lines to be logged";
                   type jt:regular-expression;
                 }
               }
               list flag {
                 key name;
                 ordered-by user;
                 junos:cli-feature "oneliner";
                 description "Tracing parameters";
                 leaf name {
                   junos:cli-feature "nokeyword";
                   type enumeration {
                     enum "configuration" {
                       description "Trace configuration events";
                     }
                     enum "routing-socket" {
                       description "Trace routing socket events";
                     }
                     enum "protocol" {
                       description "Trace protocol processing events";
                     }
                     enum "init" {
                       description "Trace events related to protocol daemon start-up";
                     }
                     enum "error" {
                       description "Trace events related to catestrophic errors in daemon";
                     }
                     enum "packet" {
                       description "Trace events related to packet flow";
                     }
                     enum "all" {
                       description "Trace everything";
                     }
                   }
                 }
               }
             }
             leaf status-counter {
               description "E-LMI status counter (N393)";
               default "4";
               type union {
                 type string {
                   pattern "<.*>|$.*";
                 }
                 type uint8 {
                   range "2 .. 10";
                 }
               }
             }
             leaf polling-verification-timer {
               description "Polling verification timer (T392)";
               default "15";
               units "seconds";
               type union {
                 type string {
                   pattern "<.*>|$.*";
                 }
                 type uint8 {
                   range "5 .. 30";
                 }
               }
             }
             list interface {
               key name;
               description "Interface options";
               leaf name {
                 junos:cli-feature "nokeyword";
                 type union {
                   type jt:interface-device;
                   type string {
                     pattern "<.*>|$.*";
                   }
                 }
               }
               uses apply-advanced;
               leaf uni-id {
                 description "UNI identifier";
                 type string {
                   length "1 .. 64";
                 }
               }
               leaf status-counter {
                 description "E-LMI status counter (N393)";
                 default "4";
                 type union {
                   type string {
                     pattern "<.*>|$.*";
                   }
                   type uint8 {
                     range "2 .. 10";
                   }
                 }
               }
               leaf polling-verification-timer {
                 description "Polling verification timer (T392)";
                 default "15";
                 units "seconds";
                 type union {
                   type string {
                     pattern "<.*>|$.*";
                   }
                   type uint8 {
                     range "5 .. 30";
                   }
                 }
               }
               leaf evc-map-type {
                 description "CE-VLAN ID/EVC map type";
                 default "bundling";
                 type enumeration {
                   enum "all-to-one-bundling" {
                     description "All to one bundling";
                   }
                   enum "service-multiplexing" {
                     description "Service multiplexing with no bundling";
                   }
                   enum "bundling" {
                     description "Bundling with service multiplexing";
                   }
                 }
               }
               list evc {
                 key name;
                 description "EVC configuration";
                 leaf name {
                   description "EVC identifier";
                   junos:cli-feature "nokeyword";
                   junos:must "(\"protocols oam ethernet evcs $$\")";
                   junos:must-message "referenced evc must be defined";
                   type string {
                     length "1 .. 100";
                   }
                 }
                 uses apply-advanced;
                 leaf default-evc {
                   description "Default EVC";
                   type empty;
                 }
                 leaf-list vlan-list {
                   description "Vlans mapped to this EVC";
                   type jt:vlan-range;
                 }
               }
             }
           }
           container fnp {
             presence "enable fnp";
             description "Failure notification protocol configuration";
             uses apply-advanced;
             container traceoptions {
               description "Tracing options for FNP";
               uses apply-advanced;
               container file {
                 junos:cli-feature "oneliner";
                 description "Trace file options";
                 leaf filename {
                   description "Name of file in which to write trace information";
                   junos:cli-feature "nokeyword";
                   type string {
                     length "1 .. 1024";
                     junos:posix-pattern "![/ %]";
                     junos:pattern-message "Must not contain \'/\', % or a space";
                   }
                 }
                 leaf replace {
                   description "Replace trace file rather than appending to it";
                   status deprecated;
                   type empty;
                 }
                 leaf size {
                   description "Maximum trace file size";
                   type string;
                 }
                 leaf files {
                   description "Maximum number of trace files";
                   default "10";
                   type union {
                     type string {
                       pattern "<.*>|$.*";
                     }
                     type uint32 {
                       range "2 .. 1000";
                     }
                   }
                 }
                 leaf no-stamp {
                   description "Do not timestamp trace file";
                   status deprecated;
                   type empty;
                 }
                 choice world-readable-choice {
                   leaf world-readable {
                     description "Allow any user to read the log file";
                     type empty;
                   }
                   leaf no-world-readable {
                     description "Don't allow any user to read the log file";
                     type empty;
                   }
                 }
               }
               list flag {
                 key name;
                 ordered-by user;
                 junos:cli-feature "oneliner";
                 description "Tracing parameters";
                 leaf name {
                   junos:cli-feature "nokeyword";
                   type enumeration {
                     enum "events" {
                       description "Trace protocol events";
                     }
                     enum "pdu" {
                       description "Trace PDU reception and transmission";
                     }
                     enum "timers" {
                       description "Trace protocol timers";
                     }
                     enum "error" {
                       description "Trace all failure conditions";
                     }
                     enum "all" {
                       description "Trace all";
                     }
                   }
                 }
               }
             }
             leaf interval {
               description "Interval between FNP messages";
               default "1s";
               type enumeration {
                 enum "100ms" {
                 }
                 enum "1s" {
                 }
                 enum "10s" {
                 }
                 enum "1m" {
                 }
                 enum "10m" {
                 }
               }
             }
             leaf loss-threshold {
               description "Number of FNP messages lost before clearing FNP state";
               default "4";
               type union {
                 type string {
                   pattern "<.*>|$.*";
                 }
                 type uint8 {
                   range "3 .. 255";
                 }
               }
             }
             list interface {
               key name;
               ordered-by user;
               junos:cli-feature "oneliner-plus";
               description "Interface configuration";
               leaf name {
                 junos:cli-feature "nokeyword";
                 junos:must "(\"interfaces $$ encapsulation vlan-vpls\")";
                 junos:must-message "FNP is allowed on interfaces with vlan-vpls encapsulation only.";
                 type union {
                   type jt:interface-name;
                   type string {
                     pattern "<.*>|$.*";
                   }
                 }
               }
               uses apply-advanced;
               leaf domain-id {
                 description "Ethernet domain identifier";
                 default "0";
                 type union {
                   type uint32;
                   type string {
                     pattern "<.*>|$.*";
                   }
                 }
               }
             }
           }
         }
       }
       container mld {
         presence "enable mld";
         description "MLD options";
         uses apply-advanced;
         container traceoptions {
           description "Trace options for MLD";
           uses apply-advanced;
           container file {
             junos:cli-feature "oneliner";
             description "Trace file options";
             leaf filename {
               description "Name of file in which to write trace information";
               junos:cli-feature "nokeyword";
               type string {
                 length "1 .. 1024";
                 junos:posix-pattern "![/ %]";
                 junos:pattern-message "Must not contain \'/\', % or a space";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             junos:cli-feature "oneliner";
             description "Tracing parameters";
             leaf name {
               junos:cli-feature "nokeyword";
               type enumeration {
                 enum "packets" {
                   description "Trace all MLD packets";
                 }
                 enum "query" {
                   description "Trace MLD membership query messages";
                 }
                 enum "report" {
                   description "Trace membership report messages";
                 }
                 enum "leave" {
                   description "Trace leave group messages (MLDv2 only)";
                 }
                 enum "mtrace" {
                   description "Trace mtrace packets";
                 }
                 enum "group" {
                   description "Trace group operations";
                 }
                 enum "client-notification" {
                   description "Trace notifications";
                 }
                 enum "host-notification" {
                   description "Trace host notifications";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
             junos:posix-pattern "^[0-9]{1,4}(.[0-9])?$";
             junos:pattern-message "Up to 1 digit to right of decimal point";
           }
         }
         leaf query-last-member-interval {
           description "When to send group query messages";
           units "seconds";
           type string {
             junos:posix-pattern "^[0-9]{1,4}(.[0-9])?$";
             junos:pattern-message "Up to 1 digit to right of decimal point";
           }
         }
         leaf robust-count {
           description "Expected packet loss on a subnet";
           type union {
             type string {
               pattern "<.*>|$.*";
             }
             type uint32 {
               range "2 .. 10";
             }
           }
         }
         leaf maximum-transmit-rate {
           description "Maximum transmission rate (packets per second)";
           type union {
             type string {
               pattern "<.*>|$.*";
             }
             type uint32 {
               range "1 .. 10000";
             }
           }
         }
         leaf accounting {
           description "Enable join and leave event notification";
           type empty;
         }
         list interface {
           key name;
           ordered-by user;
           description "Interface options for MLD";
           leaf name {
             junos:cli-feature "nokeyword";
             type string;
           }
           uses apply-advanced;
           choice enable-disable {
             case case_1 {
               leaf disable {
                 description "Disable MLD on this interface";
                 type empty;
               }
             }
           }
           leaf version {
             description "Set mld version number on this interface";
             type union {
               type string {
                 pattern "<.*>|$.*";
               }
               type uint8 {
                 range "1 .. 2";
               }
             }
           }
           container static {
             description "Static group or source membership";
             uses apply-advanced;
             list group {
               key name;
               ordered-by user;
               description "IP multicast group address";
               leaf name {
                 description "IP multicast group address";
                 junos:cli-feature "nokeyword";
                 type jt:ipv6addr;
               }
               uses apply-advanced;
               leaf group-increment {
                 description "Mask for the incrementing group IP address";
                 type jt:ipv6addr;
               }
               leaf group-count {
                 description "Number of groups";
                 type union {
                   type string {
                     pattern "<.*>|$.*";
                   }
                   type uint32 {
                     range "1 .. 512";
                   }
                 }
               }
               leaf exclude {
                 description "Exclude sources";
                 type empty;
               }
               list source {
                 key name;
                 ordered-by user;
                 description "IP multicast source address";
                 leaf name {
                   description "Source address of IP multicast data";
                   junos:cli-feature "nokeyword";
                   type jt:ipv6addr;
                 }
                 uses apply-advanced;
                 leaf source-increment {
                   description "Mask for the incrementing source IP address";
                   type jt:ipv6addr;
                 }
                 leaf source-count {
                   description "Number of sources";
                   type union {
                     type string {
                       pattern "<.*>|$.*";
                     }
                     type uint32 {
                       range "1 .. 1024";
                     }
                   }
                 }
               }
             }
           }
           leaf ssm-map {
             description "Map for ssm translation of mld v1 messages";
             type string;
           }
           leaf-list ssm-map-policy {
             ordered-by user;
             description "SSM map policy name";
             type jt:policy-algebra;
           }
           leaf immediate-leave {
             description "Group removed immediately, last membership query not sent";
             type empty;
           }
           leaf-list group-policy {
             ordered-by user;
             description "Group filter applied to incoming mld report messages";
             type jt:policy-algebra;
           }
           leaf group-limit {
             description "Maximum number of (source,group) per interface";
             type union {
               type string {
                 pattern "<.*>|$.*";
               }
               type uint16 {
                 range "1 .. 32767";
               }
             }
           }
           leaf group-threshold {
             description "Percentage of group-limit at which to start generating warnings";
             junos:must "(\".. group-limit\")";
             junos:must-message "To configure group-threshold, group-limit must be configured";
             type union {
               type string {
                 pattern "<.*>|$.*";
               }
               type uint16 {
                 range "1 .. 100";
               }
             }
           }
           leaf log-interval {
             description "Time between consecutive log messages";
             junos:must "(\".. group-limit\")";
             junos:must-message "To configure log-interval, group-limit must be configured";
             type union {
               type string {
                 pattern "<.*>|$.*";
               }
               type uint16 {
                 range "6 .. 32767";
               }
             }
           }
           choice accounting-choice {
             leaf accounting {
               description "Enable join and leave event notification";
               type empty;
             }
             leaf no-accounting {
               description "Don't enable join and leave event notification";
               type empty;
             }
           }
           container passive {
             presence "enable passive";
             junos:cli-feature "oneliner";
             description "Suppress sending and receiving mld messages";
             leaf allow-receive {
               description "Allow receiving mld messages";
               type empty;
             }
             leaf send-general-query {
               description "Send mld general query messages";
               type empty;
             }
             leaf send-group-query {
               description "Send mld group query messages";
               type empty;
             }
           }
           leaf-list oif-map {
             ordered-by user;
             description "Output interface map";
             type jt:policy-algebra;
           }
           leaf distributed {
             description "Distributed MLD interface";
             junos:must "(\"chassis network-services enhanced-ip\")";
             junos:must-message "distributed is supported only in enhanced-ip mode";
             type empty;
           }
         }
       }
       container pim {
         description "PIM configuration";
         uses juniper-protocols-pim;
       }
       container router-advertisement {
         description "IPv6 router advertisement options";
         uses apply-advanced;
         container traceoptions {
           description "Trace options for router advertisement";
           uses apply-advanced;
           container file {
             junos:cli-feature "oneliner";
             description "Trace file options";
             leaf filename {
               description "Name of file in which to write trace information";
               junos:cli-feature "nokeyword";
               type string {
                 length "1 .. 1024";
                 junos:posix-pattern "![/ %]";
                 junos:pattern-message "Must not contain \'/\', % or a space";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             junos:cli-feature "oneliner";
             description "Tracing parameters";
             leaf name {
               junos:cli-feature "nokeyword";
               type enumeration {
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
           }
         }
         list interface {
           key name;
           ordered-by user;
           description "Interfaces on which to configure router advertisement";
           leaf name {
             junos:cli-feature "nokeyword";
             type string;
           }
           uses apply-advanced;
           leaf preference {
             description "Set the Preference for Router Selection";
             type enumeration {
               enum "medium" {
                 description "Medium / (Default)";
               }
               enum "high" {
                 description "High";
               }
               enum "low" {
                 description "Low";
               }
             }
           }
           leaf max-advertisement-interval {
             description "Maximum advertisement interval";
             units "seconds";
             type union {
               type string {
                 pattern "<.*>|$.*";
               }
               type uint32 {
                 range "4 .. 1800";
               }
             }
           }
           leaf min-advertisement-interval {
             description "Minimum advertisement interval";
             units "seconds";
             type union {
               type string {
                 pattern "<.*>|$.*";
               }
               type uint32 {
                 range "3 .. 1350";
               }
             }
           }
           choice managed-configuration-choice {
             leaf managed-configuration {
               description "Set managed address configuration";
               type empty;
             }
             leaf no-managed-configuration {
               description "Don't set managed address configuration";
               type empty;
             }
           }
           choice other-stateful-configuration-choice {
             leaf other-stateful-configuration {
               description "Set other stateful configuration";
               type empty;
             }
             leaf no-other-stateful-configuration {
               description "Don't set other stateful configuration";
               type empty;
             }
           }
           choice link-mtu-choice {
             leaf link-mtu {
               description "Link MTU";
               type empty;
             }
             leaf no-link-mtu {
               description "Don't link MTU";
               type empty;
             }
           }
           leaf solicit-router-advertisement-unicast {
             description "Enable solicited router advertisement as unicast";
             type empty;
           }
           leaf reachable-time {
             description "Reachable time";
             units "milliseconds";
             type union {
               type string {
                 pattern "<.*>|$.*";
               }
               type uint32 {
                 range "0 .. 3600000";
               }
             }
           }
           leaf retransmit-timer {
             description "Retransmit timer";
             units "milliseconds";
             type union {
               type string {
                 pattern "<.*>|$.*";
               }
               type uint32 {
                 range "0 .. 4294967295";
               }
             }
           }
           leaf virtual-router-only {
             description "Send advertisements only for vrrp-inet6-group";
             type empty;
           }
           leaf current-hop-limit {
             description "Current hop limit";
             type union {
               type string {
                 pattern "<.*>|$.*";
               }
               type uint32 {
                 range "0 .. 255";
               }
             }
           }
           leaf default-lifetime {
             description "Router lifetime";
             units "seconds";
             type union {
               type string {
                 pattern "<.*>|$.*";
               }
               type uint32 {
                 range "0 .. 9000";
               }
             }
           }
           list downstream {
             key name;
             ordered-by user;
             description "Configure the list of downstream interfaces for RA proxy";
             leaf name {
               description "Configure the downstream interface for RA proxy";
               junos:cli-feature "nokeyword";
               type string;
             }
             uses apply-advanced;
           }
           leaf upstream-mode {
             description "Configure the interface as upstream interface for RA proxy";
             type empty;
           }
           leaf downstream-mode {
             description "Configure the interface as downstream interface for RA proxy";
             type empty;
           }
           leaf parameter-preference {
             description "Preference to select configured or proxied parameters for downstream interface";
             type enumeration {
               enum "proxied" {
                 description "Send proxied parameters on downstream interface";
               }
               enum "configured" {
                 description "Send configured parameters on downstream interface";
               }
             }
           }
           leaf passive-mode {
             description "RA receive only mode";
             type empty;
           }
           list dns-server-address {
             key name;
             ordered-by user;
             description "Recursive DNS address configuration";
             max-elements 3;
             leaf name {
               description "DNS address to be advertised";
               junos:cli-feature "nokeyword";
               type string;
             }
             uses apply-advanced;
             leaf lifetime {
               description "DNS address lifetime";
               default "1800";
               units "seconds";
               type union {
                 type string {
                   pattern "<.*>|$.*";
                 }
                 type uint32 {
                   range "0 .. 4294967295";
                 }
               }
             }
           }
           list prefix {
             key name;
             ordered-by user;
             description "Prefix configuration";
             leaf name {
               description "Prefix to be advertised";
               junos:cli-feature "nokeyword";
               type jt:ipv6prefix;
             }
             uses apply-advanced;
             leaf valid-lifetime {
               description "Valid lifetime (fixed)";
               units "seconds";
               type union {
                 type string {
                   pattern "<.*>|$.*";
                 }
                 type uint32 {
                   range "0 .. 4294967295";
                 }
               }
             }
             choice on-link-choice {
               leaf on-link {
                 description "Set on-link flag";
                 type empty;
               }
               leaf no-on-link {
                 description "Don't set on-link flag";
                 type empty;
               }
             }
             leaf preferred-lifetime {
               description "Preferred lifetime (fixed)";
               units "seconds";
               type union {
                 type string {
                   pattern "<.*>|$.*";
                 }
                 type uint32 {
                   range "0 .. 4294967295";
                 }
               }
             }
             choice autonomous-choice {
               leaf autonomous {
                 description "Set autonomous flag";
                 type empty;
               }
               leaf no-autonomous {
                 description "Don't set autonomous flag";
                 type empty;
               }
             }
           }
           list dns-search-list {
             key name;
             ordered-by user;
             description "DNS search list configuration";
             leaf name {
               description "DNS search list name";
               junos:cli-feature "nokeyword";
               type string;
             }
             uses apply-advanced;
             leaf lifetime {
               description "DNS search list lifetime";
               default "5400";
               units "seconds";
               type union {
                 type string {
                   pattern "<.*>|$.*";
                 }
                 type uint32 {
                   range "0 .. 4294967295";
                 }
               }
             }
           }
           list rio-prefix {
             key name;
             ordered-by user;
             description "Route information option configuration";
             leaf name {
               description "Prefix to be advertised";
               junos:cli-feature "nokeyword";
               type jt:ipv6prefix;
             }
             uses apply-advanced;
             leaf rio-lifetime {
               description "Route information lifetime";
               units "seconds";
               type union {
                 type string {
                   pattern "<.*>|$.*";
                 }
                 type uint32 {
                   range "0 .. 4294967295";
                 }
               }
             }
             leaf rio-preference {
               description "Set the preference for route information";
               type enumeration {
                 enum "medium" {
                   description "Medium / Default";
                 }
                 enum "high" {
                   description "High";
                 }
                 enum "low" {
                   description "Low";
                 }
               }
             }
           }
           list nat-prefix {
             key name;
             ordered-by user;
             description "NAT prefix";
             leaf name {
               description "NAT prefix to be advertised";
               junos:cli-feature "nokeyword";
               type jt:ipv6prefix;
             }
             uses apply-advanced;
             leaf lifetime {
               description "NAT prefix lifetime";
               units "seconds";
               type union {
                 type string {
                   pattern "<.*>|$.*";
                 }
                 type uint16 {
                   range "0 .. 65528";
                 }
               }
             }
           }
         }
         container ra-secure {
           description "Protect box against rogue incoming RA messages";
           uses apply-advanced;
           leaf accept-current-hop-limit-min {
             description "Current hop limit acceptable min for incoming RA";
             units "uint";
             type union {
               type string {
                 pattern "<.*>|$.*";
               }
               type uint32 {
                 range "1 .. 255";
               }
             }
           }
           leaf accept-current-hop-limit-max {
             description "Current hop acceptable min for incoming RA";
             units "uint";
             type union {
               type string {
                 pattern "<.*>|$.*";
               }
               type uint32 {
                 range "1 .. 255";
               }
             }
           }
           leaf accept-reachable-time-min {
             description "Reachable Time acceptable min for incoming RA";
             units "milliseconds";
             type union {
               type string {
                 pattern "<.*>|$.*";
               }
               type uint32 {
                 range "1000 .. 3600000";
               }
             }
           }
           leaf accept-reachable-time-max {
             description "Reachable Time acceptable max for incoming RA";
             units "milliseconds";
             type union {
               type string {
                 pattern "<.*>|$.*";
               }
               type uint32 {
                 range "1000 .. 3600000";
               }
             }
           }
           leaf accept-retransmit-time-min {
             description "Retransmit Time acceptable min for incoming RA";
             units "milliseconds";
             type union {
               type string {
                 pattern "<.*>|$.*";
               }
               type uint32 {
                 range "1000 .. 3600000";
               }
             }
           }
           leaf accept-retransmit-time-max {
             description "Retransmit Time acceptable min for incoming RA";
             units "milliseconds";
             type union {
               type string {
                 pattern "<.*>|$.*";
               }
               type uint32 {
                 range "1000 .. 3600000";
               }
             }
           }
         }
       }
     }
     container class-of-service {
       description "Class-of-service configuration";
       uses juniper-class-of-service-options;
     }
     container routing-options {
       description "Protocol-independent routing option configuration";
       uses apply-advanced;
       list rib {
         key name;
         description "Routing table options";
         leaf name {
           description "Routing table name";
           junos:cli-feature "nokeyword";
           type string;
         }
         uses apply-advanced;
         container static {
           description "Static routes";
           uses apply-advanced;
           leaf rib-group {
             description "Routing table group";
             type string;
           }
           container defaults {
             description "Global route options";
             uses apply-advanced;
             choice retain-choice {
               leaf retain {
                 description "Always keep route in forwarding table";
                 junos:must "(!(\".. resolve\"))";
                 junos:must-message "Must not specify resolve with retain";
                 type empty;
               }
               leaf no-retain {
                 description "Don't always keep route in forwarding table";
                 junos:must "(!(\".. resolve\"))";
                 junos:must-message "Must not specify resolve with retain";
                 type empty;
               }
             }
             choice install-choice {
               leaf install {
                 description "Install route into forwarding table";
                 type empty;
               }
               leaf no-install {
                 description "Don't install route into forwarding table";
                 type empty;
               }
             }
             choice readvertise-choice {
               leaf readvertise {
                 description "Mark route as eligible to be readvertised";
                 type empty;
               }
               leaf no-readvertise {
                 description "Don't mark route as eligible to be readvertised";
                 type empty;
               }
             }
             choice resolve-choice {
               leaf resolve {
                 description "Allow resolution of indirectly connected next hops";
                 type empty;
               }
               leaf no-resolve {
                 description "Don't allow resolution of indirectly connected next hops";
                 type empty;
               }
             }
             leaf explicit-null {
               description "Allows service label to be popped and will lookup nexthop-table inet6.0";
               junos:must "(\".. resolve\")";
               junos:must-message "Requires resolve to be configured";
               type empty;
             }
             choice longest-match-choice {
               leaf longest-match {
                 description "Always use longest prefix match to resolve next hops";
                 junos:must "(\".. resolve\")";
                 junos:must-message "Requires resolve to be configured";
                 type empty;
               }
               leaf no-longest-match {
                 description "Don't always use longest prefix match to resolve next hops";
                 junos:must "(\".. resolve\")";
                 junos:must-message "Requires resolve to be configured";
                 type empty;
               }
             }
             choice passive_flag {
               case case_1 {
                 leaf active {
                   description "Remove inactive route from forwarding table";
                   type empty;
                 }
               }
               case case_2 {
                 leaf passive {
                   description "Retain inactive route in forwarding table";
                   type empty;
                 }
               }
             }
             container metric {
               description "Metric value";
               presence "enable metric";
               junos:cli-feature "oneliner";
               uses rib_static_metric_type;
             }
             container metric2 {
               description "Metric value 2";
               presence "enable metric2";
               junos:cli-feature "oneliner";
               uses rib_static_metric_type;
             }
             container metric3 {
               description "Metric value 3";
               presence "enable metric3";
               junos:cli-feature "oneliner";
               uses rib_static_metric_type;
             }
             container metric4 {
               description "Metric value 4";
               presence "enable metric4";
               junos:cli-feature "oneliner";
               uses rib_static_metric_type;
             }
             container tag {
               description "Tag string";
               presence "enable tag";
               junos:cli-feature "oneliner";
               uses rib_static_metric_type;
             }
             container tag2 {
               description "Tag string 2";
               presence "enable tag2";
               junos:cli-feature "oneliner";
               uses rib_static_metric_type;
             }
             container preference {
               description "Preference value";
               presence "enable preference";
               junos:cli-feature "oneliner";
               uses rib_static_metric_type;
             }
             container preference2 {
               description "Preference value 2";
               presence "enable preference2";
               junos:cli-feature "oneliner";
               uses rib_static_metric_type;
             }
             container color {
               description "Color (preference) value";
               presence "enable color";
               junos:cli-feature "oneliner";
               uses rib_static_metric_type;
             }
             container color2 {
               description "Color (preference) value 2";
               presence "enable color2";
               junos:cli-feature "oneliner";
               uses rib_static_metric_type;
             }
             leaf-list community {
               ordered-by user;
               description "BGP community identifier";
               type jt:community;
             }
             container as-path {
               description "Autonomous system path";
               uses apply-advanced;
               leaf path {
                 description "Autonomous system path";
                 type string;
               }
               leaf origin {
                 type enumeration {
                   enum "igp" {
                     description "Path originated in the local IGP";
                   }
                   enum "egp" {
                     description "Path originated in another AS";
                   }
                   enum "incomplete" {
                     description "Path was learned by some other means";
                   }
                 }
               }
               leaf atomic-aggregate {
                 description "Add ATOMIC_AGGREGATE path attribute to route";
                 type empty;
               }
               container aggregator {
                 presence "enable aggregator";
                 description "Add AGGREGATOR path attribute to route";
               }
               leaf as-number {
                 description " Autonomous system number in plain number or 'higher 16bits'.'Lower 16 bits' (asdot notation) format";
                 junos:cli-feature "nokeyword";
                 type string {
                   junos:posix-pattern "^[0-9]+(.[0-9]+)?$";
                   junos:pattern-message "Use format \'x\' or \'x.y\' to specify number \'x\' (Range 1 .. 4294967295) or number with higher 2 bytes \'x\' (Range 0 .. 65535) and lower 2 bytes \'y\' (Range 0 .. 65535) respectively";
                 }
               }
               leaf address {
                 description "Address of BGP system that formed the route";
                 junos:cli-feature "nokeyword";
                 type jt:ipv4addr;
               }
             }
           }
           list route {
             key name;
             junos:cli-feature "oneliner-plus";
             description "Static route";
             leaf name {
               junos:cli-feature "nokeyword";
               type jt:ipprefix;
             }
             uses apply-advanced;
             leaf priority {
               description "Static route priority high/medium/low";
               type enumeration {
                 enum "medium" {
                   description "Static route medium priority";
                 }
                 enum "low" {
                   description "Static route low priority";
                 }
                 enum "high" {
                   description "Static route high priority";
                 }
               }
             }
             choice next_hop {
               case case_1 {
                 leaf-list next-hop {
                   ordered-by user;
                   description "Next hop to destination";
                   type union {
                     type jt:ipaddr-or-interface;
                     type string {
                       pattern "<.*>|$.*";
                     }
                   }
                 }
               }
               case case_2 {
                 leaf reject {
                   description "Drop packets to destination; send ICMP unreachables";
                   type empty;
                 }
               }
               case case_3 {
                 leaf discard {
                   description "Drop packets to destination; send no ICMP unreachables";
                   type empty;
                 }
               }
               case case_4 {
                 leaf receive {
                   description "Install a receive route for the destination";
                   type empty;
                 }
               }
               case case_5 {
                 leaf next-table {
                   description "Next hop to another table";
                   type string {
                     junos:posix-pattern "^(((.{0,128})[:](.{1,128})[.]|((.{1,128})[.]))?([a-z]|[0-9]|[-_])+[.]((1?[0-9]{1,2})|(2[0-4][0-9])|(25[0-5])))$";
                     junos:pattern-message "Must match the format [<instance-name>[:<topology-name>].]<family-name>.<rib-id>";
                   }
                 }
               }
             }
             leaf description {
               description "Static route description";
               type string {
                 junos:posix-pattern "^.{1,255}$";
                 junos:pattern-message "Must be a string of 255 characters or less";
               }
             }
             list qualified-next-hop {
               key name;
               ordered-by user;
               description "Next hop with qualifiers";
               uses qualified_nh_obj;
             }
             leaf backup-pe-group {
               description "Multicast source redundancy group";
               junos:must "(\".. p2mp-lsp-next-hop\")";
               junos:must-message "Backup groups only allowed for static routes with p2mp lsp next-hop";
               type string;
             }
             container bfd-liveness-detection {
               description "Bidirectional Forwarding Detection (BFD) options";
               uses apply-advanced;
               leaf version {
                 description "BFD protocol version number";
                 default "automatic";
                 type enumeration {
                   enum "0" {
                     description "BFD version 0 (deprecated)";
                   }
                   enum "1" {
                     description "BFD version 1";
                   }
                   enum "automatic" {
                     description "Choose BFD version automatically";
                   }
                 }
               }
               leaf minimum-interval {
                 description "Minimum transmit and receive interval";
                 units "milliseconds";
                 type union {
                   type string {
                     pattern "<.*>|$.*";
                   }
                   type uint32 {
                     range "1 .. 255000";
                   }
                 }
               }
               leaf minimum-transmit-interval {
                 description "Minimum transmit interval";
                 status deprecated;
                 units "milliseconds";
                 type union {
                   type string {
                     pattern "<.*>|$.*";
                   }
                   type uint32 {
                     range "1 .. 255000";
                   }
                 }
               }
               leaf minimum-receive-interval {
                 description "Minimum receive interval";
                 units "milliseconds";
                 type union {
                   type string {
                     pattern "<.*>|$.*";
                   }
                   type uint32 {
                     range "1 .. 255000";
                   }
                 }
               }
               leaf multiplier {
                 description "Detection time multiplier";
                 default "3";
                 type union {
                   type string {
                     pattern "<.*>|$.*";
                   }
                   type uint32 {
                     range "1 .. 255";
                   }
                 }
               }
               leaf inline-disable {
                 description "Disable inline mode for this BFD session";
                 type empty;
               }
               leaf pdu-size {
                 description "BFD transport protocol payload size";
                 default "24";
                 type union {
                   type string {
                     pattern "<.*>|$.*";
                   }
                   type uint32 {
                     range "24 .. 16000";
                   }
                 }
               }
               choice adaptation-choice {
                 case case_1 {
                   leaf no-adaptation {
                     description "Disable adaptation";
                     type empty;
                   }
                 }
               }
               container transmit-interval {
                 description "Transmit-interval options";
                 uses apply-advanced;
                 leaf minimum-interval {
                   description "Minimum transmit interval";
                   units "milliseconds";
                   type union {
                     type string {
                       pattern "<.*>|$.*";
                     }
                     type uint32 {
                       range "1 .. 255000";
                     }
                   }
                 }
                 leaf threshold {
                   description "High transmit interval triggering a trap";
                   units "milliseconds";
                   type union {
                     type uint32;
                     type string {
                       pattern "<.*>|$.*";
                     }
                   }
                 }
               }
               container detection-time {
                 description "Detection-time options";
                 uses apply-advanced;
                 leaf threshold {
                   description "High detection-time triggering a trap";
                   units "milliseconds";
                   type union {
                     type uint32;
                     type string {
                       pattern "<.*>|$.*";
                     }
                   }
                 }
               }
               container authentication {
                 description "Authentication options";
                 uses apply-advanced;
                 leaf key-chain {
                   description "Key chain name";
                   junos:must "(\".. algorithm\")";
                   junos:must-message "May not be configured without algorithm";
                   junos:must "(\"security authentication-key-chains key-chain $$\")";
                   junos:must-message "Referenced key-chain must be defined";
                   type string;
                 }
                 leaf algorithm {
                   description "Algorithm name";
                   junos:must "(\".. key-chain\")";
                   junos:must-message "May not be configured without key-chain";
                   type enumeration {
                     enum "simple-password" {
                       description "Simple password";
                     }
                     enum "keyed-md5" {
                       description "Keyed message Digest 5";
                     }
                     enum "meticulous-keyed-md5" {
                       description "Meticulous keyed message Digest 5";
                     }
                     enum "keyed-sha-1" {
                       description "Keyed secure hash algorithm (SHA1) ";
                     }
                     enum "meticulous-keyed-sha-1" {
                       description "Meticulous keyed secure hash algorithm (SHA1) ";
                     }
                   }
                 }
                 leaf loose-check {
                   description "Verify authentication only if authentication is negotiated";
                   type empty;
                 }
               }
               container echo {
                 junos:must "(!(\".. echo-lite\"))";
                 junos:must-message "'echo-lite' and 'echo' mode cannot be configured at the same time";
                 description "Echo mode parameters";
                 uses apply-advanced;
                 leaf minimum-interval {
                   description "Minimum transmit and receive interval";
                   units "milliseconds";
                   type union {
                     type string {
                       pattern "<.*>|$.*";
                     }
                     type uint32 {
                       range "100 .. 255000";
                     }
                   }
                 }
               }
               container echo-lite {
                 junos:must "(!(\".. echo\"))";
                 junos:must-message "'echo-lite' and 'echo' mode cannot be configured at the same time";
                 description "Echo-lite more parameters";
                 uses apply-advanced;
                 leaf minimum-interval {
                   description "Minimum transmit and receive interval";
                   units "milliseconds";
                   type union {
                     type string {
                       pattern "<.*>|$.*";
                     }
                     type uint32 {
                       range "1 .. 255000";
                     }
                   }
                 }
               }
               leaf neighbor {
                 description "BFD neighbor address";
                 type jt:ipaddr;
               }
               leaf local-address {
                 description "BFD local address (for multihop only)";
                 type jt:ipaddr;
               }
               leaf holddown-interval {
                 description "Time to hold the session-UP notification to the client";
                 units "milliseconds";
                 type union {
                   type string {
                     pattern "<.*>|$.*";
                   }
                   type uint32 {
                     range "0 .. 255000";
                   }
                 }
               }
               leaf minimum-receive-ttl {
                 description "Minimum receive TTL below which to drop";
                 type union {
                   type string {
                     pattern "<.*>|$.*";
                   }
                   type uint8 {
                     range "1 .. 255";
                   }
                 }
               }
             }
             choice retain-choice {
               leaf retain {
                 description "Always keep route in forwarding table";
                 junos:must "(!(\".. resolve\"))";
                 junos:must-message "Must not specify resolve with retain";
                 type empty;
               }
               leaf no-retain {
                 description "Don't always keep route in forwarding table";
                 junos:must "(!(\".. resolve\"))";
                 junos:must-message "Must not specify resolve with retain";
                 type empty;
               }
             }
             choice install-choice {
               leaf install {
                 description "Install route into forwarding table";
                 type empty;
               }
               leaf no-install {
                 description "Don't install route into forwarding table";
                 type empty;
               }
             }
             choice readvertise-choice {
               leaf readvertise {
                 description "Mark route as eligible to be readvertised";
                 type empty;
               }
               leaf no-readvertise {
                 description "Don't mark route as eligible to be readvertised";
                 type empty;
               }
             }
             choice resolve-choice {
               leaf resolve {
                 description "Allow resolution of indirectly connected next hops";
                 type empty;
               }
               leaf no-resolve {
                 description "Don't allow resolution of indirectly connected next hops";
                 type empty;
               }
             }
             leaf explicit-null {
               description "Allows service label to be popped and will lookup nexthop-table inet6.0";
               junos:must "(\".. resolve\")";
               junos:must-message "Requires resolve to be configured";
               type empty;
             }
             choice longest-match-choice {
               leaf longest-match {
                 description "Always use longest prefix match to resolve next hops";
                 junos:must "(\".. resolve\")";
                 junos:must-message "Requires resolve to be configured";
                 type empty;
               }
               leaf no-longest-match {
                 description "Don't always use longest prefix match to resolve next hops";
                 junos:must "(\".. resolve\")";
                 junos:must-message "Requires resolve to be configured";
                 type empty;
               }
             }
             choice passive_flag {
               case case_1 {
                 leaf active {
                   description "Remove inactive route from forwarding table";
                   type empty;
                 }
               }
               case case_2 {
                 leaf passive {
                   description "Retain inactive route in forwarding table";
                   type empty;
                 }
               }
             }
             container metric {
               description "Metric value";
               presence "enable metric";
               junos:cli-feature "oneliner";
               uses rib_static_metric_type;
             }
             container metric2 {
               description "Metric value 2";
               presence "enable metric2";
               junos:cli-feature "oneliner";
               uses rib_static_metric_type;
             }
             container metric3 {
               description "Metric value 3";
               presence "enable metric3";
               junos:cli-feature "oneliner";
               uses rib_static_metric_type;
             }
             container metric4 {
               description "Metric value 4";
               presence "enable metric4";
               junos:cli-feature "oneliner";
               uses rib_static_metric_type;
             }
             container tag {
               description "Tag string";
               presence "enable tag";
               junos:cli-feature "oneliner";
               uses rib_static_metric_type;
             }
             container tag2 {
               description "Tag string 2";
               presence "enable tag2";
               junos:cli-feature "oneliner";
               uses rib_static_metric_type;
             }
             container preference {
               description "Preference value";
               presence "enable preference";
               junos:cli-feature "oneliner";
               uses rib_static_metric_type;
             }
             container preference2 {
               description "Preference value 2";
               presence "enable preference2";
               junos:cli-feature "oneliner";
               uses rib_static_metric_type;
             }
             container color {
               description "Color (preference) value";
               presence "enable color";
               junos:cli-feature "oneliner";
               uses rib_static_metric_type;
             }
             container color2 {
               description "Color (preference) value 2";
               presence "enable color2";
               junos:cli-feature "oneliner";
               uses rib_static_metric_type;
             }
             leaf-list community {
               ordered-by user;
               description "BGP community identifier";
               type jt:community;
             }
             container as-path {
               description "Autonomous system path";
               uses apply-advanced;
               leaf path {
                 description "Autonomous system path";
                 type string;
               }
               leaf origin {
                 type enumeration {
                   enum "igp" {
                     description "Path originated in the local IGP";
                   }
                   enum "egp" {
                     description "Path originated in another AS";
                   }
                   enum "incomplete" {
                     description "Path was learned by some other means";
                   }
                 }
               }
               leaf atomic-aggregate {
                 description "Add ATOMIC_AGGREGATE path attribute to route";
                 type empty;
               }
               container aggregator {
                 presence "enable aggregator";
                 description "Add AGGREGATOR path attribute to route";
               }
               leaf as-number {
                 description " Autonomous system number in plain number or 'higher 16bits'.'Lower 16 bits' (asdot notation) format";
                 junos:cli-feature "nokeyword";
                 type string {
                   junos:posix-pattern "^[0-9]+(.[0-9]+)?$";
                   junos:pattern-message "Use format \'x\' or \'x.y\' to specify number \'x\' (Range 1 .. 4294967295) or number with higher 2 bytes \'x\' (Range 0 .. 65535) and lower 2 bytes \'y\' (Range 0 .. 65535) respectively";
                 }
               }
               leaf address {
                 description "Address of BGP system that formed the route";
                 junos:cli-feature "nokeyword";
                 type jt:ipv4addr;
               }
             }
             list lsp-next-hop {
               key name;
               ordered-by user;
               description "LSP next hop";
               uses lsp_nh_obj;
             }
             list p2mp-lsp-next-hop {
               key name;
               ordered-by user;
               description "Point-to-multipoint LSP next hop";
               max-elements 1;
               uses lsp_nh_obj;
             }
             container spring-te-lsp-next-hop {
               description "SPRING-TE LSP next hop";
               junos:must "(\"protocols source-packet-routing tunnel-tracking\")";
               junos:must-message "Please enable the tunnel-tracking  under 'protocols source-packet-routing' hierarchy";
               uses springte_lsp_nh_obj;
             }
             container p2mp-ldp-next-hop {
               description "Point-to-multipoint LDP LSP next hop";
               uses p2mp_ldp_lsp_nh_obj;
             }
             list static-lsp-next-hop {
               key name;
               ordered-by user;
               description "Static LSP next hop";
               uses lsp_nh_obj;
             }
           }
           leaf protocol-instance-name {
             description "Name of protocol instance under routing instance";
             type string;
           }
           container static-route {
             junos:cli-feature "oneliner";
             description "Static route Status";
             leaf bfd-admin-down {
               description "Static route State on BFD ADMIN DOWN";
               type enumeration {
                 enum "active" {
                   description "Static route will be inactive on bfd-admin-down";
                 }
                 enum "passive" {
                   description "Static route will remain active on bfd-admin-down";
                 }
               }
             }
           }
           list route-target-filter {
             key name;
             junos:cli-feature "oneliner-plus";
             description "Route-target-filter route";
             leaf name {
               junos:cli-feature "nokeyword";
               type string {
                 length "1 .. 47";
                 junos:posix-pattern "^[0-9.]{1,15}L?:[0-9]{1,10}/([0-9]|[2-5][0-9]|6[0-4])$";
                 junos:pattern-message "Use format \'x:y/len\' where \'x\' is an AS number followed by an optional \'L\' (To indicate 4 byte AS), or an IP address and \'y\' is a number. e.g. 123456L:100 and len is a prefix length from 0 to 64";
               }
             }
             uses apply-advanced;
             leaf autonomous-system {
               description "BGP AS for filter, overriding global configuration";
               type string {
                 junos:posix-pattern "^[0-9]+(.[0-9]+)?$";
                 junos:pattern-message "Use format \'x\' or \'x.y\' to specify number \'x\' (Range 1 .. 4294967295) or number with higher 2 bytes \'x\' (Range 0 .. 65535) and lower 2 bytes \'y\' (Range 0 .. 65535) respectively";
               }
             }
             leaf-list community {
               ordered-by user;
               description "BGP community identifier";
               type jt:community;
             }
             leaf-list neighbor {
               ordered-by user;
               description "BGP peers for filter";
               type jt:ipaddr-scoped;
             }
             leaf-list group {
               ordered-by user;
               description "BGP groups for filter";
               type string;
             }
             leaf local {
               description "Locally originated filter";
               type empty;
             }
           }
           list route-target-community-filter {
             key name;
             junos:cli-feature "oneliner-plus";
             description "Route-target-filter communites";
             leaf name {
               junos:cli-feature "nokeyword";
               junos:must "(\"policy-options community $$\")";
               junos:must-message "The referenced community is not defined under 'policy-options community'";
               type string;
             }
             uses apply-advanced;
             leaf autonomous-system {
               description "BGP AS for filter, overriding global configuration";
               type string {
                 junos:posix-pattern "^[0-9]+(.[0-9]+)?$";
                 junos:pattern-message "Use format \'x\' or \'x.y\' to specify number \'x\' (Range 1 .. 4294967295) or number with higher 2 bytes \'x\' (Range 0 .. 65535) and lower 2 bytes \'y\' (Range 0 .. 65535) respectively";
               }
             }
             leaf-list community {
               ordered-by user;
               description "BGP community identifier";
               type jt:community;
             }
             leaf-list neighbor {
               ordered-by user;
               description "BGP peers for filter";
               type jt:ipaddr-scoped;
             }
             leaf-list group {
               ordered-by user;
               description "BGP groups for filter";
               type string;
             }
             leaf local {
               description "Locally originated filter";
               type empty;
             }
           }
         }
         list martians {
           key "address choice-ident choice-value";
           ordered-by user;
           description "Invalid routes";
           uses martian_type;
           junos:cli-feature "homogeneous";
           junos:cli-feature "oneliner";
         }
         container aggregate {
           description "Coalesced routes";
           uses rib_aggregate_type;
         }
         container generate {
           description "Route of last resort";
           uses rib_aggregate_type;
         }
         choice maximum-paths-type {
           case case_1 {
             container maximum-routes {
               junos:cli-feature "oneliner";
               description "Maximum number of routes";
               status deprecated;
               leaf limit {
                 description "Maximum number of routes";
                 junos:cli-feature "nokeyword";
                 type union {
                   type string {
                     pattern "<.*>|$.*";
                   }
                   type uint32 {
                     range "1 .. 4294967295";
                   }
                 }
               }
               choice log_type {
                 case case_1 {
                   leaf threshold {
                     description "Percentage of limit at which to start generating warnings";
                     type union {
                       type string {
                         pattern "<.*>|$.*";
                       }
                       type uint32 {
                         range "1 .. 100";
                       }
                     }
                   }
                 }
                 case case_2 {
                   leaf log-only {
                     description "Generate warning messages only";
                     type empty;
                   }
                 }
               }
               leaf log-interval {
                 description "Minimum interval between log messages";
                 units "seconds";
                 type union {
                   type string {
                     pattern "<.*>|$.*";
                   }
                   type uint32 {
                     range "5 .. 86400";
                   }
                 }
               }
             }
           }
           case case_2 {
             container maximum-paths {
               junos:cli-feature "oneliner";
               description "Maximum number of paths";
               leaf limit {
                 description "Maximum number of paths";
                 junos:cli-feature "nokeyword";
                 type union {
                   type string {
                     pattern "<.*>|$.*";
                   }
                   type uint32 {
                     range "1 .. 4294967295";
                   }
                 }
               }
               choice log_type {
                 case case_1 {
                   leaf threshold {
                     description "Percentage of limit at which to start generating warnings";
                     type union {
                       type string {
                         pattern "<.*>|$.*";
                       }
                       type uint32 {
                         range "1 .. 100";
                       }
                     }
                   }
                 }
                 case case_2 {
                   leaf log-only {
                     description "Generate warning messages only";
                     type empty;
                   }
                 }
               }
               leaf log-interval {
                 description "Minimum interval between log messages";
                 units "seconds";
                 type union {
                   type string {
                     pattern "<.*>|$.*";
                   }
                   type uint32 {
                     range "5 .. 86400";
                   }
                 }
               }
             }
           }
         }
         container maximum-prefixes {
           junos:cli-feature "oneliner";
           description "Maximum number of prefixes";
           leaf limit {
             description "Maximum number of prefixes";
             junos:cli-feature "nokeyword";
             type union {
               type string {
                 pattern "<.*>|$.*";
               }
               type uint32 {
                 range "1 .. 4294967295";
               }
             }
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
         container multipath {
           presence "enable multipath";
           junos:cli-feature "oneliner-plus";
           description "Protocol-independent load balancing";
           uses apply-advanced;
           container vpn-unequal-cost {
             presence "enable vpn-unequal-cost";
             junos:cli-feature "oneliner";
             description "Include VPN routes with unequal IGP metrics";
             leaf equal-external-internal {
               description "Include external and internal VPN routes";
               type empty;
             }
           }
           leaf as-path-compare {
             description "Compare AS path sequences in addition to AS path length";
             type empty;
           }
           leaf preserve-nexthop-hierarchy {
             description "Force multipath to create List nexthop";
             type empty;
           }
         }
         container policy-multipath {
           junos:must "(!((\".. .. rib any.inet.3 policy-multipath\" || \".. .. rib any.inet6.3 policy-multipath\")))";
           junos:must-message "policy-multipath is configured by default for any.inet[6].3";
           junos:cli-feature "oneliner-plus";
           description "Policy based multipath";
           uses apply-advanced;
           leaf-list policy {
             ordered-by user;
             description "Import policy to create policy based multipath";
             type jt:policy-algebra;
           }
           container traceoptions {
             description "Trace options";
             uses apply-advanced;
             container file {
               junos:cli-feature "oneliner";
               description "Trace file options";
               leaf filename {
                 description "Name of file in which to write trace information";
                 junos:cli-feature "nokeyword";
                 type string {
                   length "1 .. 1024";
                   junos:posix-pattern "![/ %]";
                   junos:pattern-message "Must not contain \'/\', % or a space";
                 }
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               junos:cli-feature "oneliner";
               description "Tracing parameters";
               leaf name {
                 junos:cli-feature "nokeyword";
                 type enumeration {
                   enum "route" {
                     description "Policy-multipath route tracing.";
                   }
                 }
               }
               leaf send {
                 description "Trace transmitted packets";
                 type empty;
               }
               leaf receive {
                 description "Trace received packets";
                 type empty;
               }
               leaf detail {
                 description "Trace detailed information";
                 type empty;
               }
               leaf disable {
                 description "Disable this trace flag";
                 type empty;
               }
             }
           }
           leaf preserve-nexthop-hierarchy {
             description "Enable preserved nexthop hierarchy";
             junos:must "(\"routing-options resolution preserve-nexthop-hierarchy\")";
             junos:must-message "routing-options resolution preserve-nexthop-hierarchy         configuration is mandatory";
             type empty;
           }
         }
         container protect {
           junos:cli-feature "oneliner";
           description "Protocol-independent protection";
           leaf core {
             description "Protect against unreachability to service-edge router";
             type empty;
           }
         }
         container access {
           description "Access routes";
           uses apply-advanced;
           list route {
             key name;
             ordered-by user;
             junos:cli-feature "oneliner-plus";
             description "Access route";
             leaf name {
               description "IP address of destination";
               junos:cli-feature "nokeyword";
               type jt:ipprefix;
             }
             uses apply-advanced;
             leaf-list next-hop {
               ordered-by user;
               description "Next hop to destination";
               type union {
                 type jt:ipaddr-or-interface;
                 type string {
                   pattern "<.*>|$.*";
                 }
               }
             }
             list qualified-next-hop {
               key name;
               ordered-by user;
               description "Next hop with qualifiers";
               uses qualified_nh_obj;
             }
             leaf metric {
               description "Metric value";
               type union {
                 type string {
                   pattern "<.*>|$.*";
                 }
                 type uint32 {
                   range "1 .. 255";
                 }
               }
             }
             leaf preference {
               description "Preference value";
               type union {
                 type uint32;
                 type string {
                   pattern "<.*>|$.*";
                 }
               }
             }
             leaf tag {
               description "Tag string";
               type union {
                 type uint32;
                 type string {
                   pattern "<.*>|$.*";
                 }
               }
             }
             leaf tag2 {
               description "Tag2 string";
               type union {
                 type uint32;
                 type string {
                   pattern "<.*>|$.*";
                 }
               }
             }
           }
         }
         container access-internal {
           description "Access-internal routes";
           uses apply-advanced;
           list route {
             key name;
             ordered-by user;
             junos:cli-feature "oneliner-plus";
             description "Access-internal route";
             leaf name {
               description "IP address and optional prefix length of destination";
               junos:cli-feature "nokeyword";
               type jt:ipprefix;
             }
             uses apply-advanced;
             leaf-list next-hop {
               ordered-by user;
               description "Next hop to destination";
               type union {
                 type jt:ipaddr-or-interface;
                 type string {
                   pattern "<.*>|$.*";
                 }
               }
             }
             list qualified-next-hop {
               key name;
               ordered-by user;
               description "Next hop with qualifiers";
               uses qualified_nh_obj;
             }
           }
         }
         container bgp-static {
           description "Routes for BGP static advertisements";
           uses apply-advanced;
           list route {
             key name;
             ordered-by user;
             junos:cli-feature "oneliner-plus";
             description "BGP-static route";
             leaf name {
               description "IP address and optional prefix length of destination";
               junos:cli-feature "nokeyword";
               type jt:ipprefix;
             }
             uses apply-advanced;
             container metric {
               description "Metric value";
               presence "enable metric";
               junos:cli-feature "oneliner";
               uses rib_static_metric_type;
             }
             container metric2 {
               description "Metric value 2";
               presence "enable metric2";
               junos:cli-feature "oneliner";
               uses rib_static_metric_type;
             }
             container metric3 {
               description "Metric value 3";
               presence "enable metric3";
               junos:cli-feature "oneliner";
               uses rib_static_metric_type;
             }
             container metric4 {
               description "Metric value 4";
               presence "enable metric4";
               junos:cli-feature "oneliner";
               uses rib_static_metric_type;
             }
             container tag {
               description "Tag string";
               presence "enable tag";
               junos:cli-feature "oneliner";
               uses rib_static_metric_type;
             }
             container tag2 {
               description "Tag string 2";
               presence "enable tag2";
               junos:cli-feature "oneliner";
               uses rib_static_metric_type;
             }
             container preference {
               description "Preference value";
               presence "enable preference";
               junos:cli-feature "oneliner";
               uses rib_static_metric_type;
             }
             container preference2 {
               description "Preference value 2";
               presence "enable preference2";
               junos:cli-feature "oneliner";
               uses rib_static_metric_type;
             }
             container color {
               description "Color (preference) value";
               presence "enable color";
               junos:cli-feature "oneliner";
               uses rib_static_metric_type;
             }
             container color2 {
               description "Color (preference) value 2";
               presence "enable color2";
               junos:cli-feature "oneliner";
               uses rib_static_metric_type;
             }
             leaf-list community {
               ordered-by user;
               description "BGP community identifier";
               type jt:community;
             }
             container as-path {
               description "Autonomous system path";
               uses apply-advanced;
               leaf path {
                 description "Autonomous system path";
                 type string;
               }
               leaf origin {
                 type enumeration {
                   enum "igp" {
                     description "Path originated in the local IGP";
                   }
                   enum "egp" {
                     description "Path originated in another AS";
                   }
                   enum "incomplete" {
                     description "Path was learned by some other means";
                   }
                 }
               }
               leaf atomic-aggregate {
                 description "Add ATOMIC_AGGREGATE path attribute to route";
                 type empty;
               }
               container aggregator {
                 presence "enable aggregator";
                 description "Add AGGREGATOR path attribute to route";
               }
               leaf as-number {
                 description " Autonomous system number in plain number or 'higher 16bits'.'Lower 16 bits' (asdot notation) format";
                 junos:cli-feature "nokeyword";
                 type string {
                   junos:posix-pattern "^[0-9]+(.[0-9]+)?$";
                   junos:pattern-message "Use format \'x\' or \'x.y\' to specify number \'x\' (Range 1 .. 4294967295) or number with higher 2 bytes \'x\' (Range 0 .. 65535) and lower 2 bytes \'y\' (Range 0 .. 65535) respectively";
                 }
               }
               leaf address {
                 description "Address of BGP system that formed the route";
                 junos:cli-feature "nokeyword";
                 type jt:ipv4addr;
               }
             }
           }
         }
         container flow {
           description "Locally defined flow routing information";
           uses apply-advanced;
           container validation {
             description "Flow route validation options";
             presence "enable validation";
             uses flow-validation;
           }
           list route {
             key name;
             ordered-by user;
             description "Flow route";
             uses flow-route-inet6;
           }
           container interface-group {
             description "Interface-group for applying flow-spec filter";
             junos:cli-feature "oneliner";
             junos:cli-feature "oneliner-plus";
             uses flow-interface-group;
           }
           leaf discard-action-for-unresolved-redir-addr {
             description "For action redirect IP if redirect address is unresolved install discard action filter";
             type empty;
           }
           choice per-route-accounting-choice {
             leaf per-route-accounting {
               description "Enable traffic accounting per flowspec route";
               type empty;
             }
             leaf no-per-route-accounting {
               description "Don't enable traffic accounting per flowspec route";
               type empty;
             }
           }
         }
         container rib-export {
           presence "enable rib-export";
           description "Group of routing tables to import the routes";
           uses apply-advanced;
           leaf ribexport-name {
             description "RIB export group name";
             junos:cli-feature "nokeyword";
             type string;
           }
         }
         container label {
           presence "enable label";
           junos:cli-feature "oneliner-plus";
           description "Label processing";
           uses apply-advanced;
           leaf-list allocation {
             ordered-by user;
             description "Label allocation policy";
             junos:must "(\".. .. .. instance-type vrf\")";
             junos:must-message "'allocation' policy is valid only for 'instance-type vrf'";
             type jt:policy-algebra;
           }
           leaf-list substitution {
             ordered-by user;
             description "Label substitution policy";
             junos:must "(\".. .. .. instance-type vrf\")";
             junos:must-message "'substitution' policy is valid only for 'instance-type vrf'";
             type jt:policy-algebra;
           }
         }
         leaf-list vpn-global-import {
           ordered-by user;
           description "Import policy for L3VPN routes to global RIB";
           type jt:policy-algebra;
         }
       }
       container access {
         description "Access routes";
         uses apply-advanced;
         list route {
           key name;
           ordered-by user;
           junos:cli-feature "oneliner-plus";
           description "Access route";
           leaf name {
             description "IP address of destination";
             junos:cli-feature "nokeyword";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
           leaf metric {
             description "Metric value";
             type union {
               type string {
                 pattern "<.*>|$.*";
               }
               type uint32 {
                 range "1 .. 255";
               }
             }
           }
           leaf preference {
             description "Preference value";
             type union {
               type uint32;
               type string {
                 pattern "<.*>|$.*";
               }
             }
           }
           leaf tag {
             description "Tag string";
             type union {
               type uint32;
               type string {
                 pattern "<.*>|$.*";
               }
             }
           }
           leaf tag2 {
             description "Tag2 string";
             type union {
               type uint32;
               type string {
                 pattern "<.*>|$.*";
               }
             }
           }
         }
       }
       container access-internal {
         description "Access-internal routes";
         uses apply-advanced;
         list route {
           key name;
           ordered-by user;
           junos:cli-feature "oneliner-plus";
           description "Access-internal route";
           leaf name {
             description "IP address and optional prefix length of destination";
             junos:cli-feature "nokeyword";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
         }
       }
       container multicast {
         description "Global multicast options";
         uses apply-advanced;
         container traceoptions {
           description "Global multicast trace options";
           uses apply-advanced;
           container file {
             junos:cli-feature "oneliner";
             description "Trace file options";
             leaf filename {
               description "Name of file in which to write trace information";
               junos:cli-feature "nokeyword";
               type string {
                 length "1 .. 1024";
                 junos:posix-pattern "![/ %]";
                 junos:pattern-message "Must not contain \'/\', % or a space";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             junos:cli-feature "oneliner";
             description "Tracing parameters";
             leaf name {
               junos:cli-feature "nokeyword";
               type enumeration {
                 enum "parse" {
                   description "Trace configuration parsing";
                 }
                 enum "config-internal" {
                   description "Trace configuration internals";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf disable {
               description "Disable this trace flag";
               type empty;
             }
           }
         }
         leaf rpf {
           status deprecated;
           type string;
         }
         list scope {
           key name;
           ordered-by user;
           description "Multicast address scope";
           leaf name {
             description "Name to identify multicast address scope";
             junos:cli-feature "nokeyword";
             type string;
           }
           uses apply-advanced;
           leaf prefix {
             description "Administratively scoped address";
             type jt:ipprefix;
           }
           leaf-list interface {
             ordered-by user;
             description "Interface on which to configure scoping";
             type union {
               type jt:interface-name;
               type string {
                 pattern "<.*>|$.*";
               }
             }
           }
         }
         leaf-list scope-policy {
           ordered-by user;
           description "Scoping policy";
           type jt:policy-algebra;
         }
         list flow-map {
           key name;
           ordered-by user;
           description "Multicast flow map configuration";
           leaf name {
             description "Name of the flow map";
             junos:cli-feature "nokeyword";
             type string;
           }
           uses apply-advanced;
           leaf-list policy {
             ordered-by user;
             description "Policy for matched flows";
             type jt:policy-algebra;
           }
           container bandwidth {
             presence "enable bandwidth";
             junos:cli-feature "oneliner";
             description "Bandwidth properties for matched flows";
             leaf bandwidth-value {
               description "Static or default bandwidth for the matched flows";
               junos:cli-feature "nokeyword";
               units "bps";
               type string;
             }
             leaf adaptive {
               description "Auto-sense bandwidth for matched flows";
               type empty;
             }
           }
           leaf-list redundant-sources {
             ordered-by user;
             description "Redundant source addresses";
             junos:must "(\".. bandwidth adaptive\")";
             junos:must-message "redundant-sources can only be configured together with 'bandwidth adaptive'";
             type jt:ipaddr;
           }
           container forwarding-cache {
             description "Forwarding cache properties for matched flows";
             uses apply-advanced;
             container timeout {
               junos:cli-feature "oneliner";
               description "Timeout properties for matched flows";
               choice timeout_choice {
                 case case_1 {
                   leaf timeout-value {
                     description "Timeout for forwarding cache entry";
                     junos:cli-feature "nokeyword";
                     units "minutes";
                     type union {
                       type string {
                         pattern "<.*>|$.*";
                       }
                       type uint32 {
                         range "1 .. 720";
                       }
                     }
                   }
                 }
                 case case_2 {
                   container never {
                     presence "enable never";
                     description "Forwarding cache entries never time out";
                     uses apply-advanced;
                     leaf non-discard-entry-only {
                       description "Apply only to non-discard entries";
                       type empty;
                     }
                   }
                 }
               }
             }
           }
         }
         leaf-list resolve-filter {
           ordered-by user;
           description "Multicast resolve policy filter";
           status deprecated;
           type jt:policy-algebra;
         }
         leaf-list ssm-groups {
           ordered-by user;
           description "Source-specific multicast group ranges";
           type jt:ipprefix;
         }
         leaf cont-stats-collection-interval {
           description "IGMP/MLD continuous statistics collection interval";
           default "300";
           type union {
             type string {
               pattern "<.*>|$.*";
             }
             type uint16 {
               range "60 .. 3600";
             }
           }
         }
         leaf asm-override-ssm {
           description "Allow ASM state for SSM group ranges";
           type empty;
         }
         leaf-list rpf-check-policy {
           ordered-by user;
           description "Disable RPF check for a source group pair";
           type jt:policy-algebra;
         }
         container pim-to-igmp-proxy {
           description "PIM-to-IGMP proxy";
           uses apply-advanced;
           leaf-list upstream-interface {
             ordered-by user;
             description "Upstream interface list";
             type union {
               type jt:interface-name;
               type string {
                 pattern "<.*>|$.*";
               }
             }
             max-elements 2;
           }
         }
         container pim-to-mld-proxy {
           description "PIM-to-MLD proxy";
           uses apply-advanced;
           leaf-list upstream-interface {
             ordered-by user;
             description "Upstream interface list";
             type union {
               type jt:interface-name;
               type string {
                 pattern "<.*>|$.*";
               }
             }
             max-elements 2;
           }
         }
         leaf resolve-request-holdcount {
           description "Set resolve request holdcount for multicast";
           type union {
             type string {
               pattern "<.*>|$.*";
             }
             type uint32 {
               range "0 .. 256";
             }
           }
         }
         container forwarding-cache {
           description "Multicast forwarding cache";
           uses apply-advanced;
           leaf allow-maximum {
             description "Allow maximum of global and family level threshold values for suppress and reuse";
             type empty;
           }
           list family {
             key name;
             ordered-by user;
             description "Protocol family";
             junos:must "((!(\".. threshold\") || \".. allow-maximum\"))";
             junos:must-message "Family threshold cannot be configured if global threshold is already configured";
             leaf name {
               description "Protocol family";
               junos:cli-feature "nokeyword";
               type enumeration {
                 enum "inet" {
                   description "IPv4 family";
                 }
                 enum "inet6" {
                   description "IPv6 family";
                 }
               }
             }
             uses apply-advanced;
             container threshold {
               presence "enable threshold";
               description "Multicast forwarding cache suppress threshold";
               uses apply-advanced;
               leaf suppress {
                 description "Suppress threshold";
                 type union {
                   type string {
                     pattern "<.*>|$.*";
                   }
                   type uint32 {
                     range "1 .. 200000";
                   }
                 }
               }
               leaf reuse {
                 description "Reuse threshold";
                 junos:must "(\".. suppress\")";
                 junos:must-message "To configure reuse, suppress must be configured";
                 type union {
                   type string {
                     pattern "<.*>|$.*";
                   }
                   type uint32 {
                     range "1 .. 200000";
                   }
                 }
               }
               leaf mvpn-rpt-suppress {
                 description "MVPN RP tree entry suppress threshold";
                 junos:must "(\".. suppress\")";
                 junos:must-message "To configure mvpn-rpt-suppress, suppress must be configured";
                 type union {
                   type string {
                     pattern "<.*>|$.*";
                   }
                   type uint32 {
                     range "1 .. 200000";
                   }
                 }
               }
               leaf mvpn-rpt-reuse {
                 description "MVPN RP tree entry reuse threshold";
                 junos:must "(\".. mvpn-rpt-suppress\")";
                 junos:must-message "To configure mvpn-rpt-reuse, mvpn-rpt-suppress must be configured";
                 type union {
                   type string {
                     pattern "<.*>|$.*";
                   }
                   type uint32 {
                     range "1 .. 200000";
                   }
                 }
               }
               leaf log-warning {
                 description "Percentage at which to start generating warnings";
                 junos:must "(\".. suppress\")";
                 junos:must-message "To configure log-warning, suppress must be configured";
                 type union {
                   type string {
                     pattern "<.*>|$.*";
                   }
                   type uint32 {
                     range "1 .. 100";
                   }
                 }
               }
             }
           }
           container threshold {
             junos:must "((!(\".. family\") || \".. allow-maximum\"))";
             junos:must-message "Global threshold cannot be configured if family threshold is configured";
             description "Threshold";
             uses apply-advanced;
             leaf suppress {
               description "Suppress threshold";
               type union {
                 type string {
                   pattern "<.*>|$.*";
                 }
                 type uint32 {
                   range "1 .. 200000";
                 }
               }
             }
             leaf reuse {
               description "Reuse threshold";
               junos:must "(\".. suppress\")";
               junos:must-message "To configure reuse, suppress must be configured";
               type union {
                 type string {
                   pattern "<.*>|$.*";
                 }
                 type uint32 {
                   range "1 .. 200000";
                 }
               }
             }
             leaf mvpn-rpt-suppress {
               description "MVPN RP tree entry suppress threshold";
               junos:must "(\".. suppress\")";
               junos:must-message "To configure mvpn-rpt-suppress, suppress must be configured";
               type union {
                 type string {
                   pattern "<.*>|$.*";
                 }
                 type uint32 {
                   range "1 .. 200000";
                 }
               }
             }
             leaf mvpn-rpt-reuse {
               description "MVPN RP tree entry reuse threshold";
               junos:must "(\".. mvpn-rpt-suppress\")";
               junos:must-message "To configure mvpn-rpt-reuse, mvpn-rpt-suppress must be configured";
               type union {
                 type string {
                   pattern "<.*>|$.*";
                 }
                 type uint32 {
                   range "1 .. 200000";
                 }
               }
             }
             leaf log-warning {
               description "Percentage at which to start generating warnings";
               junos:must "(\".. suppress\")";
               junos:must-message "To configure log-warning, suppress must be configured";
               type union {
                 type string {
                   pattern "<.*>|$.*";
                 }
                 type uint32 {
                   range "1 .. 100";
                 }
               }
             }
           }
           leaf timeout {
             description "Forwarding cache entry timeout in minutes";
             type union {
               type string {
                 pattern "<.*>|$.*";
               }
               type uint32 {
                 range "1 .. 720";
               }
             }
           }
         }
         list interface {
           key name;
           ordered-by user;
           description "Multicast interface options";
           uses multicast_interface_options_type;
           junos:cli-feature "oneliner-plus";
         }
         list ssm-map {
           key name;
           ordered-by user;
           description "SSM map definitions";
           leaf name {
             description "SSM map name";
             junos:cli-feature "nokeyword";
             type string;
           }
           uses apply-advanced;
           leaf-list policy {
             ordered-by user;
             description "Policy for matching group";
             type jt:policy-algebra;
           }
           leaf-list source {
             ordered-by user;
             description "One or more source addresses";
             type jt:ipaddr;
           }
         }
         container stream-protection {
           presence "enable stream-protection";
           description "Multicast only Fast Re-Route";
           uses apply-advanced;
           leaf mofrr-primary-path-selection-by-routing {
             description "Multicast only Fast Re-Route primary path by Routing";
             type empty;
           }
           leaf mofrr-disjoint-upstream-only {
             description "Multicast only Fast Re-Route disjoint upstream only";
             type empty;
           }
           leaf mofrr-no-backup-join {
             description "Multicast only Fast Re-Route no backup join";
             type empty;
           }
           leaf mofrr-asm-starg {
             description "Multicast only Fast Re-Route asm (*,G)";
             type empty;
           }
           leaf-list policy {
             ordered-by user;
             description "MoFRR Policy";
             type jt:policy-algebra;
           }
         }
         list backup-pe-group {
           key name;
           ordered-by user;
           description "Backup PE group definitions";
           leaf name {
             description "PE group name";
             junos:cli-feature "nokeyword";
             type string;
           }
           uses apply-advanced;
           leaf-list backups {
             ordered-by user;
             description "One or more IP addresses";
             type jt:ipaddr;
             max-elements 8;
           }
           leaf local-address {
             description "Address to be used as local-address for this group";
             type jt:ipaddr;
           }
         }
         leaf omit-wildcard-address {
           description "Omit wildcard source/group fields in SPMSI AD NLRI";
           type empty;
         }
         leaf local-address {
           description "Local address for PIM and MVPN sessions";
           type jt:ipv4addr;
         }
       }
     }
     container firewall {
       description "Define a firewall configuration";
       uses apply-advanced;
       container family {
         junos:cli-feature "homogeneous";
         description "Protocol family";
         container inet {
           description "Protocol family IPv4 for firewall filter";
           uses apply-advanced;
           list dialer-filter {
             key name;
             ordered-by user;
             description "Define an IPv4 dialer filter";
             uses inet_dialer_filter;
           }
           list prefix-action {
             key name;
             ordered-by user;
             description "Define a prefix action";
             uses prefix_action;
           }
           list filter {
             key name;
             description "Define an IPv4 firewall filter";
             uses inet_filter;
           }
           list template {
             key name;
             description "Define an Inet firewall template";
             uses inet_template;
           }
           list simple-filter {
             key name;
             description "Define an IPv4 firewall simple filter";
             uses inet_simple_filter;
           }
           list service-filter {
             key name;
             description "One or more IPv4 service filters";
             uses inet_service_filter;
           }
           list fast-update-filter {
             key name;
             ordered-by user;
             description "One or more fast update filters";
             uses inet_fuf;
           }
         }
         container inet6 {
           description "Protocol family IPv6 for firewall filter";
           uses apply-advanced;
           list filter {
             key name;
             description "Define an IPv6 firewall filter";
             uses inet6_filter;
           }
           list service-filter {
             key name;
             description "One or more IPv6 service filters";
             uses inet6_service_filter;
           }
           list fast-update-filter {
             key name;
             ordered-by user;
             description "One or more fast update filters";
             uses inet6_fuf;
           }
           list template {
             key name;
             description "Define an Inet6 firewall template";
             uses inet6_template;
           }
         }
         container mpls {
           description "Protocol family MPLS for firewall filter";
           uses apply-advanced;
           list filter {
             key name;
             uses mpls_filter;
           }
           list template {
             key name;
             description "Define an MPLS firewall template";
             uses mpls_template;
           }
         }
         container vpls {
           description "Protocol family VPLS for firewall filter";
           uses apply-advanced;
           list filter {
             key name;
             uses vpls_filter;
           }
         }
         container evpn {
           description "Protocol family EVPN for firewall filter";
           uses apply-advanced;
           list filter {
             key name;
             uses vpls_filter;
           }
         }
         container ccc {
           description "Protocol family CCC for firewall filter";
           uses apply-advanced;
           list filter {
             key name;
             uses ccc_filter;
           }
         }
         container any {
           description "Protocol-independent filter";
           uses apply-advanced;
           list filter {
             key name;
             description "Define a protocol independent filter";
             uses any_filter;
           }
           list template {
             key name;
             description "Define Protocol independent filter template";
             uses any_template;
           }
         }
         container ethernet-switching {
           description "Protocol family Ethernet Switching for firewall filter";
           uses apply-advanced;
           list filter {
             key name;
             description "Define an Ethernet Switching firewall filter";
             uses es_filter;
           }
           list template {
             key name;
             description "Define an ethernet switching firewall template";
             uses es_template;
           }
         }
       }
       container v6-flowlabel-enable {
         presence "enable v6-flowlabel-enable";
         junos:must "(!(\".. no-next-header-to-payload-protocol-mapping\"))";
         junos:must-message "v6-flowlabel-enable and no-next-header-to-payload-protocol-mapping cannot be configured together.";
         description "To enable flowlabel";
       }
       list policer {
         key name;
         description "Policer template definition";
         uses firewall_policer;
       }
       list flexible-match {
         key name;
         description "Flexible packet match template definition";
         uses firewall_flexible_match;
       }
       list tunnel-end-point {
         key name;
         description "Tunnel end-point template definition";
         uses tunnel_end_point;
       }
       leaf disable-arp-policers {
         description "Disables ARP policers";
         type empty;
       }
       list interface-set {
         key name;
         description "Interface set definition";
         uses interface_set_type;
       }
       list three-color-policer {
         key name;
         description "Three-color policer";
         junos:must "(!(\".. loss-priority\"))";
         junos:must-message "cannot support three-color-policer action if loss-priority is configured";
         uses three-color-policer-type;
       }
       list filter {
         key name;
         description "Define an IPv4 firewall filter";
         uses inet_filter;
       }
     }
     container services {
       description "Service PIC applications settings";
       uses apply-advanced;
       container inline-napt {
         presence "enable inline-napt";
         description "Inline-NAPT configuration";
         uses apply-advanced;
         container nat44 {
           presence "enable nat44";
           uses apply-advanced;
           choice enable-disable {
             case case_1 {
               leaf disable {
                 description "Disable NAT44 on this interface";
                 type empty;
               }
             }
           }
         }
         container nat64 {
           presence "enable nat64";
           uses apply-advanced;
           choice enable-disable {
             case case_1 {
               leaf disable {
                 description "Disable NAT64 on this interface";
                 type empty;
               }
             }
           }
         }
       }
       container external-napt {
         presence "enable external-napt";
         description "External-NAPT configuration";
         uses apply-advanced;
         choice enable-disable {
           case case_1 {
             leaf disable {
               description "Disable External-NAPT";
               type empty;
             }
           }
         }
       }
     }
     list profile-variable-set {
       key name;
       ordered-by user;
       description "Dynamic profiles variable configuration";
       uses juniper-dynamic-profile-varset-object;
       junos:cli-feature "homogeneous";
     }
     container policy-options {
       description "Routing policy option configuration";
       uses apply-advanced;
       list prefix-list {
         key name;
         description "Define a named set of address prefixes";
         leaf name {
           description "Prefix list name";
           junos:cli-feature "nokeyword";
           type string;
         }
         uses apply-advanced;
         list prefix-list-item {
           key name;
           uses prefix_list_items;
           junos:cli-feature "nokeyword";
           junos:cli-feature "homogeneous";
         }
         leaf apply-path {
           description "Apply IP prefixes from a configuration statement";
           type string;
         }
       }
     }
     container extensible-subscriber-services {
       presence "enable extensible-subscriber-services";
       description "Extensible subscriber services";
       uses apply-advanced;
       leaf-list vsas {
         ordered-by user;
         description "Service VSAs";
         type string;
       }
     }
     container access-cac {
       description "Access ucac configuration";
       uses apply-advanced;
       list interface {
         key name;
         ordered-by user;
         description "Access ucac interface options";
         uses access_cac_interface_options;
         junos:cli-feature "oneliner-plus";
       }
     }
     container profile-type {
       presence "enable profile-type";
       description "Profile type";
       uses apply-advanced;
       leaf remote-device-service {
         description "Service profile to be programmed on a remote device";
         type empty;
       }
     }
   }
   grouping access_cac_interface_options {
     junos:cli-feature "oneliner-plus";
     description "Access ucac interface options";
     leaf name {
       description "Interface name";
       junos:cli-feature "nokeyword";
       type union {
         type jt:interface-unit;
         type string {
           pattern "<.*>|$.*";
         }
       }
     }
     uses apply-advanced;
     container multicast-video-bandwidth {
       presence "enable multicast-video-bandwidth";
       junos:cli-feature "oneliner";
       description "Maximum multicast bandwidth for the interface";
       leaf access-cac-bandwidth {
         description "Bandwidth used in access cac configuration";
         junos:cli-feature "nokeyword";
         units "bps";
         type string;
       }
     }
     container video-bandwidth {
       presence "enable video-bandwidth";
       junos:cli-feature "oneliner";
       description "Maximum video bandwidth for the interface";
       leaf access-cac-bandwidth {
         description "Bandwidth used in access cac configuration";
         junos:cli-feature "nokeyword";
         units "bps";
         type string;
       }
     }
     choice isqos {
       case case_1 {
         leaf no-qos-adjust {
           description "No qos adjustment";
           type empty;
         }
       }
       case case_2 {
         container qos-adjust-hierarchical {
           junos:cli-feature "oneliner-plus";
           description "Ucac interface set configuration";
           uses apply-advanced;
           leaf interface-set {
             description "Enable hierarchical adjust on iflset";
             type empty;
           }
         }
       }
     }
     list multicast-video-policy {
       key name;
       ordered-by user;
       junos:cli-feature "homogeneous";
       description "Mcast video policy";
       leaf name {
         description "Mcast video policy name";
         junos:cli-feature "nokeyword";
         type string {
           length "1 .. 64";
         }
       }
       uses apply-advanced;
       container family {
         presence "enable family";
         description "Access cac multicast policy family";
         uses apply-advanced;
         choice family_type {
           case case_1 {
             container inet {
               presence "enable inet";
               description "Family inet";
               uses apply-advanced;
               leaf-list source {
                 description "One or more multicast source addresses";
                 type jt:ipv4addr;
               }
               leaf-list group {
                 ordered-by user;
                 description "One or more multicast group addresses";
                 type jt:ipv4addr;
               }
             }
           }
           case case_2 {
             container inet6 {
               presence "enable inet6";
               description "Family inet6";
               uses apply-advanced;
               leaf-list source {
                 description "One or more multicast source addresses";
                 type jt:ipv6addr;
               }
               leaf-list group {
                 ordered-by user;
                 description "One or more multicast group addresses";
                 type jt:ipv6addr;
               }
             }
           }
         }
       }
       container bandwidth {
         presence "enable bandwidth";
         description "Maximum video bandwidth for the interface";
         uses apply-advanced;
         leaf access-cac-bandwidth {
           description "Bandwidth used in access cac configuration";
           junos:cli-feature "nokeyword";
           units "bps";
           type string;
         }
       }
       leaf adaptive {
         description "Use multicast real traffic rate";
         type empty;
       }
     }
   }
   grouping aggregate-load-balance {
     description "Load balancing parameters";
     uses apply-advanced;
     choice adaptive_option {
       case case_1 {
       }
       case case_2 {
         leaf no-adaptive {
           description "Disable adaptive";
           type empty;
         }
       }
       case case_3 {
         container adaptive {
           presence "enable adaptive";
           junos:must "(!(\"interfaces ${interface} aggregated-ether-options resilient-hash\"))";
           junos:must-message "load-balance adaptive is incompatible with resilient-hash";
           junos:must "(!(\"interfaces ${interface} aggregated-ether-options link-speed mixed\"))";
           junos:must-message "load-balance adaptive is incompatible with link-speed mixed";
           description "Enable adaptive load balancing by re-programming selector table";
           uses apply-advanced;
           leaf tolerance {
             description "Target tolerance in percentage (default 20%)";
             units "percent";
             type union {
               type string {
                 pattern "<.*>|$.*";
               }
               type uint32 {
                 range "1 .. 100";
               }
             }
           }
           leaf pps {
             description "Adaptive load balance based on packet per second (default bps)";
             type empty;
           }
           leaf scan-interval {
             description "Scan interval for multiple of 30 seconds (default 30 seconds)";
             type union {
               type string {
                 pattern "<.*>|$.*";
               }
               type uint32 {
                 range "1 .. 5";
               }
             }
           }
         }
       }
     }
   }
   grouping any_filter {
     leaf name {
       description "Filter name";
       junos:cli-feature "nokeyword";
       type string {
         junos:posix-pattern "!^((__.*)|(.{65,}))$";
         junos:pattern-message "Must be a non-reserved string of 64 characters or less";
       }
     }
     uses apply-advanced;
     leaf interface-specific {
       description "Defined counters are interface specific";
       type empty;
     }
     leaf transient-filter {
       description "Transient filter to be used for filter modification";
       type string;
     }
     leaf micro-segmentation {
       description "Indicates GBP tagging filter";
       junos:must "((!(any \".. term <*> from ip-version ipv4\") || !(any \".. term <*> from ip-version ipv6\")))";
       junos:must-message "ip-version ipv4 and ipv6 are together not supported for Group Based Policy classification filter.";
       junos:must "(!(any \".. term <*> then next-ip6\"))";
       junos:must-message " next-ip6 action not supported for Group Based Policy classification filter.";
       junos:must "(!(any \".. term <*> then next-ip\"))";
       junos:must-message " next-ip action not supported for Group Based Policy classification filter.";
       type empty;
     }
     leaf no-longest-prefix-match {
       description "Disable longest prefix match for GBP filters";
       type empty;
     }
     leaf layer2-policer {
       description "Layer2 policing for interface";
       type empty;
     }
     leaf global-bind {
       description "Define a gloabl bind for the filter";
       type empty;
     }
     list term {
       key name;
       ordered-by user;
       description "Define a firewall term";
       leaf name {
         description "Term name";
         junos:cli-feature "nokeyword";
         type string {
           junos:posix-pattern "!^((__.*)|(.{65,}))$";
           junos:pattern-message "Must be a non-reserved string of 64 characters or less";
         }
       }
       uses apply-advanced;
       container from {
         description "Define match criteria";
         uses apply-advanced;
         list interface {
           key name;
           ordered-by user;
           description "Match interface name";
           uses match_interface_object_oam;
           junos:cli-feature "oneliner";
         }
         list interface-set {
           key name;
           ordered-by user;
           description "Match interface in set";
           uses match_interface_set_object;
           junos:cli-feature "oneliner";
         }
         choice packet-length_choice {
           case case_1 {
             leaf-list packet-length {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
           case case_2 {
           }
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
           case case_3 {
             leaf-list mpls-forwarding-class {
               ordered-by user;
               description "String name";
               type string {
                 junos:posix-pattern "^.{1,64}$";
                 junos:pattern-message "Must be string of 64 characters or less";
               }
             }
           }
           case case_4 {
             leaf-list mpls-forwarding-class-except {
               ordered-by user;
               description "String name";
               type string {
                 junos:posix-pattern "^.{1,64}$";
                 junos:pattern-message "Must be string of 64 characters or less";
               }
             }
           }
         }
         choice loss-priority_choice {
           case case_1 {
           }
           case case_2 {
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         list destination-mac-address {
           key name;
           ordered-by user;
           description "Destination MAC address";
           uses firewall_mac_addr_object;
           junos:cli-feature "homogeneous";
           junos:cli-feature "oneliner";
         }
         list source-mac-address {
           key name;
           ordered-by user;
           description "Source MAC address";
           uses firewall_mac_addr_object;
           junos:cli-feature "homogeneous";
           junos:cli-feature "oneliner";
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
         choice learn-vlan-id_choice {
           case case_1 {
             leaf-list learn-vlan-id {
               ordered-by user;
               description "Range of values";
               type string;
             }
           }
           case case_2 {
             leaf-list learn-vlan-id-except {
               ordered-by user;
               description "Range of values";
               type string;
             }
           }
         }
         choice ether-type_choice {
           case case_1 {
             leaf-list ether-type {
               ordered-by user;
               type string;
             }
           }
           case case_2 {
             leaf-list ether-type-except {
               ordered-by user;
               type string;
             }
           }
         }
         leaf mpls-bottom-of-stack {
           description "Match MPLS BottomOfStack bit";
           type empty;
         }
         choice slice_choice {
           case case_1 {
           }
           case case_2 {
           }
         }
         choice flex-mask_choice {
           case case_1 {
             container flexible-match-mask {
               description "Match flexible mask";
               presence "enable flexible-match-mask";
               uses match_L2_flexible_mask;
             }
           }
         }
         choice flex-range_choice {
           case case_1 {
             container flexible-match-range {
               description "Match flexible range";
               presence "enable flexible-match-range";
               junos:must "(!(\".. flexible-match-ranges\"))";
               junos:must-message "'flexible-match-range' and 'flexible-match-ranges' are mutually exclusive";
               uses match_L2_flexible_range;
             }
           }
         }
         choice interface-group_choice {
           case case_1 {
           }
           case case_2 {
           }
         }
         list egress-interface {
           key name;
           ordered-by user;
           description "Match egress interface name";
           uses match_interface_object;
           junos:cli-feature "oneliner";
         }
         list mpls-label {
           key name;
           ordered-by user;
           description "MPLS label bits";
           leaf name {
             description "Range of values between 0 and 1048575 in decimal or hexadecimal";
             junos:cli-feature "nokeyword";
             type string {
               junos:posix-pattern "^([0-9]{1,6}|10[0-3][0-9][0-9][0-9][0-9]|104[0-7][0-9][0-9][0-9]|1048[0-4][0-9][0-9]|10485[0-6][0-9]|104857[0-5]|0x[0-f][0-f][0-f][0-f]|0x[0-f]|0x[0-f][0-f]|0x[0-f][0-f][0-f]|0x[0-f][0-f][0-f][0-f][0-f]|0x[0-f][0-f][0-f][0-f][0-f][0-f])(-([0-9]{1,6}|10[0-3][0-9][0-9][0-9][0-9]|104[0-7][0-9][0-9][0-9]|1048[0-4][0-9][0-9]|10485[0-6][0-9]|104857[0-5]|0x[0-f][0-f][0-f][0-f]|0x[0-f]|0x[0-f][0-f]|0x[0-f][0-f][0-f]|0x[0-f][0-f][0-f][0-f][0-f]|0x[0-f][0-f][0-f][0-f][0-f][0-f]))?$";
               junos:pattern-message "Must be a numerical value or range between 0-1048575";
             }
           }
           uses apply-advanced;
         }
         container ip-version {
           description "Define IP version";
           uses apply-advanced;
           container ipv4 {
             presence "enable ipv4";
             junos:must "(!(\".. ipv6\"))";
             junos:must-message "Same term cannot have both IPv4 & IPv6 IP version";
             description "Define L3/L4 match items to match IPv4 packets";
             uses apply-advanced;
             choice ip-protocol_choice {
               case case_1 {
                 leaf-list ip-protocol {
                   ordered-by user;
                   type string;
                 }
               }
               case case_2 {
                 leaf-list ip-protocol-except {
                   ordered-by user;
                   type string;
                 }
               }
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
               }
               case case_2 {
               }
             }
             choice ip-precedence_choice {
               case case_1 {
                 leaf-list ip-precedence {
                   ordered-by user;
                   type string;
                 }
               }
               case case_2 {
                 leaf-list ip-precedence-except {
                   ordered-by user;
                   type string;
                 }
               }
             }
             choice dscp_choice {
               case case_1 {
                 leaf-list dscp {
                   ordered-by user;
                   type string;
                 }
               }
               case case_2 {
                 leaf-list dscp-except {
                   ordered-by user;
                   type string;
                 }
               }
             }
             list ip-source-address {
               key name;
               ordered-by user;
               description "Match IP source address";
               uses firewall_addr_object;
               junos:cli-feature "homogeneous";
               junos:cli-feature "oneliner";
             }
             list ip-address {
               key name;
               ordered-by user;
               description "Match IP source or destination address";
               uses firewall_addr_object;
               junos:cli-feature "homogeneous";
               junos:cli-feature "oneliner";
             }
             list address {
               key name;
               ordered-by user;
               description "Match IP source or destination address";
               uses firewall_addr_object;
               junos:cli-feature "homogeneous";
               junos:cli-feature "oneliner";
             }
             list ip-destination-address {
               key name;
               ordered-by user;
               description "Match IP destination address";
               uses firewall_addr_object;
               junos:cli-feature "homogeneous";
               junos:cli-feature "oneliner";
             }
             list source-prefix-list {
               key name;
               ordered-by user;
               description "Match IP source prefixes in named list";
               uses firewall_prefix_list;
               junos:cli-feature "homogeneous";
               junos:cli-feature "oneliner";
             }
             list destination-prefix-list {
               key name;
               ordered-by user;
               description "Match IP destination prefixes in named list";
               uses firewall_prefix_list;
               junos:cli-feature "homogeneous";
               junos:cli-feature "oneliner";
             }
             list prefix-list {
               key name;
               ordered-by user;
               description "Match IP address prefixes in named list";
               uses firewall_prefix_list;
               junos:cli-feature "homogeneous";
               junos:cli-feature "oneliner";
             }
             leaf tcp-flags {
               description "Match TCP flags (in symbolic or hex formats)";
               junos:must "(!(\".. tcp-established\"))";
               junos:must-message "tcp-flags may not be matched in same rule as tcp-established";
               junos:must "(!(\".. tcp-initial\"))";
               junos:must-message "tcp-flags may not be matched in same rule as tcp-initial";
               type string;
             }
             leaf tcp-initial {
               description "Match initial packet of a TCP connection";
               type empty;
             }
             leaf tcp-established {
               description "Match packet of an established TCP connection";
               type empty;
             }
             leaf is-fragment {
               description "Match if packet is a fragment";
               type empty;
             }
             choice ttl_choice {
               case case_1 {
                 leaf-list ttl {
                   ordered-by user;
                   description "Range of values";
                   type string {
                     junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                     junos:pattern-message "Must be a numerical TTL value or range between 0-255";
                   }
                 }
               }
               case case_2 {
                 leaf-list ttl-except {
                   ordered-by user;
                   description "Range of values";
                   type string {
                     junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                     junos:pattern-message "Must be a numerical TTL value or range between 0-255";
                   }
                 }
               }
             }
             leaf fragment-flags {
               description "Match fragment flags (in symbolic or hex formats)";
               type string {
                 junos:posix-pattern "^(0x4000|0x2000|dont-fragment|more-fragments)$";
                 junos:pattern-message "fragment-flags must be either dont-fragment(0x4000) or more-fragments(0x2000)";
               }
             }
             choice gre-key_choice {
               case case_1 {
               }
               case case_2 {
               }
             }
             choice fragment-offset_choice {
               case case_1 {
               }
               case case_2 {
               }
             }
             container vxlan {
               description "Define vxlan match items";
               uses apply-advanced;
               choice vni_choice {
                 case case_1 {
                   leaf-list vni {
                     ordered-by user;
                     description "Range of values";
                     type string {
                       junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                       junos:pattern-message "Must be a numeric value or a range between 0-16777215";
                     }
                   }
                 }
                 case case_2 {
                   leaf-list vni-except {
                     ordered-by user;
                     description "Range of values";
                     type string {
                       junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                       junos:pattern-message "Must be a numeric value or a range between 0-16777215";
                     }
                   }
                 }
               }
             }
           }
           container ipv6 {
             presence "enable ipv6";
             junos:must "(!(\".. ipv4\"))";
             junos:must-message "Same term cannot have both IPv4 & IPv6 IP version";
             description "Define L3/L4 match items to match IPv6 packets";
             uses apply-advanced;
             list ip6-source-address {
               key name;
               ordered-by user;
               description "Match source address";
               uses firewall_addr6_object;
               junos:cli-feature "homogeneous";
               junos:cli-feature "oneliner";
             }
             list ip6-destination-address {
               key name;
               ordered-by user;
               description "Match destination address";
               uses firewall_addr6_object;
               junos:cli-feature "homogeneous";
               junos:cli-feature "oneliner";
             }
             list ip6-address {
               key name;
               ordered-by user;
               description "Match IPv6 source or destination address";
               uses firewall_addr6_object;
               junos:cli-feature "homogeneous";
               junos:cli-feature "oneliner";
             }
             list address {
               key name;
               ordered-by user;
               description "Match IPv6 source or destination address";
               uses firewall_addr6_object;
               junos:cli-feature "homogeneous";
               junos:cli-feature "oneliner";
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
               }
               case case_2 {
               }
             }
             list source-prefix-list {
               key name;
               ordered-by user;
               description "Match IP source prefixes in named list";
               uses firewall_prefix_list;
               junos:cli-feature "homogeneous";
               junos:cli-feature "oneliner";
             }
             list destination-prefix-list {
               key name;
               ordered-by user;
               description "Match IP destination prefixes in named list";
               uses firewall_prefix_list;
               junos:cli-feature "homogeneous";
               junos:cli-feature "oneliner";
             }
             list prefix-list {
               key name;
               ordered-by user;
               description "Match IPv6 address prefixes in named list";
               uses firewall_prefix_list;
               junos:cli-feature "homogeneous";
               junos:cli-feature "oneliner";
             }
             choice next-header_choice {
               case case_1 {
                 leaf-list next-header {
                   ordered-by user;
                   type string;
                 }
               }
               case case_2 {
                 leaf-list next-header-except {
                   ordered-by user;
                   type string;
                 }
               }
             }
             choice payload-protocol_choice {
               case case_1 {
                 leaf-list payload-protocol {
                   ordered-by user;
                   type string;
                 }
               }
               case case_2 {
               }
             }
             choice traffic-class_choice {
               case case_1 {
                 leaf-list traffic-class {
                   ordered-by user;
                   type string;
                 }
               }
               case case_2 {
                 leaf-list traffic-class-except {
                   ordered-by user;
                   type string;
                 }
               }
             }
             leaf tcp-flags {
               description "Match TCP flags (in symbolic or hex formats)";
               junos:must "((\".. next-header tcp\" || (\".. next-header 6\" || (\".. payload-protocol tcp\" || \".. payload-protocol 6\"))))";
               junos:must-message "next-header tcp or next-header 6 or payload-protocol tcp or payload-protocol 6 must be defined in the same clause";
               junos:must "(\".. next-header tcp\")";
               junos:must-message "next-header tcp must be defined in the same clause";
               junos:must "(!(\".. tcp-established\"))";
               junos:must-message "tcp-flags may not be matched in same rule as tcp-established";
               junos:must "(!(\".. tcp-initial\"))";
               junos:must-message "tcp-flags may not be matched in same rule as tcp-initial";
               type string;
             }
             leaf tcp-initial {
               description "Match initial packet of a TCP connection";
               junos:must "((\".. next-header tcp\" || (\".. next-header 6\" || (\".. payload-protocol tcp\" || \".. payload-protocol 6\"))))";
               junos:must-message "next-header tcp or next-header 6 or payload-protocol tcp or payload-protocol 6 must be defined in the same clause";
               type empty;
             }
             leaf tcp-established {
               description "Match packet of an established TCP connection";
               junos:must "((\".. next-header tcp\" || (\".. next-header 6\" || (\".. payload-protocol tcp\" || \".. payload-protocol 6\"))))";
               junos:must-message "next-header tcp or next-header 6 or payload-protocol tcp or payload-protocol 6 must be defined in the same clause";
               type empty;
             }
             choice hop-limit_choice {
               case case_1 {
                 leaf-list hop-limit {
                   ordered-by user;
                   description "Range of values";
                   type string {
                     junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                     junos:pattern-message "Must be a numerical hop-limit value or range between 0-255";
                   }
                 }
               }
               case case_2 {
                 leaf-list hop-limit-except {
                   ordered-by user;
                   description "Range of values";
                   type string {
                     junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                     junos:pattern-message "Must be a numerical hop-limit value or range between 0-255";
                   }
                 }
               }
             }
             choice gre-key_choice {
               case case_1 {
               }
               case case_2 {
               }
             }
             choice extension-header_choice {
               case case_1 {
               }
               case case_2 {
               }
             }
             container vxlan {
               description "Define vxlan match items";
               uses apply-advanced;
               choice vni_choice {
                 case case_1 {
                   leaf-list vni {
                     ordered-by user;
                     description "Range of values";
                     type string {
                       junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                       junos:pattern-message "Must be a numeric value or a range between 0-16777215";
                     }
                   }
                 }
                 case case_2 {
                   leaf-list vni-except {
                     ordered-by user;
                     description "Range of values";
                     type string {
                       junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                       junos:pattern-message "Must be a numeric value or a range between 0-16777215";
                     }
                   }
                 }
               }
             }
           }
         }
         list mac-address {
           key name;
           ordered-by user;
           description "GBP MAC address";
           uses firewall_mac_addr_object;
           junos:cli-feature "homogeneous";
           junos:cli-feature "oneliner";
         }
         choice vlan-id_choice {
           case case_1 {
             leaf-list vlan-id {
               ordered-by user;
               description "Vlan-id range (0..4095)";
               type string {
                 junos:posix-pattern "^([0-9]{1,3}|[1-3][0-9][0-9][0-9]|40[0-8][0-9]|409[0-5])(-([0-9]{1,3}|[1-3][0-9][0-9][0-9]|40[0-8][0-9]|409[0-5]))?$";
                 junos:pattern-message "Must be a numerical value or range between 0-4095";
               }
             }
           }
           case case_2 {
             leaf-list vlan-id-except {
               ordered-by user;
               description "Vlan-id range (0..4095)";
               type string {
                 junos:posix-pattern "^([0-9]{1,3}|[1-3][0-9][0-9][0-9]|40[0-8][0-9]|409[0-5])(-([0-9]{1,3}|[1-3][0-9][0-9][0-9]|40[0-8][0-9]|409[0-5]))?$";
                 junos:pattern-message "Must be a numerical value or range between 0-4095";
               }
             }
           }
         }
         choice gbp-src-tag_choice {
           case case_1 {
             leaf-list gbp-src-tag {
               ordered-by user;
               description "GBP Tag Range (0..65535)";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
         }
         choice gbp-dst-tag_choice {
           case case_1 {
             leaf-list gbp-dst-tag {
               ordered-by user;
               description "GBP Tag Range (0..65535)";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
         }
       }
       container then {
         junos:cli-feature "oneliner-plus";
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               junos:must "(!(\".. loss-priority\"))";
               junos:must-message "cannot support three-color-policer action if loss-priority is configured";
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
           }
           case case_4 {
           }
           case case_5 {
             leaf policer-charge {
               description "Name of policer-charge used to charge the policer";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         leaf count {
           description "Count the packet in the named counter";
           type string {
             junos:posix-pattern "!^((__.*)|(.{65,}))$";
             junos:pattern-message "Must be a non-reserved string of 64 characters or less";
           }
         }
         leaf loss-priority {
           description "Classify packet to loss-priority";
           type enumeration {
             enum "low" {
               description "Loss priority low";
             }
             enum "high" {
               description "Loss priority high";
             }
             enum "medium-low" {
               description "Loss priority medium-low";
             }
             enum "medium-high" {
               description "Loss priority medium-high";
             }
           }
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf forwarding-class {
           description "Classify packet to forwarding class";
           type string {
             junos:posix-pattern "^.{1,64}$";
             junos:pattern-message "Must be string of 64 characters or less";
           }
         }
         choice designation {
           case case_1 {
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
           case case_5 {
           }
         }
         leaf log {
           description "Log the packet";
           type empty;
         }
         leaf syslog {
           description "System log (syslog) information about the packet";
           type empty;
         }
         container routing-instance {
           junos:cli-feature "oneliner";
           description "Packets are directed to specified routing instance";
           leaf routing-instance-name {
             description "Name of routing instance";
             junos:cli-feature "nokeyword";
             type string {
               junos:posix-pattern "!^((__.*__)|(all)|(.*[ ].*)|(\"\")|(.{129,}))$";
               junos:pattern-message "Must be a non-reserved string of 128 characters or less with no spaces.";
             }
           }
           leaf topology {
             description "Packets are directed to specified topology";
             type string {
               junos:posix-pattern "!^((.*:.*)|(.{129,}))$";
               junos:pattern-message "Must be a non-reserved string of 128 characters or less";
             }
           }
         }
         leaf gbp-tag {
           description "GBP tag to be assigned";
           type union {
             type string {
               pattern "<.*>|$.*";
             }
             type uint32 {
               range "1 .. 65535";
             }
           }
         }
         container next-ip {
           junos:must "(\".. .. from ip-version ipv4\")";
           junos:must-message " next-ip needs ip-version ipv4 in same term";
           junos:must "(!(\".. discard\"))";
           junos:must-message " next-ip and discard both can't co-exist together in same term";
           junos:must "(!(\".. next-ip6\"))";
           junos:must-message " next-ip and next-ip6 both can't co-exist together in same term";
           junos:cli-feature "oneliner";
           description "Packets are directed to the specified ipv4 address";
           leaf address {
             description "Address to route";
             junos:cli-feature "nokeyword";
             type jt:ipv4prefix;
           }
           container routing-instance {
             junos:cli-feature "oneliner";
             description "Packets are directed to specified routing instance";
             leaf routing-instance-name {
               description "Name of routing instance";
               junos:cli-feature "nokeyword";
               type string {
                 junos:posix-pattern "!^((__.*__)|(all)|(.*[ ].*)|(\"\")|(.{129,}))$";
                 junos:pattern-message "Must be a non-reserved string of 128 characters or less with no spaces.";
               }
             }
             leaf topology {
               description "Packets are directed to specified topology";
               type string {
                 junos:posix-pattern "!^((.*:.*)|(.{129,}))$";
                 junos:pattern-message "Must be a non-reserved string of 128 characters or less";
               }
             }
           }
         }
         container next-ip6 {
           junos:must "(\".. .. from ip-version ipv6\")";
           junos:must-message " next-ip6 needs ip-version ipv6 in same term";
           junos:must "(!(\".. discard\"))";
           junos:must-message " next-ip6 and discard both can't co-exist together in same term";
           junos:cli-feature "oneliner";
           description "Packets are directed to the specified ipv6 address";
           leaf address {
             description "Address to route";
             junos:cli-feature "nokeyword";
             type jt:ipv6prefix;
           }
           container routing-instance {
             junos:cli-feature "oneliner";
             description "Packets are directed to specified routing instance";
             leaf routing-instance-name {
               description "Name of routing instance";
               junos:cli-feature "nokeyword";
               type string {
                 junos:posix-pattern "!^((__.*__)|(all)|(.*[ ].*)|(\"\")|(.{129,}))$";
                 junos:pattern-message "Must be a non-reserved string of 128 characters or less with no spaces.";
               }
             }
             leaf topology {
               description "Packets are directed to specified topology";
               type string {
                 junos:posix-pattern "!^((.*:.*)|(.{129,}))$";
                 junos:pattern-message "Must be a non-reserved string of 128 characters or less";
               }
             }
           }
         }
       }
       container template {
         description "Refer a template";
         uses apply-advanced;
         leaf template-name {
           description "Template name";
           junos:cli-feature "nokeyword";
           type string {
             junos:posix-pattern "!^((__.*)|(.{65,}))$";
             junos:pattern-message "Must be a non-reserved string of 64 characters or less";
           }
         }
       }
     }
   }
   grouping any_template {
     leaf name {
       description "Template name";
       junos:cli-feature "nokeyword";
       type string {
         junos:posix-pattern "!^((__.*)|(.{65,}))$";
         junos:pattern-message "Must be a non-reserved string of 64 characters or less";
       }
     }
     uses apply-advanced;
     container attributes {
       description "Template attributes";
       uses apply-advanced;
       leaf forwarding-class {
         description "Match forwarding class";
         type empty;
       }
       leaf forwarding-class-except {
         description "Do not match forwarding class";
         type empty;
       }
       leaf interface {
         description "Match interface name";
         type empty;
       }
       leaf interface-set {
         description "Match interface in set";
         type empty;
       }
       leaf loss-priority {
         description "Match Loss Priority";
         type empty;
       }
       leaf loss-priority-except {
         description "Do not match Loss Priority";
         type empty;
       }
       leaf packet-length {
         description "Match packet length";
         type empty;
       }
       leaf packet-length-except {
         description "Do not match packet length";
         type empty;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       junos:cli-feature "nokeyword";
       type string;
     }
     list data {
       key name;
       uses macro-data-type;
       junos:cli-feature "nokeyword";
       junos:cli-feature "homogeneous";
       junos:cli-feature "oneliner";
     }
   }
   grouping aps_type {
     uses apply-advanced;
     choice aps_mode {
       case case_1 {
         leaf working-circuit {
           description "Working circuit group name";
           type string;
         }
       }
       case case_2 {
         leaf protect-circuit {
           description "Protect circuit group name";
           type string;
         }
       }
     }
     leaf annex-b {
       description "Annex-b mode";
       junos:must "(!(\".. paired-group\"))";
       junos:must-message "paired-group configuration not supported in annex-b mode";
       junos:must "(!(\".. exercise\"))";
       junos:must-message "exercise request not supported in annex-b mode";
       junos:must "(!(\".. request\"))";
       junos:must-message "manual request not supported in annex-b mode";
       junos:must "(!(\".. revert-time\"))";
       junos:must-message "revert-time not supported in annex-b mode";
       junos:must "(!(\".. switching-mode unidirectional\"))";
       junos:must-message "unidirectional mode not supported in annex-b mode";
       type empty;
     }
     leaf wait-to-restore-time {
       description "Circuit wait-to-restore time for annex-b";
       units "seconds";
       junos:must "(\".. annex-b\")";
       junos:must-message "wait-to-restore-time only supported for annex-b mode";
       type union {
         type string {
           pattern "<.*>|$.*";
         }
         type uint32 {
           range "1 .. 4294967295";
         }
       }
     }
     leaf preserve-interface {
       description "Preserve interface state for fast failover";
       junos:must "(!(\".. paired-group\"))";
       junos:must-message "preserve-interface and paired-group cannot co-exist";
       type empty;
     }
     leaf neighbor {
       description "Neighbor address";
       type jt:ipv4addr;
     }
     leaf paired-group {
       description "Name of paired APS group";
       type string;
     }
     container authentication-key {
       presence "enable authentication-key";
       junos:cli-feature "oneliner";
       description "Authentication parameters";
       leaf auth_key {
         description "Authentication key";
         junos:cli-feature "nokeyword";
         type jt:unreadable;
       }
     }
     leaf switching-mode {
       description "APS switching mode";
       type enumeration {
         enum "bidirectional" {
           description "Bidirectional";
         }
         enum "unidirectional" {
           description "Unidirectional";
         }
       }
     }
     leaf advertise-interval {
       description "Advertise interval";
       units "milliseconds";
       type union {
         type string {
           pattern "<.*>|$.*";
         }
         type uint32 {
           range "1 .. 65534";
         }
       }
     }
     leaf hold-time {
       description "Hold time";
       units "milliseconds";
       type union {
         type string {
           pattern "<.*>|$.*";
         }
         type uint32 {
           range "1 .. 65534";
         }
       }
     }
     leaf revert-time {
       description "Circuit revert time";
       units "seconds";
       junos:must "(!(\".. switching-mode unidirectional\"))";
       junos:must-message "revert-time not supported in unidirectional mode";
       type union {
         type string {
           pattern "<.*>|$.*";
         }
         type uint32 {
           range "0 .. 65534";
         }
       }
     }
     choice break-before-make-choice {
       leaf break-before-make {
         description "Ensure only one interface is active at a time";
         type empty;
       }
       leaf no-break-before-make {
         description "Don't ensure only one interface is active at a time";
         type empty;
       }
     }
     choice manual_mode {
       case case_1 {
         leaf request {
           description "Request circuit state";
           type enumeration {
             enum "protect" {
               description "Request protect circuit";
             }
             enum "working" {
               description "Request working circuit";
             }
           }
         }
       }
       case case_2 {
         leaf force {
           description "Force circuit state";
           type enumeration {
             enum "protect" {
               description "Force protect circuit";
             }
             enum "working" {
               description "Force working circuit";
             }
           }
         }
       }
       case case_3 {
         leaf lockout {
           description "Lockout protection";
           type empty;
         }
       }
     }
     leaf fast-aps-switch {
       description "Fast aps switch";
       type empty;
     }
   }
   grouping base-default-variable-object {
     junos:cli-feature "nokeyword";
     junos:cli-feature "homogeneous";
     junos:cli-feature "oneliner-plus";
     leaf name {
       description "Name of predefined variable";
       junos:cli-feature "nokeyword";
       type enumeration {
         enum "igmp-enable" {
           description "Default for junos-igmp-enable";
         }
         enum "igmp-access-group-name" {
           description "Default for junos-igmp-access-group-name";
         }
         enum "igmp-access-source-group-name" {
           description "Default for junos-igmp-access-group-name";
         }
         enum "igmp-version" {
           description "Default for junos-igmp-version";
         }
         enum "igmp-immediate-leave" {
           description "Default for junos-igmp-immediate-leave";
         }
         enum "mld-access-group-name" {
           description "Default for junos-mld-access-group-name";
         }
         enum "mld-access-source-group-name" {
           description "Default for junos-mld-access-source-group-name";
         }
         enum "mld-immediate-leave" {
           description "Default for junos-mld-immediate-leave";
         }
         enum "input-filter" {
           description "Default for junos-input-filter";
         }
         enum "output-filter" {
           description "Default for junos-output-filter";
         }
         enum "input-interface-filter" {
           description "Default for junos-input-interface-filter";
         }
         enum "output-interface-filter" {
           description "Default for junos-output-interface-filter";
         }
         enum "input-ipv6-filter" {
           description "Default for junos-input-ipv6-filter";
         }
         enum "output-ipv6-filter" {
           description "Default for junos-output-ipv6-filter";
         }
         enum "adf-rule-v4" {
           description "Default for junos-adf-rule-v4";
         }
         enum "adf-rule-v6" {
           description "Default for junos-adf-rule-v6";
         }
         enum "cos-scheduler-map" {
           description "Default for junos-cos-scheduler-map";
         }
         enum "cos-shaping-rate" {
           description "Default for junos-cos-shaping-rate";
         }
         enum "cos-guaranteed-rate" {
           description "Default for junos-cos-guaranteed-rate";
         }
         enum "cos-delay-buffer-rate" {
           description "Default for junos-cos-delay-buffer-rate";
         }
         enum "cos-traffic-control-profile" {
           description "Default for junos-cos-traffic-control-profile";
         }
         enum "cos-shaping-mode" {
           description "Default for junos-cos-shaping-mode";
         }
         enum "cos-byte-adjust" {
           description "Default for junos-cos-byte-adjust";
         }
         enum "cos-scheduler" {
           description "Default for junos-cos-scheduler";
         }
         enum "cos-scheduler-pri" {
           description "Default for junos-cos-scheduler-pri";
         }
         enum "cos-scheduler-dropfile-low" {
           description "Default for junos-cos-scheduler-dropfile-low";
         }
         enum "cos-scheduler-dropfile-medium-low" {
           description "Default for junos-cos-scheduler-dropfile-medium-low";
         }
         enum "cos-scheduler-dropfile-medium-high" {
           description "Default for junos-cos-scheduler-dropfile-medium-high";
         }
         enum "cos-scheduler-dropfile-high" {
           description "Default for junos-cos-scheduler-dropfile-high";
         }
         enum "cos-scheduler-dropfile-any" {
           description "Default for junos-cos-scheduler-dropfile-any";
         }
         enum "cos-scheduler-excess-rate" {
           description "Default for junos-cos-scheduler-excess-rate";
         }
         enum "cos-scheduler-explicit-congestion-notification" {
           description "Default for junos-cos-scheduler-explicit-congestion-notification";
         }
         enum "cos-scheduler-ecn-rtlog-rate-limit" {
           description "Default for junos-cos-scheduler-ecn-rtlog-rate-limit";
         }
         enum "cos-scheduler-excess-priority" {
           description "Default for junos-cos-scheduler-excess-priority";
         }
         enum "cos-adjust-minimum" {
           description "Default for junos-cos-adjust-minimum";
         }
         enum "cos-excess-rate-high" {
           description "Default for junos-cos-excess-rate-high";
         }
         enum "cos-excess-rate-low" {
           description "Default for junos-cos-excess-rate-low";
         }
         enum "cos-shaping-rate-burst" {
           description "Default for junos-cos-shaping-rate-burst";
         }
         enum "cos-byte-adjust-frame" {
           description "Default for junos-cos-byte-adjust-frame";
         }
         enum "cos-byte-adjust-cell" {
           description "Default for junos-cos-byte-adjust-cell";
         }
         enum "cos-shaping-rate-priority-high" {
           description "Default for junos-cos-shaping-rate-priority-high";
         }
         enum "cos-shaping-rate-priority-high-burst" {
           description "Default for junos-cos-shaping-rate-priority-high-burst";
         }
         enum "cos-shaping-rate-priority-medium" {
           description "Default for junos-cos-shaping-rate-priority-medium";
         }
         enum "cos-shaping-rate-priority-medium-burst" {
           description "Default for junos-cos-shaping-rate-priority-medium-burst";
         }
         enum "cos-shaping-rate-priority-low" {
           description "Default for junos-cos-shaping-rate-priority-low";
         }
         enum "cos-shaping-rate-priority-low-burst" {
           description "Default for junos-cos-shaping-rate-priority-low-burst";
         }
         enum "cos-shaping-rate-excess-high" {
           description "Default for junos-cos-shaping-rate-excess-high";
         }
         enum "cos-shaping-rate-excess-high-burst" {
           description "Default for junos-cos-shaping-rate-excess-high-burst";
         }
         enum "cos-shaping-rate-excess-low" {
           description "Default for junos-cos-shaping-rate-excess-low";
         }
         enum "cos-shaping-rate-excess-low-burst" {
           description "Default for junos-cos-shaping-rate-excess-low-burst";
         }
         enum "cos-guaranteed-rate-burst" {
           description "Default for junos-cos-guaranteed-rate-burst";
         }
         enum "cos-traffic-control-profile-remaining" {
           description "Default for junos-cos-traffic-control-profile-remaining";
         }
         enum "cos-shaping-rate-granularity" {
           description "Default for junos-cos-shaping-rate-granluarity";
         }
         enum "cos-number-of-queues" {
           description "Default for junos-cos-number-of-queues";
         }
         enum "cos-rewrite-rules-dscp" {
           description "Default for junos-cos-rewrite-rules-dscp";
         }
         enum "cos-rewrite-rules-dscp-ipv6" {
           description "Default for junos-cos-rewrite-rules-dscp-ipv6";
         }
         enum "cos-rewrite-rules-exp" {
           description "Default for junos-cos-rewrite-rules-exp";
         }
         enum "cos-rewrite-rules-ieee802-1" {
           description "Default for junos-cos-rewrite-rules-ieee802-1";
         }
         enum "cos-rewrite-rules-ieee802-1ad" {
           description "Default for junos-cos-rewrite-rules-ieee802-1ad";
         }
         enum "cos-rewrite-rules-inet-precedence" {
           description "Default for junos-cos-rewrite-rules-inet-precedence";
         }
         enum "routing-instances" {
           description "Default for junos-routing-instance";
         }
         enum "pim-enable" {
           description "Default for junos-pim-enable";
         }
         enum "interface-mtu" {
           description "Default for junos-interface-mtu";
         }
         enum "tag-protocol-id" {
           description "Default for junos-tag-protocol-id";
         }
         enum "inner-vlan-tag-protocol-id" {
           description "Default for junos-inner-vlan-tag-protocol-id";
         }
         enum "routing-services" {
           description "Default for junos-routing-services";
         }
         enum "aggregation-interface-set-name" {
           description "Default for junos-aggregation-interface-set-name";
         }
         enum "interface-set-name" {
           description "Default for junos-interface-set-name";
         }
         enum "default-interface-set-name" {
           description "Default for junos-default-interface-set-name";
         }
         enum "phy-ifd-interface-set-name" {
           description "Default for junos-phy-ifd-interface-set-name";
         }
         enum "phy-ifd-underlying-intf-set-name" {
           description "Default for junos-phy-ifd-underlying-intf-set-name";
         }
         enum "hpolicer-high-cir" {
           description "Default for junos-hpolicer-high-cir";
         }
         enum "hpolicer-high-max-cir" {
           description "Default for junos-hpolicer-high-max-cir";
         }
         enum "hpolicer-high-committed-burst" {
           description "Default for junos-hpolicer-high-committed-burst";
         }
         enum "hpolicer-med-high-cir" {
           description "Default for junos-hpolicer-med-high-cir";
         }
         enum "hpolicer-med-high-max-cir" {
           description "Default for junos-hpolicer-med-high-max-cir";
         }
         enum "hpolicer-med-high-committed-burst" {
           description "Default for junos-hpolicer-med-high-committed-burst";
         }
         enum "hpolicer-med-low-cir" {
           description "Default for junos-hpolicer-med-low-cir";
         }
         enum "hpolicer-med-low-max-cir" {
           description "Default for junos-hpolicer-med-low-max-cir";
         }
         enum "hpolicer-med-low-committed-burst" {
           description "Default for junos-hpolicer-med-low-committed-burst";
         }
         enum "hpolicer-low-cir" {
           description "Default for junos-hpolicer-low-cir";
         }
         enum "hpolicer-low-max-cir" {
           description "Default for junos-hpolicer-low-max-cir";
         }
         enum "hpolicer-low-committed-burst" {
           description "Default for junos-hpolicer-low-committed-burst";
         }
         enum "external-napt-control" {
           description "Default for junos-external-napt-control";
         }
       }
     }
     uses apply-advanced;
     leaf default-value {
       description "Default value for predefined variable";
       junos:cli-feature "nokeyword";
       type string;
     }
   }
   grouping ccc_filter {
     description "Define a CCC firewall filter";
     leaf name {
       description "Filter name";
       junos:cli-feature "nokeyword";
       type string {
         junos:posix-pattern "!^((__.*)|(.{65,}))$";
         junos:pattern-message "Must be a non-reserved string of 64 characters or less";
       }
     }
     uses apply-advanced;
     leaf-list accounting-profile {
       ordered-by user;
       description "Accounting profile name";
       junos:must "(\"accounting-options filter-profile\")";
       junos:must-message "referenced accounting profile must be defined";
       type string;
     }
     leaf interface-specific {
       description "Any counters defined will be interface specific";
       type empty;
     }
     leaf transient-filter {
       description "Transient filter to be used for filter modification";
       type string;
     }
     leaf physical-interface-filter {
       description "Filter is physical interface filter";
       type empty;
     }
     list term {
       key name;
       ordered-by user;
       description "Define a firewall term";
       leaf name {
         description "Term name";
         junos:cli-feature "nokeyword";
         type string {
           junos:posix-pattern "!^((__.*)|(.{65,}))$";
           junos:pattern-message "Must be a non-reserved string of 64 characters or less";
         }
       }
       uses apply-advanced;
       leaf filter {
         description "Filter to include";
         junos:must "(\"firewall family ccc filter $$\")";
         junos:must-message "Referenced filter is not defined";
         junos:must "((!(\".. from\") && !(\".. then\")))";
         junos:must-message "Not compatible with 'from or then'";
         type string {
           junos:posix-pattern "!^((__.*)|(.{65,}))$";
           junos:pattern-message "Must be a non-reserved string of 64 characters or less";
         }
       }
       container from {
         description "Define match criteria";
         uses apply-advanced;
         choice interface-group_choice {
           case case_1 {
             leaf-list interface-group {
               ordered-by user;
               description "Range of values";
               type string;
             }
           }
           case case_2 {
           }
         }
         list interface {
           key name;
           ordered-by user;
           description "Match interface name";
           uses match_interface_object;
           junos:cli-feature "oneliner";
         }
         choice packet-length_choice {
           case case_1 {
           }
           case case_2 {
           }
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
           case case_3 {
             leaf-list mpls-forwarding-class {
               ordered-by user;
               description "String name";
               type string {
                 junos:posix-pattern "^.{1,64}$";
                 junos:pattern-message "Must be string of 64 characters or less";
               }
             }
           }
           case case_4 {
             leaf-list mpls-forwarding-class-except {
               ordered-by user;
               description "String name";
               type string {
                 junos:posix-pattern "^.{1,64}$";
                 junos:pattern-message "Must be string of 64 characters or less";
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         list destination-mac-address {
           key name;
           ordered-by user;
           description "Destination MAC address";
           uses firewall_mac_addr_object;
           junos:cli-feature "homogeneous";
           junos:cli-feature "oneliner";
         }
         list source-mac-address {
           key name;
           ordered-by user;
           description "Source MAC address";
           uses firewall_mac_addr_object;
           junos:cli-feature "homogeneous";
           junos:cli-feature "oneliner";
         }
         list ip-source-address {
           key name;
           ordered-by user;
           description "Match IP source address";
           uses firewall_addr_object;
           junos:cli-feature "homogeneous";
           junos:cli-feature "oneliner";
         }
         list ip-destination-address {
           key name;
           ordered-by user;
           description "Match IP destination address";
           uses firewall_addr_object;
           junos:cli-feature "homogeneous";
           junos:cli-feature "oneliner";
         }
         choice dscp_choice {
           case case_1 {
             leaf-list dscp {
               ordered-by user;
               type string;
             }
           }
           case case_2 {
           }
         }
         choice ip-precedence_choice {
           case case_1 {
             leaf-list ip-precedence {
               ordered-by user;
               type string;
             }
           }
           case case_2 {
             leaf-list ip-precedence-except {
               ordered-by user;
               type string;
             }
           }
         }
         choice ip-protocol_choice {
           case case_1 {
             leaf-list ip-protocol {
               ordered-by user;
               type string;
             }
           }
           case case_2 {
             leaf-list ip-protocol-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
         choice flex-mask_choice {
           case case_1 {
             container flexible-match-mask {
               description "Match flexible mask";
               presence "enable flexible-match-mask";
               uses match_L2_flexible_mask;
             }
           }
         }
         choice flex-range_choice {
           case case_1 {
             container flexible-match-range {
               description "Match flexible range";
               presence "enable flexible-match-range";
               junos:must "(!(\".. flexible-match-ranges\"))";
               junos:must-message "'flexible-match-range' and 'flexible-match-ranges' are mutually exclusive";
               uses match_L2_flexible_range;
             }
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
         choice ether-type_choice {
           case case_1 {
             leaf-list ether-type {
               ordered-by user;
               type string;
             }
           }
           case case_2 {
             leaf-list ether-type-except {
               ordered-by user;
               type string;
             }
           }
         }
         choice learn-vlan-id_choice {
           case case_1 {
             leaf-list learn-vlan-id {
               ordered-by user;
               description "Range of values";
               type string;
             }
           }
           case case_2 {
             leaf-list learn-vlan-id-except {
               ordered-by user;
               description "Range of values";
               type string;
             }
           }
         }
         leaf mpls-bottom-of-stack {
           description "Match MPLS BottomOfStack bit";
           type empty;
         }
         list mpls-label {
           key name;
           ordered-by user;
           description "MPLS label bits";
           leaf name {
             description "Range of values between 0 and 1048575 in decimal or hexadecimal";
             junos:cli-feature "nokeyword";
             type string {
               junos:posix-pattern "^([0-9]{1,6}|10[0-3][0-9][0-9][0-9][0-9]|104[0-7][0-9][0-9][0-9]|1048[0-4][0-9][0-9]|10485[0-6][0-9]|104857[0-5]|0x[0-f][0-f][0-f][0-f]|0x[0-f]|0x[0-f][0-f]|0x[0-f][0-f][0-f]|0x[0-f][0-f][0-f][0-f][0-f]|0x[0-f][0-f][0-f][0-f][0-f][0-f])(-([0-9]{1,6}|10[0-3][0-9][0-9][0-9][0-9]|104[0-7][0-9][0-9][0-9]|1048[0-4][0-9][0-9]|10485[0-6][0-9]|104857[0-5]|0x[0-f][0-f][0-f][0-f]|0x[0-f]|0x[0-f][0-f]|0x[0-f][0-f][0-f]|0x[0-f][0-f][0-f][0-f][0-f]|0x[0-f][0-f][0-f][0-f][0-f][0-f]))?$";
               junos:pattern-message "Must be a numerical value or range between 0-1048575";
             }
           }
           uses apply-advanced;
         }
         container ip-version {
           description "Define IP version";
           uses apply-advanced;
           container ipv4 {
             junos:must "(!(\".. ipv6\"))";
             junos:must-message "Same term cannot have both IPv4 & IPv6 IP version";
             description "Define L3/L4 match items to match IPv4 packets";
             uses apply-advanced;
             choice ip-protocol_choice {
               case case_1 {
                 leaf-list ip-protocol {
                   ordered-by user;
                   type string;
                 }
               }
               case case_2 {
                 leaf-list ip-protocol-except {
                   ordered-by user;
                   type string;
                 }
               }
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice ip-precedence_choice {
               case case_1 {
                 leaf-list ip-precedence {
                   ordered-by user;
                   type string;
                 }
               }
             }
             choice dscp_choice {
               case case_1 {
                 leaf-list dscp {
                   ordered-by user;
                   type string;
                 }
               }
               case case_2 {
                 leaf-list dscp-except {
                   ordered-by user;
                   type string;
                 }
               }
             }
             choice traffic-class_choice {
               case case_1 {
                 leaf-list traffic-class {
                   ordered-by user;
                   type string;
                 }
               }
               case case_2 {
                 leaf-list traffic-class-except {
                   ordered-by user;
                   type string;
                 }
               }
             }
             list ip-source-address {
               key name;
               ordered-by user;
               description "Match IP source address";
               uses firewall_addr_object;
               junos:cli-feature "homogeneous";
               junos:cli-feature "oneliner";
             }
             list ip-destination-address {
               key name;
               ordered-by user;
               description "Match IP destination address";
               uses firewall_addr_object;
               junos:cli-feature "homogeneous";
               junos:cli-feature "oneliner";
             }
             list source-prefix-list {
               key name;
               ordered-by user;
               description "Match IP source prefixes in named list";
               uses firewall_prefix_list;
               junos:cli-feature "homogeneous";
               junos:cli-feature "oneliner";
             }
             list destination-prefix-list {
               key name;
               ordered-by user;
               description "Match IP destination prefixes in named list";
               uses firewall_prefix_list;
               junos:cli-feature "homogeneous";
               junos:cli-feature "oneliner";
             }
             leaf tcp-flags {
               description "Match TCP flags (in symbolic or hex formats)";
               junos:must "(!(\".. tcp-established\"))";
               junos:must-message "tcp-flags may not be matched in same rule as tcp-established";
               junos:must "(!(\".. tcp-initial\"))";
               junos:must-message "tcp-flags may not be matched in same rule as tcp-initial";
               type string;
             }
             leaf tcp-initial {
               description "Match initial packet of a TCP connection";
               type empty;
             }
             leaf tcp-established {
               description "Match packet of an established TCP connection";
               type empty;
             }
             leaf is-fragment {
               description "Match if packet is a fragment";
               type empty;
             }
           }
           container ipv6 {
             junos:must "(!(\".. ipv4\"))";
             junos:must-message "Same term cannot have both IPv4 & IPv6 IP version";
             description "Define L3/L4 match items to match IPv6 packets";
             uses apply-advanced;
             list ip6-source-address {
               key name;
               ordered-by user;
               description "Match source address";
               uses firewall_addr6_object;
               junos:cli-feature "homogeneous";
               junos:cli-feature "oneliner";
             }
             list ip6-destination-address {
               key name;
               ordered-by user;
               description "Match destination address";
               uses firewall_addr6_object;
               junos:cli-feature "homogeneous";
               junos:cli-feature "oneliner";
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             list source-prefix-list {
               key name;
               ordered-by user;
               description "Match IP source prefixes in named list";
               uses firewall_prefix_list;
               junos:cli-feature "homogeneous";
               junos:cli-feature "oneliner";
             }
             list destination-prefix-list {
               key name;
               ordered-by user;
               description "Match IP destination prefixes in named list";
               uses firewall_prefix_list;
               junos:cli-feature "homogeneous";
               junos:cli-feature "oneliner";
             }
             choice next-header_choice {
               case case_1 {
                 leaf-list next-header {
                   ordered-by user;
                   type string;
                 }
               }
               case case_2 {
                 leaf-list next-header-except {
                   ordered-by user;
                   type string;
                 }
               }
             }
             choice payload-protocol_choice {
               case case_1 {
               }
               case case_2 {
               }
             }
             choice traffic-class_choice {
               case case_1 {
                 leaf-list traffic-class {
                   ordered-by user;
                   type string;
                 }
               }
               case case_2 {
                 leaf-list traffic-class-except {
                   ordered-by user;
                   type string;
                 }
               }
             }
             leaf tcp-flags {
               description "Match TCP flags (in symbolic or hex formats)";
               junos:must "((\".. next-header tcp\" || (\".. next-header 6\" || (\".. payload-protocol tcp\" || \".. payload-protocol 6\"))))";
               junos:must-message "next-header tcp or next-header 6 or payload-protocol tcp or payload-protocol 6 must be defined in the same clause";
               junos:must "(\".. next-header tcp\")";
               junos:must-message "next-header tcp must be defined in the same clause";
               junos:must "(!(\".. tcp-established\"))";
               junos:must-message "tcp-flags may not be matched in same rule as tcp-established";
               junos:must "(!(\".. tcp-initial\"))";
               junos:must-message "tcp-flags may not be matched in same rule as tcp-initial";
               type string;
             }
             leaf tcp-initial {
               description "Match initial packet of a TCP connection";
               junos:must "((\".. next-header tcp\" || (\".. next-header 6\" || (\".. payload-protocol tcp\" || \".. payload-protocol 6\"))))";
               junos:must-message "next-header tcp or next-header 6 or payload-protocol tcp or payload-protocol 6 must be defined in the same clause";
               type empty;
             }
             leaf tcp-established {
               description "Match packet of an established TCP connection";
               junos:must "((\".. next-header tcp\" || (\".. next-header 6\" || (\".. payload-protocol tcp\" || \".. payload-protocol 6\"))))";
               junos:must-message "next-header tcp or next-header 6 or payload-protocol tcp or payload-protocol 6 must be defined in the same clause";
               type empty;
             }
           }
         }
       }
       container then {
         junos:cli-feature "oneliner-plus";
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               junos:must "(!(\".. loss-priority\"))";
               junos:must-message "cannot support three-color-policer action if loss-priority is configured";
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
           }
           case case_4 {
           }
           case case_5 {
             leaf policer-charge {
               description "Name of policer-charge used to charge the policer";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         leaf count {
           description "Count the packet in the named counter";
           type string {
             junos:posix-pattern "!^((__.*)|(.{65,}))$";
             junos:pattern-message "Must be a non-reserved string of 64 characters or less";
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
             junos:posix-pattern "^.{1,64}$";
             junos:pattern-message "Must be string of 64 characters or less";
           }
         }
         leaf port-mirror-instance {
           description "Port-mirror the packet to the specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           junos:must "(\"forwarding-options port-mirroring\")";
           junos:must-message "Configure 'port-mirroring' under 'forwarding-options'";
           type empty;
         }
         leaf log {
           description "Log the packet";
           type empty;
         }
         leaf syslog {
           description "System log (syslog) information about the packet";
           type empty;
         }
         choice designation {
           case case_1 {
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
         }
       }
     }
   }
   grouping cfm-traceoptions {
     description "Trace options for connectivity fault management";
     uses apply-advanced;
     leaf no-remote-trace {
       description "Disable remote tracing";
       junos:must "(\"system tracing\")";
       junos:must-message "'no-remote-trace' is valid only when [system tracing] is configured";
       type empty;
     }
     container file {
       junos:cli-feature "oneliner";
       description "Trace file information";
       leaf filename {
         description "Name of file in which to write trace information";
         junos:cli-feature "nokeyword";
         type string {
           length "1 .. 1024";
           junos:posix-pattern "![/ %]";
           junos:pattern-message "Must not contain \'/\', % or a space";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       junos:cli-feature "oneliner";
       description "Tracing parameters";
       leaf name {
         junos:cli-feature "nokeyword";
         type enumeration {
           enum "configuration" {
             description "Trace configuration events";
           }
           enum "routing-socket" {
             description "Trace routing socket events";
           }
           enum "protocol" {
             description "Trace protocol processing events";
           }
           enum "init" {
             description "Trace events related to protocol daemon start-up";
           }
           enum "error" {
             description "Trace events related to catestrophic errors in daemon";
           }
           enum "issu" {
             description "Trace ISSU related events";
           }
           enum "all" {
             description "Trace everything";
           }
         }
       }
     }
   }
   grouping cos_policer {
     description "Define a CoS based policer";
     leaf name {
       description "Policer name";
       junos:cli-feature "nokeyword";
       type string {
         junos:posix-pattern "^.{1,64}$";
         junos:pattern-message "Must be a string of 64 characters or less";
       }
     }
     uses apply-advanced;
     container premium {
       description "Policer to apply to premium traffic";
       presence "enable premium";
       uses ethernet_policer;
     }
     container aggregate {
       description "Policer to apply to aggregate traffic";
       presence "enable aggregate";
       uses ethernet_policer;
     }
   }
   grouping cos_policer_input_priority_map {
     description "Input policer priority map";
     uses apply-advanced;
     container ieee-802.1p {
       description "Use IEEE 802.1p to determine policer priority map";
       uses apply-advanced;
       leaf-list premium {
         ordered-by user;
         description "Input traffic's IEEE 802.1p value to which premium policer is applied";
         type union {
           type string {
             pattern "<.*>|$.*";
           }
           type uint32 {
             range "0 .. 7";
           }
         }
       }
     }
   }
   grouping cos_policer_output_priority_map {
     description "Output policer priority map";
     uses apply-advanced;
     container classifier {
       description "Use classifier as policer priority map";
       uses apply-advanced;
       container premium {
         description "Output traffic classifier to which premium policer is applied";
         uses apply-advanced;
         list forwarding-class {
           key name;
           ordered-by user;
           description "Select a classification for this priority map";
           leaf name {
             description "Forwarding class name";
             junos:cli-feature "nokeyword";
             type string {
               junos:posix-pattern "^.{1,64}$";
               junos:pattern-message "Must be string of 64 characters or less";
             }
           }
           uses apply-advanced;
           list loss-priority {
             key name;
             ordered-by user;
             junos:cli-feature "oneliner";
             description "Select a loss priority";
             leaf name {
               junos:cli-feature "nokeyword";
               type enumeration {
                 enum "low" {
                   description "Select low loss priority as premium policer";
                 }
                 enum "high" {
                   description "Select high loss priority as premium policer";
                 }
               }
             }
           }
         }
       }
     }
   }
   grouping dcd_rx_bucket_config {
     uses apply-advanced;
     leaf overflow {
       description "Overflow behavior";
       type enumeration {
         enum "tag" {
           description "Tag and count overflow packets";
         }
         enum "discard" {
           description "Discard overflow packets";
         }
       }
     }
     leaf rate {
       description "Bucket rate";
       type union {
         type string {
           pattern "<.*>|$.*";
         }
         type uint32 {
           range "0 .. 100";
         }
       }
     }
     leaf threshold {
       description "Bucket threshold";
       type union {
         type string {
           pattern "<.*>|$.*";
         }
         type uint32 {
           range "0 .. 65535";
         }
       }
     }
   }
   grouping dcd_shaping_config {
     description "Traffic-shaping profile";
     uses apply-advanced;
     choice useless_shaping_choice {
       case case_1 {
         container cbr {
           presence "enable cbr";
           junos:cli-feature "oneliner";
           description "Constant bandwidth utilization";
           leaf cbr-value {
             description "Constant bandwidth utilization";
             junos:cli-feature "nokeyword";
             type string;
           }
         }
       }
       case case_2 {
         container vbr {
           junos:cli-feature "oneliner";
           description "Variable bandwidth utilization";
           leaf peak {
             description "Peak rate";
             type string;
           }
           leaf sustained {
             description "Sustained rate";
             type string;
           }
           leaf burst {
             description "Burst size";
             type string;
           }
         }
       }
       case case_3 {
         container rtvbr {
           junos:cli-feature "oneliner";
           description "ATM2 real-time variable bandwidth utilization";
           leaf peak {
             description "Peak rate";
             type string;
           }
           leaf sustained {
             description "Sustained rate";
             type string;
           }
           leaf burst {
             description "Burst size";
             type string;
           }
         }
       }
     }
     leaf queue-length {
       description "Queue length";
       type union {
         type string {
           pattern "<.*>|$.*";
         }
         type uint32 {
           range "1 .. 16383";
         }
       }
     }
   }
   grouping dcd_tx_bucket_config {
     uses apply-advanced;
     leaf overflow {
       description "Overflow behavior";
       type enumeration {
         enum "discard" {
           description "Discard overflow packets";
         }
       }
     }
     leaf rate {
       description "Bucket rate";
       type union {
         type string {
           pattern "<.*>|$.*";
         }
         type uint32 {
           range "0 .. 100";
         }
       }
     }
     leaf threshold {
       description "Bucket threshold";
       type union {
         type string {
           pattern "<.*>|$.*";
         }
         type uint32 {
           range "0 .. 65535";
         }
       }
     }
   }
   grouping dynamic_ipv4_type {
     description "Packet triggered subscribers";
     uses apply-advanced;
     container address-ranges {
       description "Packet triggered subscribers configuration";
       uses apply-advanced;
       list dynamic-profile {
         key name;
         ordered-by user;
         description "Attach dynamic-profile to packet triggered subscriber ranges";
         max-elements 16;
         leaf name {
           description "Profile name";
           junos:cli-feature "nokeyword";
           junos:must "(\"dynamic-profiles $$\")";
           junos:must-message "Dynamic-profile must be defined in the [edit dynamic-profiles] hierarchy";
           type string;
         }
         uses apply-advanced;
         list network {
           key name;
           ordered-by user;
           description "IPv4 Network address";
           max-elements 16;
           leaf name {
             description "Specify the network address";
             junos:cli-feature "nokeyword";
             type jt:ipv4prefix;
           }
           uses apply-advanced;
           list range {
             key name;
             ordered-by user;
             description "Configure demux interface based on source IP address range";
             max-elements 16;
             leaf name {
               description "Name of range";
               junos:cli-feature "nokeyword";
               type string;
             }
             uses apply-advanced;
             leaf low {
               description "Lower limit of address range";
               type jt:ipv4prefix;
             }
             leaf high {
               description "Upper limit of address range";
               type jt:ipv4prefix;
             }
           }
         }
       }
       container authentication {
         description "Auto-configure packet triggered subscriber authentication";
         uses dynamic_ip_authentication_type;
       }
       leaf session-timeout {
         description "Self destruct or auto clear timeout in seconds";
         type union {
           type string {
             pattern "<.*>|$.*";
           }
           type uint32 {
             range "600 .. 6000";
           }
         }
       }
     }
   }
   grouping dynamic_ip_authentication_type {
     description "Autoconf packet trigger subscriber authentication";
     uses apply-advanced;
     leaf password {
       description "Username password";
       type string {
         length "1 .. 64";
       }
     }
     container username-include {
       description "Username options";
       uses apply-advanced;
       leaf delimiter {
         description "Delimiter/separator character";
         type string {
           length 1;
         }
       }
       leaf domain-name {
         description "Domain name";
         type string {
           length "1 .. 64";
         }
       }
       leaf user-prefix {
         description "User defined prefix";
         type string {
           length "1 .. 64";
         }
       }
       leaf auth-server-realm {
         description "Authentication server realm name";
         type string {
           length "1 .. 64";
         }
       }
       leaf interface-name {
         description "Interface name";
         type empty;
       }
       leaf source-address {
         description "Source address";
         type empty;
       }
     }
   }
   grouping dynamic_ipv6_type {
     description "Packet triggered subscribers";
     uses apply-advanced;
     container prefix-ranges {
       description "Packet triggered subscribers configuration";
       uses apply-advanced;
       list dynamic-profile {
         key name;
         ordered-by user;
         description "Attach dynamic-profile to packet triggered subscriber ranges";
         max-elements 16;
         leaf name {
           description "Profile name";
           junos:cli-feature "nokeyword";
           junos:must "(\"dynamic-profiles $$\")";
           junos:must-message "Dynamic-profile must be defined in the [edit dynamic-profiles] hierarchy";
           type string;
         }
         uses apply-advanced;
         list prefix {
           key name;
           ordered-by user;
           description "IPv6 Network prefix ";
           max-elements 16;
           leaf name {
             description "Specify the network prefix";
             junos:cli-feature "nokeyword";
             type jt:ipv6prefix;
           }
           uses apply-advanced;
           list range {
             key name;
             ordered-by user;
             description "Configure demux interface based on source IP address range";
             max-elements 16;
             leaf name {
               description "Name of range";
               junos:cli-feature "nokeyword";
               type string;
             }
             uses apply-advanced;
             leaf low {
               description "Lower limit of prefix range";
               type jt:ipv6prefix;
             }
             leaf high {
               description "Upper limit of prefix range";
               type jt:ipv6prefix;
             }
           }
         }
       }
       container authentication {
         description "Auto-configure packet triggered subscriber authentication";
         uses dynamic_ip_authentication_type;
       }
       leaf session-timeout {
         description "Self destruct or auto clear timeout in seconds";
         type union {
           type string {
             pattern "<.*>|$.*";
           }
           type uint32 {
             range "600 .. 6000";
           }
         }
       }
     }
   }
   grouping epd_threshold_config {
     junos:cli-feature "oneliner";
     uses apply-advanced;
     leaf epd-threshold-plp0 {
       description "Early packet discard threshold value";
       junos:cli-feature "nokeyword";
       units "cells";
       type string;
     }
     leaf plp1 {
       description "Early packet drop threshold value for PLP 1";
       units "cells";
       type string;
     }
   }
   grouping es_filter {
     leaf name {
       description "Filter name";
       junos:cli-feature "nokeyword";
       type string {
         junos:posix-pattern "!^((__.*)|(.{65,}))$";
         junos:pattern-message "Must be a non-reserved string of 64 characters or less";
       }
     }
     uses apply-advanced;
     leaf interface-specific {
       description "Defined counters are interface specific";
       type empty;
     }
     leaf transient-filter {
       description "Transient filter to be used for filter modification";
       type string;
     }
     leaf physical-interface-filter {
       description "Filter is physical interface filter";
       type empty;
     }
     leaf instance-specific {
       description "Filter is instance specific";
       junos:must "(!(\".. physical-interface-filter\"))";
       junos:must-message "Cannot be both physical-interface-filter and instance-specific";
       junos:must "(!(\".. interface-specific\"))";
       junos:must-message "Cannot be both interface-specific and instance-specific";
       type empty;
     }
     list term {
       key name;
       ordered-by user;
       description "Define a firewall term";
       leaf name {
         description "Term name";
         junos:cli-feature "nokeyword";
         type string {
           junos:posix-pattern "!^((__.*)|(.{65,}))$";
           junos:pattern-message "Must be a non-reserved string of 64 characters or less";
         }
       }
       uses apply-advanced;
       container from {
         description "Define match criteria";
         uses apply-advanced;
         list interface {
           key name;
           ordered-by user;
           description "Match interface name";
           uses match_interface_object;
           junos:cli-feature "oneliner";
         }
         list source-mac-address {
           key name;
           ordered-by user;
           description "Match MAC source address";
           uses firewall_mac_addr_object;
           junos:cli-feature "homogeneous";
           junos:cli-feature "oneliner";
         }
         list destination-mac-address {
           key name;
           ordered-by user;
           description "Match MAC destination address";
           uses firewall_mac_addr_object;
           junos:cli-feature "homogeneous";
           junos:cli-feature "oneliner";
         }
         choice ether-type_choice {
           case case_1 {
             leaf-list ether-type {
               ordered-by user;
               type string;
             }
           }
           case case_2 {
             leaf-list ether-type-except {
               ordered-by user;
               type string;
             }
           }
         }
         choice l2-encap-type_choice {
           case case_1 {
             leaf-list l2-encap-type {
               ordered-by user;
               type string;
             }
           }
           case case_2 {
           }
         }
         choice vlan_choice {
           case case_1 {
             leaf-list vlan {
               ordered-by user;
               description "VLAN name or ID";
               junos:must "(!(\".. .. dot1q-tag\"))";
               junos:must-message "vlan may not be matched in same rule as dot1q-tag";
               type string;
             }
           }
           case case_2 {
           }
         }
         choice dot1q-tag_choice {
           case case_1 {
             leaf-list dot1q-tag {
               ordered-by user;
               description "Range of values";
               junos:must "(!(any \".. .. vlan <*>\"))";
               junos:must-message "dot1q-tag may not be matched in same rule as vlan";
               type string {
                 junos:posix-pattern "^([0-9]{1,3}|[1-3][0-9][0-9][0-9]|40[0-8][0-9]|409[0-5])(-([0-9]{1,3}|[1-3][0-9][0-9][0-9]|40[0-8][0-9]|409[0-5]))?$";
                 junos:pattern-message "Must be a numerical value or range between 0-4095";
               }
             }
           }
           case case_2 {
           }
         }
         choice dot1q-user-priority_choice {
           case case_1 {
             leaf-list dot1q-user-priority {
               ordered-by user;
               type string;
             }
           }
           case case_2 {
           }
         }
         list address {
           key name;
           ordered-by user;
           description "Match IP source or destination address";
           uses firewall_addr_object;
           junos:cli-feature "homogeneous";
           junos:cli-feature "oneliner";
         }
         list source-address {
           key name;
           ordered-by user;
           description "Match IP source address";
           uses firewall_addr_object;
           junos:cli-feature "homogeneous";
           junos:cli-feature "oneliner";
         }
         list destination-address {
           key name;
           ordered-by user;
           description "Match IP destination address";
           uses firewall_addr_object;
           junos:cli-feature "homogeneous";
           junos:cli-feature "oneliner";
         }
         choice dscp_choice {
           case case_1 {
             leaf-list dscp {
               ordered-by user;
               type string;
             }
           }
           case case_2 {
             leaf-list dscp-except {
               ordered-by user;
               type string;
             }
           }
         }
         choice precedence_choice {
           case case_1 {
             leaf-list precedence {
               ordered-by user;
               type string;
             }
           }
           case case_2 {
           }
         }
         choice ip-options_choice {
           case case_1 {
             leaf-list ip-options {
               ordered-by user;
               type enumeration {
                 enum "any" {
                   description "Any IP option";
                 }
               }
             }
           }
           case case_2 {
             leaf-list ip-options-except {
               ordered-by user;
               type enumeration {
                 enum "any" {
                   description "Any IP option";
                 }
               }
             }
           }
         }
         leaf fragment-flags {
           description "Match fragment flags (in symbolic or hex formats) - (Ingress only)";
           type string {
             junos:posix-pattern "^(0x4000|0x2000|dont-fragment|more-fragments)$";
             junos:pattern-message "fragment-flags must be either dont-fragment(0x4000) or more-fragments(0x2000)";
           }
         }
         leaf is-fragment {
           description "Match if packet is a fragment";
           type empty;
         }
         choice protocol_choice {
           case case_1 {
             leaf-list protocol {
               ordered-by user;
               type string;
             }
           }
           case case_2 {
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-flags {
           description "Match TCP flags (in symbolic or hex formats)";
           junos:must "(!(\".. tcp-established\"))";
           junos:must-message "tcp-flags may not be matched in same rule as tcp-established";
           junos:must "(!(\".. tcp-initial\"))";
           junos:must-message "tcp-flags may not be matched in same rule as tcp-initial";
           type string;
         }
         leaf tcp-initial {
           description "Match initial packet of a TCP connection";
           type empty;
         }
         leaf tcp-established {
           description "Match packet of an established TCP connection";
           type empty;
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         list source-prefix-list {
           key name;
           ordered-by user;
           description "Match IP source prefixes in named list";
           uses firewall_prefix_list;
           junos:cli-feature "homogeneous";
           junos:cli-feature "oneliner";
         }
         list destination-prefix-list {
           key name;
           ordered-by user;
           description "Match IP destination prefixes in named list";
           uses firewall_prefix_list;
           junos:cli-feature "homogeneous";
           junos:cli-feature "oneliner";
         }
         list ip-source-address {
           key name;
           ordered-by user;
           description "Match IP source address";
           uses firewall_addr_object;
           junos:cli-feature "homogeneous";
           junos:cli-feature "oneliner";
         }
         list ip-destination-address {
           key name;
           ordered-by user;
           description "Match IP destination address";
           uses firewall_addr_object;
           junos:cli-feature "homogeneous";
           junos:cli-feature "oneliner";
         }
         choice ip-protocol_choice {
           case case_1 {
             leaf-list ip-protocol {
               ordered-by user;
               type string;
             }
           }
           case case_2 {
             leaf-list ip-protocol-except {
               ordered-by user;
               type string;
             }
           }
         }
         choice ip-precedence_choice {
           case case_1 {
             leaf-list ip-precedence {
               ordered-by user;
               type string;
             }
           }
           case case_2 {
             leaf-list ip-precedence-except {
               ordered-by user;
               type string;
             }
           }
         }
         choice ipv6-next-header_choice {
           case case_1 {
           }
           case case_2 {
           }
         }
         choice ipv6-payload-protocol_choice {
           case case_1 {
           }
           case case_2 {
           }
         }
         choice ipv6-traffic-class_choice {
           case case_1 {
           }
           case case_2 {
           }
         }
         choice interface-group_choice {
           case case_1 {
           }
           case case_2 {
           }
         }
         choice vlan-ether-type_choice {
           case case_1 {
           }
           case case_2 {
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice learn-vlan-id_choice {
           case case_1 {
             leaf-list learn-vlan-id {
               ordered-by user;
               description "Range of values";
               type string;
             }
           }
           case case_2 {
             leaf-list learn-vlan-id-except {
               ordered-by user;
               description "Range of values";
               type string;
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice learn-vlan-dei_choice {
           case case_1 {
           }
           case case_2 {
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         choice traffic-type_choice {
           case case_1 {
             leaf-list traffic-type {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
           case case_2 {
             leaf-list traffic-type-except {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
         }
         choice isid_choice {
           case case_1 {
           }
           case case_2 {
           }
         }
         choice isid-priority-code-point_choice {
           case case_1 {
           }
           case case_2 {
           }
         }
         choice isid-dei_choice {
           case case_1 {
           }
           case case_2 {
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         container to-fabric {
           description "Match packets going to fabric";
           presence "enable to-fabric";
           uses to_fabric_object;
         }
         leaf from-fabric {
           description "Match packets coming from fabric";
           type empty;
         }
         leaf source-port-range-optimize {
           description "Optimize the source port range";
           type empty;
         }
         leaf destination-port-range-optimize {
           description "Optimize the destination port range";
           type empty;
         }
         choice arp-type_choice {
           case case_1 {
             leaf-list arp-type {
               ordered-by user;
               type string;
             }
           }
         }
         list arp-sender-address {
           key name;
           ordered-by user;
           description "Match Arp header Sender IPv4 address";
           uses firewall_addr_object;
           junos:cli-feature "homogeneous";
           junos:cli-feature "oneliner";
         }
         list arp-target-address {
           key name;
           ordered-by user;
           description "Match Arp header Target IPv4 address";
           uses firewall_addr_object;
           junos:cli-feature "homogeneous";
           junos:cli-feature "oneliner";
         }
         choice flex-mask_choice {
           case case_1 {
             container flexible-match-mask {
               description "Match flexible mask";
               presence "enable flexible-match-mask";
               uses match_L2_flexible_mask;
             }
           }
         }
         choice flex-range_choice {
           case case_1 {
             container flexible-match-range {
               description "Match flexible range";
               presence "enable flexible-match-range";
               junos:must "(!(\".. flexible-match-ranges\"))";
               junos:must-message "'flexible-match-range' and 'flexible-match-ranges' are mutually exclusive";
               uses match_L2_flexible_range;
             }
           }
         }
         container ip-version {
           description "Define IP version";
           uses apply-advanced;
           container ipv4 {
             junos:must "(!(\".. ipv6\"))";
             junos:must-message "Same term cannot have both IPv4 & IPv6 IP version";
             description "Define L3/L4 match items to match IPv4 packets";
             uses apply-advanced;
             list address {
               key name;
               ordered-by user;
               description "Match IP source or destination address";
               uses firewall_addr_object;
               junos:cli-feature "homogeneous";
               junos:cli-feature "oneliner";
             }
             list source-address {
               key name;
               ordered-by user;
               description "Match IP source address";
               uses firewall_addr_object;
               junos:cli-feature "homogeneous";
               junos:cli-feature "oneliner";
             }
             list destination-address {
               key name;
               ordered-by user;
               description "Match IP destination address";
               uses firewall_addr_object;
               junos:cli-feature "homogeneous";
               junos:cli-feature "oneliner";
             }
             choice dscp_choice {
               case case_1 {
                 leaf-list dscp {
                   ordered-by user;
                   type string;
                 }
               }
               case case_2 {
                 leaf-list dscp-except {
                   ordered-by user;
                   type string;
                 }
               }
             }
             choice precedence_choice {
               case case_1 {
                 leaf-list precedence {
                   ordered-by user;
                   type string;
                 }
               }
               case case_2 {
               }
             }
             choice ip-options_choice {
               case case_1 {
                 leaf-list ip-options {
                   ordered-by user;
                   type enumeration {
                     enum "any" {
                       description "Any IP option";
                     }
                   }
                 }
               }
               case case_2 {
                 leaf-list ip-options-except {
                   ordered-by user;
                   type enumeration {
                     enum "any" {
                       description "Any IP option";
                     }
                   }
                 }
               }
             }
             leaf fragment-flags {
               description "Match fragment flags (in symbolic or hex formats) - (Ingress only)";
               type string;
             }
             leaf is-fragment {
               description "Match if packet is a fragment";
               type empty;
             }
             choice protocol_choice {
               case case_1 {
                 leaf-list protocol {
                   ordered-by user;
                   type string;
                 }
               }
               case case_2 {
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
                 leaf-list port {
                   ordered-by user;
                   type string;
                 }
               }
               case case_2 {
                 leaf-list port-except {
                   ordered-by user;
                   type string;
                 }
               }
             }
             leaf tcp-flags {
               description "Match TCP flags (in symbolic or hex formats)";
               junos:must "(!(\".. tcp-established\"))";
               junos:must-message "tcp-flags may not be matched in same rule as tcp-established";
               junos:must "(!(\".. tcp-initial\"))";
               junos:must-message "tcp-flags may not be matched in same rule as tcp-initial";
               type string;
             }
             leaf tcp-initial {
               description "Match initial packet of a TCP connection";
               type empty;
             }
             leaf tcp-established {
               description "Match packet of an established TCP connection";
               type empty;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             list source-prefix-list {
               key name;
               ordered-by user;
               description "Match IP source prefixes in named list";
               uses firewall_prefix_list;
               junos:cli-feature "homogeneous";
               junos:cli-feature "oneliner";
             }
             list destination-prefix-list {
               key name;
               ordered-by user;
               description "Match IP destination prefixes in named list";
               uses firewall_prefix_list;
               junos:cli-feature "homogeneous";
               junos:cli-feature "oneliner";
             }
             list ip-source-address {
               key name;
               ordered-by user;
               description "Match IP source address";
               uses firewall_addr_object;
               junos:cli-feature "homogeneous";
               junos:cli-feature "oneliner";
             }
             list ip-destination-address {
               key name;
               ordered-by user;
               description "Match IP destination address";
               uses firewall_addr_object;
               junos:cli-feature "homogeneous";
               junos:cli-feature "oneliner";
             }
             choice ip-protocol_choice {
               case case_1 {
                 leaf-list ip-protocol {
                   ordered-by user;
                   type string;
                 }
               }
               case case_2 {
                 leaf-list ip-protocol-except {
                   ordered-by user;
                   type string;
                 }
               }
             }
             choice ip-precedence_choice {
               case case_1 {
                 leaf-list ip-precedence {
                   ordered-by user;
                   type string;
                 }
               }
               case case_2 {
                 leaf-list ip-precedence-except {
                   ordered-by user;
                   type string;
                 }
               }
             }
             container vxlan {
               description "Define vxlan match items";
               uses apply-advanced;
               choice tunnel {
                 case case_1 {
                   leaf tunnel-initiated {
                     description "Tunnel-initiated";
                     type empty;
                   }
                 }
               }
             }
           }
           container ipv6 {
             junos:must "(!(\".. ipv4\"))";
             junos:must-message "Same term cannot have both IPv4 & IPv6 IP version";
             description "Define L3/L4 match items to match IPv6 packets";
             uses apply-advanced;
             choice traffic-class_choice {
               case case_1 {
                 leaf-list traffic-class {
                   ordered-by user;
                   type string;
                 }
               }
               case case_2 {
                 leaf-list traffic-class-except {
                   ordered-by user;
                   type string;
                 }
               }
             }
             choice next-header_choice {
               case case_1 {
                 leaf-list next-header {
                   ordered-by user;
                   type string;
                 }
               }
               case case_2 {
                 leaf-list next-header-except {
                   ordered-by user;
                   type string;
                 }
               }
             }
             choice payload-protocol_choice {
               case case_1 {
                 leaf-list payload-protocol {
                   ordered-by user;
                   type string;
                 }
               }
               case case_2 {
                 leaf-list payload-protocol-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
                 leaf-list port {
                   ordered-by user;
                   type string;
                 }
               }
               case case_2 {
                 leaf-list port-except {
                   ordered-by user;
                   type string;
                 }
               }
             }
             choice extension-header_choice {
               case case_1 {
               }
               case case_2 {
               }
             }
             leaf tcp-flags {
               description "Match TCP flags (in symbolic or hex formats)";
               junos:must "((\".. next-header tcp\" || (\".. next-header 6\" || (\".. payload-protocol tcp\" || \".. payload-protocol 6\"))))";
               junos:must-message "next-header tcp or next-header 6 or payload-protocol tcp or payload-protocol 6 must be defined in the same clause";
               junos:must "(\".. next-header tcp\")";
               junos:must-message "next-header tcp must be defined in the same clause";
               junos:must "(!(\".. tcp-established\"))";
               junos:must-message "tcp-flags may not be matched in same rule as tcp-established";
               junos:must "(!(\".. tcp-initial\"))";
               junos:must-message "tcp-flags may not be matched in same rule as tcp-initial";
               type string;
             }
             leaf tcp-initial {
               description "Match initial packet of a TCP connection";
               junos:must "((\".. next-header tcp\" || (\".. next-header 6\" || (\".. payload-protocol tcp\" || \".. payload-protocol 6\"))))";
               junos:must-message "next-header tcp or next-header 6 or payload-protocol tcp or payload-protocol 6 must be defined in the same clause";
               type empty;
             }
             leaf tcp-established {
               description "Match packet of an established TCP connection";
               junos:must "((\".. next-header tcp\" || (\".. next-header 6\" || (\".. payload-protocol tcp\" || \".. payload-protocol 6\"))))";
               junos:must-message "next-header tcp or next-header 6 or payload-protocol tcp or payload-protocol 6 must be defined in the same clause";
               type empty;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             list source-prefix-list {
               key name;
               ordered-by user;
               description "Match IP source prefixes in named list";
               uses firewall_prefix_list;
               junos:cli-feature "homogeneous";
               junos:cli-feature "oneliner";
             }
             list destination-prefix-list {
               key name;
               ordered-by user;
               description "Match IP destination prefixes in named list";
               uses firewall_prefix_list;
               junos:cli-feature "homogeneous";
               junos:cli-feature "oneliner";
             }
             list ip6-source-address {
               key name;
               ordered-by user;
               description "Match source address";
               uses firewall_addr6_object;
               junos:cli-feature "homogeneous";
               junos:cli-feature "oneliner";
             }
             list ip6-destination-address {
               key name;
               ordered-by user;
               description "Match destination address";
               uses firewall_addr6_object;
               junos:cli-feature "homogeneous";
               junos:cli-feature "oneliner";
             }
             container vxlan {
               description "Define vxlan match items";
               uses apply-advanced;
               choice tunnel {
                 case case_1 {
                   leaf tunnel-initiated {
                     description "Tunnel-initiated";
                     type empty;
                   }
                 }
               }
             }
           }
         }
         container vxlan {
           description "Define vxlan match items";
           uses apply-advanced;
           choice vni_choice {
             case case_1 {
               leaf-list vni {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
             case case_2 {
               leaf-list vni-except {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
           }
           choice rsvd1_choice {
             case case_1 {
               leaf-list rsvd1 {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
             case case_2 {
               leaf-list rsvd1-except {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
           }
           choice rsvd2_choice {
             case case_1 {
               leaf-list rsvd2 {
                 ordered-by user;
                 description "Range of values";
                 type string {
                   junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                   junos:pattern-message "Must be a numeric value or a range between 0-255";
                 }
               }
             }
             case case_2 {
               leaf-list rsvd2-except {
                 ordered-by user;
                 description "Range of values";
                 type string {
                   junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                   junos:pattern-message "Must be a numeric value or a range between 0-255";
                 }
               }
             }
           }
           container flags {
             description "Match VXlan flag field";
             uses match_flags_value;
           }
           choice tunnel {
             case case_1 {
               leaf tunnel-initiated {
                 description "Tunnel-initiated";
                 junos:must "(!(\" .. .. ip-version ipv6 vxlan tunnel-initiated\"))";
                 junos:must-message "Same term cannot have both vxlan tunnel-initiated & IPv6 vxlan tunnel-initiated";
                 junos:must "(!(\" .. .. ip-version ipv4 vxlan tunnel-initiated\"))";
                 junos:must-message "Same term cannot have both vxlan tunnel-initiated & IPv4 vxlan tunnel-initiated";
                 type empty;
               }
             }
           }
         }
         choice packet-length_choice {
           case case_1 {
             leaf-list packet-length {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
           case case_2 {
             leaf-list packet-length-except {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
         }
       }
       container then {
         junos:cli-feature "oneliner-plus";
         description "Action to take if the 'from' condition is matched";
         uses apply-advanced;
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf log {
           description "Log the packet";
           type empty;
         }
         choice policy-map-choice {
           case case_1 {
           }
           case case_2 {
           }
         }
         leaf pkt-trace {
           description "Trace the packet";
           type empty;
         }
         leaf flood {
           description "Flood the packet";
           type empty;
         }
         leaf syslog {
           description "System log (syslog) information about the packet";
           type empty;
         }
         leaf packet-capture {
           description "Enable packet capture for telemetry";
           type empty;
         }
         leaf forwarding-class {
           description "Classify packet to forwarding class";
           junos:must "(\".. loss-priority\")";
           junos:must-message "To configure forwarding-class, loss-priority must be set";
           type string {
             junos:posix-pattern "^.{1,64}$";
             junos:pattern-message "Must be string of 64 characters or less";
           }
         }
         leaf analyzer {
           description "Name of analyzer - (Ingress only)";
           junos:must "(\"ethernet-switching-options analyzer $$\")";
           junos:must-message "Named Analyzer must be set";
           type string {
             junos:posix-pattern "!^((__.*)|(.{65,}))$";
             junos:pattern-message "Must be a non-reserved string of 64 characters or less";
           }
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           junos:must "(\"forwarding-options port-mirroring\")";
           junos:must-message "Configure 'port-mirroring' under 'forwarding-options'";
           type empty;
         }
         leaf inband-flow-telemetry-init {
           description "Initiate inband telemetry for a flow";
           junos:must "((!(\".. .. from\") || (\".. .. from destination-port\" || (\".. .. from source-port\" || (\".. .. from protocol\" || (\".. .. from ip-protocol\" || (\".. .. from next-header\" || (\".. .. from ip-destination-address\" || (\".. .. from ip-source-address\" || (\".. .. from destination-address\" || \".. .. from source-address\"))))))))))";
           junos:must-message "Match terms must either of src-ip or dest-ip or protocol or src-port or dest-port";
           junos:must "(\"services inband-flow-telemetry flow-type\")";
           junos:must-message "inband-telemetry flow-type must be defined";
           junos:must "(\"services inband-flow-telemetry profile $$\")";
           junos:must-message "Referenced inband-flow-telemetry profile does not exist";
           type string;
         }
         leaf inband-flow-telemetry-terminate {
           description "Terminate inband telemetry for a flow";
           junos:must "((!(\".. .. from\") || (\".. .. from destination-port\" || (\".. .. from source-port\" || (\".. .. from protocol\" || (\".. .. from ip-protocol\" || (\".. .. from next-header\" || (\".. .. from ip-destination-address\" || (\".. .. from ip-source-address\" || (\".. .. from destination-address\" || \".. .. from source-address\"))))))))))";
           junos:must-message "Match terms must either of src-ip or dest-ip or protocol or src-port or dest-port";
           junos:must "(\"services inband-flow-telemetry flow-type\")";
           junos:must-message "inband-telemetry flow-type must be defined";
           junos:must "(\"services inband-flow-telemetry profile $$\")";
           junos:must-message "Referenced inband-flow-telemetry profile does not exist";
           type string;
         }
         leaf sampling {
           description "Sample the packets";
           junos:must "((!(\".. discard\") && !(\".. reject\")))";
           junos:must-message "discard/reject action is not allowed with sampling action";
           junos:must "(((\"protocols sflow sample-rate ingress\" && \"protocols sflow interfaces\") || any \"protocols sflow interfaces <*> sample-rate ingress\"))";
           junos:must-message "sampling action required sflow interface configured under protocols with a valid ingress sample-rate";
           type empty;
         }
         leaf loss-priority {
           description "Packet's loss priority";
           junos:must "(\".. forwarding-class\")";
           junos:must-message "To configure loss-priority, forwarding-class must be set";
           type enumeration {
             enum "low" {
               description "Loss priority low";
             }
             enum "high" {
               description "Loss priority high";
             }
             enum "medium-low" {
               description "Loss priority medium-low";
             }
             enum "medium-high" {
               description "Loss priority medium-high";
             }
           }
         }
         leaf count {
           description "Count the packet in the named counter";
           type string {
             junos:posix-pattern "!^((__.*)|(.{65,}))$";
             junos:pattern-message "Must be a non-reserved string of 64 characters or less";
           }
         }
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               junos:must "(!(\".. loss-priority\"))";
               junos:must-message "cannot support three-color-policer action if loss-priority is configured";
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
           }
           case case_4 {
           }
           case case_5 {
             leaf policer-charge {
               description "Name of policer-charge used to charge the policer";
               type string {
                 junos:posix-pattern "!^((__.*)|(.{65,}))$";
                 junos:pattern-message "Must be a non-reserved string of 64 characters or less";
               }
             }
           }
         }
         leaf vlan {
           description "Name of VLAN - (Ingress only)";
           junos:must "((\"vlans $$\" && !(\"vlans $$ vlan-range\")))";
           junos:must-message "Named or Non-range vlan must be set";
           type string;
         }
         leaf interface {
           description "Switch traffic to the specified interface by-passing switching lookup - (Ingress only)";
           type union {
             type jt:interface-unit;
             type string {
               pattern "<.*>|$.*";
             }
           }
         }
       }
       container template {
         description "Refer a template";
         uses apply-advanced;
         leaf template-name {
           description "Template name";
           junos:cli-feature "nokeyword";
           type string {
             junos:posix-pattern "!^((__.*)|(.{65,}))$";
             junos:pattern-message "Must be a non-reserved string of 64 characters or less";
           }
         }
       }
     }
   }
   grouping es_template {
     leaf name {
       description "Template name";
       junos:cli-feature "nokeyword";
       type string {
         junos:posix-pattern "!^((__.*)|(.{65,}))$";
         junos:pattern-message "Must be a non-reserved string of 64 characters or less";
       }
     }
     uses apply-advanced;
     container attributes {
       description "Template attributes";
       uses apply-advanced;
       container ip-version {
         description "Define IP version";
         uses apply-advanced;
         container ipv4 {
           description "Define L3/L4 match items to match IPv4 packets";
           uses apply-advanced;
           leaf destination-port {
             description "Match TCP/UDP destination port";
             type empty;
           }
           leaf destination-prefix-list {
             description "Match IP destination prefixes in named list";
             type empty;
           }
           leaf dscp {
             description "Match Differentiated Services (DiffServ) code point";
             type empty;
           }
           leaf fragment-flags {
             description "Match fragment flags";
             type empty;
           }
           leaf icmp-code {
             description "Match ICMP message code";
             type empty;
           }
           leaf icmp-type {
             description "Match ICMP message type";
             type empty;
           }
           leaf ip-destination-address {
             description "Match IP destination address";
             type empty;
           }
           leaf ip-precedence {
             description "Match IP precedence value";
             type empty;
           }
           leaf ip-protocol {
             description "Match IP protocol type";
             type empty;
           }
           leaf ip-source-address {
             description "Match IP source address";
             type empty;
           }
           leaf is-fragment {
             description "Match if packet is a fragment";
             type empty;
           }
           leaf source-port {
             description "Match TCP/UDP source port";
             type empty;
           }
           leaf source-prefix-list {
             description "Match IP source prefixes in named list";
             type empty;
           }
           leaf tcp-established {
             description "Match packet of an established TCP connection";
             type empty;
           }
           leaf tcp-flags {
             description "Match TCP flags";
             type empty;
           }
           leaf tcp-initial {
             description "Match initial packet of a TCP connection";
             type empty;
           }
         }
         container ipv6 {
           description "Define L3/L4 match items to match IPv6 packets";
           uses apply-advanced;
           leaf destination-port {
             description "Match TCP/UDP destination port";
             type empty;
           }
           leaf destination-prefix-list {
             description "Match IP destination prefixes in named list";
             type empty;
           }
           leaf icmp-code {
             description "Match ICMP message code";
             type empty;
           }
           leaf icmp-type {
             description "Match ICMP message type";
             type empty;
           }
           leaf ip6-destination-address {
             description "Match destination address";
             type empty;
           }
           leaf ip6-source-address {
             description "Match source address";
             type empty;
           }
           leaf next-header {
             description "Match next header protocol type";
             type empty;
           }
           leaf source-port {
             description "Match TCP/UDP source port";
             type empty;
           }
           leaf source-prefix-list {
             description "Match IP source prefixes in named list";
             type empty;
           }
           leaf tcp-established {
             description "Match packet of an established TCP connection";
             type empty;
           }
           leaf tcp-flags {
             description "Match TCP flags";
             type empty;
           }
           leaf tcp-initial {
             description "Match initial packet of a TCP connection";
             type empty;
           }
           leaf traffic-class {
             description " Match Differentiated Services (DiffServ) code point";
             type empty;
           }
         }
       }
       leaf arp-type {
         description "Match ARP type";
         type empty;
       }
       leaf arp-sender-address {
         description "Match Arp header Sender IPv4 address";
         type empty;
       }
       leaf arp-target-address {
         description "Match Arp header Target IPv4 address";
         type empty;
       }
       leaf destination-mac-address {
         description "Match MAC destination address";
         type empty;
       }
       leaf destination-port {
         description "Match TCP/UDP destination port";
         type empty;
       }
       leaf destination-port-range-optimize {
         description "Optimize the destination port range";
         type empty;
       }
       leaf destination-prefix-list {
         description "Match IP destination prefixes in named list";
         type empty;
       }
       leaf dscp {
         description "Match Differentiated Services (DiffServ) code point";
         type empty;
       }
       leaf ether-type {
         description "Match Ethernet Type";
         type empty;
       }
       leaf fragment-flags {
         description "Match fragment flags";
         type empty;
       }
       leaf icmp-code {
         description "Match ICMP message code";
         type empty;
       }
       leaf icmp-type {
         description "Match ICMP message type";
         type empty;
       }
       leaf interface {
         description "Match interface name";
         type empty;
       }
       leaf ip-destination-address {
         description "Match IP destination address";
         type empty;
       }
       leaf ip-precedence {
         description "Match IP precedence value";
         type empty;
       }
       leaf ip-protocol {
         description "Match IP protocol type";
         type empty;
       }
       leaf ip-source-address {
         description "Match IP source address";
         type empty;
       }
       leaf is-fragment {
         description "Match if packet is a fragment";
         type empty;
       }
       leaf l2-encap-type {
         description "Match Ethernet Encapsulation Type";
         type empty;
       }
       leaf learn-vlan-id {
         description "Match Learnt VLAN ID";
         type empty;
       }
       leaf source-mac-address {
         description "Match MAC source address";
         type empty;
       }
       leaf source-port {
         description "Match TCP/UDP source port";
         type empty;
       }
       leaf source-port-range-optimize {
         description "Optimize the source port range";
         type empty;
       }
       leaf source-prefix-list {
         description "Match IP source prefixes in named list";
         type empty;
       }
       leaf tcp-established {
         description "Match packet of an established TCP connection";
         type empty;
       }
       leaf tcp-flags {
         description "Match TCP flags";
         type empty;
       }
       leaf tcp-initial {
         description "Match initial packet of a TCP connection";
         type empty;
       }
       leaf user-vlan-1p-priority {
         description "Match User 802.1p VLAN priority";
         type empty;
       }
       leaf user-vlan-id {
         description "Match User VLAN ID";
         type empty;
       }
     }
   }
   grouping ethernet-switching-type {
     description "Ethernet switching family";
     uses apply-advanced;
     leaf port-mode {
       description "Type of port mode";
       type enumeration {
         enum "access" {
           description "Interface mode is access";
         }
         enum "tagged-access" {
           description "Interface mode is tagged-access";
         }
         enum "trunk" {
           description "Interface mode is trunk";
         }
       }
     }
     leaf interface-mode {
       description "Type of interface mode";
       default "access";
       type enumeration {
         enum "access" {
           description "Interface mode is access";
           junos:must "((!(\"interfaces ${interface} vlan-tagging\") && (!(\"interfaces ${interface} flexible-vlan-tagging\") && (!(\"interfaces ${interface} stacked-vlan-tagging\") && !(\"interfaces ${interface} encapsulation extended-vlan-bridge\")))))";
           junos:must-message "interface-mode access is allowed only for untagged interfaces, also not allowed with flexible-vlan-tagging and extended-vlan-bridge";
         }
         enum "trunk" {
           description "Interface mode is trunk";
           junos:must "(!(\"interfaces ${interface} no-native-vlan-insert\"))";
           junos:must-message "'interface-mode trunk' must not be configured with 'no-native-vlan-insert'";
         }
       }
     }
     leaf inter-switch-link {
       description "PVLAN inter switch link";
       junos:must "(\".. interface-mode trunk\")";
       junos:must-message "'Inter switch link' is supported only under trunk interface mode";
       type empty;
     }
     leaf reflective-relay {
       description "Reflective-relay mode for this interface";
       junos:must "(\".. port-mode tagged-access\")";
       junos:must-message "Reflective relay is supported only on tagged-access port";
       type empty;
     }
     choice vlan_choice_list {
       case case_1 {
         container vlan {
           description "Virtual LAN parameters";
           uses apply-advanced;
           leaf-list members {
             ordered-by user;
             description "Membership for this interface (name or id)";
             type string;
           }
         }
       }
       case case_2 {
         container inner-vlan {
           description "Trunk mode vlan membership for this interface";
           uses apply-advanced;
           leaf-list members {
             ordered-by user;
             description "Membership for this interface (name or id)";
             type string;
           }
         }
       }
       case case_3 {
         leaf-list inner-vlan-id-list {
           description "Trunk mode VLAN membership for this interface based on inner VLAN tag";
           junos:must "((!(\".. .. .. vlan-tags inner\") && !(\".. .. .. vlan-tags inner-range\")))";
           junos:must-message "'inner-vlan-id-list' cannot be used on interface with vlan-tags inner or inner-range configured";
           junos:must "((\".. .. .. vlan-id\" || \".. .. .. vlan-tags\"))";
           junos:must-message "'inner-vlan-id-list' can be used only on interface with vlan-id/vlan-tags";
           junos:must "(\"interfaces ${interface} flexible-vlan-tagging\")";
           junos:must-message "'inner-vlan-id-list' is supported only on flexible-vlan-tagging mode";
           junos:must "(\".. interface-mode trunk\")";
           junos:must-message "'inner-vlan-id-list' statement supported only under trunk interface mode";
           type jt:vlan-range;
         }
       }
     }
     leaf vlan-auto-sense {
       description "Enable VLAN auto sense on this interface";
       junos:must "(\".. interface-mode trunk\")";
       junos:must-message "vlan-auto-sense can be enabled only on trunk ports";
       type empty;
     }
     leaf bridge-domain-type {
       description "Bridge domain type";
       type enumeration {
         enum "svlan" {
           description "Bridge domain type SVLAN";
           junos:must "(\".. isid-list all-service-groups\")";
           junos:must-message "bridge-domain-type SVLAN is allowed only for ISID tagged interfaces";
           junos:must "(\".. interface-mode trunk\")";
           junos:must-message "bridge-domain-type SVLAN is allowed only for trunk interfaces";
         }
         enum "bvlan" {
           description "Bridge domain type BVLAN";
           junos:must "(\".. isid-list all\")";
           junos:must-message "bridge-domain-type BVLAN is allowed only for ISID tagged interfaces";
           junos:must "(\".. interface-mode trunk\")";
           junos:must-message "bridge-domain-type BVLAN is allowed only for trunk interfaces";
         }
       }
     }
     container vlan-rewrite {
       junos:must "((\".. inner-vlan-id-list\" || \".. vlan members\"))";
       junos:must-message "'vlan-rewrite' statement can be used only with 'vlan members' or inner-vlan-id-list configured";
       junos:must "(\".. interface-mode trunk\")";
       junos:must-message "'vlan-rewrite' statement supported only under trunk interface mode";
       junos:cli-feature "oneliner-plus";
       description "Specify VLAN translation";
       uses apply-advanced;
       list translate {
         key name;
         ordered-by user;
         junos:cli-feature "oneliner";
         description "Translate incoming VLAN tag";
         leaf name {
           description "Specify the incoming VLAN tag";
           junos:cli-feature "nokeyword";
           type union {
             type string {
               pattern "<.*>|$.*";
             }
             type uint32 {
               range "1 .. 4094";
             }
           }
         }
         leaf to-vlan-id {
           description "Specify the bridge-domain VLAN-ID";
           junos:cli-feature "nokeyword";
           type union {
             type string {
               pattern "<.*>|$.*";
             }
             type uint32 {
               range "1 .. 4094";
             }
           }
         }
       }
     }
     leaf native-vlan-id {
       description "Untagged packets on a trunk/tagged-access interface belong to this vlan";
       type string {
       }
     }
     choice isid_list {
       case case_1 {
         leaf isid-list {
           description "Specify the ISID list";
           type enumeration {
             enum "all-service-groups" {
               description "Map all ISIDs specified under the service-groups";
               junos:must "(\".. interface-mode trunk\")";
               junos:must-message "'all-service-groups' statement supported only under trunk interface mode";
             }
             enum "all" {
               description "Map all ISIDs";
               junos:must "(\".. interface-mode trunk\")";
               junos:must-message "'all' statement supported only under trunk interface mode";
             }
           }
         }
       }
     }
     leaf core-facing {
       description "Interface is core facing";
       type empty;
     }
     container filter {
       description "Packet filtering";
       uses apply-advanced;
       leaf input {
         description "Name of filter applied to received packets";
         type string;
       }
       leaf input-precedence {
         description "Precedence of the filter";
         type union {
           type string {
             pattern "<.*>|$.*";
           }
           type uint32 {
             range "0 .. 255";
           }
         }
       }
       leaf-list input-list {
         ordered-by user;
         description "List of filter modules applied to received packets ";
         type string;
       }
       leaf output {
         description "Name of filter applied to transmitted packets";
         type string;
       }
       leaf output-precedence {
         description "Precedence of the filter";
         type union {
           type string {
             pattern "<.*>|$.*";
           }
           type uint32 {
             range "0 .. 255";
           }
         }
       }
       leaf-list output-list {
         ordered-by user;
         description "List of filter modules applied to transmitted packets ";
         type string;
       }
       leaf-list input-chain {
         ordered-by user;
         description "List of filter modules applied to received packets ";
         type string;
       }
       leaf-list output-chain {
         ordered-by user;
         description "List of filter modules applied to transmitted packets ";
         type string;
       }
       container adf {
         description "Ascend Data Filter definition";
         uses apply-advanced;
         list rule {
           key name;
           ordered-by user;
           description "Set of ADF rules";
           leaf name {
             description "Value for a single rule";
             junos:cli-feature "nokeyword";
             type string;
           }
           uses apply-advanced;
         }
         leaf counter {
           description "Add a counter to each rule";
           type empty;
         }
         leaf input-precedence {
           description "Precedence of the input rules";
           type union {
             type string {
               pattern "<.*>|$.*";
             }
             type uint32 {
               range "0 .. 255";
             }
           }
         }
         leaf not-mandatory {
           description "No errors will be reported if no rules are present";
           type empty;
         }
         leaf output-precedence {
           description "Precedence of the output rules";
           type union {
             type string {
               pattern "<.*>|$.*";
             }
             type uint32 {
               range "0 .. 255";
             }
           }
         }
       }
       leaf group {
         description "Group to which interface belongs";
         type union {
           type string {
             pattern "<.*>|$.*";
           }
           type uint32 {
             range "1 .. 255";
           }
         }
       }
     }
     container storm-control {
       junos:cli-feature "oneliner-plus";
       description "Storm control profile name to bind";
       uses apply-advanced;
       leaf profile-name {
         description "Profile name";
         junos:cli-feature "nokeyword";
         junos:must "(\"forwarding-options storm-control-profiles $$\")";
         junos:must-message "Storm profile name must be defined in the [edit forwarding-options storm-control-profiles] hierarchy";
         type string;
       }
     }
     container recovery-timeout {
       junos:cli-feature "oneliner";
       description "Recovery timeout for this interface";
       leaf time-in-seconds {
         junos:cli-feature "nokeyword";
         units "seconds";
         type union {
           type string {
             pattern "<.*>|$.*";
           }
           type uint32 {
             range "10 .. 3600";
           }
         }
       }
     }
   }
   grouping ethernet_policer {
     description "Define a policer";
     uses apply-advanced;
     choice bandwidth {
       case case_1 {
         leaf bandwidth-limit {
           description "Bandwidth limit";
           units "bits per second";
           type string;
         }
       }
     }
     leaf burst-size-limit {
       description "Burst size limit";
       units "bytes";
       type string;
     }
   }
   grouping ett-attributes {
     description "Transport ethernet configuration attributes";
     uses apply-advanced;
     leaf rate {
       description "Ethernet client signal rate";
       type enumeration {
         enum "100ge" {
           description "100 gigabit ethernet";
         }
       }
     }
   }
   grouping fibre-channel-type {
     description "Fibre Channel switching family";
     uses apply-advanced;
     leaf port-mode {
       description "Port mode";
       type enumeration {
         enum "f-port" {
           description "Fabric port";
         }
         enum "e-port" {
           description "Inter-switch port";
         }
         enum "np-port" {
           description "Proxy node port";
         }
         enum "auto" {
           description "Interface mode (F/E) is determined at runtime";
         }
       }
     }
     leaf no-npiv {
       description "Disable NPIV";
       junos:must "((\".. port-mode f-port\" || (\".. port-mode auto\" || !(\".. port-mode\"))))";
       junos:must-message "Interface must be f-port or auto to disable NPIV";
       type empty;
     }
     container fc-fabric {
       description "Virtual fabric parameters";
       uses apply-advanced;
       leaf-list members {
         ordered-by user;
         description "Virtual Fabric Membership for this interface (name or id)";
         type string;
       }
     }
     leaf native-fabric {
       description "FC frames with no virtual fabric header on a interface belong to this fabric";
       type string {
         junos:posix-pattern "^([[:alpha:]][[:alnum:]_.-]+)|^([1-9][0-9]{0,2}|[1-3][0-9]{3}|40[0-8][0-9]|409[0-4])$";
         junos:pattern-message "Must be a valid FC fabric name or ID";
       }
     }
   }
   grouping firewall_addr6_object {
     junos:cli-feature "homogeneous";
     junos:cli-feature "oneliner";
     leaf name {
       description "Prefix to match";
       junos:cli-feature "nokeyword";
       type jt:ipv6prefix;
     }
     leaf except {
       description "Match address not in this prefix";
       type empty;
     }
   }
   grouping firewall_addr_object {
     junos:cli-feature "homogeneous";
     junos:cli-feature "oneliner";
     leaf name {
       description "Prefix to match";
       junos:cli-feature "nokeyword";
       type jt:ipv4prefix;
     }
     leaf except {
       description "Match address not in this prefix";
       type empty;
     }
   }
   grouping firewall_flexible_match {
     description "Define a flexible match";
     leaf name {
       description "Flex match template name";
       junos:cli-feature "nokeyword";
       type string {
         junos:posix-pattern "!^((__.*)|(.{65,}))$";
         junos:pattern-message "Must be a non-reserved string of 64 characters or less";
       }
     }
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of integer input (1..32 bits), Optional length of string input (1..128 bits)";
       type union {
         type uint32;
         type string {
           pattern "<.*>|$.*";
         }
       }
     }
   }
   grouping firewall_mac_addr_object {
     junos:cli-feature "homogeneous";
     junos:cli-feature "oneliner";
     leaf name {
       description "MAC address to match";
       junos:cli-feature "nokeyword";
       type jt:mac-addr-prefix;
     }
     leaf except {
       description "Match MAC address not in this range";
       type empty;
     }
   }
   grouping firewall_policer {
     description "Define a policer";
     leaf name {
       description "Policer name";
       junos:cli-feature "nokeyword";
       type string {
         junos:posix-pattern "!^((__.*)|(.{65,}))$";
         junos:pattern-message "Must be a non-reserved string of 64 characters or less";
       }
     }
     uses apply-advanced;
     leaf filter-specific {
       description "Policer is filter-specific";
       type empty;
     }
     leaf logical-interface-policer {
       description "Policer is logical interface policer";
       type empty;
     }
     leaf physical-interface-policer {
       description "Policer is physical interface policer";
       type empty;
     }
     leaf logical-bandwidth-policer {
       description "Policer uses logical interface bandwidth";
       type empty;
     }
     choice exceeding {
       case case_1 {
         container if-exceeding {
           presence "enable if-exceeding";
           description "Define rate limits";
           uses apply-advanced;
           choice bandwidth {
             case case_1 {
               leaf bandwidth-limit {
                 description "Bandwidth limit";
                 units "bits per second";
                 type string;
               }
             }
             case case_2 {
               leaf bandwidth-percent {
                 description "Bandwidth limit in percentage";
                 units "percent";
                 type union {
                   type string {
                     pattern "<.*>|$.*";
                   }
                   type uint32 {
                     range "1 .. 100";
                   }
                 }
               }
             }
           }
           leaf burst-size-limit {
             description "Burst size limit";
             units "bytes";
             type string;
           }
           container aggregate-policing {
             presence "enable aggregate-policing";
             description "Configure Aggregate Policer";
             uses apply-advanced;
             list policer {
               key name;
               ordered-by user;
               description "Two-color policer to be used as aggregate";
               max-elements 1;
               leaf name {
                 description "Name of two-color policer to use to aggregate police";
                 junos:cli-feature "nokeyword";
                 junos:must "(\"firewall policer $$ aggregate\")";
                 junos:must-message "Referenced policer must be of type 'aggregate'";
                 junos:must "(\"firewall policer $$\")";
                 junos:must-message "Referenced aggregate policer is not defined";
                 type string;
               }
               uses apply-advanced;
               leaf aggregate-sharing-mode {
                 description "Hierarchical Metering model";
                 type enumeration {
                   enum "guarantee" {
                     description "Child policer rates are guaranteed rates for member flow";
                   }
                   enum "peak" {
                     description "Child policer rates are peak rates for member flow";
                   }
                 }
               }
             }
           }
         }
       }
       case case_2 {
         container if-exceeding-pps {
           presence "enable if-exceeding-pps";
           description "Define pps limits";
           uses apply-advanced;
           choice pps {
             case case_1 {
               leaf pps-limit {
                 description "PPS limit";
                 units "packets per second";
                 type string;
               }
             }
           }
           leaf packet-burst {
             description "PPS burst size limit";
             units "packets";
             type string;
           }
         }
       }
     }
     container then {
       junos:cli-feature "oneliner-plus";
       description "Action to take if the rate limits are exceeded";
       uses apply-advanced;
       leaf discard {
         description "Discard the packet";
         type empty;
       }
       leaf loss-priority {
         description "Packet's loss priority";
         type enumeration {
           enum "low" {
             description "Loss priority low";
           }
           enum "high" {
             description "Loss priority high";
           }
           enum "medium-low" {
             description "Loss priority medium-low";
           }
           enum "medium-high" {
             description "Loss priority medium-high";
           }
         }
       }
       leaf forwarding-class {
         description "Classify packet to forwarding class";
         type string {
           junos:posix-pattern "^.{1,64}$";
           junos:pattern-message "Must be string of 64 characters or less";
         }
       }
     }
     container aggregate {
       presence "enable aggregate";
       junos:must "(!(\".. if-exceeding aggregate-policing\"))";
       junos:must-message "Cannot use same template as both child and parent policer";
       junos:must "(!(\".. filter-specific\"))";
       junos:must-message "'filter-specific' not valid for aggregate policers; Use 'aggregate instantiation' ";
       junos:cli-feature "oneliner-plus";
       description "Aggregate policer used in Extended Hierarchical Policers";
       uses apply-advanced;
       leaf instantiation {
         description "Specify instantiation semantics of aggregate policer";
         junos:cli-feature "nokeyword";
         type enumeration {
           enum "global" {
             description "Single global instance of aggregate policer";
           }
         }
       }
     }
   }
   grouping firewall_prefix_list {
     junos:cli-feature "homogeneous";
     junos:cli-feature "oneliner";
     leaf name {
       description "Prefix list to match";
       junos:cli-feature "nokeyword";
       type string;
     }
     leaf except {
       description "Match addresses not in this prefix list";
       type empty;
     }
   }
   grouping flow-interface-group {
     junos:cli-feature "oneliner";
     junos:cli-feature "oneliner-plus";
     leaf group {
       description "Interface group ID to match traffic";
       junos:cli-feature "nokeyword";
       type union {
         type string {
           pattern "<.*>|$.*";
         }
         type uint32;
       }
     }
     leaf exclude {
       description "Don't apply flow-spec filter to traffic on this group";
       type empty;
     }
   }
   grouping flow-route-inet6 {
     leaf name {
       junos:cli-feature "nokeyword";
       type string;
     }
     uses apply-advanced;
     leaf no-install {
       description "Don't install firewall filter in forwarding";
       type empty;
     }
     container match {
       description "Flow definition";
       junos:cli-feature "oneliner-plus";
       uses flow-route-qualifier-inet6;
     }
     container then {
       description "Actions to take for this flow";
       junos:cli-feature "oneliner-plus";
       uses flow-route-op;
     }
   }
   grouping flow-route-op {
     junos:cli-feature "oneliner-plus";
     uses apply-advanced;
     leaf community {
       description "Name of BGP community";
       type string;
     }
     choice flow_op_action {
       case case_1 {
         leaf accept {
           description "Allow traffic through";
           type empty;
         }
       }
       case case_2 {
         leaf discard {
           description "Discard all traffic for this flow";
           type empty;
         }
       }
       case case_3 {
         leaf rate-limit {
           description "Rate in bits/sec to limit the flow traffic";
           type string;
         }
       }
     }
     leaf routing-instance {
       description "Redirect to instance identified via Route Target community";
       type string {
         junos:posix-pattern "^[a-z6-]+:([0-9.]+L?|(<((([0-9A-Fa-f]{1,4}:){7}([0-9A-Fa-f]{1,4}|:))|(([0-9A-Fa-f]{1,4}:){6}(:[0-9A-Fa-f]{1,4}|([0-9.]{7,15})|:))|(([0-9A-Fa-f]{1,4}:){5}(((:[0-9A-Fa-f]{1,4}){1,2})|:([0-9.]{7,15})|:))|(([0-9A-Fa-f]{1,4}:){4}(((:[0-9A-Fa-f]{1,4}){1,3})|((:[0-9A-Fa-f]{1,4})?:([0-9.]{7,15}))|:))|(([0-9A-Fa-f]{1,4}:){3}(((:[0-9A-Fa-f]{1,4}){1,4})|((:[0-9A-Fa-f]{1,4}){0,2}:([0-9.]{7,15}))|:))|(([0-9A-Fa-f]{1,4}:){2}(((:[0-9A-Fa-f]{1,4}){1,5})|((:[0-9A-Fa-f]{1,4}){0,3}:([0-9.]{7,15}))|:))|(([0-9A-Fa-f]{1,4}:){1}(((:[0-9A-Fa-f]{1,4}){1,6})|((:[0-9A-Fa-f]{1,4}){0,4}:([0-9.]{7,15}))|:))|(:(((:[0-9A-Fa-f]{1,4}){1,7})|((:[0-9A-Fa-f]{1,4}){0,5}:([0-9.]{7,15}))|:)))(%.+)?>)):+[0-9]+$";
         junos:pattern-message "Use format \'target:x:y\' where \'x\' is an AS number followed by an optional \'L\' (To indicate 4 byte AS), or an IP address and \'y\' is a number. e.g. target:123456L:100 or ipv6-target:<x>:y where \'x\' is an IPv6 Address and \'y\' is local administrator number.";
       }
     }
     leaf sample {
       description "Sample traffic that matches this flow";
       type empty;
     }
     leaf mark {
       description "Set DSCP value for traffic that matches this flow";
       type union {
         type string {
           pattern "<.*>|$.*";
         }
         type uint32 {
           range "0 .. 63";
         }
       }
     }
     leaf next-term {
       description "Continue the filter evaluation after matching this flow";
       type empty;
     }
     choice redirect_op_action {
       case case_1 {
         leaf-list redirect {
           ordered-by user;
           description "Redirect(Tunnel) this flow's traffic to given next-hop address";
           type jt:ipaddr;
         }
       }
     }
   }
   grouping flow-route-qualifier-inet6 {
     junos:cli-feature "oneliner-plus";
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     container destination {
       description "Destination prefix for this traffic flow";
       presence "enable destination";
       junos:cli-feature "oneliner";
       uses flow-prefix-with-offset;
     }
     container source {
       description "Source prefix for this traffic flow";
       presence "enable source";
       junos:cli-feature "oneliner";
       uses flow-prefix-with-offset;
     }
     leaf-list icmp6-type {
       ordered-by user;
       description "ICMP message type";
       type string;
     }
     leaf-list icmp6-code {
       ordered-by user;
       description "ICMP message code";
       type string;
     }
     leaf-list flow-label {
       ordered-by user;
       description "Flow-label (0-1048575)";
       type jt:policy-algebra;
     }
   }
   grouping flow-prefix-with-offset {
     junos:cli-feature "oneliner";
     leaf prefix {
       junos:cli-feature "nokeyword";
       type jt:ipv6prefix;
     }
     leaf prefix-offset {
       description "Offset from where prefix match will start";
       type union {
         type uint32;
         type string {
           pattern "<.*>|$.*";
         }
       }
     }
   }
   grouping flow-validation {
     uses apply-advanced;
     container traceoptions {
       description "Trace options";
       uses flow-dep-traceoptions;
     }
   }
   grouping flow-dep-traceoptions {
     uses apply-advanced;
     container file {
       junos:cli-feature "oneliner";
       description "Trace file options";
       leaf filename {
         description "Name of file in which to write trace information";
         junos:cli-feature "nokeyword";
         type string {
           length "1 .. 1024";
           junos:posix-pattern "![/ %]";
           junos:pattern-message "Must not contain \'/\', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       junos:cli-feature "oneliner";
       description "Tracing parameters";
       leaf name {
         junos:cli-feature "nokeyword";
         type enumeration {
           enum "resolution" {
             description "Trace flow to unicast route resolution";
           }
           enum "flash" {
             description "Trace flash processing";
           }
           enum "route" {
             description "Trace routing information";
           }
           enum "normal" {
             description "Trace normal events";
           }
           enum "general" {
             description "Trace general events";
           }
           enum "state" {
             description "Trace state transitions";
           }
           enum "policy" {
             description "Trace policy processing";
           }
           enum "task" {
             description "Trace routing protocol task processing";
           }
           enum "timer" {
             description "Trace routing protocol timer processing";
           }
           enum "all" {
             description "Trace everything";
           }
         }
       }
       leaf send {
         description "Trace transmitted packets";
         type empty;
       }
       leaf receive {
         description "Trace received packets";
         type empty;
       }
       leaf detail {
         description "Trace detailed information";
         type empty;
       }
       leaf disable {
         description "Disable this trace flag";
         type empty;
       }
       container filter {
         presence "enable filter";
         junos:cli-feature "oneliner";
         description "Filter to apply to tracing";
         leaf match-on {
           description "Argument on which to match";
           type enumeration {
             enum "prefix" {
               description "Filter based on prefix";
             }
             enum "route-attribute" {
               description "Filter based on route attributes";
             }
           }
         }
         leaf-list policy {
           ordered-by user;
           description "Filter policy";
           type jt:policy-algebra;
         }
       }
     }
   }
   grouping inet6_filter {
     description "Define an IPv6 firewall filter";
     leaf name {
       description "Filter name";
       junos:cli-feature "nokeyword";
       type string {
         junos:posix-pattern "!^((__.*)|(.{65,}))$";
         junos:pattern-message "Must be a non-reserved string of 64 characters or less";
       }
     }
     uses apply-advanced;
     leaf promote {
       description "Promote a firewall match to PFM";
       type enumeration {
         enum "gre-key" {
           description "Promote GRE Key to PFM";
         }
         enum "traffic-class" {
           description "Promote traffic-class to PFM";
         }
         enum "vni" {
           description "Promote VNI to PFM";
         }
       }
     }
     leaf-list accounting-profile {
       ordered-by user;
       description "Accounting profile name";
       junos:must "(\"accounting-options filter-profile\")";
       junos:must-message "referenced accounting profile must be defined";
       type string;
     }
     leaf interface-specific {
       description "Defined counters are interface specific";
       type empty;
     }
     leaf service-accounting {
       description "Enable counters for policer service accounting";
       type empty;
     }
     leaf transient-filter {
       description "Transient filter to be used for filter modification";
       type string;
     }
     leaf scale-optimized {
       description "Improve filter prefix scale";
       type empty;
     }
     leaf physical-interface-filter {
       description "Filter is physical interface filter";
       type empty;
     }
     leaf instance-specific {
       description "Filter is instance specific";
       junos:must "(!(\".. physical-interface-filter\"))";
       junos:must-message "Cannot be both physical-interface-filter and instance-specific";
       junos:must "(!(\".. interface-specific\"))";
       junos:must-message "Cannot be both interface-specific and instance-specific";
       type empty;
     }
     leaf layer2-policer {
       description "Layer2 policing for interface";
       type empty;
     }
     list term {
       key name;
       ordered-by user;
       description "Define a firewall term";
       leaf name {
         description "Term name";
         junos:cli-feature "nokeyword";
         type string {
           junos:posix-pattern "!^((__.*)|(.{65,}))$";
           junos:pattern-message "Must be a non-reserved string of 64 characters or less";
         }
       }
       uses apply-advanced;
       leaf filter {
         description "Filter to include";
         junos:must "(\"firewall family inet6 filter $$\")";
         junos:must-message "Referenced filter is not defined";
         junos:must "((!(\".. from\") && !(\".. then\")))";
         junos:must-message "Not compatible with 'from or then'";
         type string {
           junos:posix-pattern "!^((__.*)|(.{65,}))$";
           junos:pattern-message "Must be a non-reserved string of 64 characters or less";
         }
       }
       container from {
         description "Define match criteria";
         uses apply-advanced;
         choice destination-class_choice {
           case case_1 {
             leaf-list destination-class {
               ordered-by user;
               description "String name";
               type string;
             }
           }
           case case_2 {
             leaf-list destination-class-except {
               ordered-by user;
               description "String name";
               type string;
             }
           }
         }
         choice source-class_choice {
           case case_1 {
             leaf-list source-class {
               ordered-by user;
               description "String name";
               type string;
             }
           }
           case case_2 {
             leaf-list source-class-except {
               ordered-by user;
               description "String name";
               type string;
             }
           }
         }
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match  source address";
           uses firewall_addr6_object;
           junos:cli-feature "homogeneous";
           junos:cli-feature "oneliner";
         }
         list destination-address {
           key name;
           ordered-by user;
           description "Match destination address";
           uses firewall_addr6_object;
           junos:cli-feature "homogeneous";
           junos:cli-feature "oneliner";
         }
         list address {
           key name;
           ordered-by user;
           description "Match source or destination address";
           uses firewall_addr6_object;
           junos:cli-feature "homogeneous";
           junos:cli-feature "oneliner";
         }
         list source-prefix-list {
           key name;
           ordered-by user;
           description "Match source prefixes in named list";
           uses firewall_prefix_list;
           junos:cli-feature "homogeneous";
           junos:cli-feature "oneliner";
         }
         list destination-prefix-list {
           key name;
           ordered-by user;
           description "Match destination prefixes in named list";
           uses firewall_prefix_list;
           junos:cli-feature "homogeneous";
           junos:cli-feature "oneliner";
         }
         list prefix-list {
           key name;
           ordered-by user;
           description "Match source or destination prefixes in named list";
           uses firewall_prefix_list;
           junos:cli-feature "homogeneous";
           junos:cli-feature "oneliner";
         }
         choice next-header_choice {
           case case_1 {
             leaf-list next-header {
               ordered-by user;
               type string;
             }
           }
           case case_2 {
             leaf-list next-header-except {
               ordered-by user;
               type string;
             }
           }
         }
         choice payload-protocol_choice {
           case case_1 {
           }
           case case_2 {
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice extension-header_choice {
           case case_1 {
             leaf-list extension-header {
               ordered-by user;
               type string;
             }
           }
           case case_2 {
             leaf-list extension-header-except {
               ordered-by user;
               type string;
             }
           }
         }
         choice packet-length_choice {
           case case_1 {
             leaf-list packet-length {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
           case case_2 {
             leaf-list packet-length-except {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
         }
         choice traffic-class_choice {
           case case_1 {
             leaf-list traffic-class {
               ordered-by user;
               type string;
             }
           }
           case case_2 {
             leaf-list traffic-class-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice ecn_choice {
           case case_1 {
             leaf-list ecn {
               ordered-by user;
               description "ECN value 0-3";
               type union {
                 type string {
                   pattern "<.*>|$.*";
                 }
                 type uint32 {
                   range "0 .. 3";
                 }
               }
             }
           }
         }
         leaf tcp-initial {
           description "Match initial packet of a TCP connection";
           junos:must "((\".. next-header tcp\" || (\".. next-header 6\" || (\".. payload-protocol tcp\" || \".. payload-protocol 6\"))))";
           junos:must-message "next-header tcp or next-header 6 or payload-protocol tcp or payload-protocol 6 must be defined in the same clause";
           type empty;
         }
         leaf tcp-established {
           description "Match packet of an established TCP connection";
           junos:must "((\".. next-header tcp\" || (\".. next-header 6\" || (\".. payload-protocol tcp\" || \".. payload-protocol 6\"))))";
           junos:must-message "next-header tcp or next-header 6 or payload-protocol tcp or payload-protocol 6 must be defined in the same clause";
           type empty;
         }
         leaf tcp-flags {
           description "Match TCP flags (in symbolic or hex formats)";
           junos:must "((\".. next-header tcp\" || (\".. next-header 6\" || (\".. payload-protocol tcp\" || \".. payload-protocol 6\"))))";
           junos:must-message "next-header tcp or next-header 6 or payload-protocol tcp or payload-protocol 6 must be defined in the same clause";
           junos:must "(\".. next-header tcp\")";
           junos:must-message "next-header tcp must be defined in the same clause";
           junos:must "(!(\".. tcp-established\"))";
           junos:must-message "tcp-flags may not be matched in same rule as tcp-established";
           junos:must "(!(\".. tcp-initial\"))";
           junos:must-message "tcp-flags may not be matched in same rule as tcp-initial";
           type string;
         }
         list interface {
           key name;
           ordered-by user;
           description "Match interface name";
           uses match_interface_object;
           junos:cli-feature "oneliner";
         }
         list interface-set {
           key name;
           ordered-by user;
           description "Match interface in set";
           uses match_interface_set_object;
           junos:cli-feature "oneliner";
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice hop-limit_choice {
           case case_1 {
             leaf-list hop-limit {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical hop-limit value or range between 0-255";
               }
             }
           }
           case case_2 {
             leaf-list hop-limit-except {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical hop-limit value or range between 0-255";
               }
             }
           }
         }
         leaf egress-to-ingress {
           description "Match egress fields in ingress";
           type empty;
         }
         choice flex-mask_choice {
           case case_1 {
             container flexible-match-mask {
               description "Match flexible mask";
               presence "enable flexible-match-mask";
               uses match_L3_flexible_mask;
             }
           }
         }
         choice flex-range_choice {
           case case_1 {
             container flexible-match-range {
               description "Match flexible range";
               presence "enable flexible-match-range";
               junos:must "(!(\".. flexible-match-ranges\"))";
               junos:must-message "'flexible-match-range' and 'flexible-match-ranges' are mutually exclusive";
               uses match_L3_flexible_range;
             }
           }
         }
         choice gre-key_choice {
           case case_1 {
             leaf-list gre-key {
               ordered-by user;
               description "Range of values";
               type string {
                 junos:posix-pattern "^([0-9]{1,9}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]|0x[0-f]{1,8})(-([0-9]{1,9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]|0x[0-f]{1,8}))?$";
                 junos:pattern-message "Must be a numerical value or range between 0-4294967295";
               }
             }
           }
           case case_2 {
             leaf-list gre-key-except {
               ordered-by user;
               description "Range of values";
               type string {
                 junos:posix-pattern "^([0-9]{1,9}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]|0x[0-f]{1,8})(-([0-9]{1,9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]|0x[0-f]{1,8}))?$";
                 junos:pattern-message "Must be a numerical value or range between 0-4294967295";
               }
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
         choice slice_choice {
           case case_1 {
           }
           case case_2 {
           }
         }
         list payload-source-mac-address {
           key name;
           ordered-by user;
           description "Source MAC address";
           uses firewall_mac_addr_object;
           junos:cli-feature "homogeneous";
           junos:cli-feature "oneliner";
         }
         list payload-destination-mac-address {
           key name;
           ordered-by user;
           description "Destination MAC address";
           uses firewall_mac_addr_object;
           junos:cli-feature "homogeneous";
           junos:cli-feature "oneliner";
         }
         list payload-source-ipv6-address {
           key name;
           ordered-by user;
           description "Payload Source ip address";
           uses match_payload_ipv6_add;
           junos:cli-feature "homogeneous";
           junos:cli-feature "oneliner";
         }
         list payload-destination-ipv6-address {
           key name;
           ordered-by user;
           description "Payload Destination IP address";
           uses match_payload_ipv6_add;
           junos:cli-feature "homogeneous";
           junos:cli-feature "oneliner";
         }
         container vxlan {
           description "Define vxlan match items";
           uses apply-advanced;
           choice vni_choice {
             case case_1 {
               leaf-list vni {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
             case case_2 {
               leaf-list vni-except {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
           }
           choice rsvd1_choice {
             case case_1 {
               leaf-list rsvd1 {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
             case case_2 {
               leaf-list rsvd1-except {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
           }
           choice rsvd2_choice {
             case case_1 {
               leaf-list rsvd2 {
                 ordered-by user;
                 description "Range of values";
                 type string {
                   junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                   junos:pattern-message "Must be a numeric value or a range between 0-255";
                 }
               }
             }
             case case_2 {
               leaf-list rsvd2-except {
                 ordered-by user;
                 description "Range of values";
                 type string {
                   junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                   junos:pattern-message "Must be a numeric value or a range between 0-255";
                 }
               }
             }
           }
           container flags {
             description "Match VXlan flag field";
             uses match_flags_value;
           }
         }
         leaf source-port-range-optimize {
           description "Optimize the source port range";
           type empty;
         }
         leaf destination-port-range-optimize {
           description "Optimize the destination port range";
           type empty;
         }
       }
       container then {
         junos:cli-feature "oneliner-plus";
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               junos:must "(!(\".. loss-priority\"))";
               junos:must-message "cannot support three-color-policer action if loss-priority is configured";
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
           }
           case case_4 {
           }
           case case_5 {
             leaf policer-charge {
               description "Name of policer-charge used to charge the policer";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         choice inet6cnt {
           case case_1 {
           }
           case case_2 {
             leaf count {
               description "Count the packet in the named counter";
               type string {
                 junos:posix-pattern "!^((__.*)|(.{65,}))$";
                 junos:pattern-message "Must be a non-reserved string of 64 characters or less";
               }
             }
           }
         }
         leaf service-accounting {
           description "Count the packets for service accounting";
           junos:must "(!(\".. service-accounting-deferred\"))";
           junos:must-message "'service-accounting-deferred' and 'service-accounting' cannot coexist";
           junos:must "(!(\".. count\"))";
           junos:must-message "'count' and 'service-accounting' cannot coexist";
           type empty;
         }
         leaf log {
           description "Log the packet";
           type empty;
         }
         leaf pkt-trace {
           description "Trace packet forwarding ";
           type empty;
         }
         leaf packet-mode {
           description "Bypass flow mode for the packet";
           type empty;
         }
         leaf syslog {
           description "System log (syslog) information about the packet";
           type empty;
         }
         leaf packet-capture {
           description "Enable packet capture for telemetry";
           type empty;
         }
         leaf sample {
           description "Sample the packet";
           junos:must "((\"forwarding-options sampling family inet6\" || (\"forwarding-options packet-capture\" || any \"forwarding-options sampling instance <*> family inet6\")))";
           junos:must-message "Requires forwarding-options sampling or packet-capture config";
           type empty;
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           junos:must "(\"forwarding-options port-mirroring\")";
           junos:must-message "Configure 'port-mirroring' under 'forwarding-options'";
           type empty;
         }
         leaf sampling {
           description "Sample the packets";
           junos:must "((!(\".. discard\") && !(\".. reject\")))";
           junos:must-message "discard/reject action is not allowed with sampling action";
           junos:must "(((\"protocols sflow sample-rate ingress\" && \"protocols sflow interfaces\") || any \"protocols sflow interfaces <*> sample-rate ingress\"))";
           junos:must-message "sampling action required sflow interface configured under protocols with a valid ingress sample-rate";
           type empty;
         }
         leaf inline-monitoring-instance {
           description "Inline monitoring to specified instance";
           junos:must "(\"services inline-monitoring instance $$\")";
           junos:must-message "Configure 'inline-monitoring instance'";
           type string {
             junos:posix-pattern "!^((__.*)|(.{65,}))$";
             junos:pattern-message "Must be a non-reserved string of 64 characters or less";
           }
         }
         leaf inband-flow-telemetry-init {
           description "Initiate inband telemetry for a flow";
           junos:must "((!(\".. .. from\") || (\".. .. from destination-port\" || (\".. .. from source-port\" || (\".. .. from protocol\" || (\".. .. from ip-protocol\" || (\".. .. from next-header\" || (\".. .. from ip-destination-address\" || (\".. .. from ip-source-address\" || (\".. .. from destination-address\" || \".. .. from source-address\"))))))))))";
           junos:must-message "Match terms must either of src-ip or dest-ip or protocol or src-port or dest-port";
           junos:must "(\"services inband-flow-telemetry flow-type\")";
           junos:must-message "inband-telemetry flow-type must be defined";
           junos:must "(\"services inband-flow-telemetry profile $$\")";
           junos:must-message "Referenced inband-flow-telemetry profile does not exist";
           type string;
         }
         leaf inband-flow-telemetry-terminate {
           description "Terminate inband telemetry for a flow";
           junos:must "((!(\".. .. from\") || (\".. .. from destination-port\" || (\".. .. from source-port\" || (\".. .. from protocol\" || (\".. .. from ip-protocol\" || (\".. .. from next-header\" || (\".. .. from ip-destination-address\" || (\".. .. from ip-source-address\" || (\".. .. from destination-address\" || \".. .. from source-address\"))))))))))";
           junos:must-message "Match terms must either of src-ip or dest-ip or protocol or src-port or dest-port";
           junos:must "(\"services inband-flow-telemetry flow-type\")";
           junos:must-message "inband-telemetry flow-type must be defined";
           junos:must "(\"services inband-flow-telemetry profile $$\")";
           junos:must-message "Referenced inband-flow-telemetry profile does not exist";
           type string;
         }
         leaf analyzer {
           description "Name of analyzer";
           junos:must "(\"ethernet-switching-options analyzer $$\")";
           junos:must-message "Named Analyzer must be set";
           type string {
             junos:posix-pattern "!^((__.*)|(.{65,}))$";
             junos:pattern-message "Must be a non-reserved string of 64 characters or less";
           }
         }
         leaf loss-priority {
           description "Packet's loss priority";
           junos:must "(\".. forwarding-class\")";
           junos:must-message "To configure loss-priority, forwarding-class must be set";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           junos:must "(\".. loss-priority\")";
           junos:must-message "To configure forwarding-class, loss-priority must be set";
           type string {
             junos:posix-pattern "^.{1,64}$";
             junos:pattern-message "Must be string of 64 characters or less";
           }
         }
         leaf traffic-class {
           description "Set traffic-class code point";
           type string;
         }
         leaf skip-services {
           description "Skip the services";
           type empty;
         }
         leaf service-filter-hit {
           description "Marked when packet processing by the current type of chained filters is done, the packet is directed to the next type of filters";
           type empty;
         }
         choice designation {
           case case_1 {
             container decapsulate {
               presence "enable decapsulate";
               description "Terminate a tunnel";
               uses apply-advanced;
               choice tunnel-protocol {
                 case case_1 {
                   container gre {
                     presence "enable gre";
                     description "GRE protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           junos:cli-feature "oneliner";
                           description "Packets are directed to specified routing instance";
                           leaf routing-instance-name {
                             description "Name of routing instance";
                             junos:cli-feature "nokeyword";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_2 {
                 }
                 case case_3 {
                   container mpls-in-udp {
                     presence "enable mpls-in-udp";
                     description "MPLS-in-UDP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           junos:cli-feature "oneliner";
                           description "Packets are directed to specified routing instance";
                           leaf routing-instance-name {
                             description "Name of routing instance";
                             junos:cli-feature "nokeyword";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_4 {
                   container inet-in-udp {
                     presence "enable inet-in-udp";
                     description "IPv4-in-UDP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           junos:cli-feature "oneliner";
                           description "Packets are directed to specified routing instance";
                           leaf routing-instance-name {
                             description "Name of routing instance";
                             junos:cli-feature "nokeyword";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_5 {
                   container inet6-in-udp {
                     presence "enable inet6-in-udp";
                     description "IPv6-in-UDP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           junos:cli-feature "oneliner";
                           description "Packets are directed to specified routing instance";
                           leaf routing-instance-name {
                             description "Name of routing instance";
                             junos:cli-feature "nokeyword";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_6 {
                   container l2tp {
                     description "L2TP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     leaf-list cookie {
                       ordered-by user;
                       description "L2TPv3 cookie";
                       type string {
                         length "1 .. 32";
                       }
                     }
                     choice destination {
                       case case_1 {
                         leaf output-interface {
                           description "Interface name";
                           junos:must "(\"interfaces $$\")";
                           junos:must-message "Interface must be defined in the interfaces hierarchy";
                           type union {
                             type jt:interface-unit;
                             type string {
                               pattern "<.*>|$.*";
                             }
                           }
                         }
                       }
                     }
                   }
                 }
                 case case_7 {
                   container ipip {
                     presence "enable ipip";
                     description "IPIP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           junos:cli-feature "oneliner";
                           description "Packets are directed to specified routing instance";
                           leaf routing-instance-name {
                             description "Name of routing instance";
                             junos:cli-feature "nokeyword";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
               }
             }
           }
           case case_2 {
           }
           case case_3 {
             leaf accept {
               description "Accept the packet";
               type empty;
             }
           }
           case case_4 {
             leaf discard {
               description "Discard the packet";
               type empty;
             }
           }
           case case_5 {
             leaf next {
               description "Continue to next term in a filter";
               type enumeration {
                 enum "term" {
                   description "Continue to next term in a filter";
                 }
               }
             }
           }
           case case_6 {
           }
           case case_7 {
             list logical-system {
               key logical-system-name;
               ordered-by user;
               junos:cli-feature "oneliner";
               description "Packets are directed to specified logical system";
               max-elements 1;
               leaf logical-system-name {
                 description "Name of logical system";
                 junos:cli-feature "nokeyword";
                 type string {
                   junos:posix-pattern "^[a-zA-Z0-9_-]{1,63}$";
                   junos:pattern-message "Logical-system name is a string consisting of up to 63 letters, numbers, dashes and underscores";
                 }
               }
               container routing-instance {
                 junos:cli-feature "oneliner";
                 description "Packets are directed to specified routing instance";
                 leaf routing-instance-name {
                   description "Name of routing instance";
                   junos:cli-feature "nokeyword";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
               leaf topology {
                 description "Packets are directed to specified topology";
                 type string {
                   junos:posix-pattern "!^((.*:.*)|(.{129,}))$";
                   junos:pattern-message "Must be a non-reserved string of 128 characters or less";
                 }
               }
             }
           }
           case case_8 {
           }
           case case_9 {
             container routing-instance {
               junos:cli-feature "oneliner";
               description "Packets are directed to specified routing instance";
               leaf routing-instance-name {
                 description "Name of routing instance";
                 junos:cli-feature "nokeyword";
                 type string {
                   junos:posix-pattern "!^((__.*__)|(all)|(.*[ ].*)|(\"\")|(.{129,}))$";
                   junos:pattern-message "Must be a non-reserved string of 128 characters or less with no spaces.";
                 }
               }
               leaf topology {
                 description "Packets are directed to specified topology";
                 type string {
                   junos:posix-pattern "!^((.*:.*)|(.{129,}))$";
                   junos:pattern-message "Must be a non-reserved string of 128 characters or less";
                 }
               }
             }
           }
           case case_10 {
             leaf topology {
               description "Packets are directed to specified topology";
               type string {
                 junos:posix-pattern "!^((.*:.*)|(.{129,}))$";
                 junos:pattern-message "Must be a non-reserved string of 128 characters or less";
               }
             }
           }
           case case_11 {
             container next-ip6 {
               junos:cli-feature "oneliner";
               description "Packets are directed to the specified ipv6 address";
               leaf address {
                 description "Address to route";
                 junos:cli-feature "nokeyword";
                 type jt:ipv6prefix;
               }
               container routing-instance {
                 junos:cli-feature "oneliner";
                 description "Packets are directed to specified routing instance";
                 leaf routing-instance-name {
                   description "Name of routing instance";
                   junos:cli-feature "nokeyword";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
             }
           }
           case case_12 {
             container next-interface {
               presence "enable next-interface";
               description "Packets are to be routed through the specified interface";
               uses apply-advanced;
               leaf interface-name {
                 description "Interface name";
                 junos:cli-feature "nokeyword";
                 type string {
                   length "1 .. 127";
                   junos:posix-pattern "^((ge-)|(mge-)|(xe-)|(et-)|(gr-)|(ae)|(irb)|(fti))";
                   junos:pattern-message "Only ge, mge, xe, et, ae, irb, fti and point-to-point gr tunnel intefaces are supported";
                 }
               }
               container routing-instance {
                 junos:cli-feature "oneliner";
                 description "Packets are directed to specified routing instance";
                 leaf routing-instance-name {
                   description "Name of routing instance";
                   junos:cli-feature "nokeyword";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
               choice designation {
                 case case_1 {
                   leaf accept {
                     description "Accept the packet";
                     type empty;
                   }
                 }
                 case case_2 {
                   leaf next {
                     description "Continue to next term in a filter";
                     type enumeration {
                       enum "term" {
                         description "Continue to next term in a filter";
                       }
                     }
                   }
                 }
               }
             }
           }
           case case_13 {
             container reject {
               presence "enable reject";
               junos:cli-feature "oneliner";
               description "Reject the packet";
               choice style {
                 case case_1 {
                   leaf no-route {
                     description "Send ICMPv6 No Route message";
                     type empty;
                   }
                 }
                 case case_2 {
                   leaf administratively-prohibited {
                     description "Send ICMPv6 Administratively Prohibited message";
                     type empty;
                   }
                 }
                 case case_3 {
                   leaf beyond-scope {
                     description "Send ICMPv6 Beyond Scope of Source Address message";
                     type empty;
                   }
                 }
                 case case_4 {
                   leaf address-unreachable {
                     description "Send ICMPv6 Address Unreachable message";
                     type empty;
                   }
                 }
                 case case_5 {
                   leaf port-unreachable {
                     description "Send ICMPv6 Port Unreachable message";
                     type empty;
                   }
                 }
                 case case_6 {
                   leaf policy-failed {
                     description "Source address failed ingress/egress policy";
                     type empty;
                   }
                 }
                 case case_7 {
                   leaf reject-route {
                     description "Reject route to destination";
                     type empty;
                   }
                 }
                 case case_8 {
                   leaf tcp-reset {
                     description "Send TCP Reset message";
                     type empty;
                   }
                 }
                 case case_9 {
                   leaf network-unreachable {
                     description "Send ICMPv4 Network Unreachable message";
                     status deprecated;
                     type empty;
                   }
                 }
                 case case_10 {
                   leaf host-unreachable {
                     description "Send ICMPv4 Host Unreachable message";
                     status deprecated;
                     type empty;
                   }
                 }
                 case case_11 {
                   leaf protocol-unreachable {
                     description "Send ICMPv4 Protocol Unreachable message";
                     status deprecated;
                     type empty;
                   }
                 }
                 case case_12 {
                   leaf source-route-failed {
                     description "Send ICMPv4 Source Route Failed message";
                     status deprecated;
                     type empty;
                   }
                 }
                 case case_13 {
                   leaf network-unknown {
                     description "Send ICMPv4 Network Unknown message";
                     status deprecated;
                     type empty;
                   }
                 }
                 case case_14 {
                   leaf host-unknown {
                     description "Send ICMPv4 Host Unknown message";
                     status deprecated;
                     type empty;
                   }
                 }
                 case case_15 {
                   leaf source-host-isolated {
                     description "Send ICMPv4 Source Host Isolated message";
                     status deprecated;
                     type empty;
                   }
                 }
                 case case_16 {
                   leaf network-prohibited {
                     description "Send ICMPv4 Network Prohibited message";
                     status deprecated;
                     type empty;
                   }
                 }
                 case case_17 {
                   leaf host-prohibited {
                     description "Send ICMPv4 Host Prohibited message";
                     status deprecated;
                     type empty;
                   }
                 }
                 case case_18 {
                   leaf bad-network-tos {
                     description "Send ICMPv4 Bad Network ToS message";
                     status deprecated;
                     type empty;
                   }
                 }
                 case case_19 {
                   leaf bad-host-tos {
                     description "Send ICMPv4 Bad Host ToS message";
                     status deprecated;
                     type empty;
                   }
                 }
                 case case_20 {
                   leaf precedence-violation {
                     description "Send ICMPv4 Precedence Violation message";
                     status deprecated;
                     type empty;
                   }
                 }
                 case case_21 {
                   leaf precedence-cutoff {
                     description "Send ICMPv4 Precedence Cutoff message";
                     status deprecated;
                     type empty;
                   }
                 }
               }
             }
           }
         }
       }
       container template {
         description "Refer a template";
         uses apply-advanced;
         leaf template-name {
           description "Template name";
           junos:cli-feature "nokeyword";
           type string {
             junos:posix-pattern "!^((__.*)|(.{65,}))$";
             junos:pattern-message "Must be a non-reserved string of 64 characters or less";
           }
         }
       }
     }
   }
   grouping inet6_fuf {
     leaf name {
       description "Name of fast update filter";
       junos:cli-feature "nokeyword";
       junos:must "(unique \"firewall family <*> filter $$\")";
       junos:must-message "Fast update filter can not have the same name as firewall family filter";
       type string {
         junos:posix-pattern "!^((__.*)|(.{65,}))$";
         junos:pattern-message "Must be a non-reserved string of 64 characters or less";
       }
     }
     uses apply-advanced;
     leaf interface-specific {
       description "Defined counters are interface specific";
       type empty;
     }
     leaf-list match-order {
       ordered-by user;
       type enumeration {
         enum "next-header" {
           description "Include next header protocol in match set";
         }
         enum "payload-protocol" {
           description "Include payload protocol in match set";
         }
         enum "source-address" {
           description "Include source-address in match set";
         }
         enum "destination-address" {
           description "Include destination-address in match set";
         }
         enum "source-port" {
           description "Include source-port in match set";
         }
         enum "destination-port" {
           description "Include destination-port in match set";
         }
         enum "traffic-class" {
           description "Include traffic-class (DSCP) in match set";
         }
       }
     }
     list term {
       key name;
       ordered-by user;
       description "One or more firewall terms";
       leaf name {
         description "Term name";
         junos:cli-feature "nokeyword";
         type string {
           junos:posix-pattern "!^((__.*)|(.{65,}))$";
           junos:pattern-message "Must be a non-reserved string of 64 characters or less";
         }
       }
       uses apply-advanced;
       leaf only-at-create {
         description "Add term only when filter is first created.";
         type empty;
       }
       container from {
         description "Match criteria";
         uses apply-advanced;
         container source-address {
           description "Match source IP address";
           junos:cli-feature "oneliner-plus";
           uses firewall_addr6_simple_object;
         }
         container destination-address {
           description "Match destination IP address";
           junos:cli-feature "oneliner-plus";
           uses firewall_addr6_simple_object;
         }
         choice source-port_choice {
           case case_1 {
             container source-port {
               description "Match TCP/UDP source port";
               junos:cli-feature "oneliner-plus";
               uses match_simple_port_value;
             }
           }
         }
         choice destination-port_choice {
           case case_1 {
             container destination-port {
               description "Match TCP/UDP destination port";
               junos:cli-feature "oneliner-plus";
               uses match_simple_port_value;
             }
           }
         }
         choice next-header_choice {
           case case_1 {
             container next-header {
               description "Match next header protocol type";
               junos:cli-feature "oneliner-plus";
               uses match_simple_protocol_value;
             }
           }
         }
         choice traffic-class_choice {
           case case_1 {
             container traffic-class {
               description "Match Differentiated Services (DiffServ) code point";
               junos:cli-feature "oneliner-plus";
               uses match_simple_dscp_value;
             }
           }
         }
         leaf match-terms {
           description "Dynamically supplied list of match criteria";
           type string;
         }
       }
       container then {
         junos:cli-feature "oneliner-plus";
         description "Action to take if the 'from' condition is matched";
         uses apply-advanced;
         choice policer-choice {
           case case_1 {
             leaf policer {
               description "Name of policer to use to rate-limit traffic";
               type string {
                 junos:posix-pattern "!^((__.*)|(.{65,}))$";
                 junos:pattern-message "Must be a non-reserved string of 64 characters or less";
               }
             }
           }
         }
         leaf count {
           description "Count the packet in the named counter";
           type string {
             junos:posix-pattern "!^((__.*)|(.{65,}))$";
             junos:pattern-message "Must be a non-reserved string of 64 characters or less";
           }
         }
         leaf service-accounting {
           description "Count the packets for service accounting";
           junos:must "(!(\".. count\"))";
           junos:must-message "'count' and 'service-accounting' cannot coexist";
           type empty;
         }
         leaf log {
           description "Log the packet";
           type empty;
         }
         leaf port-mirror {
           description "Port-mirror the packet";
           type empty;
         }
         leaf loss-priority {
           description "Packet's loss priority";
           junos:must "(!(\".. three-color-policer\"))";
           junos:must-message "Configuring loss-priority is incompatible with configuring three-color-policer";
           junos:must "(\".. forwarding-class\")";
           junos:must-message "To configure loss-priority, forwarding-class must be set";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           junos:must "(\".. loss-priority\")";
           junos:must-message "To configure forwarding-class, loss-priority must be set";
           type string {
             junos:posix-pattern "^.{1,64}$";
             junos:pattern-message "Must be string of 64 characters or less";
           }
         }
         leaf action-terms {
           description "Dynamically supplied list of actions";
           type string;
         }
         choice designation {
           case case_1 {
             leaf accept {
               description "Accept the packet";
               type empty;
             }
           }
           case case_2 {
             leaf discard {
               description "Discard the packet";
               type empty;
             }
           }
           case case_3 {
             container routing-instance {
               junos:cli-feature "oneliner";
               description "Packets are directed to specified routing instance";
               leaf routing-instance-name {
                 description "Name of routing instance";
                 junos:cli-feature "nokeyword";
                 type string {
                   junos:posix-pattern "!^((__.*__)|(all)|(.*[ ].*)|(\"\")|(.{129,}))$";
                   junos:pattern-message "Must be a non-reserved string of 128 characters or less with no spaces.";
                 }
               }
               leaf topology {
                 description "Packets are directed to specified topology";
                 type string {
                   junos:posix-pattern "!^((.*:.*)|(.{129,}))$";
                   junos:pattern-message "Must be a non-reserved string of 128 characters or less";
                 }
               }
             }
           }
         }
       }
     }
   }
   grouping firewall_addr6_simple_object {
     junos:cli-feature "oneliner-plus";
     uses apply-advanced;
     leaf address {
       description "Prefix to match";
       junos:cli-feature "nokeyword";
       type jt:ipv6prefix;
     }
   }
   grouping inet6_service_filter {
     leaf name {
       description "Filter name";
       junos:cli-feature "nokeyword";
       type string {
         junos:posix-pattern "!^((__.*)|(.{65,}))$";
         junos:pattern-message "Must be a non-reserved string of 64 characters or less";
       }
     }
     uses apply-advanced;
     list term {
       key name;
       ordered-by user;
       description "Service filter term";
       leaf name {
         description "Term name";
         junos:cli-feature "nokeyword";
         type string {
           junos:posix-pattern "!^((__.*)|(.{65,}))$";
           junos:pattern-message "Must be a non-reserved string of 64 characters or less";
         }
       }
       uses apply-advanced;
       container from {
         description "Match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match  source address";
           uses firewall_addr6_object;
           junos:cli-feature "homogeneous";
           junos:cli-feature "oneliner";
         }
         list destination-address {
           key name;
           ordered-by user;
           description "Match destination address";
           uses firewall_addr6_object;
           junos:cli-feature "homogeneous";
           junos:cli-feature "oneliner";
         }
         list address {
           key name;
           ordered-by user;
           description "Match source or destination address";
           uses firewall_addr6_object;
           junos:cli-feature "homogeneous";
           junos:cli-feature "oneliner";
         }
         list source-prefix-list {
           key name;
           ordered-by user;
           description "Match source prefixes in named list";
           uses firewall_prefix_list;
           junos:cli-feature "homogeneous";
           junos:cli-feature "oneliner";
         }
         list destination-prefix-list {
           key name;
           ordered-by user;
           description "Match destination prefixes in named list";
           uses firewall_prefix_list;
           junos:cli-feature "homogeneous";
           junos:cli-feature "oneliner";
         }
         list prefix-list {
           key name;
           ordered-by user;
           description "Match source or destination prefixes in named list";
           uses firewall_prefix_list;
           junos:cli-feature "homogeneous";
           junos:cli-feature "oneliner";
         }
         choice next-header_choice {
           case case_1 {
             leaf-list next-header {
               ordered-by user;
               type string;
             }
           }
           case case_2 {
             leaf-list next-header-except {
               ordered-by user;
               type string;
             }
           }
         }
         choice payload-protocol_choice {
           case case_1 {
           }
           case case_2 {
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice extension-header_choice {
           case case_1 {
             leaf-list extension-header {
               ordered-by user;
               type string;
             }
           }
           case case_2 {
             leaf-list extension-header-except {
               ordered-by user;
               type string;
             }
           }
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
           }
           case case_2 {
           }
         }
         leaf tcp-flags {
           description "Match TCP flags (in symbolic or hex formats)";
           junos:must "(!(\".. tcp-established\"))";
           junos:must-message "tcp-flags may not be matched in same rule as tcp-established";
           junos:must "(!(\".. tcp-initial\"))";
           junos:must-message "tcp-flags may not be matched in same rule as tcp-initial";
           type string;
         }
         choice loss-priority_choice {
           case case_1 {
           }
           case case_2 {
           }
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
       }
       container then {
         junos:cli-feature "oneliner-plus";
         description "Action to take if the 'from' condition is matched";
         uses apply-advanced;
         leaf count {
           description "Count the packet in the named counter";
           type string {
             junos:posix-pattern "!^((__.*)|(.{65,}))$";
             junos:pattern-message "Must be a non-reserved string of 64 characters or less";
           }
         }
         leaf log {
           description "Log the packet";
           type empty;
         }
         leaf pkt-trace {
           description "Pkt-Trace the packet";
           type empty;
         }
         leaf sample {
           description "Sample the packet";
           type empty;
         }
         leaf port-mirror {
           description "Port-mirror the packet";
           type empty;
         }
         choice designation {
           case case_1 {
             leaf service {
               description "Forward packets to service processing";
               type empty;
             }
           }
           case case_2 {
             leaf skip {
               description "Skip service processing";
               type empty;
             }
           }
           case case_3 {
             leaf accept {
               description "Accept the packet";
               type empty;
             }
           }
         }
       }
     }
   }
   grouping inet6_template {
     leaf name {
       description "Template name";
       junos:cli-feature "nokeyword";
       type string {
         junos:posix-pattern "!^((__.*)|(.{65,}))$";
         junos:pattern-message "Must be a non-reserved string of 64 characters or less";
       }
     }
     uses apply-advanced;
     container attributes {
       description "Template attributes";
       uses apply-advanced;
       leaf destination-address {
         description "Match destination address";
         type empty;
       }
       leaf destination-port {
         description "Match TCP/UDP destination port";
         type empty;
       }
       leaf destination-port-range-optimize {
         description "Optimize the destination port range";
         type empty;
       }
       leaf destination-prefix-list {
         description "Match destination prefixes in named list";
         type empty;
       }
       leaf flexible-match-mask {
         description "Match flexible mask";
         type empty;
       }
       leaf flexible-match-range {
         description "Match ICMP message code";
         type empty;
       }
       leaf hop-limit {
         description "Match Hop Limit";
         type empty;
       }
       leaf icmp-code {
         description "Match ICMP message code";
         type empty;
       }
       leaf icmp-type {
         description "Match ICMP message code";
         type empty;
       }
       leaf interface {
         description "Match interface name";
         type empty;
       }
       leaf next-header {
         description "Match next header protocol type";
         type empty;
       }
       leaf source-address {
         description "Match  source address";
         type empty;
       }
       leaf source-port {
         description "Match TCP/UDP source port";
         type empty;
       }
       leaf source-port-range-optimize {
         description "Optimize the source port range";
         type empty;
       }
       leaf source-prefix-list {
         description "Match source prefixes in named list";
         type empty;
       }
       leaf tcp-established {
         description "Match packet of an established TCP connection";
         type empty;
       }
       leaf tcp-flags {
         description "Match TCP flags";
         type empty;
       }
       leaf tcp-initial {
         description "Match initial packet of a TCP connection";
         type empty;
       }
       leaf traffic-class {
         description "Match Differentiated Services (DiffServ) code point";
         type empty;
       }
       leaf egress-to-ingress {
         description "Match egress fields in ingress";
         type empty;
       }
       leaf payload-source-mac-address {
         description "Match source MAC address";
         type empty;
       }
       leaf payload-destination-mac-address {
         description "Match destination MAC address";
         type empty;
       }
       leaf payload-source-ipv6-address {
         description "Match Payload IP source address";
         type empty;
       }
       leaf payload-destination-ipv6-address {
         description "Match Payload IP destination address";
         type empty;
       }
     }
   }
   grouping inet_dialer_filter {
     leaf name {
       description "Filter name";
       junos:cli-feature "nokeyword";
       type string {
         junos:posix-pattern "!^((__.*)|(.{65,}))$";
         junos:pattern-message "Must be a non-reserved string of 64 characters or less";
       }
     }
     uses apply-advanced;
     leaf-list accounting-profile {
       ordered-by user;
       description "Accounting profile name";
       junos:must "(\"accounting-options filter-profile\")";
       junos:must-message "referenced accounting profile must be defined";
       type string;
     }
     list term {
       key name;
       ordered-by user;
       description "Define a firewall term";
       leaf name {
         description "Term name";
         junos:cli-feature "nokeyword";
         type string {
           junos:posix-pattern "!^((__.*)|(.{65,}))$";
           junos:pattern-message "Must be a non-reserved string of 64 characters or less";
         }
       }
       uses apply-advanced;
       container from {
         description "Define match criteria";
         uses apply-advanced;
         list source-address {
           key name;
           ordered-by user;
           description "Match IP source address";
           uses firewall_addr_object;
           junos:cli-feature "homogeneous";
           junos:cli-feature "oneliner";
         }
         list destination-address {
           key name;
           ordered-by user;
           description "Match IP destination address";
           uses firewall_addr_object;
           junos:cli-feature "homogeneous";
           junos:cli-feature "oneliner";
         }
         list address {
           key name;
           ordered-by user;
           description "Match IP source or destination address";
           uses firewall_addr_object;
           junos:cli-feature "homogeneous";
           junos:cli-feature "oneliner";
         }
         list source-prefix-list {
           key name;
           ordered-by user;
           description "Match IP source prefixes in named list";
           uses firewall_prefix_list;
           junos:cli-feature "homogeneous";
           junos:cli-feature "oneliner";
         }
         list destination-prefix-list {
           key name;
           ordered-by user;
           description "Match IP destination prefixes in named list";
           uses firewall_prefix_list;
           junos:cli-feature "homogeneous";
           junos:cli-feature "oneliner";
         }
         list prefix-list {
           key name;
           ordered-by user;
           description "Match IP source or destination prefixes in named list";
           uses firewall_prefix_list;
           junos:cli-feature "homogeneous";
           junos:cli-feature "oneliner";
         }
         choice packet-length_choice {
           case case_1 {
             leaf-list packet-length {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
           case case_2 {
             leaf-list packet-length-except {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
         }
         choice precedence_choice {
           case case_1 {
             leaf-list precedence {
               ordered-by user;
               type string;
             }
           }
           case case_2 {
             leaf-list precedence-except {
               ordered-by user;
               type string;
             }
           }
         }
         choice dscp_choice {
           case case_1 {
             leaf-list dscp {
               ordered-by user;
               type string;
             }
           }
           case case_2 {
             leaf-list dscp-except {
               ordered-by user;
               type string;
             }
           }
         }
         choice ip-options_choice {
           case case_1 {
             leaf-list ip-options {
               ordered-by user;
               type string;
             }
           }
           case case_2 {
             leaf-list ip-options-except {
               ordered-by user;
               type string;
             }
           }
         }
         leaf is-fragment {
           description "Match if packet is a fragment";
           type empty;
         }
         leaf first-fragment {
           description "Match if packet is the first fragment";
           type empty;
         }
         choice fragment-offset_choice {
           case case_1 {
             leaf-list fragment-offset {
               ordered-by user;
               description "Range of values";
               type string {
                 junos:posix-pattern "^[[:digit:]]+(-[[:digit:]]+)?$";
                 junos:pattern-message "Must be a in form of number or a range in the form \'<minimum-value>-<maximum-value>\'";
               }
             }
           }
           case case_2 {
             leaf-list fragment-offset-except {
               ordered-by user;
               description "Range of values";
               type string {
                 junos:posix-pattern "^[[:digit:]]+(-[[:digit:]]+)?$";
                 junos:pattern-message "Must be a in form of number or a range in the form \'<minimum-value>-<maximum-value>\'";
               }
             }
           }
         }
         leaf fragment-flags {
           description "Match fragment flags";
           type string;
         }
         choice protocol_choice {
           case case_1 {
             leaf-list protocol {
               ordered-by user;
               type string;
             }
           }
           case case_2 {
             leaf-list protocol-except {
               ordered-by user;
               type string;
             }
           }
         }
         choice ttl_choice {
           case case_1 {
           }
           case case_2 {
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-initial {
           description "Match initial packet of a TCP connection";
           type empty;
         }
         leaf tcp-established {
           description "Match packet of an established TCP connection";
           type empty;
         }
         leaf tcp-flags {
           description "Match TCP flags (in symbolic or hex formats)";
           type string;
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
           }
           case case_2 {
           }
         }
       }
       container then {
         junos:cli-feature "oneliner-plus";
         description "Action to take if the 'from' condition is matched";
         uses apply-advanced;
         leaf log {
           description "Log the packet";
           type empty;
         }
         leaf syslog {
           description "System log (syslog) information about the packet";
           type empty;
         }
         leaf sample {
           description "Sample the packet";
           type empty;
         }
         choice designation {
           case case_1 {
             leaf note {
               description "Interested ISDN packet";
               type empty;
             }
           }
           case case_2 {
             leaf ignore {
               description "Non-interested ISDN packet";
               type empty;
             }
           }
         }
       }
     }
   }
   grouping inet_filter {
     leaf name {
       description "Filter name";
       junos:cli-feature "nokeyword";
       type string {
         junos:posix-pattern "!^((__.*)|(.{65,}))$";
         junos:pattern-message "Must be a non-reserved string of 64 characters or less";
       }
     }
     uses apply-advanced;
     leaf promote {
       description "Promote a firewall match to PFM";
       type enumeration {
         enum "gre-key" {
           description "Promote GRE Key to PFM";
         }
         enum "dscp" {
           description "Promote DSCP to PFM";
         }
         enum "vni" {
           description "Promote VNI to PFM";
         }
       }
     }
     leaf-list accounting-profile {
       ordered-by user;
       description "Accounting profile name";
       junos:must "(\"accounting-options filter-profile\")";
       junos:must-message "referenced accounting profile must be defined";
       type string;
     }
     leaf interface-specific {
       description "Defined counters are interface specific";
       type empty;
     }
     leaf service-accounting {
       description "Enable counters for policer service accounting";
       type empty;
     }
     leaf transient-filter {
       description "Transient filter to be used for filter modification";
       type string;
     }
     leaf scale-optimized {
       description "Improve filter prefix scale";
       type empty;
     }
     leaf physical-interface-filter {
       description "Filter is physical interface filter";
       type empty;
     }
     leaf instance-specific {
       description "Filter is instance specific";
       junos:must "(!(\".. physical-interface-filter\"))";
       junos:must-message "Cannot be both physical-interface-filter and instance-specific";
       junos:must "(!(\".. interface-specific\"))";
       junos:must-message "Cannot be both interface-specific and instance-specific";
       type empty;
     }
     leaf layer2-policer {
       description "Layer2 policing for interface";
       type empty;
     }
     list term {
       key name;
       ordered-by user;
       description "Define a firewall term";
       leaf name {
         description "Term name";
         junos:cli-feature "nokeyword";
         type string {
           junos:posix-pattern "!^((__.*)|(.{65,}))$";
           junos:pattern-message "Must be a non-reserved string of 64 characters or less";
         }
       }
       uses apply-advanced;
       leaf filter {
         description "Filter to include";
         junos:must "((\"firewall filter $$\" || \"firewall family inet filter $$\"))";
         junos:must-message "Referenced filter is not defined";
         junos:must "((!(\".. from\") && !(\".. then\")))";
         junos:must-message "Not compatible with 'from or then'";
         type string {
           junos:posix-pattern "!^((__.*)|(.{65,}))$";
           junos:pattern-message "Must be a non-reserved string of 64 characters or less";
         }
       }
       container from {
         description "Define match criteria";
         uses apply-advanced;
         choice destination-class_choice {
           case case_1 {
             leaf-list destination-class {
               ordered-by user;
               description "String name";
               type string;
             }
           }
           case case_2 {
             leaf-list destination-class-except {
               ordered-by user;
               description "String name";
               type string;
             }
           }
         }
         choice source-class_choice {
           case case_1 {
             leaf-list source-class {
               ordered-by user;
               description "String name";
               type string;
             }
           }
           case case_2 {
             leaf-list source-class-except {
               ordered-by user;
               description "String name";
               type string;
             }
           }
         }
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match IP source address";
           uses firewall_addr_object;
           junos:cli-feature "homogeneous";
           junos:cli-feature "oneliner";
         }
         list destination-address {
           key name;
           ordered-by user;
           description "Match IP destination address";
           uses firewall_addr_object;
           junos:cli-feature "homogeneous";
           junos:cli-feature "oneliner";
         }
         list address {
           key name;
           ordered-by user;
           description "Match IP source or destination address";
           uses firewall_addr_object;
           junos:cli-feature "homogeneous";
           junos:cli-feature "oneliner";
         }
         list source-prefix-list {
           key name;
           ordered-by user;
           description "Match IP source prefixes in named list";
           uses firewall_prefix_list;
           junos:cli-feature "homogeneous";
           junos:cli-feature "oneliner";
         }
         list destination-prefix-list {
           key name;
           ordered-by user;
           description "Match IP destination prefixes in named list";
           uses firewall_prefix_list;
           junos:cli-feature "homogeneous";
           junos:cli-feature "oneliner";
         }
         list prefix-list {
           key name;
           ordered-by user;
           description "Match IP source or destination prefixes in named list";
           uses firewall_prefix_list;
           junos:cli-feature "homogeneous";
           junos:cli-feature "oneliner";
         }
         choice packet-length_choice {
           case case_1 {
             leaf-list packet-length {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
           case case_2 {
             leaf-list packet-length-except {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
         }
         choice dscp_choice {
           case case_1 {
             leaf-list dscp {
               ordered-by user;
               type string;
             }
           }
           case case_2 {
             leaf-list dscp-except {
               ordered-by user;
               type string;
             }
           }
         }
         choice ecn_choice {
           case case_1 {
             leaf-list ecn {
               ordered-by user;
               description "ECN value 0-3";
               type union {
                 type string {
                   pattern "<.*>|$.*";
                 }
                 type uint32 {
                   range "0 .. 3";
                 }
               }
             }
           }
         }
         choice precedence_choice {
           case case_1 {
             leaf-list precedence {
               ordered-by user;
               type string;
             }
           }
           case case_2 {
             leaf-list precedence-except {
               ordered-by user;
               type string;
             }
           }
         }
         choice ip-options_choice {
           case case_1 {
             leaf-list ip-options {
               ordered-by user;
               type string;
             }
           }
           case case_2 {
             leaf-list ip-options-except {
               ordered-by user;
               type string;
             }
           }
         }
         leaf is-fragment {
           description "Match if packet is a fragment";
           type empty;
         }
         leaf egress-to-ingress {
           description "Match egress fields in ingress";
           type empty;
         }
         leaf first-fragment {
           description "Match if packet is the first fragment";
           type empty;
         }
         choice fragment-offset_choice {
           case case_1 {
             leaf-list fragment-offset {
               ordered-by user;
               description "Range of values";
               type string {
                 junos:posix-pattern "^[[:digit:]]+(-[[:digit:]]+)?$";
                 junos:pattern-message "Must be a in form of number or a range in the form \'<minimum-value>-<maximum-value>\'";
               }
             }
           }
           case case_2 {
             leaf-list fragment-offset-except {
               ordered-by user;
               description "Range of values";
               type string {
                 junos:posix-pattern "^[[:digit:]]+(-[[:digit:]]+)?$";
                 junos:pattern-message "Must be a in form of number or a range in the form \'<minimum-value>-<maximum-value>\'";
               }
             }
           }
         }
         leaf fragment-flags {
           description "Match fragment flags (in symbolic or hex formats) - (Ingress only)";
           type string {
             junos:posix-pattern "^(0x4000|0x2000|dont-fragment|more-fragments)$";
             junos:pattern-message "fragment-flags must be either dont-fragment(0x4000) or more-fragments(0x2000)";
           }
         }
         choice protocol_choice {
           case case_1 {
             leaf-list protocol {
               ordered-by user;
               type string;
             }
           }
           case case_2 {
             leaf-list protocol-except {
               ordered-by user;
               type string;
             }
           }
         }
         choice ttl_choice {
           case case_1 {
             leaf-list ttl {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical TTL value or range between 0-255";
               }
             }
           }
           case case_2 {
             leaf-list ttl-except {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical TTL value or range between 0-255";
               }
             }
           }
         }
         list payload-source-mac-address {
           key name;
           ordered-by user;
           description "Source MAC address";
           uses firewall_mac_addr_object;
           junos:cli-feature "homogeneous";
           junos:cli-feature "oneliner";
         }
         list payload-destination-mac-address {
           key name;
           ordered-by user;
           description "Destination MAC address";
           uses firewall_mac_addr_object;
           junos:cli-feature "homogeneous";
           junos:cli-feature "oneliner";
         }
         list payload-source-ipv4-address {
           key name;
           ordered-by user;
           description "Payload Source ip address";
           uses match_payload_ipv4_add;
           junos:cli-feature "homogeneous";
           junos:cli-feature "oneliner";
         }
         list payload-destination-ipv4-address {
           key name;
           ordered-by user;
           description "Payload Destination IP address";
           uses match_payload_ipv4_add;
           junos:cli-feature "homogeneous";
           junos:cli-feature "oneliner";
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-initial {
           description "Match initial packet of a TCP connection";
           type empty;
         }
         leaf tcp-established {
           description "Match packet of an established TCP connection";
           type empty;
         }
         leaf tcp-flags {
           description "Match TCP flags (in symbolic or hex formats)";
           junos:must "(!(\".. tcp-established\"))";
           junos:must-message "tcp-flags may not be matched in same rule as tcp-established";
           junos:must "(!(\".. tcp-initial\"))";
           junos:must-message "tcp-flags may not be matched in same rule as tcp-initial";
           type string;
         }
         choice esp-spi_choice {
           case case_1 {
           }
           case case_2 {
           }
         }
         choice ah-spi_choice {
           case case_1 {
           }
           case case_2 {
           }
         }
         list interface {
           key name;
           ordered-by user;
           description "Match interface name";
           uses match_interface_object;
           junos:cli-feature "oneliner";
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         leaf source-port-range-optimize {
           description "Optimize the source port range";
           type empty;
         }
         leaf destination-port-range-optimize {
           description "Optimize the destination port range";
           type empty;
         }
         choice rat-type_choice {
           case case_1 {
             leaf-list rat-type {
               ordered-by user;
               type string;
             }
           }
           case case_2 {
           }
         }
         choice redirect-reason_choice {
           case case_1 {
             leaf-list redirect-reason {
               ordered-by user;
               type enumeration {
                 enum "aoc" {
                   description "Advice of Charge";
                 }
                 enum "aolb" {
                   description "Advice of Low Balance";
                 }
                 enum "dpi" {
                   description "Layer7 match required";
                 }
               }
             }
           }
           case case_2 {
           }
         }
         choice gre-key_choice {
           case case_1 {
             leaf-list gre-key {
               ordered-by user;
               description "Range of values";
               type string {
                 junos:posix-pattern "^([0-9]{1,9}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]|0x[0-f]{1,8})(-([0-9]{1,9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]|0x[0-f]{1,8}))?$";
                 junos:pattern-message "Must be a numerical value or range between 0-4294967295";
               }
             }
           }
           case case_2 {
             leaf-list gre-key-except {
               ordered-by user;
               description "Range of values";
               type string {
                 junos:posix-pattern "^([0-9]{1,9}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]|0x[0-f]{1,8})(-([0-9]{1,9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]|0x[0-f]{1,8}))?$";
                 junos:pattern-message "Must be a numerical value or range between 0-4294967295";
               }
             }
           }
         }
         choice flex-mask_choice {
           case case_1 {
             container flexible-match-mask {
               description "Match flexible mask";
               presence "enable flexible-match-mask";
               uses match_L3_flexible_mask;
             }
           }
         }
         choice flex-range_choice {
           case case_1 {
             container flexible-match-range {
               description "Match flexible range";
               presence "enable flexible-match-range";
               junos:must "(!(\".. flexible-match-ranges\"))";
               junos:must-message "'flexible-match-range' and 'flexible-match-ranges' are mutually exclusive";
               uses match_L3_flexible_range;
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
         choice slice_choice {
           case case_1 {
           }
           case case_2 {
           }
         }
         container vxlan {
           description "Define vxlan match items";
           uses apply-advanced;
           choice vni_choice {
             case case_1 {
               leaf-list vni {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
             case case_2 {
               leaf-list vni-except {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
           }
           choice rsvd1_choice {
             case case_1 {
               leaf-list rsvd1 {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
             case case_2 {
               leaf-list rsvd1-except {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
           }
           choice rsvd2_choice {
             case case_1 {
               leaf-list rsvd2 {
                 ordered-by user;
                 description "Range of values";
                 type string {
                   junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                   junos:pattern-message "Must be a numeric value or a range between 0-255";
                 }
               }
             }
             case case_2 {
               leaf-list rsvd2-except {
                 ordered-by user;
                 description "Range of values";
                 type string {
                   junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                   junos:pattern-message "Must be a numeric value or a range between 0-255";
                 }
               }
             }
           }
           container flags {
             description "Match VXlan flag field";
             uses match_flags_value;
           }
         }
       }
       container then {
         junos:cli-feature "oneliner-plus";
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               junos:must "(!(\".. loss-priority\"))";
               junos:must-message "cannot support three-color-policer action if loss-priority is configured";
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
           }
           case case_4 {
           }
           case case_5 {
             leaf policer-charge {
               description "Name of policer-charge used to charge the policer";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         choice inetcnt {
           case case_1 {
           }
           case case_2 {
             leaf count {
               description "Count the packet in the named counter";
               type string {
                 junos:posix-pattern "!^((__.*)|(.{65,}))$";
                 junos:pattern-message "Must be a non-reserved string of 64 characters or less";
               }
             }
           }
         }
         leaf service-accounting {
           description "Count the packets for service accounting";
           junos:must "(!(\".. service-accounting-deferred\"))";
           junos:must-message "'service-accounting-deferred' and 'service-accounting' cannot coexist";
           junos:must "(!(\".. count\"))";
           junos:must-message "'count' and 'service-accounting' cannot coexist";
           type empty;
         }
         leaf skip-services {
           description "Skip the services";
           type empty;
         }
         leaf log {
           description "Log the packet";
           type empty;
         }
         leaf pkt-trace {
           description "Trace the packet";
           type empty;
         }
         leaf packet-mode {
           description "Bypass flow mode for the packet";
           type empty;
         }
         leaf syslog {
           description "System log (syslog) information about the packet";
           type empty;
         }
         leaf packet-capture {
           description "Enable packet capture for telemetry";
           type empty;
         }
         leaf sample {
           description "Sample the packet";
           junos:must "(!(\".. sampling-instance\"))";
           junos:must-message "'sampling' and 'sampling-instance' are mutually exclusive";
           junos:must "((\"forwarding-options sampling family inet\" || (\"forwarding-options packet-capture\" || any \"forwarding-options sampling instance <*> family inet\")))";
           junos:must-message "Requires forwarding-options sampling or packet-capture config";
           type empty;
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           junos:must "(\"forwarding-options port-mirroring\")";
           junos:must-message "Configure 'port-mirroring' under 'forwarding-options'";
           type empty;
         }
         leaf sampling {
           description "Sample the packets";
           junos:must "((!(\".. discard\") && !(\".. reject\")))";
           junos:must-message "discard/reject action is not allowed with sampling action";
           junos:must "(((\"protocols sflow sample-rate ingress\" && \"protocols sflow interfaces\") || any \"protocols sflow interfaces <*> sample-rate ingress\"))";
           junos:must-message "sampling action required sflow interface configured under protocols with a valid ingress sample-rate";
           type empty;
         }
         leaf inline-monitoring-instance {
           description "Inline monitoring to specified instance";
           junos:must "(\"services inline-monitoring instance $$\")";
           junos:must-message "Configure 'inline-monitoring instance'";
           type string {
             junos:posix-pattern "!^((__.*)|(.{65,}))$";
             junos:pattern-message "Must be a non-reserved string of 64 characters or less";
           }
         }
         leaf inband-flow-telemetry-init {
           description "Initiate inband telemetry for a flow";
           junos:must "((!(\".. .. from\") || (\".. .. from destination-port\" || (\".. .. from source-port\" || (\".. .. from protocol\" || (\".. .. from ip-protocol\" || (\".. .. from next-header\" || (\".. .. from ip-destination-address\" || (\".. .. from ip-source-address\" || (\".. .. from destination-address\" || \".. .. from source-address\"))))))))))";
           junos:must-message "Match terms must either of src-ip or dest-ip or protocol or src-port or dest-port";
           junos:must "(\"services inband-flow-telemetry flow-type\")";
           junos:must-message "inband-telemetry flow-type must be defined";
           junos:must "(\"services inband-flow-telemetry profile $$\")";
           junos:must-message "Referenced inband-flow-telemetry profile does not exist";
           type string;
         }
         leaf inband-flow-telemetry-terminate {
           description "Terminate inband telemetry for a flow";
           junos:must "((!(\".. .. from\") || (\".. .. from destination-port\" || (\".. .. from source-port\" || (\".. .. from protocol\" || (\".. .. from ip-protocol\" || (\".. .. from next-header\" || (\".. .. from ip-destination-address\" || (\".. .. from ip-source-address\" || (\".. .. from destination-address\" || \".. .. from source-address\"))))))))))";
           junos:must-message "Match terms must either of src-ip or dest-ip or protocol or src-port or dest-port";
           junos:must "(\"services inband-flow-telemetry flow-type\")";
           junos:must-message "inband-telemetry flow-type must be defined";
           junos:must "(\"services inband-flow-telemetry profile $$\")";
           junos:must-message "Referenced inband-flow-telemetry profile does not exist";
           type string;
         }
         leaf analyzer {
           description "Name of analyzer - (Ingress only)";
           junos:must "(\"ethernet-switching-options analyzer $$\")";
           junos:must-message "Named Analyzer must be set";
           type string {
             junos:posix-pattern "!^((__.*)|(.{65,}))$";
             junos:pattern-message "Must be a non-reserved string of 64 characters or less";
           }
         }
         leaf loss-priority {
           description "Packet's loss priority";
           junos:must "(!(\".. three-color-policer\"))";
           junos:must-message "Configuring loss-priority is incompatible with configuring three-color-policer";
           junos:must "(\".. forwarding-class\")";
           junos:must-message "To configure loss-priority, forwarding-class must be set";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           junos:must "(\".. loss-priority\")";
           junos:must-message "To configure forwarding-class, loss-priority must be set";
           type string {
             junos:posix-pattern "^.{1,64}$";
             junos:pattern-message "Must be string of 64 characters or less";
           }
         }
         leaf service-filter-hit {
           description "Marked when packet processing by the current type of chained filters is done, the packet is directed to the next type of filters";
           type empty;
         }
         choice designation {
           case case_1 {
             leaf accept {
               description "Accept the packet";
               type empty;
             }
           }
           case case_2 {
             container discard {
               presence "enable discard";
               junos:cli-feature "oneliner-plus";
               description "Discard the packet";
               uses apply-advanced;
               leaf accounting {
                 description "Named discard collector for packet";
                 type string;
               }
             }
           }
           case case_3 {
             leaf next {
               description "Continue to next term in a filter";
               type enumeration {
                 enum "term" {
                   description "Continue to next term in a filter";
                 }
               }
             }
           }
           case case_4 {
             list logical-system {
               key logical-system-name;
               ordered-by user;
               junos:cli-feature "oneliner";
               description "Packets are directed to specified logical system";
               max-elements 1;
               leaf logical-system-name {
                 description "Name of logical system";
                 junos:cli-feature "nokeyword";
                 type string {
                   junos:posix-pattern "^[a-zA-Z0-9_-]{1,63}$";
                   junos:pattern-message "Logical-system name is a string consisting of up to 63 letters, numbers, dashes and underscores";
                 }
               }
               container routing-instance {
                 junos:cli-feature "oneliner";
                 description "Packets are directed to specified routing instance";
                 leaf routing-instance-name {
                   description "Name of routing instance";
                   junos:cli-feature "nokeyword";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
               leaf topology {
                 description "Packets are directed to specified topology";
                 type string {
                   junos:posix-pattern "!^((.*:.*)|(.{129,}))$";
                   junos:pattern-message "Must be a non-reserved string of 128 characters or less";
                 }
               }
             }
           }
           case case_5 {
           }
           case case_6 {
             container routing-instance {
               junos:cli-feature "oneliner";
               description "Packets are directed to specified routing instance";
               leaf routing-instance-name {
                 description "Name of routing instance";
                 junos:cli-feature "nokeyword";
                 type string {
                   junos:posix-pattern "!^((__.*__)|(all)|(.*[ ].*)|(\"\")|(.{129,}))$";
                   junos:pattern-message "Must be a non-reserved string of 128 characters or less with no spaces.";
                 }
               }
               leaf topology {
                 description "Packets are directed to specified topology";
                 type string {
                   junos:posix-pattern "!^((.*:.*)|(.{129,}))$";
                   junos:pattern-message "Must be a non-reserved string of 128 characters or less";
                 }
               }
             }
           }
           case case_7 {
             leaf topology {
               description "Packets are directed to specified topology";
               type string {
                 junos:posix-pattern "!^((.*:.*)|(.{129,}))$";
                 junos:pattern-message "Must be a non-reserved string of 128 characters or less";
               }
             }
           }
           case case_8 {
             container next-ip {
               junos:cli-feature "oneliner";
               description "Packets are directed to the specified ipv4 address";
               leaf address {
                 description "Address to route";
                 junos:cli-feature "nokeyword";
                 type jt:ipv4prefix;
               }
               container routing-instance {
                 junos:cli-feature "oneliner";
                 description "Packets are directed to specified routing instance";
                 leaf routing-instance-name {
                   description "Name of routing instance";
                   junos:cli-feature "nokeyword";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
             }
           }
           case case_9 {
             container next-interface {
               presence "enable next-interface";
               description "Packets are to be routed through the specified interface";
               uses apply-advanced;
               leaf interface-name {
                 description "Interface name";
                 junos:cli-feature "nokeyword";
                 type string {
                   length "1 .. 127";
                   junos:posix-pattern "^((ge-)|(mge-)|(xe-)|(et-)|(gr-)|(ae)|(irb)|(fti))";
                   junos:pattern-message "Only ge, mge, xe, et, ae, irb, fti and point-to-point gr tunnel intefaces are supported";
                 }
               }
               container routing-instance {
                 junos:cli-feature "oneliner";
                 description "Packets are directed to specified routing instance";
                 leaf routing-instance-name {
                   description "Name of routing instance";
                   junos:cli-feature "nokeyword";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
               choice designation {
                 case case_1 {
                   leaf accept {
                     description "Accept the packet";
                     type empty;
                   }
                 }
                 case case_2 {
                   leaf next {
                     description "Continue to next term in a filter";
                     type enumeration {
                       enum "term" {
                         description "Continue to next term in a filter";
                       }
                     }
                   }
                 }
               }
             }
           }
           case case_10 {
             leaf ipsec-sa {
               description "Use specified IPSec security association";
               type string;
             }
           }
           case case_11 {
           }
           case case_12 {
             container decapsulate {
               presence "enable decapsulate";
               description "Terminate a tunnel";
               uses apply-advanced;
               choice tunnel-protocol {
                 case case_1 {
                   container gre {
                     presence "enable gre";
                     description "GRE protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           junos:cli-feature "oneliner";
                           description "Packets are directed to specified routing instance";
                           leaf routing-instance-name {
                             description "Name of routing instance";
                             junos:cli-feature "nokeyword";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_2 {
                 }
                 case case_3 {
                   container mpls-in-udp {
                     presence "enable mpls-in-udp";
                     description "MPLS-in-UDP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           junos:cli-feature "oneliner";
                           description "Packets are directed to specified routing instance";
                           leaf routing-instance-name {
                             description "Name of routing instance";
                             junos:cli-feature "nokeyword";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_4 {
                   container inet-in-udp {
                     presence "enable inet-in-udp";
                     description "IPv4-in-UDP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           junos:cli-feature "oneliner";
                           description "Packets are directed to specified routing instance";
                           leaf routing-instance-name {
                             description "Name of routing instance";
                             junos:cli-feature "nokeyword";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_5 {
                   container inet6-in-udp {
                     presence "enable inet6-in-udp";
                     description "IPv6-in-UDP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           junos:cli-feature "oneliner";
                           description "Packets are directed to specified routing instance";
                           leaf routing-instance-name {
                             description "Name of routing instance";
                             junos:cli-feature "nokeyword";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_6 {
                   container l2tp {
                     description "L2TP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     leaf-list cookie {
                       ordered-by user;
                       description "L2TPv3 cookie";
                       type string {
                         length "1 .. 32";
                       }
                     }
                     choice destination {
                       case case_1 {
                         leaf output-interface {
                           description "Interface name";
                           junos:must "(\"interfaces $$\")";
                           junos:must-message "Interface must be defined in the interfaces hierarchy";
                           type union {
                             type jt:interface-unit;
                             type string {
                               pattern "<.*>|$.*";
                             }
                           }
                         }
                       }
                     }
                   }
                 }
                 case case_7 {
                   container ipip {
                     presence "enable ipip";
                     description "IPIP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           junos:cli-feature "oneliner";
                           description "Packets are directed to specified routing instance";
                           leaf routing-instance-name {
                             description "Name of routing instance";
                             junos:cli-feature "nokeyword";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
               }
             }
           }
           case case_13 {
           }
           case case_14 {
             container reject {
               presence "enable reject";
               junos:cli-feature "oneliner";
               description "Reject the packet";
               choice style {
                 case case_1 {
                   leaf network-unreachable {
                     description "Send ICMP Network Unreachable message";
                     type empty;
                   }
                 }
                 case case_2 {
                   leaf host-unreachable {
                     description "Send ICMP Host Unreachable message";
                     type empty;
                   }
                 }
                 case case_3 {
                   leaf protocol-unreachable {
                     description "Send ICMP Protocol Unreachable message";
                     type empty;
                   }
                 }
                 case case_4 {
                   leaf port-unreachable {
                     description "Send ICMP Port Unreachable message";
                     type empty;
                   }
                 }
                 case case_5 {
                   leaf fragmentation-needed {
                     description "Send ICMP Fragmentation Needed message";
                     type empty;
                   }
                 }
                 case case_6 {
                   leaf source-route-failed {
                     description "Send ICMP Source Route Failed message";
                     type empty;
                   }
                 }
                 case case_7 {
                   leaf network-unknown {
                     description "Send ICMP Network Unknown message";
                     type empty;
                   }
                 }
                 case case_8 {
                   leaf host-unknown {
                     description "Send ICMP Host Unknown message";
                     type empty;
                   }
                 }
                 case case_9 {
                   leaf source-host-isolated {
                     description "Send ICMP Source Host Isolated message";
                     type empty;
                   }
                 }
                 case case_10 {
                   leaf network-prohibited {
                     description "Send ICMP Network Prohibited message";
                     type empty;
                   }
                 }
                 case case_11 {
                   leaf host-prohibited {
                     description "Send ICMP Host Prohibited message";
                     type empty;
                   }
                 }
                 case case_12 {
                   leaf bad-network-tos {
                     description "Send ICMP Bad Network ToS message";
                     type empty;
                   }
                 }
                 case case_13 {
                   leaf bad-host-tos {
                     description "Send ICMP Bad Host ToS message";
                     type empty;
                   }
                 }
                 case case_14 {
                   leaf administratively-prohibited {
                     description "Send ICMP Administratively Prohibited message";
                     type empty;
                   }
                 }
                 case case_15 {
                   leaf precedence-violation {
                     description "Send ICMP Precedence Violation message";
                     type empty;
                   }
                 }
                 case case_16 {
                   leaf precedence-cutoff {
                     description "Send ICMP Precedence Cutoff message";
                     type empty;
                   }
                 }
                 case case_17 {
                   leaf tcp-reset {
                     description "Send TCP Reset message";
                     type empty;
                   }
                 }
               }
             }
           }
           case case_15 {
           }
         }
         leaf dscp {
           description "Set Differentiated Services (DiffServ) code point";
           type string;
         }
         leaf outer-dscp {
           description "Set differentiated services code point for outer header";
           type string;
         }
         leaf qfi {
           description "Set QFI for N3 interface";
           type string;
         }
         leaf nat-translated-sip {
           description "IPv4 source address used for Static NAT";
           junos:must "(!(\".. nat-translated-dip\"))";
           junos:must-message " nat-translated-sip cannot be configured with nat-translated-dip";
           junos:must "(!((\".. .. from source-prefix-list\" || \".. .. from destination-prefix-list\")))";
           junos:must-message " prefix-list match is not supported with nat-translated-sip";
           junos:must "(\".. .. from source-address\")";
           junos:must-message " nat-translated-sip needs IPv4 source-address match in same term";
           type jt:ipv4addr;
         }
         leaf nat-translated-srcport {
           description "UDP/TCP source port used for Static NAT";
           junos:must "(\".. nat-translated-sip\")";
           junos:must-message " nat-translated-srcport needs nat-translated-sip action in same term";
           junos:must "(\".. .. from source-port\")";
           junos:must-message " nat-translated-srcport needs source-port match in same term";
           type union {
             type string {
               pattern "<.*>|$.*";
             }
             type uint16 {
               range "0 .. 65535";
             }
           }
         }
         leaf nat-translated-dip {
           description "IPv4 destination address used for Static NAT";
           junos:must "(!(\".. nat-translated-sip\"))";
           junos:must-message " nat-translated-dip cannot be configured with nat-translated-sip";
           junos:must "(!((\".. .. from source-prefix-list\" || \".. .. from destination-prefix-list\")))";
           junos:must-message " prefix-list is not supported with nat-translated-dip";
           junos:must "(\".. .. from destination-address\")";
           junos:must-message " nat-translated-dip needs IPv4 destination-address match in same term";
           type jt:ipv4addr;
         }
         leaf nat-translated-dstport {
           description "UDP/TCP destination port used for Static NAT";
           junos:must "(\".. nat-translated-dip\")";
           junos:must-message " nat-translated-dstport needs nat-translated-dip action in same term";
           junos:must "(\".. .. from destination-port\")";
           junos:must-message " nat-translated-dstport needs destination-port match in same term";
           type union {
             type string {
               pattern "<.*>|$.*";
             }
             type uint16 {
               range "0 .. 65535";
             }
           }
         }
         leaf prefix-action {
           description "Police or count packets using named prefix action";
           type string {
             junos:posix-pattern "!^((__.*)|(.{65,}))$";
             junos:pattern-message "Must be a non-reserved string of 64 characters or less";
           }
         }
       }
       container template {
         description "Refer a template";
         uses apply-advanced;
         leaf template-name {
           description "Template name";
           junos:cli-feature "nokeyword";
           type string {
             junos:posix-pattern "!^((__.*)|(.{65,}))$";
             junos:pattern-message "Must be a non-reserved string of 64 characters or less";
           }
         }
       }
     }
   }
   grouping inet_fuf {
     leaf name {
       description "Name of fast update filter";
       junos:cli-feature "nokeyword";
       junos:must "(unique \"firewall family <*> filter $$\")";
       junos:must-message "Fast update filter can not have the same name as firewall family filter";
       type string {
         junos:posix-pattern "!^((__.*)|(.{65,}))$";
         junos:pattern-message "Must be a non-reserved string of 64 characters or less";
       }
     }
     uses apply-advanced;
     leaf interface-specific {
       description "Defined counters are interface specific";
       type empty;
     }
     leaf-list match-order {
       ordered-by user;
       type enumeration {
         enum "protocol" {
           description "Include IP protocol in match set";
         }
         enum "source-address" {
           description "Include source-address in match set";
         }
         enum "destination-address" {
           description "Include destination-address in match set";
         }
         enum "source-port" {
           description "Include source-port in match set";
         }
         enum "destination-port" {
           description "Include destination-port in match set";
         }
         enum "dscp" {
           description "Include Differentiated Services (DiffServ) code point in match set";
         }
       }
     }
     list term {
       key name;
       ordered-by user;
       description "One or more firewall terms";
       leaf name {
         description "Term name";
         junos:cli-feature "nokeyword";
         type string {
           junos:posix-pattern "!^((__.*)|(.{65,}))$";
           junos:pattern-message "Must be a non-reserved string of 64 characters or less";
         }
       }
       uses apply-advanced;
       leaf only-at-create {
         description "Add term only when filter is first created.";
         type empty;
       }
       container from {
         description "Match criteria";
         uses apply-advanced;
         container source-address {
           description "Match source IP address";
           junos:cli-feature "oneliner-plus";
           uses firewall_addr_simple_object;
         }
         container destination-address {
           description "Match destination IP address";
           junos:cli-feature "oneliner-plus";
           uses firewall_addr_simple_object;
         }
         choice source-port_choice {
           case case_1 {
             container source-port {
               description "Match TCP/UDP source port";
               junos:cli-feature "oneliner-plus";
               uses match_simple_port_value;
             }
           }
         }
         choice destination-port_choice {
           case case_1 {
             container destination-port {
               description "Match TCP/UDP destination port";
               junos:cli-feature "oneliner-plus";
               uses match_simple_port_value;
             }
           }
         }
         choice protocol_choice {
           case case_1 {
             container protocol {
               description "Match IP protocol type";
               junos:cli-feature "oneliner-plus";
               uses match_simple_protocol_value;
             }
           }
         }
         choice dscp_choice {
           case case_1 {
             container dscp {
               description "Match Differentiated Services (DiffServ) code point";
               junos:cli-feature "oneliner-plus";
               uses match_simple_dscp_value;
             }
           }
         }
         leaf match-terms {
           description "Dynamically supplied list of match criteria";
           type string;
         }
       }
       container then {
         junos:cli-feature "oneliner-plus";
         description "Action to take if the 'from' condition is matched";
         uses apply-advanced;
         choice policer-choice {
           case case_1 {
             leaf policer {
               description "Name of policer to use to rate-limit traffic";
               type string {
                 junos:posix-pattern "!^((__.*)|(.{65,}))$";
                 junos:pattern-message "Must be a non-reserved string of 64 characters or less";
               }
             }
           }
         }
         leaf count {
           description "Count the packet in the named counter";
           type string {
             junos:posix-pattern "!^((__.*)|(.{65,}))$";
             junos:pattern-message "Must be a non-reserved string of 64 characters or less";
           }
         }
         leaf service-accounting {
           description "Count the packets for service accounting";
           junos:must "(!(\".. count\"))";
           junos:must-message "'count' and 'service-accounting' cannot coexist";
           type empty;
         }
         leaf log {
           description "Log the packet";
           type empty;
         }
         leaf port-mirror {
           description "Port-mirror the packet";
           type empty;
         }
         leaf loss-priority {
           description "Packet's loss priority";
           junos:must "(!(\".. three-color-policer\"))";
           junos:must-message "Configuring loss-priority is incompatible with configuring three-color-policer";
           junos:must "(\".. forwarding-class\")";
           junos:must-message "To configure loss-priority, forwarding-class must be set";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           junos:must "(\".. loss-priority\")";
           junos:must-message "To configure forwarding-class, loss-priority must be set";
           type string {
             junos:posix-pattern "^.{1,64}$";
             junos:pattern-message "Must be string of 64 characters or less";
           }
         }
         leaf action-terms {
           description "Dynamically supplied list of actions";
           type string;
         }
         choice designation {
           case case_1 {
             leaf accept {
               description "Accept the packet";
               type empty;
             }
           }
           case case_2 {
             leaf discard {
               description "Discard the packet";
               type empty;
             }
           }
           case case_3 {
             container routing-instance {
               junos:cli-feature "oneliner";
               description "Packets are directed to specified routing instance";
               leaf routing-instance-name {
                 description "Name of routing instance";
                 junos:cli-feature "nokeyword";
                 type string {
                   junos:posix-pattern "!^((__.*__)|(all)|(.*[ ].*)|(\"\")|(.{129,}))$";
                   junos:pattern-message "Must be a non-reserved string of 128 characters or less with no spaces.";
                 }
               }
               leaf topology {
                 description "Packets are directed to specified topology";
                 type string {
                   junos:posix-pattern "!^((.*:.*)|(.{129,}))$";
                   junos:pattern-message "Must be a non-reserved string of 128 characters or less";
                 }
               }
             }
           }
         }
       }
     }
   }
   grouping firewall_addr_simple_object {
     junos:cli-feature "oneliner-plus";
     uses apply-advanced;
     leaf address {
       description "Prefix to match";
       junos:cli-feature "nokeyword";
       type jt:ipv4prefix;
     }
   }
   grouping inet_service_filter {
     leaf name {
       description "Filter name";
       junos:cli-feature "nokeyword";
       type string {
         junos:posix-pattern "!^((__.*)|(.{65,}))$";
         junos:pattern-message "Must be a non-reserved string of 64 characters or less";
       }
     }
     uses apply-advanced;
     list term {
       key name;
       ordered-by user;
       description "Service filter term";
       leaf name {
         description "Term name";
         junos:cli-feature "nokeyword";
         type string {
           junos:posix-pattern "!^((__.*)|(.{65,}))$";
           junos:pattern-message "Must be a non-reserved string of 64 characters or less";
         }
       }
       uses apply-advanced;
       container from {
         description "Match criteria";
         uses apply-advanced;
         choice interface-group_choice {
           case case_1 {
             leaf-list interface-group {
               ordered-by user;
               description "Range of values";
               type string;
             }
           }
           case case_2 {
           }
         }
         list source-address {
           key name;
           ordered-by user;
           description "Match IP source address";
           uses firewall_addr_object;
           junos:cli-feature "homogeneous";
           junos:cli-feature "oneliner";
         }
         list destination-address {
           key name;
           ordered-by user;
           description "Match IP destination address";
           uses firewall_addr_object;
           junos:cli-feature "homogeneous";
           junos:cli-feature "oneliner";
         }
         list address {
           key name;
           ordered-by user;
           description "Match IP source or destination address";
           uses firewall_addr_object;
           junos:cli-feature "homogeneous";
           junos:cli-feature "oneliner";
         }
         list source-prefix-list {
           key name;
           ordered-by user;
           description "Match IP source prefixes in named list";
           uses firewall_prefix_list;
           junos:cli-feature "homogeneous";
           junos:cli-feature "oneliner";
         }
         list destination-prefix-list {
           key name;
           ordered-by user;
           description "Match IP destination prefixes in named list";
           uses firewall_prefix_list;
           junos:cli-feature "homogeneous";
           junos:cli-feature "oneliner";
         }
         list prefix-list {
           key name;
           ordered-by user;
           description "Match IP source or destination prefixes in named list";
           uses firewall_prefix_list;
           junos:cli-feature "homogeneous";
           junos:cli-feature "oneliner";
         }
         choice protocol_choice {
           case case_1 {
             leaf-list protocol {
               ordered-by user;
               type string;
             }
           }
           case case_2 {
             leaf-list protocol-except {
               ordered-by user;
               type string;
             }
           }
         }
         choice ip-options_choice {
           case case_1 {
             leaf-list ip-options {
               ordered-by user;
               type enumeration {
                 enum "any" {
                   description "Any IP option";
                 }
               }
             }
           }
           case case_2 {
             leaf-list ip-options-except {
               ordered-by user;
               type enumeration {
                 enum "any" {
                   description "Any IP option";
                 }
               }
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
           }
         }
         choice esp-spi_choice {
           case case_1 {
             leaf-list esp-spi {
               ordered-by user;
               description "Range of values";
               type string;
             }
           }
           case case_2 {
           }
         }
         leaf is-fragment {
           description "Match if packet is a fragment";
           type empty;
         }
         leaf first-fragment {
           description "Match if packet is the first fragment";
           type empty;
         }
         choice fragment-offset_choice {
           case case_1 {
             leaf-list fragment-offset {
               ordered-by user;
               description "Range of values";
               type string {
                 junos:posix-pattern "^[[:digit:]]+(-[[:digit:]]+)?$";
                 junos:pattern-message "Must be a in form of number or a range in the form \'<minimum-value>-<maximum-value>\'";
               }
             }
           }
           case case_2 {
           }
         }
         leaf fragment-flags {
           description "Match fragment flags";
           type string;
         }
         leaf tcp-flags {
           description "Match TCP flags (in symbolic or hex formats)";
           junos:must "(!(\".. tcp-established\"))";
           junos:must-message "tcp-flags may not be matched in same rule as tcp-established";
           junos:must "(!(\".. tcp-initial\"))";
           junos:must-message "tcp-flags may not be matched in same rule as tcp-initial";
           type string;
         }
         choice ah-spi_choice {
           case case_1 {
           }
           case case_2 {
           }
         }
         choice loss-priority_choice {
           case case_1 {
           }
           case case_2 {
           }
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice redirect-reason_choice {
           case case_1 {
             leaf-list redirect-reason {
               ordered-by user;
               type enumeration {
                 enum "aoc" {
                   description "Advice of Charge";
                 }
                 enum "aolb" {
                   description "Advice of Low Balance";
                 }
                 enum "dpi" {
                   description "Layer7 match required";
                 }
               }
             }
           }
           case case_2 {
             leaf-list redirect-reason-except {
               ordered-by user;
               type enumeration {
                 enum "aoc" {
                   description "Advice of Charge";
                 }
                 enum "aolb" {
                   description "Advice of Low Balance";
                 }
                 enum "dpi" {
                   description "Layer7 match required";
                 }
               }
             }
           }
         }
       }
       container then {
         junos:cli-feature "oneliner-plus";
         description "Action to take if the 'from' condition is matched";
         uses apply-advanced;
         leaf count {
           description "Count the packet in the named counter";
           type string {
             junos:posix-pattern "!^((__.*)|(.{65,}))$";
             junos:pattern-message "Must be a non-reserved string of 64 characters or less";
           }
         }
         leaf log {
           description "Log the packet";
           type empty;
         }
         leaf pkt-trace {
           description "Pkt-Trace the packet";
           type empty;
         }
         leaf sample {
           description "Sample the packet";
           type empty;
         }
         leaf port-mirror {
           description "Port-mirror the packet";
           type empty;
         }
         choice designation {
           case case_1 {
             leaf service {
               description "Forward packets to service processing";
               type empty;
             }
           }
           case case_2 {
             leaf skip {
               description "Skip service processing";
               type empty;
             }
           }
           case case_3 {
             leaf accept {
               description "Accept the packet";
               type empty;
             }
           }
         }
       }
     }
   }
   grouping inet_simple_filter {
     leaf name {
       description "Name of simple filter";
       junos:cli-feature "nokeyword";
       type string {
         junos:posix-pattern "!^((__.*)|(.{65,}))$";
         junos:pattern-message "Must be a non-reserved string of 64 characters or less";
       }
     }
     uses apply-advanced;
     leaf interface-specific {
       description "Defined counters are interface specific";
       status deprecated;
       type empty;
     }
     list term {
       key name;
       ordered-by user;
       description "One or more firewall terms";
       leaf name {
         description "Term name";
         junos:cli-feature "nokeyword";
         type string {
           junos:posix-pattern "!^((__.*)|(.{65,}))$";
           junos:pattern-message "Must be a non-reserved string of 64 characters or less";
         }
       }
       uses apply-advanced;
       container from {
         description "Match criteria";
         uses apply-advanced;
         container source-address {
           description "Source IP address";
           junos:cli-feature "oneliner-plus";
           uses firewall_addr_simple_object;
         }
         container destination-address {
           description "Destination IP address";
           junos:cli-feature "oneliner-plus";
           uses firewall_addr_simple_object;
         }
         choice protocol_choice {
           case case_1 {
             container protocol {
               description "Match IP protocol type";
               junos:cli-feature "oneliner-plus";
               uses match_simple_protocol_value;
             }
           }
         }
         choice source-port_choice {
           case case_1 {
             container source-port {
               description "Match TCP/UDP source port";
               junos:cli-feature "oneliner-plus";
               uses match_simple_port_value;
             }
           }
         }
         choice destination-port_choice {
           case case_1 {
             container destination-port {
               description "Match TCP/UDP destination port";
               junos:cli-feature "oneliner-plus";
               uses match_simple_port_value;
             }
           }
         }
         choice forwarding-class_choice {
           case case_1 {
             leaf-list forwarding-class {
               ordered-by user;
               description "String name";
               type string {
                 junos:posix-pattern "^.{1,64}$";
                 junos:pattern-message "Must be string of 64 characters or less";
               }
             }
           }
         }
       }
       container then {
         junos:cli-feature "oneliner-plus";
         description "Action to take if the 'from' condition is matched";
         uses apply-advanced;
         choice policer-choice {
           case case_1 {
             leaf policer {
               description "Name of policer to use to rate-limit traffic";
               type string {
                 junos:posix-pattern "!^((__.*)|(.{65,}))$";
                 junos:pattern-message "Must be a non-reserved string of 64 characters or less";
               }
             }
           }
           case case_2 {
             container three-color-policer {
               junos:must "(!(\".. loss-priority\"))";
               junos:must-message "cannot support three-color-policer action if loss-priority is configured";
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
               }
             }
           }
         }
         leaf loss-priority {
           description "Packet's loss priority";
           type enumeration {
             enum "low" {
               description "Low loss priority";
             }
             enum "medium-high" {
               description "Medium-high loss priority";
             }
             enum "medium-low" {
               description "Medium-low loss priority";
             }
             enum "high" {
               description "High loss priority";
             }
           }
         }
         leaf forwarding-class {
           description "Classify packet to forwarding class";
           type string {
             junos:posix-pattern "^.{1,64}$";
             junos:pattern-message "Must be string of 64 characters or less";
           }
         }
         leaf discard {
           description "Discard the packet";
           type empty;
         }
         leaf accept {
           description "Accept the packet";
           type empty;
         }
       }
     }
   }
   grouping inet_template {
     leaf name {
       description "Template name";
       junos:cli-feature "nokeyword";
       type string {
         junos:posix-pattern "!^((__.*)|(.{65,}))$";
         junos:pattern-message "Must be a non-reserved string of 64 characters or less";
       }
     }
     uses apply-advanced;
     container attributes {
       description "Template attributes";
       uses apply-advanced;
       leaf destination-address {
         description "Match IP destination address";
         type empty;
       }
       leaf destination-port {
         description "Match TCP/UDP destination port";
         type empty;
       }
       leaf destination-port-range-optimize {
         description "Optimize the destination port range";
         type empty;
       }
       leaf destination-prefix-list {
         description "Match IP destination prefixes in named list";
         type empty;
       }
       leaf dscp {
         description "Match Differentiated Services (DiffServ) code point";
         type empty;
       }
       leaf ecn {
         description "Match Explicit-congestion-notification";
         type empty;
       }
       leaf flexible-match-mask {
         description "Match flexible mask";
         type empty;
       }
       leaf flexible-match-range {
         description "Match flexible range";
         type empty;
       }
       leaf fragment-flags {
         description "Match fragment flags";
         type empty;
       }
       leaf icmp-code {
         description "Match ICMP message code";
         type empty;
       }
       leaf icmp-type {
         description "Match ICMP message type";
         type empty;
       }
       leaf interface {
         description "Match interface name";
         type empty;
       }
       leaf ip-options {
         description "Match IP options";
         type empty;
       }
       leaf is-fragment {
         description "Match if packet is a fragment";
         type empty;
       }
       leaf packet-length {
         description "Match packet length";
         type empty;
       }
       leaf precedence {
         description "Match IP precedence value";
         type empty;
       }
       leaf protocol {
         description "Match IP protocol type";
         type empty;
       }
       leaf rat-type {
         description "Match RAT Type";
         type empty;
       }
       leaf redirect-reason {
         description "Match Redirect Reason";
         type empty;
       }
       leaf source-address {
         description "Match IP source address";
         type empty;
       }
       leaf source-port {
         description "Match TCP/UDP source port";
         type empty;
       }
       leaf source-port-range-optimize {
         description "Optimize the source port range";
         type empty;
       }
       leaf source-prefix-list {
         description "Match IP source prefixes in named list";
         type empty;
       }
       leaf tcp-established {
         description "Match packet of an established TCP connection";
         type empty;
       }
       leaf tcp-flags {
         description "Match TCP flags";
         type empty;
       }
       leaf tcp-initial {
         description "Match initial packet of a TCP connection";
         type empty;
       }
       leaf sctp-initial {
         description "Match initial packet of a SCTP connection";
         type empty;
       }
       leaf ttl {
         description "Match IP ttl type";
         type empty;
       }
       leaf egress-to-ingress {
         description "Match egress fields in ingress";
         type empty;
       }
       leaf payload-source-mac-address {
         description "Match source MAC address";
         type empty;
       }
       leaf payload-destination-mac-address {
         description "Match destination MAC address";
         type empty;
       }
       leaf payload-source-ipv4-address {
         description "Match Payload IP source address";
         type empty;
       }
       leaf payload-destination-ipv4-address {
         description "Match Payload IP destination address";
         type empty;
       }
     }
   }
   grouping interface_set_type {
     leaf name {
       description "Interface set name";
       junos:cli-feature "nokeyword";
       type string {
         junos:posix-pattern "!^((__.*)|(.{65,}))$";
         junos:pattern-message "Must be a non-reserved string of 64 characters or less";
       }
     }
     uses apply-advanced;
     list interface-list {
       key name;
       ordered-by user;
       junos:cli-feature "nokeyword";
       junos:cli-feature "homogeneous";
       description "Interface list";
       leaf name {
         description "Interface name";
         junos:cli-feature "nokeyword";
         type union {
           type jt:interface-wildcard;
           type string {
             pattern "<.*>|$.*";
           }
         }
       }
       uses apply-advanced;
     }
   }
   grouping interfaces_type {
     junos:cli-feature "nokeyword";
     junos:cli-feature "homogeneous";
     description "Physical interface";
     leaf name {
       junos:cli-feature "nokeyword";
       junos:must "(!(\".. es-options backup-interface $$\"))";
       junos:must-message "Primary and backup ES PIC interfaces must be different";
       type string;
     }
     uses apply-advanced;
     leaf description {
       description "Text description of interface";
       type string;
     }
     leaf external-model-name {
       description "Name for interface as configured using 3rd-party model";
       type string;
     }
     container management-ethernet-redundancy {
       presence "enable management-ethernet-redundancy";
       description "Management Interface Redundancy";
       uses apply-advanced;
       choice enable_choice {
         case case_1 {
           leaf redundancy-enable {
             description "Enable Managment Ethernet Redundancy";
             type empty;
           }
         }
         case case_2 {
           leaf redundancy-disable {
             description "Disable  Managment Ethernet Redundancy";
             type empty;
           }
         }
       }
       leaf connectivity-test-interval {
         description "Connectivity test interval";
         default "5";
         units "seconds";
         type union {
           type string {
             pattern "<.*>|$.*";
           }
           type uint32 {
             range "1 .. 10";
           }
         }
       }
       leaf connectivity-test-response-interval {
         description "Connectivity test response wait time";
         default "5";
         units "seconds";
         type union {
           type string {
             pattern "<.*>|$.*";
           }
           type uint32 {
             range "1 .. 10";
           }
         }
       }
       leaf remote-ipv4-address {
         description "Destination IPV4 address to reach remote ";
         default "nil";
         type jt:ipv4addr;
       }
       leaf remote-ipv6-address {
         description "Destination IPV6 address to reach remote";
         default "nil";
         type jt:ipv6addr;
       }
       leaf number-of-connectivity-retries {
         description "Number of Connectivity retries ";
         default "2";
         type union {
           type string {
             pattern "<.*>|$.*";
           }
           type uint32 {
             range "1 .. 8";
           }
         }
       }
     }
     leaf metadata {
       description "Text metadata attached to interface";
       type string;
     }
     choice enable-disable {
       case case_1 {
         leaf disable {
           description "Disable this interface";
           type empty;
         }
       }
     }
     container fabric-options {
       description "Fabric interface specific options";
       uses apply-advanced;
       list member-interfaces {
         key name;
         junos:cli-feature "homogeneous";
         description "Member interface for the fabric interface";
         leaf name {
           description "Interface name of member";
           junos:cli-feature "nokeyword";
           junos:must "(!((\"interfaces $$ flexible-vlan-tagging\" || (\"interfaces $$ stacked-vlan-tagging\" || (\"interfaces $$ vlan-vci-tagging\" || \"interfaces $$ vlan-tagging\")))))";
           junos:must-message "VLAN configuration is not allowed on fabric member";
           junos:must "(!(any \"tenants <*> interfaces $$\"))";
           junos:must-message "Fabric member can't be part of any tenants";
           junos:must "(!(any \"logical-systems <*> interfaces $$\"))";
           junos:must-message "Fabric member can't be part of any logical system";
           junos:must "(!(\"interfaces $$ disable\"))";
           junos:must-message "fabric member device disable setting is not allowed";
           junos:must "(!(\"interfaces $$ encapsulation\"))";
           junos:must-message "fabric member device encapsulation is not allowed";
           junos:must "(!(\"interfaces $$ mac\"))";
           junos:must-message "fabric member device mac address setting is not allowed";
           junos:must "(!(\"interfaces $$ mtu\"))";
           junos:must-message "fabric member device mtu setting and vlan-tagging is not allowed";
           junos:must "(!(\"interfaces $$ passive-monitor-mode\"))";
           junos:must-message "Fabric member cannot be configured in passive monitor mode";
           junos:must "(!(\"interfaces $$ gigether-options 802.3ad\"))";
           junos:must-message "Fabric member cannot be part of aggregated ethernet";
           junos:must "(!(\"interfaces $$ gigether-options redundant-parent\"))";
           junos:must-message "Fabric member cannot be part of redundant ethernet";
           junos:must "(!(\"interfaces $$ unit\"))";
           junos:must-message "Logical unit is not allowed on fabric member";
           junos:must "(!(\"system autoinstallation\"))";
           junos:must-message "incompatible with 'system autoinstallation'";
           type union {
             type jt:interface-device;
             type string {
               pattern "<.*>|$.*";
             }
           }
         }
         uses apply-advanced;
       }
       container remote-chassis {
         presence "enable remote-chassis";
         description "Remote chassis reachability";
         uses apply-advanced;
         leaf destination {
           description "Destination IP address to reach remote chassis";
           type jt:ipv4addr;
         }
       }
     }
     container traceoptions {
       presence "enable traceoptions";
       description "Interface trace options";
       uses apply-advanced;
       list flag {
         key name;
         ordered-by user;
         junos:cli-feature "oneliner";
         description "Tracing parameters";
         leaf name {
           junos:cli-feature "nokeyword";
           type enumeration {
             enum "ipc" {
               description "Trace interface IPC messages";
             }
             enum "event" {
               description "Trace interface events";
             }
             enum "media" {
               description "Trace interface media changes";
             }
             enum "all" {
               description "Enable all interface trace flags";
             }
           }
         }
       }
     }
     leaf passive-monitor-mode {
       description "Use interface to tap packets from another router";
       junos:must "(!((\"services nat ipv6-multicast-interfaces $$={all}\" || \"services nat ipv6-multicast-interfaces ${interface}\")))";
       junos:must-message "Can not configure 'services nat ipv6-multicast-interfaces' when passive montioring is enabled for the interface";
       junos:must "(!((\".. encapsulation ethernet-ccc\" || (\".. encapsulation ethernet-tcc\" || (\".. encapsulation ethernet-bridge\" || (\".. encapsulation ethernet-vpls\" || (\".. encapsulation extended-vlan-ccc\" || (\".. encapsulation extended-vlan-tcc\" || (\".. encapsulation extended-vlan-vpls\" || (\".. encapsulation extended-vlan-bridge\" || (\".. encapsulation flexible-ethernet-services\" || (\".. encapsulation vlan-ccc\" || (\".. encapsulation vlan-vci-ccc\" || \".. encapsulation vlan-vpls\")))))))))))))";
       junos:must-message "Not compatible with specified 'encapsulation`";
       type empty;
     }
     choice keepalive_choices {
       case case_1 {
         container keepalives {
           description "Send or demand keepalive messages";
           presence "enable keepalives";
           junos:cli-feature "oneliner";
           uses keepalives_type;
         }
       }
       case case_2 {
         leaf no-keepalives {
           description "Do not send keepalive messages";
           type empty;
         }
       }
     }
     choice traps-choice {
       leaf traps {
         description "Enable SNMP notifications on state changes";
         type empty;
       }
       leaf no-traps {
         description "Don't enable SNMP notifications on state changes";
         type empty;
       }
     }
     choice interface-mib-choice {
       leaf interface-mib {
         description "Enable interface-related MIBs";
         type empty;
       }
       leaf no-interface-mib {
         description "Don't enable interface-related MIBs";
         type empty;
       }
     }
     leaf accounting-profile {
       description "Accounting profile name";
       junos:must "((\"accounting-options interface-profile $$\" || \"accounting-options flat-file-profile $$\"))";
       junos:must-message "referenced accounting profile must be defined";
       type string;
     }
     container anchor-point {
       description "Anchor point";
       uses apply-advanced;
       leaf interface-name {
         description "Interface name";
         junos:cli-feature "nokeyword";
         type union {
           type jt:interface-device;
           type string {
             pattern "<.*>|$.*";
           }
         }
       }
     }
     choice scheduler_type {
       case case_1 {
         choice per-unit-scheduler-choice {
           leaf per-unit-scheduler {
             description "Enable subunit queuing on Frame Relay or VLAN IQ interface";
             type empty;
           }
           leaf no-per-unit-scheduler {
             description "Don't enable subunit queuing on Frame Relay or VLAN IQ interface";
             type empty;
           }
         }
       }
       case case_2 {
         leaf shared-scheduler {
           description "Enabled shared queuing on an IQ2 interface";
           junos:must "((\".. vlan-tagging\" || (\".. stacked-vlan-tagging\" || (\".. flexible-vlan-tagging\" || \".. vlan-vci-tagging\"))))";
           junos:must-message "vlan tagging needs to be enabled for shared scheduler";
           type empty;
         }
       }
       case case_3 {
         container hierarchical-scheduler {
           presence "enable hierarchical-scheduler";
           junos:cli-feature "oneliner";
           description "Enable hierarchical scheduling";
           leaf maximum-hierarchy-levels {
             description "Maximum hierarchy levels";
             type union {
               type string {
                 pattern "<.*>|$.*";
               }
               type uint32;
             }
           }
           leaf implicit-hierarchy {
             description "Implicit hierarchy (follows interface hierarchy)";
             type empty;
           }
           leaf no-priority-propogation {
             description "Hierarchical scheduling priority propogation";
             type empty;
           }
         }
       }
     }
     leaf l2tp-maximum-session {
       description "Maximum L2TP session";
       type union {
         type string {
           pattern "<.*>|$.*";
         }
         type uint32 {
           range "0 .. 64000";
         }
       }
     }
     leaf schedulers {
       description "Number of schedulers to allocate for interface";
       type union {
         type uint32;
         type string {
           pattern "<.*>|$.*";
         }
       }
     }
     leaf cascade-port {
       description "Cascade port";
       junos:must "(!(any \"logical-systems <*> interfaces ${interface}\"))";
       junos:must-message "cascade-port cannot be part of logical-systems config";
       junos:must "(!(\".. flexible-vlan-tagging\"))";
       junos:must-message "cascade-port cannot have flexible-vlan-tagging config";
       junos:must "(!(\".. stacked-vlan-tagging\"))";
       junos:must-message "cascade-port cannot have stacked-vlan-tagging config";
       junos:must "(!(\".. vlan-tagging\"))";
       junos:must-message "cascade-port cannot have vlan-tagging config";
       junos:must "(\"chassis satellite-management\")";
       junos:must-message "chassis satellite-management must be defined";
       type empty;
     }
     leaf port-extender-cascade-port {
       description "NGPE Cascade port";
       junos:must "(!(\".. shared-scheduler\"))";
       junos:must-message "NGPE cascade-port cannot have shared-scheduler config";
       junos:must "(!(\".. hierarchical-scheduler\"))";
       junos:must-message "NGPE cascade-port cannot have hierarchical-scheduler config";
       type empty;
     }
     leaf dce {
       description "Respond to Frame Relay status enquiry messages";
       type empty;
     }
     choice vlan_tag_mode {
       case case_1 {
         leaf vlan-tagging {
           description "802.1q VLAN tagging support";
           type empty;
         }
       }
       case case_2 {
         leaf stacked-vlan-tagging {
           description "Stacked 802.1q VLAN tagging support";
           junos:must "(!((\".. passive-monitor-mode\" || \".. 802.3ad\")))";
           junos:must-message "Not compatible with passive-monitor-mode statement";
           type empty;
         }
       }
       case case_3 {
         leaf flexible-vlan-tagging {
           description "Support for no tagging, or single and double 802.1q VLAN tagging";
           type empty;
         }
       }
       case case_4 {
       }
     }
     leaf native-vlan-id {
       description "Virtual LAN identifier for untagged frames";
       type union {
         type string {
           pattern "<.*>|$.*";
         }
         type uint32 {
           range "0 .. 4094";
         }
       }
     }
     leaf no-native-vlan-insert {
       description "Disable native-vlan-id insertion to untagged frames";
       junos:must "(\".. native-vlan-id\")";
       junos:must-message "native-vlan-id should be configured";
       type empty;
     }
     leaf input-native-vlan-push {
       description "Control native-vlan-id insertion to untagged frames when input-vlan-map push is configured";
       default "enable";
       junos:must "(any \"interfaces ${interface}  unit <*> input-vlan-map push \")";
       junos:must-message "input-native-vlan-push can be set only when input-vlan-map push is configured";
       type enumeration {
         enum "disable" {
           description "Disable input-native-vlan-push";
         }
         enum "enable" {
           description "Enable input-native-vlan-push";
         }
       }
     }
     leaf number-of-sub-ports {
       description "Number of channels to create for a port";
       type union {
         type string {
           pattern "<.*>|$.*";
         }
         type uint32 {
           range "1 .. 8";
         }
       }
     }
     leaf unused {
       description "Disable physical port";
       type empty;
     }
     container timestamp {
       presence "enable timestamp";
       junos:must "(!(\"interfaces ${interface} aggregated-ether-options\"))";
       junos:must-message "timestamp cannot be configured for an aggregated ethernet interface";
       junos:must "(\"forwarding-options tap-aggregation tap-enable\")";
       junos:must-message "Tap-enable under tap aggregation must be set";
       description "Enable timestamp";
       uses apply-advanced;
       leaf ingress {
         description "Enable ingress timestamping";
         type empty;
       }
     }
     leaf speed {
       description "Link speed";
       type enumeration {
         enum "auto" {
           description "Enable auto negotiation of interface speed";
           junos:must "((!(\"interfaces ${interface} gigether-options 802.3ad\") || !(\"interfaces ${interface} ether-options 802.3ad\")))";
           junos:must-message "Auto speed cannot be configured for an aggregated ethernet member link";
           junos:must "((\"interfaces ${interface} gigether-options auto-negotiation\" || \"interfaces ${interface} ether-options auto-negotiation\"))";
           junos:must-message "gigether-options/ether-options auto-negotiation must be enabled";
         }
         enum "auto-10m-100m" {
           description "Enable auto negotiation of limiting interface speed to 10m/100m";
           junos:must "((!(\"interfaces ${interface} gigether-options 802.3ad\") || !(\"interfaces ${interface} ether-options 802.3ad\")))";
           junos:must-message "Auto speed cannot be configured for an aggregated ethernet member link";
           junos:must "((\"interfaces ${interface} gigether-options auto-negotiation\" || \"interfaces ${interface} ether-options auto-negotiation\"))";
           junos:must-message "gigether-options/ether-options auto-negotiation must be enabled";
         }
         enum "10m" {
         }
         enum "100m" {
         }
         enum "1g" {
         }
         enum "2.5g" {
         }
         enum "5g" {
         }
         enum "10g" {
         }
         enum "25g" {
         }
         enum "40g" {
         }
         enum "50g" {
         }
         enum "100g" {
         }
         enum "200g" {
         }
         enum "400g" {
         }
         enum "800g" {
         }
         enum "oc3" {
         }
         enum "oc12" {
         }
         enum "oc48" {
         }
         enum "1.6t" {
         }
       }
     }
     leaf mtu {
       description "Maximum transmit packet size";
       junos:must "(!(\"interfaces ${interface} container-options container-list\"))";
       junos:must-message "mtu is not supported for container child interfaces";
       type union {
         type string {
           pattern "<.*>|$.*";
         }
         type uint32;
       }
     }
     container hold-time {
       junos:cli-feature "oneliner";
       description "Hold time for link up and link down";
       leaf up {
         description "Link up hold time";
         units "milliseconds";
         type union {
           type uint32;
           type string {
             pattern "<.*>|$.*";
           }
         }
       }
       leaf down {
         description "Link down hold time";
         units "milliseconds";
         type union {
           type uint32;
           type string {
             pattern "<.*>|$.*";
           }
         }
       }
     }
     container port-extender {
       description "Tunnel binding information for the extended port";
       uses apply-advanced;
       container vxlan {
         presence "enable vxlan";
         description "VXLAN binding information for the extended port";
         uses apply-advanced;
         leaf end-point {
           description "Satellite loopback IP address";
           type jt:ipaddr;
         }
         leaf vni {
           description "VNI of the satellite extended-port";
           type union {
             type string {
               pattern "<.*>|$.*";
             }
             type uint32 {
               range "0 .. 16777214";
             }
           }
         }
       }
     }
     container damping {
       description "Interface damping parameters";
       uses apply-advanced;
       leaf half-life {
         description "Damping half life time";
         default "5";
         units "seconds";
         type union {
           type string {
             pattern "<.*>|$.*";
           }
           type uint32 {
             range "1 .. 30";
           }
         }
       }
       leaf max-suppress {
         description "Maximum suppress time";
         default "20";
         units "seconds";
         type union {
           type string {
             pattern "<.*>|$.*";
           }
           type uint32 {
             range "1 .. 20000";
           }
         }
       }
       leaf reuse {
         description "Reuse threshold";
         default "1000";
         type union {
           type string {
             pattern "<.*>|$.*";
           }
           type uint32 {
             range "1 .. 20000";
           }
         }
       }
       leaf suppress {
         description "Suppress threshold";
         default "2000";
         type union {
           type string {
             pattern "<.*>|$.*";
           }
           type uint32 {
             range "1 .. 20000";
           }
         }
       }
       leaf enable {
         description "Enable interface damping";
         type empty;
       }
     }
     container link-degrade-monitor {
       presence "enable link-degrade-monitor";
       description "Enable link degrade monitoring";
       uses apply-advanced;
       choice enable_choice {
         case case_1 {
           leaf link-degrade-monitor-enable {
             description "Enable Link Degrade Monitoring";
             type empty;
           }
         }
         case case_2 {
           leaf no-link-degrade-monitor-enable {
             description "Disable Link Degrade Monitoring";
             type empty;
           }
         }
       }
       container actions {
         description "Action upon link degrade event";
         uses apply-advanced;
         choice action_choice {
           case case_1 {
             leaf media-based {
               description "Media based";
               type empty;
             }
           }
         }
       }
       container recovery {
         description "Link degrade recovery mechanism";
         uses apply-advanced;
         leaf timer {
           description "Auto recovery timer in seconds";
           default "1800";
           junos:must "(!(\".. manual\"))";
           junos:must-message "Recovery mechanism must be auto to configure recovery timer";
           type union {
             type uint32;
             type string {
               pattern "<.*>|$.*";
             }
           }
         }
         choice receovery_choice {
           case case_1 {
             leaf auto {
               description "Automatic recovery";
               type empty;
             }
           }
           case case_2 {
             leaf manual {
               description "Manual recovery";
               type empty;
             }
           }
         }
       }
       container thresholds {
         description "Link degrade threshold parameters";
         uses apply-advanced;
         leaf set {
           description "BER at which link considered degraded(1..16)";
           default "1e-7";
           type string {
             junos:posix-pattern "^1e-(1[0-6]?|[2-9])$";
             junos:pattern-message "Ber threshold value in format: 1e-n, n = 1..16";
           }
         }
         leaf clear {
           description "BER at which link considered improved(1..16)";
           default "1e-12";
           type string {
             junos:posix-pattern "^1e-(1[0-6]?|[2-9])$";
             junos:pattern-message "Ber threshold value in format: 1e-n, n = 1..16";
           }
         }
         leaf warning-set {
           description "BER at which link degrade warning raised(1..16)";
           default "1e-9";
           type string {
             junos:posix-pattern "^1e-(1[0-6]?|[2-9])$";
             junos:pattern-message "Ber threshold value in format: 1e-n, n = 1..16";
           }
         }
         leaf warning-clear {
           description "BER at which link degrade warning cleared(1..16)";
           default "1e-11";
           type string {
             junos:posix-pattern "^1e-(1[0-6]?|[2-9])$";
             junos:pattern-message "Ber threshold value in format: 1e-n, n = 1..16";
           }
         }
         leaf interval {
           description "Consecutive link degrade events";
           default "10";
           type union {
             type string {
               pattern "<.*>|$.*";
             }
             type uint32 {
               range "1 .. 256";
             }
           }
         }
       }
     }
     container satop-options {
       junos:must "((!(\".. t1-options framing\") && !(\".. e1-options framing\")))";
       junos:must-message "SAToP & Framing cannot be configured on same interface";
       junos:must "(!(\".. ima-link-options\"))";
       junos:must-message "SAToP & IMA cannot be configured on same interface";
       junos:must "((!(\"interfaces ${interface} container-options\") || (\"interfaces ${interface} container-options container-type\" || \"interfaces ${interface} container-options allow-configuration-override\")))";
       junos:must-message "satop-options cannot be configured without allow-configuration-override";
       junos:cli-feature "oneliner-plus";
       description "Structure-Agnostic TDM over Packet protocol options";
       uses apply-advanced;
       leaf idle-pattern {
         description "An 8-bit hexadecimal pattern to replace TDM data in a lost packet";
         type union {
           type string {
             pattern "<.*>|$.*";
           }
           type uint32 {
             range "0 .. 255";
           }
         }
       }
       leaf payload-size {
         description "Number of payload bytes per packet";
         type union {
           type string {
             pattern "<.*>|$.*";
           }
           type uint32 {
             range "64 .. 1024";
           }
         }
       }
       container excessive-packet-loss-rate {
         junos:cli-feature "oneliner-plus";
         description "Packet loss options";
         uses apply-advanced;
         leaf threshold {
           description "Percentile designating the threshold of excessive packet loss rate";
           type union {
             type string {
               pattern "<.*>|$.*";
             }
             type uint8 {
               range "1 .. 100";
             }
           }
         }
         leaf sample-period {
           description "Number of milliseconds over which excessive packet loss rate is calculated";
           type union {
             type string {
               pattern "<.*>|$.*";
             }
             type uint32 {
               range "1000 .. 65535";
             }
           }
         }
       }
       choice jitter-buffer-size {
         case case_1 {
           leaf jitter-buffer-packets {
             description "Number of packets in jitter buffer before packet data is played out in the line";
             type union {
               type string {
                 pattern "<.*>|$.*";
               }
               type uint32 {
                 range "1 .. 64";
               }
             }
           }
         }
         case case_2 {
           leaf jitter-buffer-latency {
             description "Number of milliseconds delay in jitter buffer before packet data is played out in the line";
             units "milliseconds";
             type union {
               type string {
                 pattern "<.*>|$.*";
               }
               type uint32 {
                 range "1 .. 1000";
               }
             }
           }
         }
         case case_3 {
           leaf jitter-buffer-auto-adjust {
             description "Automatically adjust jitter buffer";
             type empty;
           }
         }
       }
       leaf bit-rate {
         description "In multiples of DS0";
         type union {
           type string {
             pattern "<.*>|$.*";
           }
           type uint32 {
             range "1 .. 10240";
           }
         }
       }
     }
     container cesopsn-options {
       junos:must "((!(\"interfaces ${interface} container-options\") || (\"interfaces ${interface} container-options container-type\" || \"interfaces ${interface} container-options allow-configuration-override\")))";
       junos:must-message "cesopsn-options cannot be configured without allow-configuration-override";
       junos:cli-feature "oneliner-plus";
       description "Structure-Aware TDM over Packet protocol options";
       uses apply-advanced;
       leaf idle-pattern {
         description "An 8-bit hexadecimal pattern to replace TDM data in a lost packet";
         type union {
           type string {
             pattern "<.*>|$.*";
           }
           type uint32 {
             range "0 .. 255";
           }
         }
       }
       leaf packetization-latency {
         description "Number of microseconds to create packets";
         units "microseconds";
         type union {
           type string {
             pattern "<.*>|$.*";
           }
           type uint32 {
             range "1000 .. 8000";
           }
         }
       }
       leaf payload-size {
         description "Number of payload bytes per packet";
         type union {
           type string {
             pattern "<.*>|$.*";
           }
           type uint32 {
             range "64 .. 1024";
           }
         }
       }
       container excessive-packet-loss-rate {
         junos:cli-feature "oneliner-plus";
         description "Packet loss options";
         uses apply-advanced;
         leaf threshold {
           description "Percentile designating the threshold of excessive packet loss rate";
           type union {
             type string {
               pattern "<.*>|$.*";
             }
             type uint8 {
               range "1 .. 100";
             }
           }
         }
         leaf sample-period {
           description "Number of milliseconds over which excessive packet loss rate is calculated";
           type union {
             type string {
               pattern "<.*>|$.*";
             }
             type uint32 {
               range "1000 .. 65535";
             }
           }
         }
       }
       choice jitter-buffer-size {
         case case_1 {
           leaf jitter-buffer-packets {
             description "Number of packets in jitter buffer before packet data is played out in the line";
             type union {
               type string {
                 pattern "<.*>|$.*";
               }
               type uint32 {
                 range "1 .. 64";
               }
             }
           }
         }
         case case_2 {
           leaf jitter-buffer-latency {
             description "Number of milliseconds delay in jitter buffer before packet data is played out in the line";
             units "milliseconds";
             type union {
               type string {
                 pattern "<.*>|$.*";
               }
               type uint32 {
                 range "1 .. 1000";
               }
             }
           }
         }
         case case_3 {
           leaf jitter-buffer-auto-adjust {
             description "Automatically adjust jitter buffer";
             type empty;
           }
         }
       }
       leaf bit-rate {
         description "In multiples of DS0";
         type union {
           type string {
             pattern "<.*>|$.*";
           }
           type uint32 {
             range "1 .. 10240";
           }
         }
       }
     }
     list multi-chassis-protection {
       key name;
       description "Inter-Chassis protection configuration";
       junos:must "(\"interfaces ${interface} aggregated-ether-options mc-ae mode active-active\")";
       junos:must-message "multi-chassis-protection is only supported for MC-AE active-active mode";
       uses multi-chassis-protection-group;
     }
     container clocking {
       junos:cli-feature "oneliner";
       description "Interface clock source";
       choice clocking_choices {
         case case_1 {
           leaf internal {
             description "Clocking provided by local system";
             type empty;
           }
         }
         case case_2 {
           container external {
             presence "enable external";
             description "Clocking provided by DCE (loop timing)";
           }
         }
       }
     }
     leaf link-mode {
       description "Link operational mode";
       type enumeration {
         enum "automatic" {
           description "Automatically negotiate duplex";
         }
         enum "half-duplex" {
           description "Half-duplex operation";
         }
         enum "full-duplex" {
           description "Full-duplex operation";
         }
       }
     }
     leaf encapsulation {
       description "Physical link-layer encapsulation";
       junos:must "(!(\"interfaces ${interface} container-options container-list\"))";
       junos:must-message "encapsulation is not supported for container child interfaces";
       type enumeration {
         enum "ethernet" {
           description "Ethernet physical media";
         }
         enum "fddi" {
           description "FDDI physical media";
         }
         enum "token-ring" {
           description "Token Ring physical media";
         }
         enum "ppp" {
           description "Serial PPP device";
         }
         enum "ppp-ccc" {
           description "Serial PPP device for a cross-connect";
         }
         enum "ppp-tcc" {
           description "Serial PPP device for a translational cross-connect";
         }
         enum "ether-vpls-ppp" {
           description "Ethernet VPLS over PPP (bridging) device";
         }
         enum "frame-relay" {
           description "Frame Relay encapsulation";
         }
         enum "frame-relay-ccc" {
           description "Frame Relay for cross-connect";
         }
         enum "frame-relay-tcc" {
           description "Frame Relay for translational cross-connect";
         }
         enum "extended-frame-relay-ccc" {
           description "Any Frame Relay DLCI for cross-connect";
         }
         enum "extended-frame-relay-tcc" {
           description "Any Frame Relay DLCI for translational cross-connect";
         }
         enum "flexible-frame-relay" {
           description "Multiple Frame Relay encapsulations";
         }
         enum "frame-relay-port-ccc" {
           description "Frame Relay port encapsulation for a cross-connect";
         }
         enum "frame-relay-ether-type" {
           description "Cisco-compatible Frame Relay encapsulation";
         }
         enum "frame-relay-ether-type-tcc" {
           description "Cisco-compatible Frame Relay encapsulation for translational cross-connect";
         }
         enum "extended-frame-relay-ether-type-tcc" {
           description "Cisco-compatible Frame Relay encapsulation any DLCI for translational cross-connect";
         }
         enum "cisco-hdlc" {
           description "Cisco-compatible HDLC framing";
         }
         enum "cisco-hdlc-ccc" {
           description "Cisco-compatible HDLC framing for a cross-connect";
         }
         enum "cisco-hdlc-tcc" {
           description "Cisco-compatible HDLC framing for a translational cross-connect";
         }
         enum "vlan-ccc" {
           description "802.1q tagging for a cross-connect";
         }
         enum "extended-vlan-ccc" {
           description "Nonstandard TPID tagging for a cross-connect";
         }
         enum "ethernet-ccc" {
           description "Ethernet cross-connect";
         }
         enum "flexible-ethernet-services" {
           description "Allows per-unit Ethernet encapsulation configuration";
         }
         enum "smds-dxi" {
           description "SMDS DXI framing";
         }
         enum "atm-pvc" {
           description "ATM permanent virtual circuits";
         }
         enum "atm-ccc-cell-relay" {
           description "ATM cell relay encapsulation for cross-connect";
         }
         enum "ethernet-over-atm" {
           description "Ethernet over ATM encapsulation";
         }
         enum "ethernet-tcc" {
           description "Ethernet translational cross-connect";
         }
         enum "extended-vlan-tcc" {
           description "802.1q tagging for a translational cross-connect";
         }
         enum "multilink-frame-relay-uni-nni" {
           description "Multilink Frame Relay UNI NNI (FRF.16) encapsulation";
         }
         enum "satop" {
           description "Structure-Agnostic TDM over Packet encapsulation";
           junos:must "((!(\".. t1-options framing\") && !(\".. e1-options framing\")))";
           junos:must-message "SAToP & Framing cannot be configured on same interface";
           junos:must "(!(\".. ima-link-options\"))";
           junos:must-message "SAToP & IMA cannot be configured on same interface";
         }
         enum "cesopsn" {
           description "Structure-Agnostic TDM over Packet encapsulation";
         }
         enum "ima" {
           description "Inverse Multiplexing for ATM";
           junos:must "(!(\".. satop-options\"))";
           junos:must-message "SAToP & IMA cannot be configured on same interface";
         }
         enum "ethernet-vpls" {
           description "Ethernet virtual private LAN service";
         }
         enum "ethernet-bridge" {
           description "Ethernet layer-2 bridging";
         }
         enum "vlan-vpls" {
           description "VLAN virtual private LAN service";
         }
         enum "vlan-vci-ccc" {
           description "CCC for VLAN Q-in-Q and ATM VPI/VCI interworking";
           junos:must "(\"interfaces ${interface} vlan-vci-tagging\")";
           junos:must-message "valid only with vlan-vci-tagging mode";
         }
         enum "extended-vlan-vpls" {
           description "Extended VLAN virtual private LAN service";
         }
         enum "extended-vlan-bridge" {
           description "VLAN layer-2 bridging";
         }
         enum "multilink-ppp" {
           description "Multilink PPP";
         }
         enum "generic-services" {
           description "Generic services";
         }
       }
     }
     leaf network-isolation-profile {
       description "Attach a network isolation profile on this interface";
       junos:must "(!((\".. .. .. protocols network-isolation group $$ service-tracking-action lacp-out-of-sync\" && !(\".. aggregated-ether-options lacp\"))))";
       junos:must-message "lacp-out-of-sync is allowed only on LACP interfaces";
       junos:must "(\".. .. .. protocols network-isolation group $$ service-tracking-action\")";
       junos:must-message "service-tracking-action must be configured";
       junos:must "((\".. .. .. protocols network-isolation group $$ detection service-tracking\" || \".. .. .. protocols network-isolation group $$ detection link-tracking\"))";
       junos:must-message "service-tracking or link-tracking must be configured";
       type string;
     }
     container esi {
       description "ESI configuration of multi-homed interface";
       uses apply-advanced;
       container auto-derive {
         description "Auto-derive ESI value for the interface";
         uses apply-advanced;
         choice esitype {
           case case_1 {
             leaf lacp-pe-system-id-and-admin-key {
               description "Auto-derive ESI from lacp pe system-id and admin key";
               type empty;
             }
           }
           case case_2 {
             leaf type-1-lacp {
               description "Auto-generate Type1 ESI LACP";
               junos:must "(\".. .. .. aggregated-ether-options lacp\")";
               junos:must-message "Aggregated-ether-options lacp must be configured";
               type empty;
             }
           }
           case case_3 {
             container type-3-system-mac {
               description "Auto-generate Type3 ESI System-mac";
               uses apply-advanced;
               leaf mac {
                 description "System mac";
                 junos:must "(\".. local-discriminator\")";
                 junos:must-message "Local-discriminator must be configured";
                 type jt:mac-unicast;
               }
               leaf local-discriminator {
                 description "Local-discriminator";
                 junos:must "(\".. mac\")";
                 junos:must-message "Mac must be configured";
                 type union {
                   type string {
                     pattern "<.*>|$.*";
                   }
                   type int32 {
                     range "0 .. 16777215";
                   }
                 }
               }
             }
           }
         }
       }
       leaf identifier {
         description "ESI value for the interface";
         junos:cli-feature "nokeyword";
         junos:must "(!(\".. .. gigether-options 802.3ad\"))";
         junos:must-message "ESI cannot be configured for member link interfaces";
         junos:must "(!(any \"interfaces <*> unit <*> esi $$\"))";
         junos:must-message "ESI value must be unique across all IFDs";
         junos:must "(unique \"interfaces <*> esi $$\")";
         junos:must-message "ESI value must be unique across all IFDs";
         junos:must "(!(\"interfaces ${interface} esi auto-derive\"))";
         junos:must-message "ESI identifier can not be configured when auto-derive is configured under IFD";
         type jt:esi;
       }
       choice mode {
         case case_1 {
           leaf single-active {
             description "Single-active mode";
             type empty;
           }
         }
         case case_2 {
           leaf all-active {
             description "All-active mode";
             type empty;
           }
         }
       }
       container df-election-granularity {
         presence "enable df-election-granularity";
         description "DF Election Granularity Selection ";
         uses apply-advanced;
         choice mode {
           case case_1 {
             container per-esi {
               presence "enable per-esi";
               description "DF Election Granularity Per Esi";
               uses apply-advanced;
               leaf lacp-oos-on-ndf {
                 description "Lacp Oos";
                 junos:must "(!(\"interfaces ${interface} esi all-active\"))";
                 junos:must-message "lacp-oos-on-ndf can be configured only with single-active";
                 junos:must "(\"interfaces ${interface} aggregated-ether-options lacp\")";
                 junos:must-message "LACP must be enbled for lacp-oos-on-ndf";
                 type empty;
               }
             }
           }
           case case_2 {
             leaf per-esi-vlan {
               description "Per Esi Vlan";
               type empty;
             }
           }
           case case_3 {
             leaf per-evi {
               description "Per Esi EVI";
               type empty;
             }
           }
         }
       }
       container df-election-type {
         presence "enable df-election-type";
         description "DF Election Type";
         uses apply-advanced;
         choice pref_choice {
           case case_1 {
             container preference {
               presence "enable preference";
               description "Preference based DF election";
               uses apply-advanced;
               leaf value {
                 description "Preference value for EVPN Multihoming DF election";
                 default "32767";
                 type union {
                   type string {
                     pattern "<.*>|$.*";
                   }
                   type uint32 {
                     range "0 .. 65535";
                   }
                 }
               }
               leaf non-revertive {
                 description "Don't allow DF Election preemption";
                 type empty;
               }
               leaf least {
                 description "Use least preference in DF election";
                 type empty;
               }
             }
           }
         }
         choice mod_choice {
           case case_1 {
             container mod {
               presence "enable mod";
               junos:must "(!(\".. preference\"))";
               junos:must-message "preference must not be configured";
               description "MOD based DF election";
             }
           }
         }
       }
       leaf source-bmac {
         description "Unicast Source B-MAC address per ESI for PBB-EVPN";
         junos:must "(!(any \"routing-instances <*> service-groups <*> pbb-service-options source-bmac $$\"))";
         junos:must-message "Source B-MAC must be unique across all routing-instances";
         junos:must "(!(any \"interfaces <*> unit <*> esi source-bmac $$\"))";
         junos:must-message "Source B-MAC must be unique under all IFDs and IFLs";
         junos:must "(unique \"interfaces <*> esi source-bmac $$\")";
         junos:must-message "Source B-MAC must be unique under all IFDs and IFLs";
         type jt:mac-unicast;
       }
       leaf anycast {
         description "ESI anycast Multihoming";
         type empty;
       }
     }
     container framing {
       description "Frame type";
       uses apply-advanced;
       choice frame {
         case case_1 {
           leaf lan-phy {
             description "802.3ae 10-Gbps LAN-mode interface";
             type empty;
           }
         }
         case case_2 {
           leaf wan-phy {
             description "802.3ae 10-Gbps WAN-mode interface";
             type empty;
           }
         }
         case case_3 {
           leaf sonet {
             description "SONET framing";
             type empty;
           }
         }
         case case_4 {
           leaf sdh {
             description "SDH framing";
             type empty;
           }
         }
       }
     }
     container lmi {
       description "Local Management Interface settings";
       uses apply-advanced;
       leaf n391dte {
         description "DTE full status polling interval";
         junos:must "(!((\".. .. dce\" || \".. .. loose-ncp\")))";
         junos:must-message "LMI DTE options not valid for DCE interface";
         type union {
           type string {
             pattern "<.*>|$.*";
           }
           type uint16 {
             range "1 .. 255";
           }
         }
       }
       leaf n392dce {
         description "DCE error threshold";
         junos:must "((\".. .. dce\" || \".. .. loose-ncp\"))";
         junos:must-message "LMI DCE options not valid for DTE interface";
         type union {
           type string {
             pattern "<.*>|$.*";
           }
           type uint16 {
             range "1 .. 10";
           }
         }
       }
       leaf n392dte {
         description "DTE error threshold";
         junos:must "(!((\".. .. dce\" || \".. .. loose-ncp\")))";
         junos:must-message "LMI DTE options not valid for DCE interface";
         type union {
           type string {
             pattern "<.*>|$.*";
           }
           type uint16 {
             range "1 .. 10";
           }
         }
       }
       leaf n393dce {
         description "DCE monitored event count";
         junos:must "((\".. .. dce\" || \".. .. loose-ncp\"))";
         junos:must-message "LMI DCE options not valid for DTE interface.";
         type union {
           type string {
             pattern "<.*>|$.*";
           }
           type uint16 {
             range "1 .. 10";
           }
         }
       }
       leaf n393dte {
         description "DTE monitored event count";
         junos:must "(!((\".. .. dce\" || \".. .. loose-ncp\")))";
         junos:must-message "LMI DTE options not valid for DCE interface";
         type union {
           type string {
             pattern "<.*>|$.*";
           }
           type uint16 {
             range "1 .. 10";
           }
         }
       }
       leaf t391dte {
         description "DTE polling timer";
         units "seconds";
         junos:must "(!((\".. .. dce\" || \".. .. loose-ncp\")))";
         junos:must-message "LMI DTE options not valid for DCE interface";
         type union {
           type string {
             pattern "<.*>|$.*";
           }
           type uint16 {
             range "5 .. 30";
           }
         }
       }
       leaf t392dce {
         description "DCE polling verification timer";
         units "seconds";
         junos:must "((\".. .. dce\" || \".. .. loose-ncp\"))";
         junos:must-message "LMI DCE options not valid for DTE interface.";
         type union {
           type string {
             pattern "<.*>|$.*";
           }
           type uint16 {
             range "5 .. 30";
           }
         }
       }
       leaf lmi-type {
         description "Specify the Frame Relay LMI type";
         type enumeration {
           enum "ansi" {
             description "Use ANSI Annex D LMI";
           }
           enum "itu" {
             description "Use ITU Q933a Annex A LMI";
           }
           enum "c-lmi" {
             description "Use Consortium LMI";
           }
         }
       }
     }
     container mlfr-uni-nni-bundle-options {
       description "Multilink Frame Relay UNI NNI (FRF.16) management settings";
       uses apply-advanced;
       container cisco-interoperability {
         description "FRF.16 Cisco interoperability settings";
         uses apply-advanced;
         leaf send-lip-remove-link-for-link-reject {
           description "Send Link Integrity Protocol remove link on receiving add-link rejection";
           type empty;
         }
       }
       leaf mrru {
         description "Maximum received reconstructed unit";
         units "bytes";
         type union {
           type string {
             pattern "<.*>|$.*";
           }
           type uint16 {
             range "1500 .. 4500";
           }
         }
       }
       leaf yellow-differential-delay {
         description "Yellow differential delay among bundle links to give warning";
         units "milliseconds";
         type union {
           type string {
             pattern "<.*>|$.*";
           }
           type uint16 {
             range "3 .. 2000";
           }
         }
       }
       leaf red-differential-delay {
         description "Red differential delay among bundle links to take action";
         units "milliseconds";
         type union {
           type string {
             pattern "<.*>|$.*";
           }
           type uint16 {
             range "5 .. 2000";
           }
         }
       }
       leaf action-red-differential-delay {
         description "Type of actions when differential delay exceeds red limit";
         type enumeration {
           enum "remove-link" {
             description "Remove bundle link from service when exceeding red limit";
           }
           enum "disable-tx" {
             description "Disable transfer of bundle link when exceeding red limit";
           }
         }
       }
       leaf fragment-threshold {
         description "Fragmentation threshold";
         units "bytes";
         type union {
           type string {
             pattern "<.*>|$.*";
           }
           type uint32 {
             range "64 .. 16320";
           }
         }
       }
       leaf drop-timeout {
         description "Drop timeout";
         units "milliseconds";
         type union {
           type string {
             pattern "<.*>|$.*";
           }
           type uint16 {
             range "0 .. 2000";
           }
         }
       }
       leaf link-layer-overhead {
         description "Link layer bit stuffing overhead (0.0 .. 50.0 percent)";
         type jt:unsigned-float;
       }
       leaf lmi-type {
         description "Specify the multilink Frame Relay UNI NNI LMI type";
         type enumeration {
           enum "ansi" {
             description "Use ANSI Annex D LMI";
           }
           enum "itu" {
             description "Use ITU Q933a Annex A LMI";
           }
           enum "c-lmi" {
             description "Use Consortium LMI";
           }
         }
       }
       leaf minimum-links {
         description "Minimum number of links to sustain the bundle";
         type union {
           type string {
             pattern "<.*>|$.*";
           }
           type uint16 {
             range "1 .. 8";
           }
         }
       }
       leaf hello-timer {
         description "LIP hello timer";
         type union {
           type string {
             pattern "<.*>|$.*";
           }
           type uint16 {
             range "5 .. 180";
           }
         }
       }
       leaf acknowledge-timer {
         description "LIP ack timer";
         type union {
           type string {
             pattern "<.*>|$.*";
           }
           type uint16 {
             range "1 .. 10";
           }
         }
       }
       leaf acknowledge-retries {
         description "LIP ack retry times";
         type union {
           type string {
             pattern "<.*>|$.*";
           }
           type uint16 {
             range "1 .. 5";
           }
         }
       }
       leaf n391 {
         description "Multilink Frame Relay UNI NNI full status polling counter";
         type union {
           type string {
             pattern "<.*>|$.*";
           }
           type uint16 {
             range "1 .. 255";
           }
         }
       }
       leaf n392 {
         description "Multilink Frame Relay UNI NNI LMI error threshold";
         type union {
           type string {
             pattern "<.*>|$.*";
           }
           type uint16 {
             range "1 .. 10";
           }
         }
       }
       leaf n393 {
         description "Multilink Frame Relay UNI NNI LMI monitored event count";
         type union {
           type string {
             pattern "<.*>|$.*";
           }
           type uint16 {
             range "1 .. 10";
           }
         }
       }
       leaf t391 {
         description "Multilink Frame Relay UNI NNI link integrity verify polling timer";
         type union {
           type string {
             pattern "<.*>|$.*";
           }
           type uint16 {
             range "5 .. 30";
           }
         }
       }
       leaf t392 {
         description "Multilink Frame Relay UNI NNI polling verification timer";
         type union {
           type string {
             pattern "<.*>|$.*";
           }
           type uint16 {
             range "5 .. 30";
           }
         }
       }
     }
     leaf mac {
       description "Hardware MAC address";
       type jt:mac-unicast;
     }
     leaf no-forwarding-viable {
       description "Disable forwarding";
       type empty;
     }
     container p4rt {
       description "P4-runtime interfaces";
       uses apply-advanced;
       leaf id {
         description "Port number";
         type union {
           type string {
             pattern "<.*>|$.*";
           }
           type uint64 {
             range "1 .. 4294967296";
           }
         }
       }
       leaf node-id {
         description "Device Id";
         type union {
           type string {
             pattern "<.*>|$.*";
           }
           type uint64 {
             range "1 .. 18446744073709551615";
           }
         }
       }
     }
     container receive-bucket {
       description "Set receive bucket parameters";
       uses dcd_rx_bucket_config;
     }
     container transmit-bucket {
       description "Set transmit bucket parameters";
       uses dcd_tx_bucket_config;
     }
     leaf shared-interface {
       description "Enable shared interface on the interface";
       type empty;
     }
     container sonet-options {
       description "SONET interface-specific options";
       junos:must "((!(\"interfaces ${interface} container-options\") || (\"interfaces ${interface} container-options container-type\" || \"interfaces ${interface} container-options allow-configuration-override\")))";
       junos:must-message "sonet-options cannot be configured without allow-configuration-override";
       uses sonet_options_type;
     }
     container logical-tunnel-options {
       description "Logical Tunnel interface-specific options";
       uses apply-advanced;
       container link-protection {
         presence "enable link-protection";
         junos:must "(any \"interfaces ${interface} redundancy-group member-interface <*> active\")";
         junos:must-message "Active and Backup child links must be configured to use link-protection";
         description "Enable link protection mode";
         uses apply-advanced;
         leaf revertive {
           description "Revert back (Default mode) from active backup link to primary, if primary is UP";
           junos:must "(!(\"interfaces ${interface} logical-tunnel-options link-protection non-revertive\"))";
           junos:must-message "link-protection revertive and non-revertive are mutually exclusive";
           junos:must "(any \"interfaces ${interface} redundancy-group member-interface <*> active\")";
           junos:must-message "link-protection mode can be configured only when link-protection is enabled";
           type empty;
         }
         leaf non-revertive {
           description "Do not revert back from active backup link to primary, if primary is UP";
           junos:must "(!(\"interfaces ${interface} logical-tunnel-options link-protection revertive\"))";
           junos:must-message "link-protection revertive and non-revertive are mutually exclusive";
           junos:must "(any \"interfaces ${interface} redundancy-group member-interface <*> active\")";
           junos:must-message "link-protection mode can be configured only when link-protection is enabled";
           type empty;
         }
       }
       leaf per-unit-mac-disable {
         description "Disable the creation of per unit mac address on LT IFLs for VPLS/CCC encaps";
         type empty;
       }
     }
     container aggregated-sonet-options {
       description "Aggregated SONET interface-specific options";
       uses apply-advanced;
       leaf minimum-links {
         description "Minimum number of aggregated links";
         type union {
           type string {
             pattern "<.*>|$.*";
           }
           type uint16;
         }
       }
       leaf link-speed {
         description "Aggregated links speed";
         type enumeration {
           enum "oc3" {
             description "Links are OC-3c or STM-1c";
           }
           enum "oc12" {
             description "Links are OC-12c or STM-4c";
           }
           enum "oc48" {
             description "Links are OC-48c or STM-16c";
           }
           enum "oc192" {
             description "Links are OC-192c or STM-64c";
           }
           enum "oc768" {
             description "Links are OC-768c or STM-256c";
           }
           enum "mixed" {
             description "Links are various speeds";
           }
         }
       }
       leaf minimum-bandwidth {
         description "Minimum bandwidth necessary to sustain bundle";
         units "bps";
         type union {
           type string {
             pattern "<.*>|$.*";
           }
           type uint64 {
             range "0 .. 159232000000";
           }
         }
       }
     }
     container atm-options {
       junos:must "((!(\"interfaces ${interface} container-options\") || (\"interfaces ${interface} container-options container-type\" || !(\"interfaces ${interface} container-options container-list\"))))";
       junos:must-message "atm-options cannot be configured on container children";
       description "ATM interface-specific options";
       uses apply-advanced;
       leaf pic-type {
         description "Type of ATM PIC (ATM I, ATM II or ATM CE)";
         type enumeration {
           enum "atm-ce" {
             description "CE PIC";
           }
           enum "atm2" {
             description "ATM II IQ PIC";
           }
           enum "atm1" {
             description "ATM I PIC";
             junos:must "(!(\"interfaces ${interface} container-options\"))";
             junos:must-message "Only ATM-II pics are supported as container member link";
           }
         }
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf use-null-cw {
         description "Always insert/strip null control words with cell-relay";
         type empty;
       }
       container promiscuous-mode {
         presence "enable promiscuous-mode";
         description "Set ATM interface to promiscuous mode";
         uses apply-advanced;
         list vpi {
           key name;
           ordered-by user;
           junos:cli-feature "oneliner";
           description "Open this VPI in promiscuous mode";
           leaf name {
             description "Virtual path index";
             junos:cli-feature "nokeyword";
             type union {
               type string {
                 pattern "<.*>|$.*";
               }
               type uint32 {
                 range "0 .. 255";
               }
             }
           }
         }
       }
       list vpi {
         key name;
         ordered-by user;
         description "Define a virtual path";
         leaf name {
           description "Virtual path index";
           junos:cli-feature "nokeyword";
           type union {
             type string {
               pattern "<.*>|$.*";
             }
             type uint32 {
               range "0 .. 255";
             }
           }
         }
         uses apply-advanced;
         leaf maximum-vcs {
           description "Maximum number of virtual circuits on this VP";
           junos:must "(!(\"interfaces ${interface} container-options\"))";
           junos:must-message "Only ATM-II pics are supported as container member link";
           type union {
             type uint32;
             type string {
               pattern "<.*>|$.*";
             }
           }
         }
         container shaping {
           description "Virtual path traffic-shaping options";
           uses dcd_shaping_config;
         }
         container oam-period {
           junos:cli-feature "oneliner";
           description "F4 OAM cell period";
           choice oam_period_choices {
             case case_1 {
               leaf oam-period {
                 description "F4 OAM cell period";
                 junos:cli-feature "nokeyword";
                 units "seconds";
                 type union {
                   type string {
                     pattern "<.*>|$.*";
                   }
                   type uint32 {
                     range "1 .. 900";
                   }
                 }
               }
             }
             case case_2 {
               container disable {
                 presence "enable disable";
                 junos:cli-feature "oneliner";
                 description "Disable F4 OAM loopback";
               }
             }
           }
         }
         container oam-liveness {
           description "F4 OAM virtual path liveness parameters";
           uses apply-advanced;
           leaf up-count {
             description "Number of F4 OAM cells to consider VP up";
             type union {
               type string {
                 pattern "<.*>|$.*";
               }
               type uint32 {
                 range "1 .. 255";
               }
             }
           }
           leaf down-count {
             description "Number of F4 OAM cells to consider VP down";
             type union {
               type string {
                 pattern "<.*>|$.*";
               }
               type uint32 {
                 range "1 .. 255";
               }
             }
           }
         }
       }
       container ilmi {
         presence "enable ilmi";
         description "Enable Interim Local Management Interface";
         uses apply-advanced;
       }
       list linear-red-profiles {
         key name;
         ordered-by user;
         junos:cli-feature "homogeneous";
         junos:cli-feature "oneliner";
         description "ATM2 CoS virtual circuit drop profiles";
         leaf name {
           description "Linear RED profile name";
           junos:cli-feature "nokeyword";
           type string {
             junos:posix-pattern "^.{1,64}$";
             junos:pattern-message "Must be string of 64 characters or less";
           }
         }
         leaf queue-depth {
           description "Maximum queue depth";
           units "cells";
           type string;
         }
         leaf high-plp-threshold {
           description "Fill level percentage when linear RED is applied for high PLP";
           type union {
             type string {
               pattern "<.*>|$.*";
             }
             type uint32 {
               range "0 .. 100";
             }
           }
         }
         leaf low-plp-threshold {
           description "Fill level percentage when linear RED is applied for low PLP";
           type union {
             type string {
               pattern "<.*>|$.*";
             }
             type uint32 {
               range "0 .. 100";
             }
           }
         }
         leaf high-plp-max-threshold {
           description "Fill level percentage with 100 percent packet drop for high PLP";
           type union {
             type string {
               pattern "<.*>|$.*";
             }
             type uint32 {
               range "0 .. 100";
             }
           }
         }
         leaf low-plp-max-threshold {
           description "Fill level percentage with 100 percent packet drop for low PLP";
           type union {
             type string {
               pattern "<.*>|$.*";
             }
             type uint32 {
               range "0 .. 100";
             }
           }
         }
       }
       list scheduler-maps {
         key name;
         ordered-by user;
         junos:cli-feature "homogeneous";
         description "ATM2 CoS parameters assigned to forwarding classes";
         leaf name {
           description "ATM2 CoS scheduler map name";
           junos:cli-feature "nokeyword";
           type string {
             junos:posix-pattern "^((default)|(.{1,64}))$";
             junos:pattern-message "Must be a string of 64 characters or less and not \'default\'";
           }
         }
         uses apply-advanced;
         leaf vc-cos-mode {
           description "ATM2 virtual circuit CoS mode";
           type enumeration {
             enum "strict" {
               description "Always schedule high priority queue first";
             }
             enum "alternate" {
               description "Every other packet from high priority queue (default)";
             }
           }
         }
         list forwarding-class {
           key name;
           ordered-by user;
           description "Scheduling parameters associated with forwarding class";
           leaf name {
             description "Forwarding class name";
             junos:cli-feature "nokeyword";
             type string {
               junos:posix-pattern "^.{1,64}$";
               junos:pattern-message "Must be string of 64 characters or less";
             }
           }
           uses apply-advanced;
           leaf priority {
             description "Queuing priority assigned to forwarding class";
             type enumeration {
               enum "low" {
                 description "Low priority queuing";
               }
               enum "high" {
                 description "High priority queuing";
               }
             }
           }
           container transmit-weight {
             junos:cli-feature "oneliner";
             description "Transmit weight";
             choice weight-method {
               case case_1 {
                 leaf percent {
                   description "Transmit weight as percentage";
                   type union {
                     type string {
                       pattern "<.*>|$.*";
                     }
                     type uint32 {
                       range "5 .. 100";
                     }
                   }
                 }
               }
               case case_2 {
                 leaf cells {
                   description "Transmit weight by cells count";
                   type string;
                 }
               }
             }
           }
           choice drop-profile-method {
             case case_1 {
               container epd-threshold {
                 description "Early packet discard threshold for ATM2";
                 junos:cli-feature "oneliner";
                 uses epd_threshold_config;
               }
             }
             case case_2 {
               leaf linear-red-profile {
                 description "Linear RED profile profile name";
                 type string;
               }
             }
           }
         }
       }
       container mpls {
         description "MPLS options";
         uses mpls_ifd_options;
       }
       choice payload-scrambler-choice {
         leaf payload-scrambler {
           description "Enable payload scrambling";
           type empty;
         }
         leaf no-payload-scrambler {
           description "Don't enable payload scrambling";
           type empty;
         }
       }
     }
     container multiservice-options {
       description "Multiservice interface-specific options";
       uses apply-advanced;
       choice syslog-choice {
         leaf syslog {
           description "Enable system logging on this interface";
           type empty;
         }
         leaf no-syslog {
           description "Don't enable system logging on this interface";
           type empty;
         }
       }
       choice core-dump-choice {
         leaf core-dump {
           description "Enable core dumping on this interface";
           type empty;
         }
         leaf no-core-dump {
           description "Don't enable core dumping on this interface";
           type empty;
         }
       }
       choice dump-on-flow-control-choice {
         leaf dump-on-flow-control {
           description "Enable dumping for this interface on prolonged flow-control";
           status deprecated;
           type empty;
         }
         leaf no-dump-on-flow-control {
           description "Don't enable dumping for this interface on prolonged flow-control";
           status deprecated;
           type empty;
         }
       }
       choice reset-on-flow-control-choice {
         leaf reset-on-flow-control {
           description "Enable resetting this interface on prolonged flow-control";
           status deprecated;
           type empty;
         }
         leaf no-reset-on-flow-control {
           description "Don't enable resetting this interface on prolonged flow-control";
           status deprecated;
           type empty;
         }
       }
       container flow-control-options {
         description "Flow control configuration";
         uses apply-advanced;
         leaf dump-on-flow-control {
           description "Cause core dump during prolonged flow-control";
           junos:must "(!(\".. up-on-flow-control\"))";
           junos:must-message "Option not valid with up-on-flow-control";
           junos:must "(!(\".. down-on-flow-control\"))";
           junos:must-message "Option not valid with down-on-flow-control";
           junos:must "(!(\".. reset-on-flow-control\"))";
           junos:must-message "Option not valid with reset-on-flow-control";
           type empty;
         }
         leaf reset-on-flow-control {
           description "Reset interface during prolonged flow-control";
           junos:must "(!(\".. up-on-flow-control\"))";
           junos:must-message "Option not valid with up-on-flow-control";
           junos:must "(!(\".. down-on-flow-control\"))";
           junos:must-message "Option not valid with down-on-flow-control";
           junos:must "(!(\".. dump-on-flow-control\"))";
           junos:must-message "Option not valid with dump-on-flow-control";
           type empty;
         }
         leaf down-on-flow-control {
           description "Bring interface down during prolonged flow-control";
           junos:must "(!(\".. up-on-flow-control\"))";
           junos:must-message "Option not valid with up-on-flow-control";
           junos:must "(!(\".. reset-on-flow-control\"))";
           junos:must-message "Option not valid with reset-on-flow-control";
           junos:must "(!(\".. dump-on-flow-control\"))";
           junos:must-message "Option not valid with dump-on-flow-control";
           type empty;
         }
         leaf up-on-flow-control {
           description "Keep interface up during prolonged flow-control";
           junos:must "(!(\".. down-on-flow-control\"))";
           junos:must-message "Option not valid with down-on-flow-control";
           junos:must "(!(\".. reset-on-flow-control\"))";
           junos:must-message "Option not valid with reset-on-flow-control";
           junos:must "(!(\".. dump-on-flow-control\"))";
           junos:must-message "Option not valid with dump-on-flow-control";
           type empty;
         }
       }
     }
     container ggsn-options {
       description "GGSN interface-specific options";
       uses apply-advanced;
       choice syslog-choice {
         leaf syslog {
           description "Enable system logging on this interface";
           type empty;
         }
         leaf no-syslog {
           description "Don't enable system logging on this interface";
           type empty;
         }
       }
       choice core-dump-choice {
         leaf core-dump {
           description "Enable core dumping on this interface";
           type empty;
         }
         leaf no-core-dump {
           description "Don't enable core dumping on this interface";
           type empty;
         }
       }
     }
     container ppp-options {
       description "Point-to-Point Protocol (PPP) interface-specific options";
       junos:must "((\".. encapsulation ppp\" || (\".. encapsulation ether-vpls-ppp\" || !(\".. encapsulation\"))))";
       junos:must-message "invalid encapsulation";
       uses ppp_options_type;
     }
     container redundancy-options {
       description "Redundancy options";
       uses apply-advanced;
       leaf primary {
         description "Specify the primary interface";
         type union {
           type jt:interface-device;
           type string {
             pattern "<.*>|$.*";
           }
         }
       }
       leaf secondary {
         description "Specify the secondary interface";
         type union {
           type jt:interface-device;
           type string {
             pattern "<.*>|$.*";
           }
         }
       }
       container redundancy-peer {
         description "Specify information for peer";
         uses apply-advanced;
         leaf ipaddress {
           description "Specify the IP address";
           type jt:ipv4addr;
         }
       }
       container redundancy-local {
         description "Specify information for the local peer";
         uses apply-advanced;
         leaf data-address {
           description "Specify the HA local data IP address";
           type jt:ipv4addr;
         }
       }
       leaf routing-instance {
         description "Specify routing-instance for the HA traffic";
         junos:must "((\"routing-instances $$\" || any \"tenants <*> routing-instances $$\"))";
         junos:must-message "referenced routing-instance must be defined";
         type string;
       }
       leaf replication-threshold {
         description "Duration for which flow should remain active for replication";
         default "180";
         units "seconds";
         type union {
           type string {
             pattern "<.*>|$.*";
           }
           type uint32 {
             range "60 .. 3600";
           }
         }
       }
       container replication-options {
         description "Specify state replication attributes";
         uses apply-advanced;
         leaf mtu {
           description "Specify the maximal packet size for replicated data";
           default "1500";
           type union {
             type string {
               pattern "<.*>|$.*";
             }
             type uint32 {
               range "1500 .. 8000";
             }
           }
         }
       }
       container replicate-services {
         description "Replicate services state from active to backup";
         uses apply-advanced;
         leaf pgcp {
           description "Replicate the PGCP service state";
           type empty;
         }
       }
     }
     container lsq-failure-options {
       description "Link services queuing failure options";
       uses apply-advanced;
       list trigger-link-failure {
         key name;
         ordered-by user;
         junos:cli-feature "oneliner-plus";
         description "Link on which to trigger failure";
         leaf name {
           description "Interface name";
           junos:cli-feature "nokeyword";
           type union {
             type jt:interface-device;
             type string {
               pattern "<.*>|$.*";
             }
           }
         }
         uses apply-advanced;
       }
       choice no-termination-request-choice {
         leaf no-termination-request {
           description "Do not send PPP termination requests";
           type empty;
         }
         leaf no-no-termination-request {
           description "Don't do not send PPP termination requests";
           type empty;
         }
       }
     }
     container services-options {
       description "Services interface-specific options";
       uses apply-advanced;
       container syslog {
         description "Define system log parameters";
         uses log-object;
       }
       container jflow-log {
         description "Define Jflow-log parameters.";
         uses apply-advanced;
         leaf message-rate-limit {
           description "Maximum jflow-log NAT error events allowed per second from this interface";
           units "messages per second";
           type union {
             type string {
               pattern "<.*>|$.*";
             }
             type uint32 {
               range "1 .. 2147483647";
             }
           }
         }
       }
       container deterministic-nat-configuration-log-interval {
         presence "enable deterministic-nat-configuration-log-interval";
         description "Define Deterministic NAT parameters";
         uses apply-advanced;
         leaf interval {
           description "Interval in which deterministic NAT logs are generated";
           units "seconds";
           type union {
             type string {
               pattern "<.*>|$.*";
             }
             type uint32 {
               range "1800 .. 86400";
             }
           }
         }
       }
       leaf open-timeout {
         description "Timeout period for TCP session establishment";
         units "seconds";
         type union {
           type string {
             pattern "<.*>|$.*";
           }
           type uint32 {
             range "4 .. 300";
           }
         }
       }
       leaf close-timeout {
         description "Timeout period for TCP session tear-down";
         units "seconds";
         type union {
           type string {
             pattern "<.*>|$.*";
           }
           type uint32 {
             range "2 .. 300";
           }
         }
       }
       leaf inactivity-timeout {
         description "Inactivity timeout period for established sessions (4..86400)";
         units "seconds";
         type union {
           type uint32;
           type string {
             pattern "<.*>|$.*";
           }
         }
       }
       leaf inactivity-tcp-timeout {
         description "Inactivity timeout period for TCP established sessions";
         units "seconds";
         type union {
           type string {
             pattern "<.*>|$.*";
           }
           type uint32 {
             range "4 .. 86400";
           }
         }
       }
       leaf inactivity-asymm-tcp-timeout {
         description "Inactivity timeout period for asymmetric TCP established sessions";
         units "seconds";
         type union {
           type string {
             pattern "<.*>|$.*";
           }
           type uint32 {
             range "4 .. 86400";
           }
         }
       }
       leaf inactivity-non-tcp-timeout {
         description "Inactivity timeout period for non-TCP established sessions";
         units "seconds";
         type union {
           type string {
             pattern "<.*>|$.*";
           }
           type uint32 {
             range "4 .. 86400";
           }
         }
       }
       leaf session-timeout {
         description "Session timeout period for established sessions";
         units "seconds";
         type union {
           type string {
             pattern "<.*>|$.*";
           }
           type uint32 {
             range "4 .. 86400";
           }
         }
       }
       leaf disable-global-timeout-override {
         description "Disallow overriding  global inactivity or session timeout";
         type empty;
       }
       leaf tcp-tickles {
         description "Number of TCP keep-alive packets to be sent for bi-directional TCP flows";
         default "4";
         type union {
           type string {
             pattern "<.*>|$.*";
           }
           type uint8 {
             range "0 .. 30";
           }
         }
       }
       leaf fragment-limit {
         description "Maximum number of fragments allowed for a packet";
         default "64";
         type union {
           type string {
             pattern "<.*>|$.*";
           }
           type uint8 {
             range "1 .. 250";
           }
         }
       }
       leaf reassembly-timeout {
         description "Re-assembly timeout (seconds) for fragments of a packet";
         default "4";
         units "seconds";
         type union {
           type string {
             pattern "<.*>|$.*";
           }
           type uint8 {
             range "1 .. 60";
           }
         }
       }
       leaf cgn-pic {
         description "PIC will be used for Carrier Grade NAT configuration only";
         type empty;
       }
       leaf pba-interim-logging-interval {
         description "Interim logging interval in seconds";
         default "0";
         units "seconds";
         type union {
           type string {
             pattern "<.*>|$.*";
           }
           type uint32 {
             range "0 .. 86400";
           }
         }
       }
       container session-limit {
         presence "enable session-limit";
         description "Session limit";
         uses apply-advanced;
         leaf maximum {
           description "Maximum number of sessions allowed simultaneously";
           type string;
         }
         leaf rate {
           description "Maximum number of new sessions allowed per second";
           type string;
         }
         leaf cpu-load-threshold {
           description "CPU limit in percentage for auto-tuning of session rate";
           units "percent";
           type union {
             type string {
               pattern "<.*>|$.*";
             }
             type uint8 {
               range "1 .. 100";
             }
           }
         }
       }
       leaf enable-subscriber-analysis {
         description "Enable subscriber analysis on the interface";
         junos:must "(!(\".. disable-subscriber-analysis\"))";
         junos:must-message "can not set with enable-subscriber-analysis";
         type empty;
       }
       leaf disable-subscriber-analysis {
         description "Disable subscriber analysis on the interface";
         junos:must "(!(\".. enable-subscriber-analysis\"))";
         junos:must-message "can not set with disable-subscriber-analysis";
         type empty;
       }
       leaf disable-usp-tracing {
         description "Disable usp tracing on this pic";
         type empty;
       }
       leaf disable-drop-flows {
         description "Disable drop flows on this pic";
         type empty;
       }
       container ignore-errors {
         presence "enable ignore-errors";
         junos:cli-feature "oneliner";
         description "Ignore anomalies or errors";
         leaf tcp {
           description "TCP protocol errors";
           type empty;
         }
         leaf alg {
           description "ALG anomalies or errors";
           type empty;
         }
       }
       container capture {
         description "Packet capture for SFW and NAT on the Services PIC";
         uses apply-advanced;
         leaf capture-size {
           description "The number of packets to store";
           type union {
             type string {
               pattern "<.*>|$.*";
             }
             type uint32 {
               range "1 .. 344000";
             }
           }
         }
         leaf pkt-size {
           description "Number of bytes to be saved from each packet";
           type union {
             type string {
               pattern "<.*>|$.*";
             }
             type uint16 {
               range "64 .. 15000";
             }
           }
         }
         leaf logs-per-packet {
           description "The number of trace messages stored for each packet";
           type union {
             type string {
               pattern "<.*>|$.*";
             }
             type uint16 {
               range "0 .. 500";
             }
           }
         }
         leaf max-log-line-size {
           description "The maximum length of a stored trace message";
           type union {
             type uint8;
             type string {
               pattern "<.*>|$.*";
             }
           }
         }
         container filter {
           presence "enable filter";
           description "Filtering options for the packet capture";
           uses apply-advanced;
           container source-ip {
             junos:cli-feature "oneliner";
             description "Filter based on source-ip (and wildcard)";
             leaf ip {
               description "Source IP";
               junos:cli-feature "nokeyword";
               type jt:ipaddr;
             }
             leaf wildcard {
               description "Source IP wildcard";
               type jt:ipaddr;
             }
           }
           container dest-ip {
             junos:cli-feature "oneliner";
             description "Filter based on dest-ip (and wildcard)";
             leaf ip {
               description "Dest IP";
               junos:cli-feature "nokeyword";
               type jt:ipaddr;
             }
             leaf wildcard {
               description "Dest IP wildcard";
               type jt:ipaddr;
             }
           }
           container sw-sip {
             junos:cli-feature "oneliner";
             description "Filter based on source softwire ip (and wildcard)";
             leaf ip {
               description "Source softwire IP";
               junos:cli-feature "nokeyword";
               type jt:ipv6addr;
             }
             leaf wildcard {
               description "Source IP wildcard";
               type jt:ipv6addr;
             }
           }
           container sw-dip {
             junos:cli-feature "oneliner";
             description "Filter based on destination softwire ip (and wildcard)";
             leaf ip {
               description "Destination softwire IP";
               junos:cli-feature "nokeyword";
               type jt:ipaddr;
             }
             leaf wildcard {
               description "Destination IP wildcard";
               type jt:ipaddr;
             }
           }
           container sport-range {
             junos:cli-feature "oneliner";
             description "Filter based on source port";
             leaf low {
               description "Source port range start";
               type union {
                 type uint16;
                 type string {
                   pattern "<.*>|$.*";
                 }
               }
             }
             leaf high {
               description "Source port range end";
               type union {
                 type uint16;
                 type string {
                   pattern "<.*>|$.*";
                 }
               }
             }
           }
           container dport-range {
             junos:cli-feature "oneliner";
             description "Filter based on destination port";
             leaf low {
               description "Destination port range start";
               type union {
                 type uint16;
                 type string {
                   pattern "<.*>|$.*";
                 }
               }
             }
             leaf high {
               description "Destination port range end";
               type union {
                 type uint16;
                 type string {
                   pattern "<.*>|$.*";
                 }
               }
             }
           }
           leaf proto {
             description "Filter based on L4 protocol";
             type enumeration {
               enum "icmp" {
               }
               enum "tcp" {
               }
               enum "udp" {
               }
             }
           }
         }
       }
       container flow {
         description "Define flow parameters";
         uses apply-advanced;
         container traceoptions {
           description "Trace options for flow services";
         }
       }
       leaf fpc-pic-information {
         description "Include FPC and PIC slot number in the syslogs";
         type empty;
       }
       leaf utc-timestamp {
         description "Use UTC time for security log timestamps";
         type empty;
       }
       leaf syslog-local-system-timestamp {
         description "Use local system time for services syslog timestamp";
         type empty;
       }
     }
     container t3-options {
       junos:must "((!(\"interfaces ${interface} container-options\") || (\"interfaces ${interface} container-options container-type\" || \"interfaces ${interface} container-options allow-configuration-override\")))";
       junos:must-message "t1-options cannot be configured without allow-configuration-override";
       description "T3 interface-specific options";
       uses apply-advanced;
       leaf loopback {
         description "Loopback mode";
         type enumeration {
           enum "local" {
             description "Local loopback";
           }
           enum "remote" {
             description "Remote loopback";
           }
           enum "payload" {
             description "Payload loopback";
           }
         }
       }
       choice long-buildout-choice {
         leaf long-buildout {
           description "Set hardware to drive line longer than 255 feet";
           type empty;
         }
         leaf no-long-buildout {
           description "Don't set hardware to drive line longer than 255 feet";
           type empty;
         }
       }
       choice loop-timing-choice {
         leaf loop-timing {
           description "Set loop timing for T3";
           type empty;
         }
         leaf no-loop-timing {
           description "Don't set loop timing for T3";
           type empty;
         }
       }
       container compatibility-mode {
         junos:cli-feature "oneliner";
         description "Set CSU compatibility mode";
         choice vendor {
           case case_1 {
             container larscom {
               presence "enable larscom";
               junos:must "(!(\".. .. unframed\"))";
               junos:must-message "unframed and larscom cannot coexist";
               junos:cli-feature "oneliner";
               description "Compatible with Larscom CSU";
               leaf subrate {
                 description "Set subrate value";
                 type union {
                   type string {
                     pattern "<.*>|$.*";
                   }
                   type uint32 {
                     range "1 .. 14";
                   }
                 }
               }
             }
           }
           case case_2 {
             container verilink {
               presence "enable verilink";
               junos:must "(!(\".. .. unframed\"))";
               junos:must-message "unframed and verilink cannot coexist";
               junos:cli-feature "oneliner";
               description "Compatible with Verilink CSU (not on 2/4-port T3 PIC)";
               leaf subrate {
                 description "Set subrate value";
                 type union {
                   type string {
                     pattern "<.*>|$.*";
                   }
                   type uint32 {
                     range "1 .. 28";
                   }
                 }
               }
             }
           }
           case case_3 {
             container adtran {
               presence "enable adtran";
               junos:must "(!(\".. .. unframed\"))";
               junos:must-message "unframed and adtran cannot coexist";
               junos:cli-feature "oneliner";
               description "Compatible with Adtran CSU (not on 2/4-port T3 PIC)";
               leaf subrate {
                 description "Set subrate value";
                 type union {
                   type string {
                     pattern "<.*>|$.*";
                   }
                   type uint32 {
                     range "1 .. 588";
                   }
                 }
               }
             }
           }
           case case_4 {
             container kentrox {
               presence "enable kentrox";
               junos:cli-feature "oneliner";
               description "Compatible with Kentrox CSU";
               leaf subrate {
                 description "Set subrate value (not on 2/4-port T3 PIC)";
                 type union {
                   type string {
                     pattern "<.*>|$.*";
                   }
                   type uint32 {
                     range "1 .. 69";
                   }
                 }
               }
             }
           }
           case case_5 {
             container digital-link {
               presence "enable digital-link";
               junos:must "(!(\".. .. unframed\"))";
               junos:must-message "unframed and digital-link cannot coexist";
               junos:cli-feature "oneliner";
               description "Compatible with Digital Link CSU";
               leaf subrate {
                 description "Set subrate value";
                 type enumeration {
                   enum "301Kb" {
                     description "301 Kbps";
                   }
                   enum "601Kb" {
                     description "601 Kbps";
                   }
                   enum "902Kb" {
                     description "902 Kbps";
                   }
                   enum "1.2Mb" {
                     description "1.2 Mbps";
                   }
                   enum "1.5Mb" {
                     description "1.5 Mbps";
                   }
                   enum "1.8Mb" {
                     description "1.8 Mbps";
                   }
                   enum "2.1Mb" {
                     description "2.1 Mbps";
                   }
                   enum "2.4Mb" {
                     description "2.4 Mbps";
                   }
                   enum "2.7Mb" {
                     description "2.7 Mbps";
                   }
                   enum "3.0Mb" {
                     description "3.0 Mbps";
                   }
                   enum "3.3Mb" {
                     description "3.3 Mbps";
                   }
                   enum "3.6Mb" {
                     description "3.6 Mbps";
                   }
                   enum "3.9Mb" {
                     description "3.9 Mbps";
                   }
                   enum "4.2Mb" {
                     description "4.2 Mbps";
                   }
                   enum "4.5Mb" {
                     description "4.5 Mbps";
                   }
                   enum "4.8Mb" {
                     description "4.8 Mbps";
                   }
                   enum "5.1Mb" {
                     description "5.1 Mbps";
                   }
                   enum "5.4Mb" {
                     description "5.4 Mbps";
                   }
                   enum "5.7Mb" {
                     description "5.7 Mbps";
                   }
                   enum "6.0Mb" {
                     description "6.0 Mbps";
                   }
                   enum "6.3Mb" {
                     description "6.3 Mbps";
                   }
                   enum "6.6Mb" {
                     description "6.6 Mbps";
                   }
                   enum "6.9Mb" {
                     description "6.9 Mbps";
                   }
                   enum "7.2Mb" {
                     description "7.2 Mbps";
                   }
                   enum "7.5Mb" {
                     description "7.5 Mbps";
                   }
                   enum "7.8Mb" {
                     description "7.8 Mbps";
                   }
                   enum "8.1Mb" {
                     description "8.1 Mbps";
                   }
                   enum "8.4Mb" {
                     description "8.4 Mbps";
                   }
                   enum "8.7Mb" {
                     description "8.7 Mbps";
                   }
                   enum "9.0Mb" {
                     description "9.0 Mbps";
                   }
                   enum "9.3Mb" {
                     description "9.3 Mbps";
                   }
                   enum "9.6Mb" {
                     description "9.6 Mbps";
                   }
                   enum "9.9Mb" {
                     description "9.9 Mbps";
                   }
                   enum "10.2Mb" {
                     description "10.2 Mbps";
                   }
                   enum "10.5Mb" {
                     description "10.5 Mbps";
                   }
                   enum "10.8Mb" {
                     description "10.8 Mbps";
                   }
                   enum "11.1Mb" {
                     description "11.1 Mbps";
                   }
                   enum "11.4Mb" {
                     description "11.4 Mbps";
                   }
                   enum "11.7Mb" {
                     description "11.7 Mbps";
                   }
                   enum "12.0Mb" {
                     description "12.0 Mbps";
                   }
                   enum "12.3Mb" {
                     description "12.3 Mbps";
                   }
                   enum "12.6Mb" {
                     description "12.6 Mbps";
                   }
                   enum "12.9Mb" {
                     description "12.9 Mbps";
                   }
                   enum "13.2Mb" {
                     description "13.2 Mbps";
                   }
                   enum "13.5Mb" {
                     description "13.5 Mbps";
                   }
                   enum "13.8Mb" {
                     description "13.8 Mbps";
                   }
                   enum "14.1Mb" {
                     description "14.1 Mbps";
                   }
                   enum "14.4Mb" {
                     description "14.4 Mbps";
                   }
                   enum "14.7Mb" {
                     description "14.7 Mbps";
                   }
                   enum "15.0Mb" {
                     description "15.0 Mbps";
                   }
                   enum "15.3Mb" {
                     description "15.3 Mbps";
                   }
                   enum "15.6Mb" {
                     description "15.6 Mbps";
                   }
                   enum "15.9Mb" {
                     description "15.9 Mbps";
                   }
                   enum "16.2Mb" {
                     description "16.2 Mbps";
                   }
                   enum "16.5Mb" {
                     description "16.5 Mbps";
                   }
                   enum "16.8Mb" {
                     description "16.8 Mbps";
                   }
                   enum "17.1Mb" {
                     description "17.1 Mbps";
                   }
                   enum "17.4Mb" {
                     description "17.4 Mbps";
                   }
                   enum "17.7Mb" {
                     description "17.7 Mbps";
                   }
                   enum "18.0Mb" {
                     description "18.0 Mbps";
                   }
                   enum "18.3Mb" {
                     description "18.3 Mbps";
                   }
                   enum "18.6Mb" {
                     description "18.6 Mbps";
                   }
                   enum "18.9Mb" {
                     description "18.9 Mbps";
                   }
                   enum "19.2Mb" {
                     description "19.2 Mbps";
                   }
                   enum "19.5Mb" {
                     description "19.5 Mbps";
                   }
                   enum "19.8Mb" {
                     description "19.8 Mbps";
                   }
                   enum "20.1Mb" {
                     description "20.1 Mbps";
                   }
                   enum "20.5Mb" {
                     description "20.5 Mbps";
                   }
                   enum "20.8Mb" {
                     description "20.8 Mbps";
                   }
                   enum "21.1Mb" {
                     description "21.1 Mbps";
                   }
                   enum "21.4Mb" {
                     description "21.4 Mbps";
                   }
                   enum "21.7Mb" {
                     description "21.7 Mbps";
                   }
                   enum "22.0Mb" {
                     description "22.0 Mbps";
                   }
                   enum "22.3Mb" {
                     description "22.3 Mbps";
                   }
                   enum "22.6Mb" {
                     description "22.6 Mbps";
                   }
                   enum "22.9Mb" {
                     description "22.9 Mbps";
                   }
                   enum "23.2Mb" {
                     description "23.2 Mbps";
                   }
                   enum "23.5Mb" {
                     description "23.5 Mbps";
                   }
                   enum "23.8Mb" {
                     description "23.8 Mbps";
                   }
                   enum "24.1Mb" {
                     description "24.1 Mbps";
                   }
                   enum "24.4Mb" {
                     description "24.4 Mbps";
                   }
                   enum "24.7Mb" {
                     description "24.7 Mbps";
                   }
                   enum "25.0Mb" {
                     description "25.0 Mbps";
                   }
                   enum "25.3Mb" {
                     description "25.3 Mbps";
                   }
                   enum "25.6Mb" {
                     description "25.6 Mbps";
                   }
                   enum "25.9Mb" {
                     description "25.9 Mbps";
                   }
                   enum "26.2Mb" {
                     description "26.2 Mbps";
                   }
                   enum "26.5Mb" {
                     description "26.5 Mbps";
                   }
                   enum "26.8Mb" {
                     description "26.8 Mbps";
                   }
                   enum "27.1Mb" {
                     description "27.1 Mbps";
                   }
                   enum "27.4Mb" {
                     description "27.4 Mbps";
                   }
                   enum "27.7Mb" {
                     description "27.7 Mbps";
                   }
                   enum "28.0Mb" {
                     description "28.0 Mbps";
                   }
                   enum "28.3Mb" {
                     description "28.3 Mbps";
                   }
                   enum "28.6Mb" {
                     description "28.6 Mbps";
                   }
                   enum "28.9Mb" {
                     description "28.9 Mbps";
                   }
                   enum "29.2Mb" {
                     description "29.2 Mbps";
                   }
                   enum "29.5Mb" {
                     description "29.5 Mbps";
                   }
                   enum "29.8Mb" {
                     description "29.8 Mbps";
                   }
                   enum "30.1Mb" {
                     description "30.1 Mbps";
                   }
                   enum "30.4Mb" {
                     description "30.4 Mbps";
                   }
                   enum "30.7Mb" {
                     description "30.7 Mbps";
                   }
                   enum "31.0Mb" {
                     description "31.0 Mbps";
                   }
                   enum "31.3Mb" {
                     description "31.3 Mbps";
                   }
                   enum "31.6Mb" {
                     description "31.6 Mbps";
                   }
                   enum "31.9Mb" {
                     description "31.9 Mbps";
                   }
                   enum "32.2Mb" {
                     description "32.2 Mbps";
                   }
                   enum "32.5Mb" {
                     description "32.5 Mbps";
                   }
                   enum "32.8Mb" {
                     description "32.8 Mbps";
                   }
                   enum "33.1Mb" {
                     description "33.1 Mbps";
                   }
                   enum "33.4Mb" {
                     description "33.4 Mbps";
                   }
                   enum "33.7Mb" {
                     description "33.7 Mbps";
                   }
                   enum "34.0Mb" {
                     description "34.0 Mbps";
                   }
                   enum "34.3Mb" {
                     description "34.3 Mbps";
                   }
                   enum "34.6Mb" {
                     description "34.6 Mbps";
                   }
                   enum "34.9Mb" {
                     description "34.9 Mbps";
                   }
                   enum "35.2Mb" {
                     description "35.2 Mbps";
                   }
                   enum "35.5Mb" {
                     description "35.5 Mbps";
                   }
                   enum "35.8Mb" {
                     description "35.8 Mbps";
                   }
                   enum "36.1Mb" {
                     description "36.1 Mbps";
                   }
                   enum "36.4Mb" {
                     description "36.4 Mbps";
                   }
                   enum "36.7Mb" {
                     description "36.7 Mbps";
                   }
                   enum "37.0Mb" {
                     description "37.0 Mbps";
                   }
                   enum "37.3Mb" {
                     description "37.3 Mbps";
                   }
                   enum "37.6Mb" {
                     description "37.6 Mbps";
                   }
                   enum "37.9Mb" {
                     description "37.9 Mbps";
                   }
                   enum "38.2Mb" {
                     description "38.2 Mbps";
                   }
                   enum "38.5Mb" {
                     description "38.5 Mbps";
                   }
                   enum "38.8Mb" {
                     description "38.8 Mbps";
                   }
                   enum "39.1Mb" {
                     description "39.1 Mbps";
                   }
                   enum "39.4Mb" {
                     description "39.4 Mbps";
                   }
                   enum "39.7Mb" {
                     description "39.7 Mbps";
                   }
                   enum "40.0Mb" {
                     description "40.0 Mbps";
                   }
                   enum "40.3Mb" {
                     description "40.3 Mbps";
                   }
                   enum "40.6Mb" {
                     description "40.6 Mbps";
                   }
                   enum "40.9Mb" {
                     description "40.9 Mbps";
                   }
                   enum "41.2Mb" {
                     description "41.2 Mbps";
                   }
                   enum "41.5Mb" {
                     description "41.5 Mbps";
                   }
                   enum "41.8Mb" {
                     description "41.8 Mbps";
                   }
                   enum "42.1Mb" {
                     description "42.1 Mbps";
                   }
                   enum "42.4Mb" {
                     description "42.4 Mbps";
                   }
                   enum "42.7Mb" {
                     description "42.7 Mbps";
                   }
                   enum "43.0Mb" {
                     description "43.0 Mbps";
                   }
                   enum "43.3Mb" {
                     description "43.3 Mbps";
                   }
                   enum "43.6Mb" {
                     description "43.6 Mbps";
                   }
                   enum "43.9Mb" {
                     description "43.9 Mbps";
                   }
                   enum "44.2Mb" {
                     description "44.2 Mbps";
                   }
                 }
               }
             }
           }
         }
       }
       choice payload-scrambler-choice {
         leaf payload-scrambler {
           description "Enable payload scrambling";
           type empty;
         }
         leaf no-payload-scrambler {
           description "Don't enable payload scrambling";
           type empty;
         }
       }
       choice cbit-parity-choice {
         leaf cbit-parity {
           description "Enable C-bit parity mode";
           junos:must "(!(\".. unframed\"))";
           junos:must-message "cbit-parity and unframed cannot coexist";
           type empty;
         }
         leaf no-cbit-parity {
           description "Don't enable C-bit parity mode";
           junos:must "(!(\".. unframed\"))";
           junos:must-message "cbit-parity and unframed cannot coexist";
           type empty;
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       choice feac-loop-respond-choice {
         leaf feac-loop-respond {
           description "Respond to FEAC loop requests";
           type empty;
         }
         leaf no-feac-loop-respond {
           description "Don't respond to FEAC loop requests";
           type empty;
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
       leaf buildout {
         description "Line buildout";
         units "feet";
         type union {
           type string {
             pattern "<.*>|$.*";
           }
           type uint32 {
             range "0 .. 450";
           }
         }
       }
       leaf atm-encapsulation {
         description "DS-3 interface encapsulation";
         type enumeration {
           enum "plcp" {
             description "PLCP encapsulation";
           }
           enum "direct" {
             description "ATM direct mapping";
           }
         }
       }
     }
     container e3-options {
       junos:must "((!(\"interfaces ${interface} container-options\") || (\"interfaces ${interface} container-options container-type\" || \"interfaces ${interface} container-options allow-configuration-override\")))";
       junos:must-message "t1-options cannot be configured without allow-configuration-override";
       description "E3 interface-specific options";
       uses apply-advanced;
       leaf loopback {
         description "Loopback mode";
         type enumeration {
           enum "local" {
             description "Local loopback";
           }
           enum "remote" {
             description "Remote loopback";
           }
         }
       }
       choice unframed-choice {
         leaf unframed {
           description "Enable unframed mode";
           type empty;
         }
         leaf no-unframed {
           description "Don't enable unframed mode";
           type empty;
         }
       }
       container compatibility-mode {
         junos:cli-feature "oneliner";
         description "Set CSU compatibility mode";
         choice vendor {
           case case_1 {
             leaf larscom {
               description "Compatible with Larscom CSU (only non IQ E3 interfaces)";
               type empty;
             }
           }
           case case_2 {
             container digital-link {
               presence "enable digital-link";
               junos:cli-feature "oneliner";
               description "Compatible with Digital Link CSU";
               leaf subrate {
                 description "Set subrate value";
                 type enumeration {
                   enum "358Kb" {
                     description "358 Kbps";
                   }
                   enum "716Kb" {
                     description "716 Kbps";
                   }
                   enum "1.1Mb" {
                     description "1.1 Mbps";
                   }
                   enum "1.4Mb" {
                     description "1.4 Mbps";
                   }
                   enum "1.8Mb" {
                     description "1.8 Mbps";
                   }
                   enum "2.1Mb" {
                     description "2.1 Mbps";
                   }
                   enum "2.5Mb" {
                     description "2.5 Mbps";
                   }
                   enum "2.9Mb" {
                     description "2.9 Mbps";
                   }
                   enum "3.2Mb" {
                     description "3.2 Mbps";
                   }
                   enum "3.6Mb" {
                     description "3.6 Mbps";
                   }
                   enum "3.9Mb" {
                     description "3.9 Mbps";
                   }
                   enum "4.3Mb" {
                     description "4.3 Mbps";
                   }
                   enum "4.7Mb" {
                     description "4.7 Mbps";
                   }
                   enum "5.0Mb" {
                     description "5.0 Mbps";
                   }
                   enum "5.4Mb" {
                     description "5.4 Mbps";
                   }
                   enum "5.7Mb" {
                     description "5.7 Mbps";
                   }
                   enum "6.1Mb" {
                     description "6.1 Mbps";
                   }
                   enum "6.4Mb" {
                     description "6.4 Mbps";
                   }
                   enum "6.8Mb" {
                     description "6.8 Mbps";
                   }
                   enum "7.2Mb" {
                     description "7.2 Mbps";
                   }
                   enum "7.5Mb" {
                     description "7.5 Mbps";
                   }
                   enum "7.9Mb" {
                     description "7.9 Mbps";
                   }
                   enum "8.2Mb" {
                     description "8.2 Mbps";
                   }
                   enum "8.6Mb" {
                     description "8.6 Mbps";
                   }
                   enum "9.0Mb" {
                     description "9.0 Mbps";
                   }
                   enum "9.3Mb" {
                     description "9.3 Mbps";
                   }
                   enum "9.7Mb" {
                     description "9.7 Mbps";
                   }
                   enum "10.0Mb" {
                     description "10.0 Mbps";
                   }
                   enum "10.4Mb" {
                     description "10.4 Mbps";
                   }
                   enum "10.7Mb" {
                     description "10.7 Mbps";
                   }
                   enum "11.1Mb" {
                     description "11.1 Mbps";
                   }
                   enum "11.5Mb" {
                     description "11.5 Mbps";
                   }
                   enum "11.8Mb" {
                     description "11.8 Mbps";
                   }
                   enum "12.2Mb" {
                     description "12.2 Mbps";
                   }
                   enum "12.5Mb" {
                     description "12.5 Mbps";
                   }
                   enum "12.9Mb" {
                     description "12.9 Mbps";
                   }
                   enum "13.2Mb" {
                     description "13.2 Mbps";
                   }
                   enum "13.6Mb" {
                     description "13.6 Mbps";
                   }
                   enum "14.0Mb" {
                     description "14.0 Mbps";
                   }
                   enum "14.3Mb" {
                     description "14.3 Mbps";
                   }
                   enum "14.7Mb" {
                     description "14.7 Mbps";
                   }
                   enum "15.0Mb" {
                     description "15.0 Mbps";
                   }
                   enum "15.4Mb" {
                     description "15.4 Mbps";
                   }
                   enum "15.8Mb" {
                     description "15.8 Mbps";
                   }
                   enum "16.1Mb" {
                     description "16.1 Mbps";
                   }
                   enum "16.5Mb" {
                     description "16.5 Mbps";
                   }
                   enum "16.8Mb" {
                     description "16.8 Mbps";
                   }
                   enum "17.2Mb" {
                     description "17.2 Mbps";
                   }
                   enum "17.5Mb" {
                     description "17.5 Mbps";
                   }
                   enum "17.9Mb" {
                     description "17.9 Mbps";
                   }
                   enum "18.3Mb" {
                     description "18.3 Mbps";
                   }
                   enum "18.6Mb" {
                     description "18.6 Mbps";
                   }
                   enum "19.0Mb" {
                     description "19.0 Mbps";
                   }
                   enum "19.3Mb" {
                     description "19.3 Mbps";
                   }
                   enum "19.7Mb" {
                     description "19.7 Mbps";
                   }
                   enum "20.0Mb" {
                     description "20.0 Mbps";
                   }
                   enum "20.4Mb" {
                     description "20.4 Mbps";
                   }
                   enum "20.8Mb" {
                     description "20.8 Mbps";
                   }
                   enum "21.1Mb" {
                     description "21.1 Mbps";
                   }
                   enum "21.5Mb" {
                     description "21.5 Mbps";
                   }
                   enum "21.8Mb" {
                     description "21.8 Mbps";
                   }
                   enum "22.2Mb" {
                     description "22.2 Mbps";
                   }
                   enum "22.6Mb" {
                     description "22.6 Mbps";
                   }
                   enum "22.9Mb" {
                     description "22.9 Mbps";
                   }
                   enum "23.3Mb" {
                     description "23.3 Mbps";
                   }
                   enum "23.6Mb" {
                     description "23.6 Mbps";
                   }
                   enum "24.0Mb" {
                     description "24.0 Mbps";
                   }
                   enum "24.3Mb" {
                     description "24.3 Mbps";
                   }
                   enum "24.7Mb" {
                     description "24.7 Mbps";
                   }
                   enum "25.1Mb" {
                     description "25.1 Mbps";
                   }
                   enum "25.4Mb" {
                     description "25.4 Mbps";
                   }
                   enum "25.8Mb" {
                     description "25.8 Mbps";
                   }
                   enum "26.1Mb" {
                     description "26.1 Mbps";
                   }
                   enum "26.5Mb" {
                     description "26.5 Mbps";
                   }
                   enum "26.9Mb" {
                     description "26.9 Mbps";
                   }
                   enum "27.2Mb" {
                     description "27.2 Mbps";
                   }
                   enum "27.6Mb" {
                     description "27.6 Mbps";
                   }
                   enum "27.9Mb" {
                     description "27.9 Mbps";
                   }
                   enum "28.3Mb" {
                     description "28.3 Mbps";
                   }
                   enum "28.6Mb" {
                     description "28.6 Mbps";
                   }
                   enum "29.0Mb" {
                     description "29.0 Mbps";
                   }
                   enum "29.4Mb" {
                     description "29.4 Mbps";
                   }
                   enum "29.7Mb" {
                     description "29.7 Mbps";
                   }
                   enum "30.1Mb" {
                     description "30.1 Mbps";
                   }
                   enum "30.4Mb" {
                     description "30.4 Mbps";
                   }
                   enum "30.8Mb" {
                     description "30.8 Mbps";
                   }
                   enum "31.1Mb" {
                     description "31.1 Mbps";
                   }
                   enum "31.5Mb" {
                     description "31.5 Mbps";
                   }
                   enum "31.9Mb" {
                     description "31.9 Mbps";
                   }
                   enum "32.2Mb" {
                     description "32.2 Mbps";
                   }
                   enum "32.6Mb" {
                     description "32.6 Mbps";
                   }
                   enum "32.9Mb" {
                     description "32.9 Mbps";
                   }
                   enum "33.3Mb" {
                     description "33.3 Mbps";
                   }
                   enum "33.7Mb" {
                     description "33.7 Mbps";
                   }
                   enum "34.0Mb" {
                     description "34.0 Mbps";
                   }
                 }
               }
             }
           }
           case case_3 {
             container kentrox {
               presence "enable kentrox";
               junos:cli-feature "oneliner";
               description "Compatible with Kentrox CSU";
               leaf subrate {
                 description "Set subrate value (only for E3 IQ interfaces)";
                 type union {
                   type string {
                     pattern "<.*>|$.*";
                   }
                   type uint32 {
                     range "1 .. 48";
                   }
                 }
               }
             }
           }
         }
       }
       choice payload-scrambler-choice {
         leaf payload-scrambler {
           description "Enable payload scrambling";
           type empty;
         }
         leaf no-payload-scrambler {
           description "Don't enable payload scrambling";
           type empty;
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf invert-data {
         description "Invert data";
         type empty;
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
       leaf buildout {
         description "Line buildout";
         units "feet";
         type union {
           type string {
             pattern "<.*>|$.*";
           }
           type uint32 {
             range "0 .. 450";
           }
         }
       }
       leaf atm-encapsulation {
         description "E3 interface encapsulation";
         type enumeration {
           enum "plcp" {
             description "PLCP encapsulation";
           }
           enum "direct" {
             description "ATM direct mapping";
           }
         }
       }
       leaf framing {
         description "E3 line format";
         type enumeration {
           enum "g.751" {
             description "G.751 format";
           }
           enum "g.832" {
             description "G.832 format";
           }
         }
       }
     }
     container e1-options {
       junos:must "((!(\"interfaces ${interface} container-options\") || (\"interfaces ${interface} container-options container-type\" || \"interfaces ${interface} container-options allow-configuration-override\")))";
       junos:must-message "e1-options cannot be configured without allow-configuration-override";
       description "E1 interface-specific options";
       uses apply-advanced;
       leaf timeslots {
         description "Timeslots (1..32); for example, 1-4,6,9-11,32 (no space)";
         type string;
       }
       leaf loopback {
         description "Loopback mode";
         type enumeration {
           enum "local" {
             description "Local loopback";
           }
           enum "remote" {
             description "Remote loopback";
           }
         }
       }
       leaf framing {
         description "Framing mode";
         type enumeration {
           enum "g704" {
             description "G704 mode with CRC4";
           }
           enum "unframed" {
             description "Unframed mode";
           }
           enum "g704-no-crc4" {
             description "G704 mode without CRC4";
           }
         }
       }
       leaf fcs {
         description "Frame checksum";
         type enumeration {
           enum "32" {
             description "32-bit mode";
           }
           enum "16" {
             description "16-bit mode";
           }
         }
       }
       leaf invert-data {
         description "Invert data";
         type empty;
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 86400";
           }
         }
       }
     }
     container t1-options {
       junos:must "((!(\"interfaces ${interface} container-options\") || (\"interfaces ${interface} container-options container-type\" || \"interfaces ${interface} container-options allow-configuration-override\")))";
       junos:must-message "t1-options cannot be configured without allow-configuration-override";
       description "T1 interface-specific options";
       uses apply-advanced;
       leaf timeslots {
         description "Timeslots (1..24; for example, 1-3,4,9,22-24 (no space)";
         type string;
       }
       leaf disable-remote-alarm-detection {
         description "Disable detection of a remote alarm";
         type enumeration {
           enum "yellow" {
             description "Disable yellow alarm detection";
           }
         }
       }
       leaf loopback {
         description "Loopback mode";
         type enumeration {
           enum "local" {
             description "Local loopback";
           }
           enum "remote" {
             description "Remote loopback";
           }
           enum "payload" {
             description "Payload loopback";
           }
         }
       }
       leaf buildout {
         description "Line buildout";
         type enumeration {
           enum "0-132" {
             description "Line buildout is between 0-132 feet";
           }
           enum "133-265" {
             description "Line buildout is between 133-265 feet";
           }
           enum "266-398" {
             description "Line buildout is between 266-398 feet";
           }
           enum "399-531" {
             description "Line buildout is between 399-531 feet";
           }
           enum "532-655" {
             description "Line buildout is between 532-655 feet";
           }
           enum "long-0db" {
             description "Long buildout with 0 dB transmit attenuation";
           }
           enum "long-7.5db" {
             description "Long buildout with 7.5 dB transmit attenuation";
           }
           enum "long-15db" {
             description "Long buildout with 15 dB transmit attenuation";
           }
           enum "long-22.5db" {
             description "Long buildout with 22.5 dB transmit attenuation";
           }
         }
       }
       leaf byte-encoding {
         description "Byte encoding";
         type enumeration {
           enum "nx64" {
             description "8 bits per byte";
           }
           enum "nx56" {
             description "7 bits per byte";
           }
         }
       }
       leaf line-encoding {
         description "Line encoding";
         type enumeration {
           enum "ami" {
             description "Automatic mark inversion";
           }
           enum "b8zs" {
             description "8-bit zero suppression";
           }
         }
       }
       leaf invert-data {
         description "Invert data";
         type empty;
       }
       leaf framing {
         description "Framing mode";
         type enumeration {
           enum "sf" {
             description "Super frame";
           }
           enum "esf" {
             description "Extended super frame";
           }
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 86400";
           }
         }
       }
       leaf remote-loopback-respond {
         description "Respond to loop requests from remote end";
         type empty;
       }
       leaf crc-major-alarm-threshold {
         description "CRC Major alarm threshold value";
         default "5e-5";
         type enumeration {
           enum "1e-3" {
             description "1 crc error in 10^3 bits";
           }
           enum "5e-4" {
             description "5 crc errors in 10^4 bits";
           }
           enum "1e-4" {
             description "1 crc error in 10^4 bits";
           }
           enum "5e-5" {
             description "5 crc errors in 10^5 bits";
           }
           enum "1e-5" {
             description "1 crc error in 10^5 bits";
           }
         }
       }
       leaf crc-minor-alarm-threshold {
         description "CRC Minor alarm threshold value";
         default "5e-6";
         type enumeration {
           enum "1e-3" {
             description "1 crc error in 10^3 bits";
           }
           enum "5e-4" {
             description "5 crc errors in 10^4 bits";
           }
           enum "1e-4" {
             description "1 crc error in 10^4 bits";
           }
           enum "5e-5" {
             description "5 crc errors in 10^5 bits";
           }
           enum "1e-5" {
             description "1 crc error in 10^5 bits";
           }
           enum "5e-6" {
             description "5 crc errors in 10^6 bits";
           }
           enum "1e-6" {
             description "1 crc error in 10^6 bits";
           }
         }
       }
     }
     container ds0-options {
       junos:must "((!(\"interfaces ${interface} container-options\") || (\"interfaces ${interface} container-options container-type\" || \"interfaces ${interface} container-options allow-configuration-override\")))";
       junos:must-message "ds0-options cannot be configured without allow-configuration-override";
       description "DS-0 interface-specific options";
       uses apply-advanced;
       leaf loopback {
         description "Loopback mode";
         type enumeration {
           enum "payload" {
             description "Payload loopback";
           }
         }
       }
       leaf byte-encoding {
         description "Byte encoding";
         type enumeration {
           enum "nx64" {
             description "8 bits per byte";
           }
           enum "nx56" {
             description "7 bits per byte";
           }
         }
       }
       leaf invert-data {
         description "Invert data";
         type empty;
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e11-o152" {
             description "Pattern is 2^11 -1 (per O.152 standard)";
           }
           enum "pseudo-2e15-o151" {
             description "Pattern is 2^15 - 1 (per O.151 standard)";
           }
           enum "pseudo-2e20-o153" {
             description "Pattern is 2^20 - 1 (per O.153 standard)";
           }
           enum "pseudo-2e20-o151" {
             description "Pattern is 2^20 - 1 (per O.151 standard)";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
           enum "repeating-1-in-16" {
             description "1 bit in 16 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
     }
     container serial-options {
       description "Serial interface-specific options";
       uses apply-advanced;
       leaf line-protocol {
         description "Line protocol to be used";
         default "eia530";
         type enumeration {
           enum "eia530" {
             description "Line protocol EIA530";
           }
           enum "v.35" {
             description "Line protocol V.35";
           }
           enum "x.21" {
             description "Line protocol X.21";
           }
         }
       }
       choice control_leads_choice {
         case case_1 {
           container dte-options {
             description "DTE options/control leads";
             uses apply-advanced;
             leaf ignore-all {
               description "Ignore all control leads";
               junos:must "(!(\".. indication\"))";
               junos:must-message "SERIAL: ignore-all configured when indication explicitly configured";
               junos:must "(!(\".. cts\"))";
               junos:must-message "SERIAL: ignore-all configured when cts explicitly configured";
               junos:must "(!(\".. dsr\"))";
               junos:must-message "SERIAL: ignore-all configured when dsr explicitly configured";
               junos:must "(!(\".. tm\"))";
               junos:must-message "SERIAL: ignore-all configured when tm explicitly configured";
               junos:must "(!(\".. dcd\"))";
               junos:must-message "SERIAL: ignore-all configured when dcd explicitly configured";
               type empty;
             }
             container dtr {
               junos:cli-feature "oneliner";
               description "Data Transmit Ready signal handling";
               choice dtr_choices {
                 case case_1 {
                   leaf assert {
                     description "Assert DTR signal";
                     type empty;
                   }
                 }
                 case case_2 {
                   leaf de-assert {
                     description "Deassert DTR signal";
                     type empty;
                   }
                 }
                 case case_3 {
                   leaf normal {
                     description "Normal DTR signal";
                     type empty;
                   }
                 }
                 case case_4 {
                   container auto-synchronize {
                     presence "enable auto-synchronize";
                     description "Normal DTR signal, with autoresynchronization";
                     uses apply-advanced;
                     leaf duration {
                       description "Duration of autoresynchronization";
                       units "milliseconds";
                       type union {
                         type string {
                           pattern "<.*>|$.*";
                         }
                         type uint16 {
                           range "1 .. 1000";
                         }
                       }
                     }
                     leaf interval {
                       description "Interval for autoresynchronization";
                       units "seconds";
                       type union {
                         type string {
                           pattern "<.*>|$.*";
                         }
                         type uint16 {
                           range "1 .. 31";
                         }
                       }
                     }
                   }
                 }
               }
             }
             leaf control-signal {
               description "X.21 control signal handling";
               junos:must "(!(\".. .. line-protocol eia530\"))";
               junos:must-message "Control signal  invalid on line-protocol eia530";
               junos:must "(!(\".. .. line-protocol v.35\"))";
               junos:must-message "Control signal invalid on line-protocol v.35";
               type enumeration {
                 enum "assert" {
                   description "Assert control signal";
                 }
                 enum "de-assert" {
                   description "Deassert control signal";
                 }
                 enum "normal" {
                   description "Normal control signal";
                 }
               }
             }
             leaf rts {
               description "Request To Send signal handling";
               junos:must "(!(\".. .. line-protocol x.21\"))";
               junos:must-message "rts invalid on line-protocol x.21";
               type enumeration {
                 enum "assert" {
                   description "Assert RTS signal";
                 }
                 enum "de-assert" {
                   description "Deassert RTS signal";
                 }
                 enum "normal" {
                   description "Normal RTS signal";
                 }
               }
             }
             leaf dcd {
               description "Data Carrier Detect signal handling";
               type enumeration {
                 enum "require" {
                   description "Require DCD signal";
                 }
                 enum "ignore" {
                   description "Ignore DCD signal";
                 }
                 enum "normal" {
                   description "Normal DCD signal";
                 }
               }
             }
             leaf dsr {
               description "Data Set Ready signal handling";
               type enumeration {
                 enum "require" {
                   description "Require DSR signal";
                 }
                 enum "ignore" {
                   description "Ignore DSR signal";
                 }
                 enum "normal" {
                   description "Normal DSR signal";
                 }
               }
             }
             leaf cts {
               description "Clear To Send signal handling";
               junos:must "(!(\".. .. line-protocol x.21\"))";
               junos:must-message "cts invalid on line-protocol x.21";
               type enumeration {
                 enum "require" {
                   description "Require CTS signal";
                 }
                 enum "ignore" {
                   description "Ignore CTS signal";
                 }
                 enum "normal" {
                   description "Normal CTS signal";
                 }
               }
             }
             leaf indication {
               description "X.21 Indication signal handling";
               junos:must "(!(\".. .. line-protocol eia530\"))";
               junos:must-message "Indication   invalid on line-protocol eia530";
               junos:must "(!(\".. .. line-protocol v.35\"))";
               junos:must-message "Indication invalid on line-protocol v.35";
               type enumeration {
                 enum "require" {
                   description "Require Indication signal";
                 }
                 enum "ignore" {
                   description "Ignore Indication signal";
                 }
                 enum "normal" {
                   description "Normal Indication signal";
                 }
               }
             }
             leaf tm {
               description "Test Mode signal handling";
               type enumeration {
                 enum "require" {
                   description "Require TM signal";
                 }
                 enum "ignore" {
                   description "Ignore TM signal";
                 }
                 enum "normal" {
                   description "Normal TM signal";
                 }
               }
             }
           }
         }
         case case_2 {
         }
       }
       leaf dtr-circuit {
         description "Data Transmit Ready circuit mode";
         junos:must "(!(\".. line-protocol x.21\"))";
         junos:must-message "dtr-circuit invalid with line protocol x.21";
         type enumeration {
           enum "balanced" {
             description "Balanced signal";
           }
           enum "unbalanced" {
             description "Unbalanced signal";
           }
         }
       }
       leaf dtr-polarity {
         description "Data Transmit Ready signal polarity";
         junos:must "(!(\".. line-protocol x.21\"))";
         junos:must-message "dtr-polarity invalid with line protocol x.21";
         type enumeration {
           enum "positive" {
             description "Positive polarity";
           }
           enum "negative" {
             description "Negative polarity";
           }
         }
       }
       leaf rts-polarity {
         description "Request To Send signal polarity";
         junos:must "(!(\".. line-protocol x.21\"))";
         junos:must-message "rts invalid on line-protocol x.21";
         type enumeration {
           enum "positive" {
             description "Positive polarity";
           }
           enum "negative" {
             description "Negative polarity";
           }
         }
       }
       leaf control-polarity {
         description "X.21 Control signal polarity";
         junos:must "(!(\".. line-protocol eia530\"))";
         junos:must-message "Control signal  invalid on line-protocol eia530";
         junos:must "(!(\".. line-protocol v.35\"))";
         junos:must-message "Control signal invalid on line-protocol v.35";
         type enumeration {
           enum "positive" {
             description "Positive polarity";
           }
           enum "negative" {
             description "Negative polarity";
           }
         }
       }
       leaf dcd-polarity {
         description "Data Carrier Detect signal polarity";
         junos:must "(!(\".. line-protocol x.21\"))";
         junos:must-message "dcd-polarity invalid with line protocol x.21";
         type enumeration {
           enum "positive" {
             description "Positive polarity";
           }
           enum "negative" {
             description "Negative polarity";
           }
         }
       }
       leaf dsr-polarity {
         description "Data Set Ready signal polarity";
         junos:must "(!(\".. line-protocol x.21\"))";
         junos:must-message "dsr-polarity invalid with line protocol x.21";
         type enumeration {
           enum "positive" {
             description "Positive polarity";
           }
           enum "negative" {
             description "Negative polarity";
           }
         }
       }
       leaf cts-polarity {
         description "Clear To Send signal polarity";
         junos:must "(!(\".. line-protocol x.21\"))";
         junos:must-message "cts invalid on line-protocol x.21";
         type enumeration {
           enum "positive" {
             description "Positive polarity";
           }
           enum "negative" {
             description "Negative polarity";
           }
         }
       }
       leaf indication-polarity {
         description "X.21 Indication signal polarity";
         junos:must "(!(\".. line-protocol eia530\"))";
         junos:must-message "Indication  invalid on line-protocol eia530";
         junos:must "(!(\".. line-protocol v.35\"))";
         junos:must-message "Indication invalid on line-protocol v.35";
         type enumeration {
           enum "positive" {
             description "Positive polarity";
           }
           enum "negative" {
             description "Negative polarity";
           }
         }
       }
       leaf tm-polarity {
         description "Test Mode signal polarity";
         junos:must "(!(\".. line-protocol x.21\"))";
         junos:must-message "tm-polarity invalid for line protocol x.21";
         junos:must "(!(\".. line-protocol v.35\"))";
         junos:must-message "tm-polarity invalid for line protocol v.35";
         type enumeration {
           enum "positive" {
             description "Positive polarity";
           }
           enum "negative" {
             description "Negative polarity";
           }
         }
       }
       leaf clocking-mode {
         description "Clock mode";
         type enumeration {
           enum "dce" {
             description "DCE timing (DTE mode only, not valid for X.21)";
           }
           enum "internal" {
             description "Internal baud timing";
           }
           enum "loop" {
             description "Loop timing";
           }
         }
       }
       leaf transmit-clock {
         description "Transmit clock phase";
         type enumeration {
           enum "invert" {
             description "Shift clock phase 180 degrees";
           }
         }
       }
       leaf clock-rate {
         description "Interface clock rate";
         type enumeration {
           enum "2.048mhz" {
             description "2.048 MHz";
           }
           enum "2.341mhz" {
             description "2.341 MHz";
           }
           enum "2.731mhz" {
             description "2.731 MHz";
           }
           enum "3.277mhz" {
             description "3.277 MHz";
           }
           enum "4.096mhz" {
             description "4.096 MHz";
           }
           enum "5.461mhz" {
             description "5.461 MHz";
           }
           enum "8.192mhz" {
             description "8.192 MHz";
           }
           enum "16.384mhz" {
             description "16.384 MHz";
           }
           enum "1.2khz" {
             description "1.2 KHz";
           }
           enum "2.4khz" {
             description "2.4 KHz";
           }
           enum "9.6khz" {
             description "9.6 KHz";
           }
           enum "19.2khz" {
             description "19.2 KHz";
           }
           enum "38.4khz" {
             description "38.4 KHz";
           }
           enum "56.0khz" {
             description "56.0 KHz";
           }
           enum "64.0khz" {
             description "64.0 KHz";
           }
           enum "72.0khz" {
             description "72.0 KHz";
           }
           enum "125.0khz" {
             description "125.0 KHz";
           }
           enum "148.0khz" {
             description "148.0 KHz";
           }
           enum "250.0khz" {
             description "250.0 KHz";
           }
           enum "500.0khz" {
             description "500.0 KHz";
           }
           enum "800.0khz" {
             description "800.0 KHz";
           }
           enum "1.0mhz" {
             description "1.0 MHz";
           }
           enum "1.3mhz" {
             description "1.3 MHz";
           }
           enum "2.0mhz" {
             description "2.0 MHz";
           }
           enum "4.0mhz" {
             description "4.0 MHz";
           }
           enum "8.0mhz" {
             description "8.0 MHz";
           }
         }
       }
       leaf loopback {
         description "Loopback mode";
         type enumeration {
           enum "local" {
             description "Local loopback";
           }
           enum "remote" {
             description "Remote/LIU loopback";
           }
           enum "dce-local" {
             description "DCE local loopback (DTE mode only)";
           }
           enum "dce-remote" {
             description "DCE remote loopback";
           }
         }
       }
       leaf encoding {
         description "Line encoding";
         type enumeration {
           enum "nrz" {
             description "Non-Return-To-Zero";
           }
           enum "nrzi" {
             description "Non-Return-To-Zero-Invertible";
           }
         }
       }
     }
     choice gratuitous-arp-reply-choice {
       leaf gratuitous-arp-reply {
         description "Enable gratuitous ARP reply";
         type empty;
       }
       leaf no-gratuitous-arp-reply {
         description "Don't enable gratuitous ARP reply";
         type empty;
       }
     }
     choice no-gratuitous-arp-request-choice {
       leaf no-gratuitous-arp-request {
         description "Ignore gratuitous ARP request";
         type empty;
       }
       leaf no-no-gratuitous-arp-request {
         description "Don't ignore gratuitous ARP request";
         type empty;
       }
     }
     leaf arp-l2-validate {
       description "Validate ARP against L2";
       type empty;
     }
     container ether-options {
       description "Ethernet interface-specific options";
       uses apply-advanced;
       choice loopback-choice {
         leaf loopback {
           description "Enable loopback";
           type empty;
         }
         leaf no-loopback {
           description "Don't enable loopback";
           type empty;
         }
       }
       leaf loopback-remote {
         description "Enable remote loopback";
         junos:must "(!(\".. .. optics-options loopback\"))";
         junos:must-message "'optics-options loopback' and loopback-remote are mutually exclusive";
         junos:must "(!(\".. loopback\"))";
         junos:must-message "loopback and loopback-remote are mutually exclusive";
         type empty;
       }
       choice source-filtering-choice {
         leaf source-filtering {
           description "Enable source address filtering";
           type empty;
         }
         leaf no-source-filtering {
           description "Don't enable source address filtering";
           type empty;
         }
       }
       container ethernet-switch-profile {
         description "Ethernet virtual LAN/media access control-level options";
         uses apply-advanced;
         leaf-list tag-protocol-id {
           ordered-by user;
           description "IEEE 802.1q Tag Protocol Identifier values for VLAN-tagged frames";
           type string;
         }
         container ethernet-policer-profile {
           description "Ethernet level CoS-based policer configuration";
           uses apply-advanced;
           container input-priority-map {
             description "Input policer priority map";
             uses cos_policer_input_priority_map;
           }
           container output-priority-map {
             description "Output policer priority map";
             uses cos_policer_output_priority_map;
           }
           list policer {
             key name;
             ordered-by user;
             description "Policer template definition";
             uses cos_policer;
           }
         }
         container storm-control {
           junos:must "(!(any \"interfaces ${interface} unit <*> family ethernet-switching storm-control <*>\"))";
           junos:must-message "An interface cannot have storm control on both family ethernet-switching and ethernet switch profile";
           junos:cli-feature "oneliner-plus";
           description "Storm control profile name to bind";
           uses apply-advanced;
           leaf profile-name {
             description "Profile name";
             junos:cli-feature "nokeyword";
             junos:must "(\"forwarding-options storm-control-profiles $$\")";
             junos:must-message "Storm profile name must be defined in the [edit forwarding-options storm-control-profiles] hierarchy";
             type string;
           }
         }
         container recovery-timeout {
           junos:cli-feature "oneliner";
           description "Recovery timeout for this interface";
           leaf time-in-seconds {
             junos:cli-feature "nokeyword";
             units "seconds";
             type union {
               type string {
                 pattern "<.*>|$.*";
               }
               type uint32 {
                 range "10 .. 3600";
               }
             }
           }
         }
         choice mac-learn-enable-choice {
           leaf mac-learn-enable {
             description "Learn MAC addresses dynamically";
             type empty;
           }
           leaf no-mac-learn-enable {
             description "Don't learn MAC addresses dynamically";
             type empty;
           }
         }
       }
       leaf asynchronous-notification {
         description "Enable sending asynchronous notification to peer on CCC-down";
         type empty;
       }
       list source-address-filter {
         key name;
         junos:cli-feature "homogeneous";
         junos:cli-feature "oneliner";
         description "Source address filters";
         leaf name {
           description "Remote MAC address";
           junos:cli-feature "nokeyword";
           type jt:mac-addr;
         }
       }
       choice auto-negotiation-choice {
         leaf auto-negotiation {
           description "Enable auto-negotiation";
           type empty;
         }
         leaf no-auto-negotiation {
           description "Don't enable auto-negotiation";
           type empty;
         }
       }
       choice flow-control-choice {
         leaf flow-control {
           description "Enable flow control";
           type empty;
         }
         leaf no-flow-control {
           description "Don't enable flow control";
           type empty;
         }
       }
       container configured-flow-control {
         presence "enable configured-flow-control";
         junos:must "(!((\".. flow-control\" || \".. no-flow-control\")))";
         junos:must-message "flow-control and configured-flow-control are not allowed together";
         description "Enable flow control";
         uses apply-advanced;
         leaf rx-buffers {
           description "Enable/Disable Rx buffers";
           type enumeration {
             enum "on" {
               description "Enable Rx buffers";
             }
             enum "off" {
               description "Disable Rx buffers";
             }
           }
         }
         leaf tx-buffers {
           description "Enable/Disable Tx buffers";
           type enumeration {
             enum "on" {
               description "Enable Tx buffers";
             }
             enum "off" {
               description "Disable Tx buffers";
             }
           }
         }
       }
       leaf link-mode {
         description "Link duplex";
         type enumeration {
           enum "automatic" {
             description "Automatic negotiate duplex ";
           }
           enum "half-duplex" {
             description "Half-duplex operation";
           }
           enum "full-duplex" {
             description "Full-duplex operation";
           }
         }
       }
       container mpls {
         description "MPLS options";
         uses mpls_ifd_options;
       }
       leaf ignore-l3-incompletes {
         description "Ignore L3 incomplete errors";
         type empty;
       }
       leaf no-auto-mdix {
         description "Disable auto MDI/MDIX";
         type empty;
       }
       leaf fec {
         description "Forward Error Correction mode";
         type enumeration {
           enum "none" {
             description "FEC disabled";
           }
           enum "fec91" {
             description "IEEE 802.3bj Clause 91, Reed-Solomon FEC (RS-FEC)";
           }
           enum "fec74" {
             description "FEC74 enabled";
           }
           enum "fec108" {
             description "IEEE 802.3by Clause 108, Reed-Solomon FEC (RS-FEC) on 25g links";
           }
           enum "fec161" {
             description "IEEE 802.3ck Clause 161 for 100G electrical links";
           }
           enum "fec-etc" {
             description "ETC fec based on IEEE 802.3 Clause 119 for 800G links";
           }
           enum "fec172" {
             description "IEEE 802.3dj Clause 172, RS-FEC for 800G links";
           }
         }
       }
       container speed {
         description "Specify speed";
         choice automatic {
           case case_1 {
             container auto-negotiation {
               presence "enable auto-negotiation";
               junos:cli-feature "oneliner";
               description "Enable auto-negotiation";
               leaf auto-negotiate-10-100 {
                 description "Limits the auto-negotiation to 10m/100m only";
                 type empty;
               }
             }
           }
           case case_2 {
             leaf ethernet-10m {
               description "10Mbps";
               type empty;
             }
           }
           case case_3 {
             leaf ethernet-100m {
               description "100Mbps";
               type empty;
             }
           }
           case case_4 {
             leaf ethernet-1g {
               description "1Gbps";
               type empty;
             }
           }
           case case_5 {
             leaf ethernet-10g {
               description "10Gbps";
               type empty;
             }
           }
         }
       }
       container ieee-802.3ad {
         junos:must "(!(\"system autoinstallation\"))";
         junos:must-message "incompatible with 'system autoinstallation'";
         junos:cli-feature "oneliner-plus";
         description "IEEE 802.3ad";
         uses apply-advanced;
         container lacp {
           description "Link Aggregation Control Protocol configuration";
           uses apply-advanced;
           leaf force-up {
             description "Keep the port up in absence of received LACPDU";
             type empty;
           }
           leaf port-priority {
             description "Priority of the port (0 ... 65535)";
             type union {
               type uint16;
               type string {
                 pattern "<.*>|$.*";
               }
             }
           }
         }
         leaf bundle {
           description "Join an aggregated Ethernet interface";
           junos:cli-feature "nokeyword";
           junos:must "(!(\"class-of-service interfaces ${interface} dynamic-threshold-profile\"))";
           junos:must-message "dynamic-threshold-profile config cannot be applied on ae child";
           junos:must "(!(any \"class-of-service interfaces ${interface} unit <*> rewrite-rules\"))";
           junos:must-message "rewrite config can not be applied on ae child";
           junos:must "(!(any \"class-of-service interfaces ${interface} unit <*> classifiers\"))";
           junos:must-message "classifier config can not be applied on ae child";
           junos:must "(!(any \"class-of-service interfaces ${interface} unit <*> output-traffic-control-profile\"))";
           junos:must-message "output-traffic-control-profile config can not be applied on ae child";
           junos:must "(!(\"class-of-service interfaces ${interface} output-traffic-control-profile\"))";
           junos:must-message "output-traffic-control-profile config can not be applied on ae child";
           junos:must "(!(\"class-of-service interfaces ${interface} shaping-rate\"))";
           junos:must-message "shaping-rate config can not be applied on ae child";
           junos:must "(!(\"class-of-service interfaces ${interface} scheduler-map\"))";
           junos:must-message "scheduler-map config can not be applied on ae child";
           junos:must "(!(\".. .. .. gigether-options 802.3ad\"))";
           junos:must-message "Member link cannot be a part of multiple aggregation group";
           junos:must "(!(\".. .. .. vlan-offload\"))";
           junos:must-message "ae child device vlan-offload is not allowed";
           junos:must "(!(\".. .. .. flow-control\"))";
           junos:must-message "Setting flow-control on ae child device is not allowed";
           junos:must "(!(\".. .. .. mtu\"))";
           junos:must-message "Setting mtu on ae child device is not allowed";
           junos:must "(!(\".. .. .. vlan-vci-tagging\"))";
           junos:must-message "ae child device vlan-vci-tagging is not allowed";
           junos:must "(!(\".. .. .. stacked-vlan-tagging\"))";
           junos:must-message "ae child device stacked-vlan-tagging is not allowed";
           junos:must "(!(\".. .. .. flexible-vlan-tagging\"))";
           junos:must-message "ae child device flexible-vlan-tagging is not allowed";
           junos:must "(!(\".. .. .. vlan-tagging\"))";
           junos:must-message "ae child device vlan-tagging is not allowed";
           junos:must "(!(\".. .. .. passive-monitor-mode\"))";
           junos:must-message "802.3ad not valid for passive-monitor-mode";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
         container link-protection-sub-group {
           description "Link Protection subgroup configuration";
           uses apply-advanced;
           leaf subgroup-name {
             description "Name of the subgroup";
             junos:cli-feature "nokeyword";
             type string {
               length "2 .. 64";
             }
           }
         }
         leaf port-priority {
           description "Link protection Priority of the port (0 ... 65535)";
           type union {
             type uint16;
             type string {
               pattern "<.*>|$.*";
             }
           }
         }
       }
       leaf ieee-802-3az-eee {
         description "IEEE 802.3az Energy Efficient Ethernet(EEE)";
         type empty;
       }
       leaf autostate-exclude {
         description "Interface will not contribute to IRB state";
         type empty;
       }
     }
     container fibrechannel-options {
       description "Fibre Channel interface-specific options";
       uses apply-advanced;
       choice loopback-choice {
         leaf loopback {
           description "Enable loopback";
           type empty;
         }
         leaf no-loopback {
           description "Don't enable loopback";
           type empty;
         }
       }
       leaf bb-sc-n {
         description "B2B state change number";
         type union {
           type string {
             pattern "<.*>|$.*";
           }
           type uint16 {
             range "0 .. 15";
           }
         }
       }
       leaf speed {
         description "Specify speed";
         type enumeration {
           enum "auto-negotiation" {
             description "Enable auto-negotiation";
           }
           enum "1g" {
             description "1Gbps";
           }
           enum "2g" {
             description "2Gbps";
           }
           enum "4g" {
             description "4Gbps";
           }
           enum "8g" {
             description "8Gbps";
           }
         }
       }
     }
     container gigether-options {
       description "Gigabit Ethernet interface-specific options";
       uses apply-advanced;
       choice loopback-choice {
         leaf loopback {
           description "Enable loopback";
           type empty;
         }
         leaf no-loopback {
           description "Don't enable loopback";
           type empty;
         }
       }
       leaf loopback-remote {
         description "Enable remote loopback";
         junos:must "(!(\".. .. optics-options loopback\"))";
         junos:must-message "'optics-options loopback' and loopback-remote are mutually exclusive";
         junos:must "(!(\".. loopback\"))";
         junos:must-message "loopback and loopback-remote are mutually exclusive";
         type empty;
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       choice auto_negotiation_option {
         case case_1 {
           leaf no-auto-negotiation {
             description "Disable auto-negotiation";
             type empty;
           }
         }
         case case_2 {
           container auto-negotiation {
             presence "enable auto-negotiation";
             junos:cli-feature "oneliner";
             description "Enable auto-negotiation";
             leaf remote-fault {
               type enumeration {
                 enum "local-interface-offline" {
                   description "Disable local interface";
                 }
                 enum "local-interface-online" {
                   description "Enable local interface";
                 }
               }
             }
           }
         }
       }
       leaf asynchronous-notification {
         description "Enable sending asynchronous notification to peer on CCC-down";
         type empty;
       }
       list source-address-filter {
         key name;
         junos:cli-feature "homogeneous";
         junos:cli-feature "oneliner";
         description "Source address filters";
         leaf name {
           description "Remote MAC address";
           junos:cli-feature "nokeyword";
           type jt:mac-addr;
         }
       }
       container ieee-802.3ad {
         junos:must "(!(\"system autoinstallation\"))";
         junos:must-message "incompatible with 'system autoinstallation'";
         junos:cli-feature "oneliner-plus";
         description "IEEE 802.3ad";
         uses apply-advanced;
         container lacp {
           description "Link Aggregation Control Protocol configuration";
           uses apply-advanced;
           leaf port-priority {
             description "Priority of the port (0 ... 65535)";
             type union {
               type uint16;
               type string {
                 pattern "<.*>|$.*";
               }
             }
           }
         }
         leaf bundle {
           description "Join an aggregated Ethernet interface";
           junos:cli-feature "nokeyword";
           junos:must "(!(any \"class-of-service interfaces ${interface} unit <*> rewrite-rules\"))";
           junos:must-message "rewrite config can not be applied on ae child";
           junos:must "(!(any \"class-of-service interfaces ${interface} unit <*> classifiers\"))";
           junos:must-message "classifier config can not be applied on ae child";
           junos:must "(!(any \"class-of-service interfaces ${interface} unit <*> output-traffic-control-profile\"))";
           junos:must-message "output-traffic-control-profile config can not be applied on ae child";
           junos:must "(!(\"class-of-service interfaces ${interface} output-traffic-control-profile\"))";
           junos:must-message "output-traffic-control-profile config can not be applied on ae child";
           junos:must "(!(\"class-of-service interfaces ${interface} shaping-rate\"))";
           junos:must-message "shaping-rate config can not be applied on ae child";
           junos:must "(!(\"class-of-service interfaces ${interface} scheduler-map\"))";
           junos:must-message "scheduler-map config can not be applied on ae child";
           junos:must "(!(\".. .. .. ether-options 802.3ad\"))";
           junos:must-message "Member link cannot be a part of multiple aggregation group";
           junos:must "(!(\".. .. .. vlan-offload\"))";
           junos:must-message "ae child device vlan-offload is not allowed";
           junos:must "(!(\".. .. .. flow-control\"))";
           junos:must-message "Setting flow-control on ae child device is not allowed";
           junos:must "(!(\".. .. .. mtu\"))";
           junos:must-message "Setting mtu on ae child device is not allowed";
           junos:must "(!(\".. .. .. vlan-vci-tagging\"))";
           junos:must-message "ae child device vlan-vci-tagging is not allowed";
           junos:must "(!(\".. .. .. stacked-vlan-tagging\"))";
           junos:must-message "ae child device stacked-vlan-tagging is not allowed";
           junos:must "(!(\".. .. .. flexible-vlan-tagging\"))";
           junos:must-message "ae child device flexible-vlan-tagging is not allowed";
           junos:must "(!(\".. .. .. vlan-tagging\"))";
           junos:must-message "ae child device vlan-tagging is not allowed";
           junos:must "(!(\".. .. .. passive-monitor-mode\"))";
           junos:must-message "802.3ad not valid for passive-monitor-mode";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
       }
       container ethernet-switch-profile {
         description "Ethernet virtual LAN/media access control-level options";
         uses apply-advanced;
         leaf-list tag-protocol-id {
           ordered-by user;
           description "IEEE 802.1q Tag Protocol Identifier values for VLAN-tagged frames";
           type string;
         }
         container ethernet-policer-profile {
           description "Ethernet level CoS-based policer configuration";
           uses apply-advanced;
           container ieee802.1-priority-map {
             presence "enable ieee802.1-priority-map";
             description "Premium priority values for IEEE 802.1p bits";
             status deprecated;
             uses apply-advanced;
             leaf-list premium {
               ordered-by user;
               description "Premium policer priority map";
               type union {
                 type string {
                   pattern "<.*>|$.*";
                 }
                 type uint32 {
                   range "0 .. 7";
                 }
               }
             }
           }
           container input-priority-map {
             description "Input policer priority map";
             uses cos_policer_input_priority_map;
           }
           container output-priority-map {
             description "Output policer priority map";
             uses cos_policer_output_priority_map;
           }
           list policer {
             key name;
             ordered-by user;
             description "Policer template definition";
             uses cos_policer;
           }
         }
         container accept-from {
           description "Accept traffic from or to specified remote MAC";
           status deprecated;
           uses apply-advanced;
           list mac-address {
             key name;
             description "Remote MAC";
             uses mac_list;
           }
         }
         choice reject-the-rest-choice {
           leaf reject-the-rest {
             description "Accept traffic from only the specified MAC addresses";
             status deprecated;
             type empty;
           }
           leaf no-reject-the-rest {
             description "Don't accept traffic from only the specified MAC addresses";
             status deprecated;
             type empty;
           }
         }
         leaf mac-learn-enable {
           description "Learn MAC addresses dynamically";
           type empty;
         }
       }
       container mpls {
         description "MPLS options";
         uses mpls_ifd_options;
       }
       leaf ignore-l3-incompletes {
         description "Ignore L3 incomplete errors";
         type empty;
       }
       leaf no-auto-mdix {
         description "Disable auto MDI/MDIX";
         type empty;
       }
       leaf ieee-802-3az-eee {
         description "IEEE 802.3az Energy Efficient Ethernet(EEE)";
         type empty;
       }
       leaf fec {
         description "Forward Error Correction mode";
         type enumeration {
           enum "none" {
             description "FEC disabled";
           }
           enum "fec91" {
             description "IEEE 802.3bj Clause 91, Reed-Solomon FEC (RS-FEC)";
           }
           enum "fec74" {
             description "FEC74 enabled";
           }
           enum "fec108" {
             description "IEEE 802.3by Clause 108, Reed-Solomon FEC (RS-FEC) on 25g links";
           }
           enum "fec161" {
             description "IEEE 802.3ck Clause 161 for 100G electrical links";
           }
         }
       }
     }
     container optics-options {
       description "Optics options";
       uses apply-advanced;
       leaf wavelength {
         description "Wavelength of the optics (nanometers) for 50Ghz/100Ghz spacing";
         type enumeration {
           enum "1611.79" {
             description "1611.79 nm/186.000000 THz 3.125/6.25/12.5/50/75/100GHz spacing";
           }
           enum "1611.76" {
             description "1611.76 nm/186.003125 THz 3.125GHz spacing";
           }
           enum "1611.73" {
             description "1611.73 nm/186.006250 THz 3.125/6.25GHz spacing";
           }
           enum "1611.71" {
             description "1611.71 nm/186.009375 THz 3.125GHz spacing";
           }
           enum "1611.68" {
             description "1611.68 nm/186.012500 THz 3.125/6.25/12.5GHz spacing";
           }
           enum "1611.65" {
             description "1611.65 nm/186.015625 THz 3.125GHz spacing";
           }
           enum "1611.62" {
             description "1611.62 nm/186.018750 THz 3.125/6.25GHz spacing";
           }
           enum "1611.60" {
             description "1611.60 nm/186.021875 THz 3.125GHz spacing";
           }
           enum "1611.57" {
             description "1611.57 nm/186.025000 THz 3.125/6.25/12.5GHz spacing";
           }
           enum "1611.54" {
             description "1611.54 nm/186.028125 THz 3.125GHz spacing";
           }
           enum "1611.52" {
             description "1611.52 nm/186.031250 THz 3.125/6.25GHz spacing";
           }
           enum "1611.49" {
             description "1611.49 nm/186.034375 THz 3.125GHz spacing";
           }
           enum "1611.46" {
             description "1611.46 nm/186.037500 THz 3.125/6.25/12.5GHz spacing";
           }
           enum "1611.44" {
             description "1611.44 nm/186.040625 THz 3.125GHz spacing";
           }
           enum "1611.41" {
             description "1611.41 nm/186.043750 THz 3.125/6.25GHz spacing";
           }
           enum "1611.38" {
             description "1611.38 nm/186.046875 THz 3.125GHz spacing";
           }
           enum "1611.35" {
             description "1611.35 nm/186.050000 THz 3.125/6.25/12.5/50/75GHz spacing";
           }
           enum "1611.33" {
             description "1611.33 nm/186.053125 THz 3.125GHz spacing";
           }
           enum "1611.30" {
             description "1611.30 nm/186.056250 THz 3.125/6.25GHz spacing";
           }
           enum "1611.27" {
             description "1611.27 nm/186.059375 THz 3.125GHz spacing";
           }
           enum "1611.25" {
             description "1611.25 nm/186.062500 THz 3.125/6.25/12.5GHz spacing";
           }
           enum "1611.22" {
             description "1611.22 nm/186.065625 THz 3.125GHz spacing";
           }
           enum "1611.19" {
             description "1611.19 nm/186.068750 THz 3.125/6.25GHz spacing";
           }
           enum "1611.16" {
             description "1611.16 nm/186.071875 THz 3.125GHz spacing";
           }
           enum "1611.14" {
             description "1611.14 nm/186.075000 THz 3.125/6.25/12.5GHz spacing";
           }
           enum "1611.11" {
             description "1611.11 nm/186.078125 THz 3.125GHz spacing";
           }
           enum "1611.08" {
             description "1611.08 nm/186.081250 THz 3.125/6.25GHz spacing";
           }
           enum "1611.06" {
             description "1611.06 nm/186.084375 THz 3.125GHz spacing";
           }
           enum "1611.03" {
             description "1611.03 nm/186.087500 THz 3.125/6.25/12.5GHz spacing";
           }
           enum "1611.00" {
             description "1611.00 nm/186.090625 THz 3.125GHz spacing";
           }
           enum "1610.98" {
             description "1610.98 nm/186.093750 THz 3.125/6.25GHz spacing";
           }
           enum "1610.95" {
             description "1610.95 nm/186.096875 THz 3.125GHz spacing";
           }
           enum "1610.92" {
             description "1610.92 nm/186.100000 THz 3.125/6.25/12.5/100GHz spacing";
           }
           enum "1610.89" {
             description "1610.89 nm/186.103125 THz 3.125GHz spacing";
           }
           enum "1610.87" {
             description "1610.87 nm/186.106250 THz 3.125/6.25GHz spacing";
           }
           enum "1610.84" {
             description "1610.84 nm/186.109375 THz 3.125GHz spacing";
           }
           enum "1610.81" {
             description "1610.81 nm/186.112500 THz 3.125/6.25/12.5GHz spacing";
           }
           enum "1610.79" {
             description "1610.79 nm/186.115625 THz 3.125GHz spacing";
           }
           enum "1610.76" {
             description "1610.76 nm/186.118750 THz 3.125/6.25GHz spacing";
           }
           enum "1610.73" {
             description "1610.73 nm/186.121875 THz 3.125GHz spacing";
           }
           enum "1610.70" {
             description "1610.70 nm/186.125000 THz 3.125/6.25/12.5/75GHz spacing";
           }
           enum "1610.68" {
             description "1610.68 nm/186.128125 THz 3.125GHz spacing";
           }
           enum "1610.65" {
             description "1610.65 nm/186.131250 THz 3.125/6.25GHz spacing";
           }
           enum "1610.62" {
             description "1610.62 nm/186.134375 THz 3.125GHz spacing";
           }
           enum "1610.60" {
             description "1610.60 nm/186.137500 THz 3.125/6.25/12.5GHz spacing";
           }
           enum "1610.57" {
             description "1610.57 nm/186.140625 THz 3.125GHz spacing";
           }
           enum "1610.54" {
             description "1610.54 nm/186.143750 THz 3.125/6.25GHz spacing";
           }
           enum "1610.52" {
             description "1610.52 nm/186.146875 THz 3.125GHz spacing";
           }
           enum "1610.49" {
             description "1610.49 nm/186.150000 THz 3.125/6.25/12.5/50GHz spacing";
           }
           enum "1610.46" {
             description "1610.46 nm/186.153125 THz 3.125GHz spacing";
           }
           enum "1610.43" {
             description "1610.43 nm/186.156250 THz 3.125/6.25GHz spacing";
           }
           enum "1610.41" {
             description "1610.41 nm/186.159375 THz 3.125GHz spacing";
           }
           enum "1610.38" {
             description "1610.38 nm/186.162500 THz 3.125/6.25/12.5GHz spacing";
           }
           enum "1610.35" {
             description "1610.35 nm/186.165625 THz 3.125GHz spacing";
           }
           enum "1610.33" {
             description "1610.33 nm/186.168750 THz 3.125/6.25GHz spacing";
           }
           enum "1610.30" {
             description "1610.30 nm/186.171875 THz 3.125GHz spacing";
           }
           enum "1610.27" {
             description "1610.27 nm/186.175000 THz 3.125/6.25/12.5GHz spacing";
           }
           enum "1610.25" {
             description "1610.25 nm/186.178125 THz 3.125GHz spacing";
           }
           enum "1610.22" {
             description "1610.22 nm/186.181250 THz 3.125/6.25GHz spacing";
           }
           enum "1610.19" {
             description "1610.19 nm/186.184375 THz 3.125GHz spacing";
           }
           enum "1610.16" {
             description "1610.16 nm/186.187500 THz 3.125/6.25/12.5GHz spacing";
           }
           enum "1610.14" {
             description "1610.14 nm/186.190625 THz 3.125GHz spacing";
           }
           enum "1610.11" {
             description "1610.11 nm/186.193750 THz 3.125/6.25GHz spacing";
           }
           enum "1610.08" {
             description "1610.08 nm/186.196875 THz 3.125GHz spacing";
           }
           enum "1610.06" {
             description "1610.06 nm/186.200000 THz 3.125/6.25/12.5/100GHz spacing";
           }
           enum "1610.03" {
             description "1610.03 nm/186.203125 THz 3.125GHz spacing";
           }
           enum "1610.00" {
             description "1610.00 nm/186.206250 THz 3.125/6.25GHz spacing";
           }
           enum "1609.98" {
             description "1609.98 nm/186.209375 THz 3.125GHz spacing";
           }
           enum "1609.95" {
             description "1609.95 nm/186.212500 THz 3.125/6.25/12.5GHz spacing";
           }
           enum "1609.92" {
             description "1609.92 nm/186.215625 THz 3.125GHz spacing";
           }
           enum "1609.89" {
             description "1609.89 nm/186.218750 THz 3.125/6.25GHz spacing";
           }
           enum "1609.87" {
             description "1609.87 nm/186.221875 THz 3.125GHz spacing";
           }
           enum "1609.84" {
             description "1609.84 nm/186.225000 THz 3.125/6.25/12.5GHz spacing";
           }
           enum "1609.81" {
             description "1609.81 nm/186.228125 THz 3.125GHz spacing";
           }
           enum "1609.79" {
             description "1609.79 nm/186.231250 THz 3.125/6.25GHz spacing";
           }
           enum "1609.76" {
             description "1609.76 nm/186.234375 THz 3.125GHz spacing";
           }
           enum "1609.73" {
             description "1609.73 nm/186.237500 THz 3.125/6.25/12.5GHz spacing";
           }
           enum "1609.70" {
             description "1609.70 nm/186.240625 THz 3.125GHz spacing";
           }
           enum "1609.68" {
             description "1609.68 nm/186.243750 THz 3.125/6.25GHz spacing";
           }
           enum "1609.65" {
             description "1609.65 nm/186.246875 THz 3.125GHz spacing";
           }
           enum "1609.62" {
             description "1609.62 nm/186.250000 THz 3.125/6.25/12.5/50GHz spacing";
           }
           enum "1609.60" {
             description "1609.60 nm/186.253125 THz 3.125GHz spacing";
           }
           enum "1609.57" {
             description "1609.57 nm/186.256250 THz 3.125/6.25GHz spacing";
           }
           enum "1609.54" {
             description "1609.54 nm/186.259375 THz 3.125GHz spacing";
           }
           enum "1609.52" {
             description "1609.52 nm/186.262500 THz 3.125/6.25/12.5GHz spacing";
           }
           enum "1609.49" {
             description "1609.49 nm/186.265625 THz 3.125GHz spacing";
           }
           enum "1609.46" {
             description "1609.46 nm/186.268750 THz 3.125/6.25GHz spacing";
           }
           enum "1609.43" {
             description "1609.43 nm/186.271875 THz 3.125GHz spacing";
           }
           enum "1609.41" {
             description "1609.41 nm/186.275000 THz 3.125/6.25/12.5/75GHz spacing";
           }
           enum "1609.38" {
             description "1609.38 nm/186.278125 THz 3.125GHz spacing";
           }
           enum "1609.35" {
             description "1609.35 nm/186.281250 THz 3.125/6.25GHz spacing";
           }
           enum "1609.33" {
             description "1609.33 nm/186.284375 THz 3.125GHz spacing";
           }
           enum "1609.30" {
             description "1609.30 nm/186.287500 THz 3.125/6.25/12.5GHz spacing";
           }
           enum "1609.27" {
             description "1609.27 nm/186.290625 THz 3.125GHz spacing";
           }
           enum "1609.25" {
             description "1609.25 nm/186.293750 THz 3.125/6.25GHz spacing";
           }
           enum "1609.22" {
             description "1609.22 nm/186.296875 THz 3.125GHz spacing";
           }
           enum "1609.19" {
             description "1609.19 nm/186.300000 THz 3.125/6.25/12.5/50/75/100GHz spacing";
           }
           enum "1609.16" {
             description "1609.16 nm/186.303125 THz 3.125GHz spacing";
           }
           enum "1609.14" {
             description "1609.14 nm/186.306250 THz 3.125/6.25GHz spacing";
           }
           enum "1609.11" {
             description "1609.11 nm/186.309375 THz 3.125GHz spacing";
           }
           enum "1609.08" {
             description "1609.08 nm/186.312500 THz 3.125/6.25/12.5GHz spacing";
           }
           enum "1609.06" {
             description "1609.06 nm/186.315625 THz 3.125GHz spacing";
           }
           enum "1609.03" {
             description "1609.03 nm/186.318750 THz 3.125/6.25GHz spacing";
           }
           enum "1609.00" {
             description "1609.00 nm/186.321875 THz 3.125GHz spacing";
           }
           enum "1608.98" {
             description "1608.98 nm/186.325000 THz 3.125/6.25/12.5GHz spacing";
           }
           enum "1608.95" {
             description "1608.95 nm/186.328125 THz 3.125GHz spacing";
           }
           enum "1608.92" {
             description "1608.92 nm/186.331250 THz 3.125/6.25GHz spacing";
           }
           enum "1608.90" {
             description "1608.90 nm/186.334375 THz 3.125GHz spacing";
           }
           enum "1608.87" {
             description "1608.87 nm/186.337500 THz 3.125/6.25/12.5GHz spacing";
           }
           enum "1608.84" {
             description "1608.84 nm/186.340625 THz 3.125GHz spacing";
           }
           enum "1608.81" {
             description "1608.81 nm/186.343750 THz 3.125/6.25GHz spacing";
           }
           enum "1608.79" {
             description "1608.79 nm/186.346875 THz 3.125GHz spacing";
           }
           enum "1608.76" {
             description "1608.76 nm/186.350000 THz 3.125/6.25/12.5/50/75GHz spacing";
           }
           enum "1608.73" {
             description "1608.73 nm/186.353125 THz 3.125GHz spacing";
           }
           enum "1608.71" {
             description "1608.71 nm/186.356250 THz 3.125/6.25GHz spacing";
           }
           enum "1608.68" {
             description "1608.68 nm/186.359375 THz 3.125GHz spacing";
           }
           enum "1608.65" {
             description "1608.65 nm/186.362500 THz 3.125/6.25/12.5GHz spacing";
           }
           enum "1608.63" {
             description "1608.63 nm/186.365625 THz 3.125GHz spacing";
           }
           enum "1608.60" {
             description "1608.60 nm/186.368750 THz 3.125/6.25GHz spacing";
           }
           enum "1608.57" {
             description "1608.57 nm/186.371875 THz 3.125GHz spacing";
           }
           enum "1608.54" {
             description "1608.54 nm/186.375000 THz 3.125/6.25/12.5GHz spacing";
           }
           enum "1608.52" {
             description "1608.52 nm/186.378125 THz 3.125GHz spacing";
           }
           enum "1608.49" {
             description "1608.49 nm/186.381250 THz 3.125/6.25GHz spacing";
           }
           enum "1608.46" {
             description "1608.46 nm/186.384375 THz 3.125GHz spacing";
           }
           enum "1608.44" {
             description "1608.44 nm/186.387500 THz 3.125/6.25/12.5GHz spacing";
           }
           enum "1608.41" {
             description "1608.41 nm/186.390625 THz 3.125GHz spacing";
           }
           enum "1608.38" {
             description "1608.38 nm/186.393750 THz 3.125/6.25GHz spacing";
           }
           enum "1608.36" {
             description "1608.36 nm/186.396875 THz 3.125GHz spacing";
           }
           enum "1608.33" {
             description "1608.33 nm/186.400000 THz 3.125/6.25/12.5/100GHz spacing";
           }
           enum "1608.30" {
             description "1608.30 nm/186.403125 THz 3.125GHz spacing";
           }
           enum "1608.27" {
             description "1608.27 nm/186.406250 THz 3.125/6.25GHz spacing";
           }
           enum "1608.25" {
             description "1608.25 nm/186.409375 THz 3.125GHz spacing";
           }
           enum "1608.22" {
             description "1608.22 nm/186.412500 THz 3.125/6.25/12.5GHz spacing";
           }
           enum "1608.19" {
             description "1608.19 nm/186.415625 THz 3.125GHz spacing";
           }
           enum "1608.17" {
             description "1608.17 nm/186.418750 THz 3.125/6.25GHz spacing";
           }
           enum "1608.14" {
             description "1608.14 nm/186.421875 THz 3.125GHz spacing";
           }
           enum "1608.11" {
             description "1608.11 nm/186.425000 THz 3.125/6.25/12.5/75GHz spacing";
           }
           enum "1608.09" {
             description "1608.09 nm/186.428125 THz 3.125GHz spacing";
           }
           enum "1608.06" {
             description "1608.06 nm/186.431250 THz 3.125/6.25GHz spacing";
           }
           enum "1608.03" {
             description "1608.03 nm/186.434375 THz 3.125GHz spacing";
           }
           enum "1608.01" {
             description "1608.01 nm/186.437500 THz 3.125/6.25/12.5GHz spacing";
           }
           enum "1607.98" {
             description "1607.98 nm/186.440625 THz 3.125GHz spacing";
           }
           enum "1607.95" {
             description "1607.95 nm/186.443750 THz 3.125/6.25GHz spacing";
           }
           enum "1607.92" {
             description "1607.92 nm/186.446875 THz 3.125GHz spacing";
           }
           enum "1607.90" {
             description "1607.90 nm/186.450000 THz 3.125/6.25/12.5/50GHz spacing";
           }
           enum "1607.87" {
             description "1607.87 nm/186.453125 THz 3.125GHz spacing";
           }
           enum "1607.84" {
             description "1607.84 nm/186.456250 THz 3.125/6.25GHz spacing";
           }
           enum "1607.82" {
             description "1607.82 nm/186.459375 THz 3.125GHz spacing";
           }
           enum "1607.79" {
             description "1607.79 nm/186.462500 THz 3.125/6.25/12.5GHz spacing";
           }
           enum "1607.76" {
             description "1607.76 nm/186.465625 THz 3.125GHz spacing";
           }
           enum "1607.74" {
             description "1607.74 nm/186.468750 THz 3.125/6.25GHz spacing";
           }
           enum "1607.71" {
             description "1607.71 nm/186.471875 THz 3.125GHz spacing";
           }
           enum "1607.68" {
             description "1607.68 nm/186.475000 THz 3.125/6.25/12.5GHz spacing";
           }
           enum "1607.65" {
             description "1607.65 nm/186.478125 THz 3.125GHz spacing";
           }
           enum "1607.63" {
             description "1607.63 nm/186.481250 THz 3.125/6.25GHz spacing";
           }
           enum "1607.60" {
             description "1607.60 nm/186.484375 THz 3.125GHz spacing";
           }
           enum "1607.57" {
             description "1607.57 nm/186.487500 THz 3.125/6.25/12.5GHz spacing";
           }
           enum "1607.55" {
             description "1607.55 nm/186.490625 THz 3.125GHz spacing";
           }
           enum "1607.52" {
             description "1607.52 nm/186.493750 THz 3.125/6.25GHz spacing";
           }
           enum "1607.49" {
             description "1607.49 nm/186.496875 THz 3.125GHz spacing";
           }
           enum "1607.47" {
             description "1607.47 nm/186.500000 THz 3.125/6.25/12.5/100GHz spacing";
           }
           enum "1607.44" {
             description "1607.44 nm/186.503125 THz 3.125GHz spacing";
           }
           enum "1607.41" {
             description "1607.41 nm/186.506250 THz 3.125/6.25GHz spacing";
           }
           enum "1607.39" {
             description "1607.39 nm/186.509375 THz 3.125GHz spacing";
           }
           enum "1607.36" {
             description "1607.36 nm/186.512500 THz 3.125/6.25/12.5GHz spacing";
           }
           enum "1607.33" {
             description "1607.33 nm/186.515625 THz 3.125GHz spacing";
           }
           enum "1607.30" {
             description "1607.30 nm/186.518750 THz 3.125/6.25GHz spacing";
           }
           enum "1607.28" {
             description "1607.28 nm/186.521875 THz 3.125GHz spacing";
           }
           enum "1607.25" {
             description "1607.25 nm/186.525000 THz 3.125/6.25/12.5GHz spacing";
           }
           enum "1607.22" {
             description "1607.22 nm/186.528125 THz 3.125GHz spacing";
           }
           enum "1607.20" {
             description "1607.20 nm/186.531250 THz 3.125/6.25GHz spacing";
           }
           enum "1607.17" {
             description "1607.17 nm/186.534375 THz 3.125GHz spacing";
           }
           enum "1607.14" {
             description "1607.14 nm/186.537500 THz 3.125/6.25/12.5GHz spacing";
           }
           enum "1607.12" {
             description "1607.12 nm/186.540625 THz 3.125GHz spacing";
           }
           enum "1607.09" {
             description "1607.09 nm/186.543750 THz 3.125/6.25GHz spacing";
           }
           enum "1607.06" {
             description "1607.06 nm/186.546875 THz 3.125GHz spacing";
           }
           enum "1607.04" {
             description "1607.04 nm/186.550000 THz 3.125/6.25/12.5/50GHz spacing";
           }
           enum "1607.01" {
             description "1607.01 nm/186.553125 THz 3.125GHz spacing";
           }
           enum "1606.98" {
             description "1606.98 nm/186.556250 THz 3.125/6.25GHz spacing";
           }
           enum "1606.95" {
             description "1606.95 nm/186.559375 THz 3.125GHz spacing";
           }
           enum "1606.93" {
             description "1606.93 nm/186.562500 THz 3.125/6.25/12.5GHz spacing";
           }
           enum "1606.90" {
             description "1606.90 nm/186.565625 THz 3.125GHz spacing";
           }
           enum "1606.87" {
             description "1606.87 nm/186.568750 THz 3.125/6.25GHz spacing";
           }
           enum "1606.85" {
             description "1606.85 nm/186.571875 THz 3.125GHz spacing";
           }
           enum "1606.82" {
             description "1606.82 nm/186.575000 THz 3.125/6.25/12.5/75GHz spacing";
           }
           enum "1606.79" {
             description "1606.79 nm/186.578125 THz 3.125GHz spacing";
           }
           enum "1606.77" {
             description "1606.77 nm/186.581250 THz 3.125/6.25GHz spacing";
           }
           enum "1606.74" {
             description "1606.74 nm/186.584375 THz 3.125GHz spacing";
           }
           enum "1606.71" {
             description "1606.71 nm/186.587500 THz 3.125/6.25/12.5GHz spacing";
           }
           enum "1606.69" {
             description "1606.69 nm/186.590625 THz 3.125GHz spacing";
           }
           enum "1606.66" {
             description "1606.66 nm/186.593750 THz 3.125/6.25GHz spacing";
           }
           enum "1606.63" {
             description "1606.63 nm/186.596875 THz 3.125GHz spacing";
           }
           enum "1606.60" {
             description "1606.60 nm/186.600000 THz 3.125/6.25/12.5/50/75/100GHz spacing";
           }
           enum "1606.58" {
             description "1606.58 nm/186.603125 THz 3.125GHz spacing";
           }
           enum "1606.55" {
             description "1606.55 nm/186.606250 THz 3.125/6.25GHz spacing";
           }
           enum "1606.52" {
             description "1606.52 nm/186.609375 THz 3.125GHz spacing";
           }
           enum "1606.50" {
             description "1606.50 nm/186.612500 THz 3.125/6.25/12.5GHz spacing";
           }
           enum "1606.47" {
             description "1606.47 nm/186.615625 THz 3.125GHz spacing";
           }
           enum "1606.44" {
             description "1606.44 nm/186.618750 THz 3.125/6.25GHz spacing";
           }
           enum "1606.42" {
             description "1606.42 nm/186.621875 THz 3.125GHz spacing";
           }
           enum "1606.39" {
             description "1606.39 nm/186.625000 THz 3.125/6.25/12.5GHz spacing";
           }
           enum "1606.36" {
             description "1606.36 nm/186.628125 THz 3.125GHz spacing";
           }
           enum "1606.34" {
             description "1606.34 nm/186.631250 THz 3.125/6.25GHz spacing";
           }
           enum "1606.31" {
             description "1606.31 nm/186.634375 THz 3.125GHz spacing";
           }
           enum "1606.28" {
             description "1606.28 nm/186.637500 THz 3.125/6.25/12.5GHz spacing";
           }
           enum "1606.26" {
             description "1606.26 nm/186.640625 THz 3.125GHz spacing";
           }
           enum "1606.23" {
             description "1606.23 nm/186.643750 THz 3.125/6.25GHz spacing";
           }
           enum "1606.20" {
             description "1606.20 nm/186.646875 THz 3.125GHz spacing";
           }
           enum "1606.17" {
             description "1606.17 nm/186.650000 THz 3.125/6.25/12.5/50/75GHz spacing";
           }
           enum "1606.15" {
             description "1606.15 nm/186.653125 THz 3.125GHz spacing";
           }
           enum "1606.12" {
             description "1606.12 nm/186.656250 THz 3.125/6.25GHz spacing";
           }
           enum "1606.09" {
             description "1606.09 nm/186.659375 THz 3.125GHz spacing";
           }
           enum "1606.07" {
             description "1606.07 nm/186.662500 THz 3.125/6.25/12.5GHz spacing";
           }
           enum "1606.04" {
             description "1606.04 nm/186.665625 THz 3.125GHz spacing";
           }
           enum "1606.01" {
             description "1606.01 nm/186.668750 THz 3.125/6.25GHz spacing";
           }
           enum "1605.99" {
             description "1605.99 nm/186.671875 THz 3.125GHz spacing";
           }
           enum "1605.96" {
             description "1605.96 nm/186.675000 THz 3.125/6.25/12.5GHz spacing";
           }
           enum "1605.93" {
             description "1605.93 nm/186.678125 THz 3.125GHz spacing";
           }
           enum "1605.91" {
             description "1605.91 nm/186.681250 THz 3.125/6.25GHz spacing";
           }
           enum "1605.88" {
             description "1605.88 nm/186.684375 THz 3.125GHz spacing";
           }
           enum "1605.85" {
             description "1605.85 nm/186.687500 THz 3.125/6.25/12.5GHz spacing";
           }
           enum "1605.82" {
             description "1605.82 nm/186.690625 THz 3.125GHz spacing";
           }
           enum "1605.80" {
             description "1605.80 nm/186.693750 THz 3.125/6.25GHz spacing";
           }
           enum "1605.77" {
             description "1605.77 nm/186.696875 THz 3.125GHz spacing";
           }
           enum "1605.74" {
             description "1605.74 nm/186.700000 THz 3.125/6.25/12.5/100GHz spacing";
           }
           enum "1605.72" {
             description "1605.72 nm/186.703125 THz 3.125GHz spacing";
           }
           enum "1605.69" {
             description "1605.69 nm/186.706250 THz 3.125/6.25GHz spacing";
           }
           enum "1605.66" {
             description "1605.66 nm/186.709375 THz 3.125GHz spacing";
           }
           enum "1605.64" {
             description "1605.64 nm/186.712500 THz 3.125/6.25/12.5GHz spacing";
           }
           enum "1605.61" {
             description "1605.61 nm/186.715625 THz 3.125GHz spacing";
           }
           enum "1605.58" {
             description "1605.58 nm/186.718750 THz 3.125/6.25GHz spacing";
           }
           enum "1605.56" {
             description "1605.56 nm/186.721875 THz 3.125GHz spacing";
           }
           enum "1605.53" {
             description "1605.53 nm/186.725000 THz 3.125/6.25/12.5/75GHz spacing";
           }
           enum "1605.50" {
             description "1605.50 nm/186.728125 THz 3.125GHz spacing";
           }
           enum "1605.48" {
             description "1605.48 nm/186.731250 THz 3.125/6.25GHz spacing";
           }
           enum "1605.45" {
             description "1605.45 nm/186.734375 THz 3.125GHz spacing";
           }
           enum "1605.42" {
             description "1605.42 nm/186.737500 THz 3.125/6.25/12.5GHz spacing";
           }
           enum "1605.39" {
             description "1605.39 nm/186.740625 THz 3.125GHz spacing";
           }
           enum "1605.37" {
             description "1605.37 nm/186.743750 THz 3.125/6.25GHz spacing";
           }
           enum "1605.34" {
             description "1605.34 nm/186.746875 THz 3.125GHz spacing";
           }
           enum "1605.31" {
             description "1605.31 nm/186.750000 THz 3.125/6.25/12.5/50GHz spacing";
           }
           enum "1605.29" {
             description "1605.29 nm/186.753125 THz 3.125GHz spacing";
           }
           enum "1605.26" {
             description "1605.26 nm/186.756250 THz 3.125/6.25GHz spacing";
           }
           enum "1605.23" {
             description "1605.23 nm/186.759375 THz 3.125GHz spacing";
           }
           enum "1605.21" {
             description "1605.21 nm/186.762500 THz 3.125/6.25/12.5GHz spacing";
           }
           enum "1605.18" {
             description "1605.18 nm/186.765625 THz 3.125GHz spacing";
           }
           enum "1605.15" {
             description "1605.15 nm/186.768750 THz 3.125/6.25GHz spacing";
           }
           enum "1605.13" {
             description "1605.13 nm/186.771875 THz 3.125GHz spacing";
           }
           enum "1605.10" {
             description "1605.10 nm/186.775000 THz 3.125/6.25/12.5GHz spacing";
           }
           enum "1605.07" {
             description "1605.07 nm/186.778125 THz 3.125GHz spacing";
           }
           enum "1605.05" {
             description "1605.05 nm/186.781250 THz 3.125/6.25GHz spacing";
           }
           enum "1605.02" {
             description "1605.02 nm/186.784375 THz 3.125GHz spacing";
           }
           enum "1604.99" {
             description "1604.99 nm/186.787500 THz 3.125/6.25/12.5GHz spacing";
           }
           enum "1604.97" {
             description "1604.97 nm/186.790625 THz 3.125GHz spacing";
           }
           enum "1604.94" {
             description "1604.94 nm/186.793750 THz 3.125/6.25GHz spacing";
           }
           enum "1604.91" {
             description "1604.91 nm/186.796875 THz 3.125GHz spacing";
           }
           enum "1604.88" {
             description "1604.88 nm/186.800000 THz 3.125/6.25/12.5/100GHz spacing";
           }
           enum "1604.86" {
             description "1604.86 nm/186.803125 THz 3.125GHz spacing";
           }
           enum "1604.83" {
             description "1604.83 nm/186.806250 THz 3.125/6.25GHz spacing";
           }
           enum "1604.80" {
             description "1604.80 nm/186.809375 THz 3.125GHz spacing";
           }
           enum "1604.78" {
             description "1604.78 nm/186.812500 THz 3.125/6.25/12.5GHz spacing";
           }
           enum "1604.75" {
             description "1604.75 nm/186.815625 THz 3.125GHz spacing";
           }
           enum "1604.72" {
             description "1604.72 nm/186.818750 THz 3.125/6.25GHz spacing";
           }
           enum "1604.70" {
             description "1604.70 nm/186.821875 THz 3.125GHz spacing";
           }
           enum "1604.67" {
             description "1604.67 nm/186.825000 THz 3.125/6.25/12.5GHz spacing";
           }
           enum "1604.64" {
             description "1604.64 nm/186.828125 THz 3.125GHz spacing";
           }
           enum "1604.62" {
             description "1604.62 nm/186.831250 THz 3.125/6.25GHz spacing";
           }
           enum "1604.59" {
             description "1604.59 nm/186.834375 THz 3.125GHz spacing";
           }
           enum "1604.56" {
             description "1604.56 nm/186.837500 THz 3.125/6.25/12.5GHz spacing";
           }
           enum "1604.54" {
             description "1604.54 nm/186.840625 THz 3.125GHz spacing";
           }
           enum "1604.51" {
             description "1604.51 nm/186.843750 THz 3.125/6.25GHz spacing";
           }
           enum "1604.48" {
             description "1604.48 nm/186.846875 THz 3.125GHz spacing";
           }
           enum "1604.46" {
             description "1604.46 nm/186.850000 THz 3.125/6.25/12.5/50GHz spacing";
           }
           enum "1604.43" {
             description "1604.43 nm/186.853125 THz 3.125GHz spacing";
           }
           enum "1604.40" {
             description "1604.40 nm/186.856250 THz 3.125/6.25GHz spacing";
           }
           enum "1604.37" {
             description "1604.37 nm/186.859375 THz 3.125GHz spacing";
           }
           enum "1604.35" {
             description "1604.35 nm/186.862500 THz 3.125/6.25/12.5GHz spacing";
           }
           enum "1604.32" {
             description "1604.32 nm/186.865625 THz 3.125GHz spacing";
           }
           enum "1604.29" {
             description "1604.29 nm/186.868750 THz 3.125/6.25GHz spacing";
           }
           enum "1604.27" {
             description "1604.27 nm/186.871875 THz 3.125GHz spacing";
           }
           enum "1604.24" {
             description "1604.24 nm/186.875000 THz 3.125/6.25/12.5/75GHz spacing";
           }
           enum "1604.21" {
             description "1604.21 nm/186.878125 THz 3.125GHz spacing";
           }
           enum "1604.19" {
             description "1604.19 nm/186.881250 THz 3.125/6.25GHz spacing";
           }
           enum "1604.16" {
             description "1604.16 nm/186.884375 THz 3.125GHz spacing";
           }
           enum "1604.13" {
             description "1604.13 nm/186.887500 THz 3.125/6.25/12.5GHz spacing";
           }
           enum "1604.11" {
             description "1604.11 nm/186.890625 THz 3.125GHz spacing";
           }
           enum "1604.08" {
             description "1604.08 nm/186.893750 THz 3.125/6.25GHz spacing";
           }
           enum "1604.05" {
             description "1604.05 nm/186.896875 THz 3.125GHz spacing";
           }
           enum "1604.03" {
             description "1604.03 nm/186.900000 THz 3.125/6.25/12.5/50/75/100GHz spacing";
           }
           enum "1604.00" {
             description "1604.00 nm/186.903125 THz 3.125GHz spacing";
           }
           enum "1603.97" {
             description "1603.97 nm/186.906250 THz 3.125/6.25GHz spacing";
           }
           enum "1603.95" {
             description "1603.95 nm/186.909375 THz 3.125GHz spacing";
           }
           enum "1603.92" {
             description "1603.92 nm/186.912500 THz 3.125/6.25/12.5GHz spacing";
           }
           enum "1603.89" {
             description "1603.89 nm/186.915625 THz 3.125GHz spacing";
           }
           enum "1603.87" {
             description "1603.87 nm/186.918750 THz 3.125/6.25GHz spacing";
           }
           enum "1603.84" {
             description "1603.84 nm/186.921875 THz 3.125GHz spacing";
           }
           enum "1603.81" {
             description "1603.81 nm/186.925000 THz 3.125/6.25/12.5GHz spacing";
           }
           enum "1603.78" {
             description "1603.78 nm/186.928125 THz 3.125GHz spacing";
           }
           enum "1603.76" {
             description "1603.76 nm/186.931250 THz 3.125/6.25GHz spacing";
           }
           enum "1603.73" {
             description "1603.73 nm/186.934375 THz 3.125GHz spacing";
           }
           enum "1603.70" {
             description "1603.70 nm/186.937500 THz 3.125/6.25/12.5GHz spacing";
           }
           enum "1603.68" {
             description "1603.68 nm/186.940625 THz 3.125GHz spacing";
           }
           enum "1603.65" {
             description "1603.65 nm/186.943750 THz 3.125/6.25GHz spacing";
           }
           enum "1603.62" {
             description "1603.62 nm/186.946875 THz 3.125GHz spacing";
           }
           enum "1603.60" {
             description "1603.60 nm/186.950000 THz 3.125/6.25/12.5/50/75GHz spacing";
           }
           enum "1603.57" {
             description "1603.57 nm/186.953125 THz 3.125GHz spacing";
           }
           enum "1603.54" {
             description "1603.54 nm/186.956250 THz 3.125/6.25GHz spacing";
           }
           enum "1603.52" {
             description "1603.52 nm/186.959375 THz 3.125GHz spacing";
           }
           enum "1603.49" {
             description "1603.49 nm/186.962500 THz 3.125/6.25/12.5GHz spacing";
           }
           enum "1603.46" {
             description "1603.46 nm/186.965625 THz 3.125GHz spacing";
           }
           enum "1603.44" {
             description "1603.44 nm/186.968750 THz 3.125/6.25GHz spacing";
           }
           enum "1603.41" {
             description "1603.41 nm/186.971875 THz 3.125GHz spacing";
           }
           enum "1603.38" {
             description "1603.38 nm/186.975000 THz 3.125/6.25/12.5GHz spacing";
           }
           enum "1603.36" {
             description "1603.36 nm/186.978125 THz 3.125GHz spacing";
           }
           enum "1603.33" {
             description "1603.33 nm/186.981250 THz 3.125/6.25GHz spacing";
           }
           enum "1603.30" {
             description "1603.30 nm/186.984375 THz 3.125GHz spacing";
           }
           enum "1603.28" {
             description "1603.28 nm/186.987500 THz 3.125/6.25/12.5GHz spacing";
           }
           enum "1603.25" {
             description "1603.25 nm/186.990625 THz 3.125GHz spacing";
           }
           enum "1603.22" {
             description "1603.22 nm/186.993750 THz 3.125/6.25GHz spacing";
           }
           enum "1603.20" {
             description "1603.20 nm/186.996875 THz 3.125GHz spacing";
           }
           enum "1603.17" {
             description "1603.17 nm/187.000000 THz 3.125/6.25/12.5/100GHz spacing";
           }
           enum "1603.14" {
             description "1603.14 nm/187.003125 THz 3.125GHz spacing";
           }
           enum "1603.11" {
             description "1603.11 nm/187.006250 THz 3.125/6.25GHz spacing";
           }
           enum "1603.09" {
             description "1603.09 nm/187.009375 THz 3.125GHz spacing";
           }
           enum "1603.06" {
             description "1603.06 nm/187.012500 THz 3.125/6.25/12.5GHz spacing";
           }
           enum "1603.03" {
             description "1603.03 nm/187.015625 THz 3.125GHz spacing";
           }
           enum "1603.01" {
             description "1603.01 nm/187.018750 THz 3.125/6.25GHz spacing";
           }
           enum "1602.98" {
             description "1602.98 nm/187.021875 THz 3.125GHz spacing";
           }
           enum "1602.95" {
             description "1602.95 nm/187.025000 THz 3.125/6.25/12.5/75GHz spacing";
           }
           enum "1602.93" {
             description "1602.93 nm/187.028125 THz 3.125GHz spacing";
           }
           enum "1602.90" {
             description "1602.90 nm/187.031250 THz 3.125/6.25GHz spacing";
           }
           enum "1602.87" {
             description "1602.87 nm/187.034375 THz 3.125GHz spacing";
           }
           enum "1602.85" {
             description "1602.85 nm/187.037500 THz 3.125/6.25/12.5GHz spacing";
           }
           enum "1602.82" {
             description "1602.82 nm/187.040625 THz 3.125GHz spacing";
           }
           enum "1602.79" {
             description "1602.79 nm/187.043750 THz 3.125/6.25GHz spacing";
           }
           enum "1602.77" {
             description "1602.77 nm/187.046875 THz 3.125GHz spacing";
           }
           enum "1602.74" {
             description "1602.74 nm/187.050000 THz 3.125/6.25/12.5/50GHz spacing";
           }
           enum "1602.71" {
             description "1602.71 nm/187.053125 THz 3.125GHz spacing";
           }
           enum "1602.69" {
             description "1602.69 nm/187.056250 THz 3.125/6.25GHz spacing";
           }
           enum "1602.66" {
             description "1602.66 nm/187.059375 THz 3.125GHz spacing";
           }
           enum "1602.63" {
             description "1602.63 nm/187.062500 THz 3.125/6.25/12.5GHz spacing";
           }
           enum "1602.61" {
             description "1602.61 nm/187.065625 THz 3.125GHz spacing";
           }
           enum "1602.58" {
             description "1602.58 nm/187.068750 THz 3.125/6.25GHz spacing";
           }
           enum "1602.55" {
             description "1602.55 nm/187.071875 THz 3.125GHz spacing";
           }
           enum "1602.53" {
             description "1602.53 nm/187.075000 THz 3.125/6.25/12.5GHz spacing";
           }
           enum "1602.50" {
             description "1602.50 nm/187.078125 THz 3.125GHz spacing";
           }
           enum "1602.47" {
             description "1602.47 nm/187.081250 THz 3.125/6.25GHz spacing";
           }
           enum "1602.45" {
             description "1602.45 nm/187.084375 THz 3.125GHz spacing";
           }
           enum "1602.42" {
             description "1602.42 nm/187.087500 THz 3.125/6.25/12.5GHz spacing";
           }
           enum "1602.39" {
             description "1602.39 nm/187.090625 THz 3.125GHz spacing";
           }
           enum "1602.36" {
             description "1602.36 nm/187.093750 THz 3.125/6.25GHz spacing";
           }
           enum "1602.34" {
             description "1602.34 nm/187.096875 THz 3.125GHz spacing";
           }
           enum "1602.31" {
             description "1602.31 nm/187.100000 THz 3.125/6.25/12.5/100GHz spacing";
           }
           enum "1602.28" {
             description "1602.28 nm/187.103125 THz 3.125GHz spacing";
           }
           enum "1602.26" {
             description "1602.26 nm/187.106250 THz 3.125/6.25GHz spacing";
           }
           enum "1602.23" {
             description "1602.23 nm/187.109375 THz 3.125GHz spacing";
           }
           enum "1602.20" {
             description "1602.20 nm/187.112500 THz 3.125/6.25/12.5GHz spacing";
           }
           enum "1602.18" {
             description "1602.18 nm/187.115625 THz 3.125GHz spacing";
           }
           enum "1602.15" {
             description "1602.15 nm/187.118750 THz 3.125/6.25GHz spacing";
           }
           enum "1602.12" {
             description "1602.12 nm/187.121875 THz 3.125GHz spacing";
           }
           enum "1602.10" {
             description "1602.10 nm/187.125000 THz 3.125/6.25/12.5GHz spacing";
           }
           enum "1602.07" {
             description "1602.07 nm/187.128125 THz 3.125GHz spacing";
           }
           enum "1602.04" {
             description "1602.04 nm/187.131250 THz 3.125/6.25GHz spacing";
           }
           enum "1602.02" {
             description "1602.02 nm/187.134375 THz 3.125GHz spacing";
           }
           enum "1601.99" {
             description "1601.99 nm/187.137500 THz 3.125/6.25/12.5GHz spacing";
           }
           enum "1601.96" {
             description "1601.96 nm/187.140625 THz 3.125GHz spacing";
           }
           enum "1601.94" {
             description "1601.94 nm/187.143750 THz 3.125/6.25GHz spacing";
           }
           enum "1601.91" {
             description "1601.91 nm/187.146875 THz 3.125GHz spacing";
           }
           enum "1601.88" {
             description "1601.88 nm/187.150000 THz 3.125/6.25/12.5/50GHz spacing";
           }
           enum "1601.86" {
             description "1601.86 nm/187.153125 THz 3.125GHz spacing";
           }
           enum "1601.83" {
             description "1601.83 nm/187.156250 THz 3.125/6.25GHz spacing";
           }
           enum "1601.80" {
             description "1601.80 nm/187.159375 THz 3.125GHz spacing";
           }
           enum "1601.78" {
             description "1601.78 nm/187.162500 THz 3.125/6.25/12.5GHz spacing";
           }
           enum "1601.75" {
             description "1601.75 nm/187.165625 THz 3.125GHz spacing";
           }
           enum "1601.72" {
             description "1601.72 nm/187.168750 THz 3.125/6.25GHz spacing";
           }
           enum "1601.70" {
             description "1601.70 nm/187.171875 THz 3.125GHz spacing";
           }
           enum "1601.67" {
             description "1601.67 nm/187.175000 THz 3.125/6.25/12.5/75GHz spacing";
           }
           enum "1601.64" {
             description "1601.64 nm/187.178125 THz 3.125GHz spacing";
           }
           enum "1601.62" {
             description "1601.62 nm/187.181250 THz 3.125/6.25GHz spacing";
           }
           enum "1601.59" {
             description "1601.59 nm/187.184375 THz 3.125GHz spacing";
           }
           enum "1601.56" {
             description "1601.56 nm/187.187500 THz 3.125/6.25/12.5GHz spacing";
           }
           enum "1601.54" {
             description "1601.54 nm/187.190625 THz 3.125GHz spacing";
           }
           enum "1601.51" {
             description "1601.51 nm/187.193750 THz 3.125/6.25GHz spacing";
           }
           enum "1601.48" {
             description "1601.48 nm/187.196875 THz 3.125GHz spacing";
           }
           enum "1601.46" {
             description "1601.46 nm/187.200000 THz 3.125/6.25/12.5/50/75/100GHz spacing";
           }
           enum "1601.43" {
             description "1601.43 nm/187.203125 THz 3.125GHz spacing";
           }
           enum "1601.40" {
             description "1601.40 nm/187.206250 THz 3.125/6.25GHz spacing";
           }
           enum "1601.38" {
             description "1601.38 nm/187.209375 THz 3.125GHz spacing";
           }
           enum "1601.35" {
             description "1601.35 nm/187.212500 THz 3.125/6.25/12.5GHz spacing";
           }
           enum "1601.32" {
             description "1601.32 nm/187.215625 THz 3.125GHz spacing";
           }
           enum "1601.30" {
             description "1601.30 nm/187.218750 THz 3.125/6.25GHz spacing";
           }
           enum "1601.27" {
             description "1601.27 nm/187.221875 THz 3.125GHz spacing";
           }
           enum "1601.24" {
             description "1601.24 nm/187.225000 THz 3.125/6.25/12.5GHz spacing";
           }
           enum "1601.21" {
             description "1601.21 nm/187.228125 THz 3.125GHz spacing";
           }
           enum "1601.19" {
             description "1601.19 nm/187.231250 THz 3.125/6.25GHz spacing";
           }
           enum "1601.16" {
             description "1601.16 nm/187.234375 THz 3.125GHz spacing";
           }
           enum "1601.13" {
             description "1601.13 nm/187.237500 THz 3.125/6.25/12.5GHz spacing";
           }
           enum "1601.11" {
             description "1601.11 nm/187.240625 THz 3.125GHz spacing";
           }
           enum "1601.08" {
             description "1601.08 nm/187.243750 THz 3.125/6.25GHz spacing";
           }
           enum "1601.05" {
             description "1601.05 nm/187.246875 THz 3.125GHz spacing";
           }
           enum "1601.03" {
             description "1601.03 nm/187.250000 THz 3.125/6.25/12.5/50/75GHz spacing";
           }
           enum "1601.00" {
             description "1601.00 nm/187.253125 THz 3.125GHz spacing";
           }
           enum "1600.97" {
             description "1600.97 nm/187.256250 THz 3.125/6.25GHz spacing";
           }
           enum "1600.95" {
             description "1600.95 nm/187.259375 THz 3.125GHz spacing";
           }
           enum "1600.92" {
             description "1600.92 nm/187.262500 THz 3.125/6.25/12.5GHz spacing";
           }
           enum "1600.89" {
             description "1600.89 nm/187.265625 THz 3.125GHz spacing";
           }
           enum "1600.87" {
             description "1600.87 nm/187.268750 THz 3.125/6.25GHz spacing";
           }
           enum "1600.84" {
             description "1600.84 nm/187.271875 THz 3.125GHz spacing";
           }
           enum "1600.81" {
             description "1600.81 nm/187.275000 THz 3.125/6.25/12.5GHz spacing";
           }
           enum "1600.79" {
             description "1600.79 nm/187.278125 THz 3.125GHz spacing";
           }
           enum "1600.76" {
             description "1600.76 nm/187.281250 THz 3.125/6.25GHz spacing";
           }
           enum "1600.73" {
             description "1600.73 nm/187.284375 THz 3.125GHz spacing";
           }
           enum "1600.71" {
             description "1600.71 nm/187.287500 THz 3.125/6.25/12.5GHz spacing";
           }
           enum "1600.68" {
             description "1600.68 nm/187.290625 THz 3.125GHz spacing";
           }
           enum "1600.65" {
             description "1600.65 nm/187.293750 THz 3.125/6.25GHz spacing";
           }
           enum "1600.63" {
             description "1600.63 nm/187.296875 THz 3.125GHz spacing";
           }
           enum "1600.60" {
             description "1600.60 nm/187.300000 THz 3.125/6.25/12.5/100GHz spacing";
           }
           enum "1600.57" {
             description "1600.57 nm/187.303125 THz 3.125GHz spacing";
           }
           enum "1600.55" {
             description "1600.55 nm/187.306250 THz 3.125/6.25GHz spacing";
           }
           enum "1600.52" {
             description "1600.52 nm/187.309375 THz 3.125GHz spacing";
           }
           enum "1600.49" {
             description "1600.49 nm/187.312500 THz 3.125/6.25/12.5GHz spacing";
           }
           enum "1600.47" {
             description "1600.47 nm/187.315625 THz 3.125GHz spacing";
           }
           enum "1600.44" {
             description "1600.44 nm/187.318750 THz 3.125/6.25GHz spacing";
           }
           enum "1600.41" {
             description "1600.41 nm/187.321875 THz 3.125GHz spacing";
           }
           enum "1600.39" {
             description "1600.39 nm/187.325000 THz 3.125/6.25/12.5/75GHz spacing";
           }
           enum "1600.36" {
             description "1600.36 nm/187.328125 THz 3.125GHz spacing";
           }
           enum "1600.33" {
             description "1600.33 nm/187.331250 THz 3.125/6.25GHz spacing";
           }
           enum "1600.31" {
             description "1600.31 nm/187.334375 THz 3.125GHz spacing";
           }
           enum "1600.28" {
             description "1600.28 nm/187.337500 THz 3.125/6.25/12.5GHz spacing";
           }
           enum "1600.25" {
             description "1600.25 nm/187.340625 THz 3.125GHz spacing";
           }
           enum "1600.23" {
             description "1600.23 nm/187.343750 THz 3.125/6.25GHz spacing";
           }
           enum "1600.20" {
             description "1600.20 nm/187.346875 THz 3.125GHz spacing";
           }
           enum "1600.17" {
             description "1600.17 nm/187.350000 THz 3.125/6.25/12.5/50GHz spacing";
           }
           enum "1600.15" {
             description "1600.15 nm/187.353125 THz 3.125GHz spacing";
           }
           enum "1600.12" {
             description "1600.12 nm/187.356250 THz 3.125/6.25GHz spacing";
           }
           enum "1600.09" {
             description "1600.09 nm/187.359375 THz 3.125GHz spacing";
           }
           enum "1600.07" {
             description "1600.07 nm/187.362500 THz 3.125/6.25/12.5GHz spacing";
           }
           enum "1600.04" {
             description "1600.04 nm/187.365625 THz 3.125GHz spacing";
           }
           enum "1600.01" {
             description "1600.01 nm/187.368750 THz 3.125/6.25GHz spacing";
           }
           enum "1599.99" {
             description "1599.99 nm/187.371875 THz 3.125GHz spacing";
           }
           enum "1599.96" {
             description "1599.96 nm/187.375000 THz 3.125/6.25/12.5GHz spacing";
           }
           enum "1599.93" {
             description "1599.93 nm/187.378125 THz 3.125GHz spacing";
           }
           enum "1599.91" {
             description "1599.91 nm/187.381250 THz 3.125/6.25GHz spacing";
           }
           enum "1599.88" {
             description "1599.88 nm/187.384375 THz 3.125GHz spacing";
           }
           enum "1599.85" {
             description "1599.85 nm/187.387500 THz 3.125/6.25/12.5GHz spacing";
           }
           enum "1599.83" {
             description "1599.83 nm/187.390625 THz 3.125GHz spacing";
           }
           enum "1599.80" {
             description "1599.80 nm/187.393750 THz 3.125/6.25GHz spacing";
           }
           enum "1599.77" {
             description "1599.77 nm/187.396875 THz 3.125GHz spacing";
           }
           enum "1599.75" {
             description "1599.75 nm/187.400000 THz 3.125/6.25/12.5/100GHz spacing";
           }
           enum "1599.72" {
             description "1599.72 nm/187.403125 THz 3.125GHz spacing";
           }
           enum "1599.69" {
             description "1599.69 nm/187.406250 THz 3.125/6.25GHz spacing";
           }
           enum "1599.67" {
             description "1599.67 nm/187.409375 THz 3.125GHz spacing";
           }
           enum "1599.64" {
             description "1599.64 nm/187.412500 THz 3.125/6.25/12.5GHz spacing";
           }
           enum "1599.61" {
             description "1599.61 nm/187.415625 THz 3.125GHz spacing";
           }
           enum "1599.59" {
             description "1599.59 nm/187.418750 THz 3.125/6.25GHz spacing";
           }
           enum "1599.56" {
             description "1599.56 nm/187.421875 THz 3.125GHz spacing";
           }
           enum "1599.53" {
             description "1599.53 nm/187.425000 THz 3.125/6.25/12.5GHz spacing";
           }
           enum "1599.51" {
             description "1599.51 nm/187.428125 THz 3.125GHz spacing";
           }
           enum "1599.48" {
             description "1599.48 nm/187.431250 THz 3.125/6.25GHz spacing";
           }
           enum "1599.45" {
             description "1599.45 nm/187.434375 THz 3.125GHz spacing";
           }
           enum "1599.43" {
             description "1599.43 nm/187.437500 THz 3.125/6.25/12.5GHz spacing";
           }
           enum "1599.40" {
             description "1599.40 nm/187.440625 THz 3.125GHz spacing";
           }
           enum "1599.37" {
             description "1599.37 nm/187.443750 THz 3.125/6.25GHz spacing";
           }
           enum "1599.35" {
             description "1599.35 nm/187.446875 THz 3.125GHz spacing";
           }
           enum "1599.32" {
             description "1599.32 nm/187.450000 THz 3.125/6.25/12.5/50GHz spacing";
           }
           enum "1599.29" {
             description "1599.29 nm/187.453125 THz 3.125GHz spacing";
           }
           enum "1599.27" {
             description "1599.27 nm/187.456250 THz 3.125/6.25GHz spacing";
           }
           enum "1599.24" {
             description "1599.24 nm/187.459375 THz 3.125GHz spacing";
           }
           enum "1599.21" {
             description "1599.21 nm/187.462500 THz 3.125/6.25/12.5GHz spacing";
           }
           enum "1599.19" {
             description "1599.19 nm/187.465625 THz 3.125GHz spacing";
           }
           enum "1599.16" {
             description "1599.16 nm/187.468750 THz 3.125/6.25GHz spacing";
           }
           enum "1599.13" {
             description "1599.13 nm/187.471875 THz 3.125GHz spacing";
           }
           enum "1599.11" {
             description "1599.11 nm/187.475000 THz 3.125/6.25/12.5/75GHz spacing";
           }
           enum "1599.08" {
             description "1599.08 nm/187.478125 THz 3.125GHz spacing";
           }
           enum "1599.05" {
             description "1599.05 nm/187.481250 THz 3.125/6.25GHz spacing";
           }
           enum "1599.03" {
             description "1599.03 nm/187.484375 THz 3.125GHz spacing";
           }
           enum "1599.00" {
             description "1599.00 nm/187.487500 THz 3.125/6.25/12.5GHz spacing";
           }
           enum "1598.97" {
             description "1598.97 nm/187.490625 THz 3.125GHz spacing";
           }
           enum "1598.95" {
             description "1598.95 nm/187.493750 THz 3.125/6.25GHz spacing";
           }
           enum "1598.92" {
             description "1598.92 nm/187.496875 THz 3.125GHz spacing";
           }
           enum "1598.89" {
             description "1598.89 nm/187.500000 THz 3.125/6.25/12.5/50/75/100GHz spacing";
           }
           enum "1598.87" {
             description "1598.87 nm/187.503125 THz 3.125GHz spacing";
           }
           enum "1598.84" {
             description "1598.84 nm/187.506250 THz 3.125/6.25GHz spacing";
           }
           enum "1598.81" {
             description "1598.81 nm/187.509375 THz 3.125GHz spacing";
           }
           enum "1598.79" {
             description "1598.79 nm/187.512500 THz 3.125/6.25/12.5GHz spacing";
           }
           enum "1598.76" {
             description "1598.76 nm/187.515625 THz 3.125GHz spacing";
           }
           enum "1598.73" {
             description "1598.73 nm/187.518750 THz 3.125/6.25GHz spacing";
           }
           enum "1598.71" {
             description "1598.71 nm/187.521875 THz 3.125GHz spacing";
           }
           enum "1598.68" {
             description "1598.68 nm/187.525000 THz 3.125/6.25/12.5GHz spacing";
           }
           enum "1598.65" {
             description "1598.65 nm/187.528125 THz 3.125GHz spacing";
           }
           enum "1598.63" {
             description "1598.63 nm/187.531250 THz 3.125/6.25GHz spacing";
           }
           enum "1598.60" {
             description "1598.60 nm/187.534375 THz 3.125GHz spacing";
           }
           enum "1598.57" {
             description "1598.57 nm/187.537500 THz 3.125/6.25/12.5GHz spacing";
           }
           enum "1598.55" {
             description "1598.55 nm/187.540625 THz 3.125GHz spacing";
           }
           enum "1598.52" {
             description "1598.52 nm/187.543750 THz 3.125/6.25GHz spacing";
           }
           enum "1598.49" {
             description "1598.49 nm/187.546875 THz 3.125GHz spacing";
           }
           enum "1598.47" {
             description "1598.47 nm/187.550000 THz 3.125/6.25/12.5/50/75GHz spacing";
           }
           enum "1598.44" {
             description "1598.44 nm/187.553125 THz 3.125GHz spacing";
           }
           enum "1598.41" {
             description "1598.41 nm/187.556250 THz 3.125/6.25GHz spacing";
           }
           enum "1598.39" {
             description "1598.39 nm/187.559375 THz 3.125GHz spacing";
           }
           enum "1598.36" {
             description "1598.36 nm/187.562500 THz 3.125/6.25/12.5GHz spacing";
           }
           enum "1598.33" {
             description "1598.33 nm/187.565625 THz 3.125GHz spacing";
           }
           enum "1598.31" {
             description "1598.31 nm/187.568750 THz 3.125/6.25GHz spacing";
           }
           enum "1598.28" {
             description "1598.28 nm/187.571875 THz 3.125GHz spacing";
           }
           enum "1598.25" {
             description "1598.25 nm/187.575000 THz 3.125/6.25/12.5GHz spacing";
           }
           enum "1598.23" {
             description "1598.23 nm/187.578125 THz 3.125GHz spacing";
           }
           enum "1598.20" {
             description "1598.20 nm/187.581250 THz 3.125/6.25GHz spacing";
           }
           enum "1598.17" {
             description "1598.17 nm/187.584375 THz 3.125GHz spacing";
           }
           enum "1598.15" {
             description "1598.15 nm/187.587500 THz 3.125/6.25/12.5GHz spacing";
           }
           enum "1598.12" {
             description "1598.12 nm/187.590625 THz 3.125GHz spacing";
           }
           enum "1598.09" {
             description "1598.09 nm/187.593750 THz 3.125/6.25GHz spacing";
           }
           enum "1598.07" {
             description "1598.07 nm/187.596875 THz 3.125GHz spacing";
           }
           enum "1598.04" {
             description "1598.04 nm/187.600000 THz 3.125/6.25/12.5/100GHz spacing";
           }
           enum "1598.01" {
             description "1598.01 nm/187.603125 THz 3.125GHz spacing";
           }
           enum "1597.99" {
             description "1597.99 nm/187.606250 THz 3.125/6.25GHz spacing";
           }
           enum "1597.96" {
             description "1597.96 nm/187.609375 THz 3.125GHz spacing";
           }
           enum "1597.93" {
             description "1597.93 nm/187.612500 THz 3.125/6.25/12.5GHz spacing";
           }
           enum "1597.91" {
             description "1597.91 nm/187.615625 THz 3.125GHz spacing";
           }
           enum "1597.88" {
             description "1597.88 nm/187.618750 THz 3.125/6.25GHz spacing";
           }
           enum "1597.85" {
             description "1597.85 nm/187.621875 THz 3.125GHz spacing";
           }
           enum "1597.83" {
             description "1597.83 nm/187.625000 THz 3.125/6.25/12.5/75GHz spacing";
           }
           enum "1597.80" {
             description "1597.80 nm/187.628125 THz 3.125GHz spacing";
           }
           enum "1597.77" {
             description "1597.77 nm/187.631250 THz 3.125/6.25GHz spacing";
           }
           enum "1597.75" {
             description "1597.75 nm/187.634375 THz 3.125GHz spacing";
           }
           enum "1597.72" {
             description "1597.72 nm/187.637500 THz 3.125/6.25/12.5GHz spacing";
           }
           enum "1597.69" {
             description "1597.69 nm/187.640625 THz 3.125GHz spacing";
           }
           enum "1597.67" {
             description "1597.67 nm/187.643750 THz 3.125/6.25GHz spacing";
           }
           enum "1597.64" {
             description "1597.64 nm/187.646875 THz 3.125GHz spacing";
           }
           enum "1597.62" {
             description "1597.62 nm/187.650000 THz 3.125/6.25/12.5/50GHz spacing";
           }
           enum "1597.59" {
             description "1597.59 nm/187.653125 THz 3.125GHz spacing";
           }
           enum "1597.56" {
             description "1597.56 nm/187.656250 THz 3.125/6.25GHz spacing";
           }
           enum "1597.54" {
             description "1597.54 nm/187.659375 THz 3.125GHz spacing";
           }
           enum "1597.51" {
             description "1597.51 nm/187.662500 THz 3.125/6.25/12.5GHz spacing";
           }
           enum "1597.48" {
             description "1597.48 nm/187.665625 THz 3.125GHz spacing";
           }
           enum "1597.46" {
             description "1597.46 nm/187.668750 THz 3.125/6.25GHz spacing";
           }
           enum "1597.43" {
             description "1597.43 nm/187.671875 THz 3.125GHz spacing";
           }
           enum "1597.40" {
             description "1597.40 nm/187.675000 THz 3.125/6.25/12.5GHz spacing";
           }
           enum "1597.38" {
             description "1597.38 nm/187.678125 THz 3.125GHz spacing";
           }
           enum "1597.35" {
             description "1597.35 nm/187.681250 THz 3.125/6.25GHz spacing";
           }
           enum "1597.32" {
             description "1597.32 nm/187.684375 THz 3.125GHz spacing";
           }
           enum "1597.30" {
             description "1597.30 nm/187.687500 THz 3.125/6.25/12.5GHz spacing";
           }
           enum "1597.27" {
             description "1597.27 nm/187.690625 THz 3.125GHz spacing";
           }
           enum "1597.24" {
             description "1597.24 nm/187.693750 THz 3.125/6.25GHz spacing";
           }
           enum "1597.22" {
             description "1597.22 nm/187.696875 THz 3.125GHz spacing";
           }
           enum "1597.19" {
             description "1597.19 nm/187.700000 THz 3.125/6.25/12.5/100GHz spacing";
           }
           enum "1597.16" {
             description "1597.16 nm/187.703125 THz 3.125GHz spacing";
           }
           enum "1597.14" {
             description "1597.14 nm/187.706250 THz 3.125/6.25GHz spacing";
           }
           enum "1597.11" {
             description "1597.11 nm/187.709375 THz 3.125GHz spacing";
           }
           enum "1597.08" {
             description "1597.08 nm/187.712500 THz 3.125/6.25/12.5GHz spacing";
           }
           enum "1597.06" {
             description "1597.06 nm/187.715625 THz 3.125GHz spacing";
           }
           enum "1597.03" {
             description "1597.03 nm/187.718750 THz 3.125/6.25GHz spacing";
           }
           enum "1597.00" {
             description "1597.00 nm/187.721875 THz 3.125GHz spacing";
           }
           enum "1596.98" {
             description "1596.98 nm/187.725000 THz 3.125/6.25/12.5GHz spacing";
           }
           enum "1596.95" {
             description "1596.95 nm/187.728125 THz 3.125GHz spacing";
           }
           enum "1596.92" {
             description "1596.92 nm/187.731250 THz 3.125/6.25GHz spacing";
           }
           enum "1596.90" {
             description "1596.90 nm/187.734375 THz 3.125GHz spacing";
           }
           enum "1596.87" {
             description "1596.87 nm/187.737500 THz 3.125/6.25/12.5GHz spacing";
           }
           enum "1596.84" {
             description "1596.84 nm/187.740625 THz 3.125GHz spacing";
           }
           enum "1596.82" {
             description "1596.82 nm/187.743750 THz 3.125/6.25GHz spacing";
           }
           enum "1596.79" {
             description "1596.79 nm/187.746875 THz 3.125GHz spacing";
           }
           enum "1596.76" {
             description "1596.76 nm/187.750000 THz 3.125/6.25/12.5/50GHz spacing";
           }
           enum "1596.74" {
             description "1596.74 nm/187.753125 THz 3.125GHz spacing";
           }
           enum "1596.71" {
             description "1596.71 nm/187.756250 THz 3.125/6.25GHz spacing";
           }
           enum "1596.68" {
             description "1596.68 nm/187.759375 THz 3.125GHz spacing";
           }
           enum "1596.66" {
             description "1596.66 nm/187.762500 THz 3.125/6.25/12.5GHz spacing";
           }
           enum "1596.63" {
             description "1596.63 nm/187.765625 THz 3.125GHz spacing";
           }
           enum "1596.60" {
             description "1596.60 nm/187.768750 THz 3.125/6.25GHz spacing";
           }
           enum "1596.58" {
             description "1596.58 nm/187.771875 THz 3.125GHz spacing";
           }
           enum "1596.55" {
             description "1596.55 nm/187.775000 THz 3.125/6.25/12.5/75GHz spacing";
           }
           enum "1596.52" {
             description "1596.52 nm/187.778125 THz 3.125GHz spacing";
           }
           enum "1596.50" {
             description "1596.50 nm/187.781250 THz 3.125/6.25GHz spacing";
           }
           enum "1596.47" {
             description "1596.47 nm/187.784375 THz 3.125GHz spacing";
           }
           enum "1596.45" {
             description "1596.45 nm/187.787500 THz 3.125/6.25/12.5GHz spacing";
           }
           enum "1596.42" {
             description "1596.42 nm/187.790625 THz 3.125GHz spacing";
           }
           enum "1596.39" {
             description "1596.39 nm/187.793750 THz 3.125/6.25GHz spacing";
           }
           enum "1596.37" {
             description "1596.37 nm/187.796875 THz 3.125GHz spacing";
           }
           enum "1596.34" {
             description "1596.34 nm/187.800000 THz 3.125/6.25/12.5/50/75/100GHz spacing";
           }
           enum "1596.31" {
             description "1596.31 nm/187.803125 THz 3.125GHz spacing";
           }
           enum "1596.29" {
             description "1596.29 nm/187.806250 THz 3.125/6.25GHz spacing";
           }
           enum "1596.26" {
             description "1596.26 nm/187.809375 THz 3.125GHz spacing";
           }
           enum "1596.23" {
             description "1596.23 nm/187.812500 THz 3.125/6.25/12.5GHz spacing";
           }
           enum "1596.21" {
             description "1596.21 nm/187.815625 THz 3.125GHz spacing";
           }
           enum "1596.18" {
             description "1596.18 nm/187.818750 THz 3.125/6.25GHz spacing";
           }
           enum "1596.15" {
             description "1596.15 nm/187.821875 THz 3.125GHz spacing";
           }
           enum "1596.13" {
             description "1596.13 nm/187.825000 THz 3.125/6.25/12.5GHz spacing";
           }
           enum "1596.10" {
             description "1596.10 nm/187.828125 THz 3.125GHz spacing";
           }
           enum "1596.07" {
             description "1596.07 nm/187.831250 THz 3.125/6.25GHz spacing";
           }
           enum "1596.05" {
             description "1596.05 nm/187.834375 THz 3.125GHz spacing";
           }
           enum "1596.02" {
             description "1596.02 nm/187.837500 THz 3.125/6.25/12.5GHz spacing";
           }
           enum "1595.99" {
             description "1595.99 nm/187.840625 THz 3.125GHz spacing";
           }
           enum "1595.97" {
             description "1595.97 nm/187.843750 THz 3.125/6.25GHz spacing";
           }
           enum "1595.94" {
             description "1595.94 nm/187.846875 THz 3.125GHz spacing";
           }
           enum "1595.91" {
             description "1595.91 nm/187.850000 THz 3.125/6.25/12.5/50/75GHz spacing";
           }
           enum "1595.89" {
             description "1595.89 nm/187.853125 THz 3.125GHz spacing";
           }
           enum "1595.86" {
             description "1595.86 nm/187.856250 THz 3.125/6.25GHz spacing";
           }
           enum "1595.83" {
             description "1595.83 nm/187.859375 THz 3.125GHz spacing";
           }
           enum "1595.81" {
             description "1595.81 nm/187.862500 THz 3.125/6.25/12.5GHz spacing";
           }
           enum "1595.78" {
             description "1595.78 nm/187.865625 THz 3.125GHz spacing";
           }
           enum "1595.75" {
             description "1595.75 nm/187.868750 THz 3.125/6.25GHz spacing";
           }
           enum "1595.73" {
             description "1595.73 nm/187.871875 THz 3.125GHz spacing";
           }
           enum "1595.70" {
             description "1595.70 nm/187.875000 THz 3.125/6.25/12.5GHz spacing";
           }
           enum "1595.68" {
             description "1595.68 nm/187.878125 THz 3.125GHz spacing";
           }
           enum "1595.65" {
             description "1595.65 nm/187.881250 THz 3.125/6.25GHz spacing";
           }
           enum "1595.62" {
             description "1595.62 nm/187.884375 THz 3.125GHz spacing";
           }
           enum "1595.60" {
             description "1595.60 nm/187.887500 THz 3.125/6.25/12.5GHz spacing";
           }
           enum "1595.57" {
             description "1595.57 nm/187.890625 THz 3.125GHz spacing";
           }
           enum "1595.54" {
             description "1595.54 nm/187.893750 THz 3.125/6.25GHz spacing";
           }
           enum "1595.52" {
             description "1595.52 nm/187.896875 THz 3.125GHz spacing";
           }
           enum "1595.49" {
             description "1595.49 nm/187.900000 THz 3.125/6.25/12.5/100GHz spacing";
           }
           enum "1595.46" {
             description "1595.46 nm/187.903125 THz 3.125GHz spacing";
           }
           enum "1595.44" {
             description "1595.44 nm/187.906250 THz 3.125/6.25GHz spacing";
           }
           enum "1595.41" {
             description "1595.41 nm/187.909375 THz 3.125GHz spacing";
           }
           enum "1595.38" {
             description "1595.38 nm/187.912500 THz 3.125/6.25/12.5GHz spacing";
           }
           enum "1595.36" {
             description "1595.36 nm/187.915625 THz 3.125GHz spacing";
           }
           enum "1595.33" {
             description "1595.33 nm/187.918750 THz 3.125/6.25GHz spacing";
           }
           enum "1595.30" {
             description "1595.30 nm/187.921875 THz 3.125GHz spacing";
           }
           enum "1595.28" {
             description "1595.28 nm/187.925000 THz 3.125/6.25/12.5/75GHz spacing";
           }
           enum "1595.25" {
             description "1595.25 nm/187.928125 THz 3.125GHz spacing";
           }
           enum "1595.22" {
             description "1595.22 nm/187.931250 THz 3.125/6.25GHz spacing";
           }
           enum "1595.20" {
             description "1595.20 nm/187.934375 THz 3.125GHz spacing";
           }
           enum "1595.17" {
             description "1595.17 nm/187.937500 THz 3.125/6.25/12.5GHz spacing";
           }
           enum "1595.14" {
             description "1595.14 nm/187.940625 THz 3.125GHz spacing";
           }
           enum "1595.12" {
             description "1595.12 nm/187.943750 THz 3.125/6.25GHz spacing";
           }
           enum "1595.09" {
             description "1595.09 nm/187.946875 THz 3.125GHz spacing";
           }
           enum "1595.06" {
             description "1595.06 nm/187.950000 THz 3.125/6.25/12.5/50GHz spacing";
           }
           enum "1595.04" {
             description "1595.04 nm/187.953125 THz 3.125GHz spacing";
           }
           enum "1595.01" {
             description "1595.01 nm/187.956250 THz 3.125/6.25GHz spacing";
           }
           enum "1594.99" {
             description "1594.99 nm/187.959375 THz 3.125GHz spacing";
           }
           enum "1594.96" {
             description "1594.96 nm/187.962500 THz 3.125/6.25/12.5GHz spacing";
           }
           enum "1594.93" {
             description "1594.93 nm/187.965625 THz 3.125GHz spacing";
           }
           enum "1594.91" {
             description "1594.91 nm/187.968750 THz 3.125/6.25GHz spacing";
           }
           enum "1594.88" {
             description "1594.88 nm/187.971875 THz 3.125GHz spacing";
           }
           enum "1594.85" {
             description "1594.85 nm/187.975000 THz 3.125/6.25/12.5GHz spacing";
           }
           enum "1594.83" {
             description "1594.83 nm/187.978125 THz 3.125GHz spacing";
           }
           enum "1594.80" {
             description "1594.80 nm/187.981250 THz 3.125/6.25GHz spacing";
           }
           enum "1594.77" {
             description "1594.77 nm/187.984375 THz 3.125GHz spacing";
           }
           enum "1594.75" {
             description "1594.75 nm/187.987500 THz 3.125/6.25/12.5GHz spacing";
           }
           enum "1594.72" {
             description "1594.72 nm/187.990625 THz 3.125GHz spacing";
           }
           enum "1594.69" {
             description "1594.69 nm/187.993750 THz 3.125/6.25GHz spacing";
           }
           enum "1594.67" {
             description "1594.67 nm/187.996875 THz 3.125GHz spacing";
           }
           enum "1594.64" {
             description "1594.64 nm/188.000000 THz 3.125/6.25/12.5/100GHz spacing";
           }
           enum "1594.61" {
             description "1594.61 nm/188.003125 THz 3.125GHz spacing";
           }
           enum "1594.59" {
             description "1594.59 nm/188.006250 THz 3.125/6.25GHz spacing";
           }
           enum "1594.56" {
             description "1594.56 nm/188.009375 THz 3.125GHz spacing";
           }
           enum "1594.53" {
             description "1594.53 nm/188.012500 THz 3.125/6.25/12.5GHz spacing";
           }
           enum "1594.51" {
             description "1594.51 nm/188.015625 THz 3.125GHz spacing";
           }
           enum "1594.48" {
             description "1594.48 nm/188.018750 THz 3.125/6.25GHz spacing";
           }
           enum "1594.46" {
             description "1594.46 nm/188.021875 THz 3.125GHz spacing";
           }
           enum "1594.43" {
             description "1594.43 nm/188.025000 THz 3.125/6.25/12.5GHz spacing";
           }
           enum "1594.40" {
             description "1594.40 nm/188.028125 THz 3.125GHz spacing";
           }
           enum "1594.38" {
             description "1594.38 nm/188.031250 THz 3.125/6.25GHz spacing";
           }
           enum "1594.35" {
             description "1594.35 nm/188.034375 THz 3.125GHz spacing";
           }
           enum "1594.32" {
             description "1594.32 nm/188.037500 THz 3.125/6.25/12.5GHz spacing";
           }
           enum "1594.30" {
             description "1594.30 nm/188.040625 THz 3.125GHz spacing";
           }
           enum "1594.27" {
             description "1594.27 nm/188.043750 THz 3.125/6.25GHz spacing";
           }
           enum "1594.24" {
             description "1594.24 nm/188.046875 THz 3.125GHz spacing";
           }
           enum "1594.22" {
             description "1594.22 nm/188.050000 THz 3.125/6.25/12.5/50GHz spacing";
           }
           enum "1594.19" {
             description "1594.19 nm/188.053125 THz 3.125GHz spacing";
           }
           enum "1594.16" {
             description "1594.16 nm/188.056250 THz 3.125/6.25GHz spacing";
           }
           enum "1594.14" {
             description "1594.14 nm/188.059375 THz 3.125GHz spacing";
           }
           enum "1594.11" {
             description "1594.11 nm/188.062500 THz 3.125/6.25/12.5GHz spacing";
           }
           enum "1594.08" {
             description "1594.08 nm/188.065625 THz 3.125GHz spacing";
           }
           enum "1594.06" {
             description "1594.06 nm/188.068750 THz 3.125/6.25GHz spacing";
           }
           enum "1594.03" {
             description "1594.03 nm/188.071875 THz 3.125GHz spacing";
           }
           enum "1594.00" {
             description "1594.00 nm/188.075000 THz 3.125/6.25/12.5/75GHz spacing";
           }
           enum "1593.98" {
             description "1593.98 nm/188.078125 THz 3.125GHz spacing";
           }
           enum "1593.95" {
             description "1593.95 nm/188.081250 THz 3.125/6.25GHz spacing";
           }
           enum "1593.93" {
             description "1593.93 nm/188.084375 THz 3.125GHz spacing";
           }
           enum "1593.90" {
             description "1593.90 nm/188.087500 THz 3.125/6.25/12.5GHz spacing";
           }
           enum "1593.87" {
             description "1593.87 nm/188.090625 THz 3.125GHz spacing";
           }
           enum "1593.85" {
             description "1593.85 nm/188.093750 THz 3.125/6.25GHz spacing";
           }
           enum "1593.82" {
             description "1593.82 nm/188.096875 THz 3.125GHz spacing";
           }
           enum "1593.79" {
             description "1593.79 nm/188.100000 THz 3.125/6.25/12.5/50/75/100GHz spacing";
           }
           enum "1593.77" {
             description "1593.77 nm/188.103125 THz 3.125GHz spacing";
           }
           enum "1593.74" {
             description "1593.74 nm/188.106250 THz 3.125/6.25GHz spacing";
           }
           enum "1593.71" {
             description "1593.71 nm/188.109375 THz 3.125GHz spacing";
           }
           enum "1593.69" {
             description "1593.69 nm/188.112500 THz 3.125/6.25/12.5GHz spacing";
           }
           enum "1593.66" {
             description "1593.66 nm/188.115625 THz 3.125GHz spacing";
           }
           enum "1593.63" {
             description "1593.63 nm/188.118750 THz 3.125/6.25GHz spacing";
           }
           enum "1593.61" {
             description "1593.61 nm/188.121875 THz 3.125GHz spacing";
           }
           enum "1593.58" {
             description "1593.58 nm/188.125000 THz 3.125/6.25/12.5GHz spacing";
           }
           enum "1593.55" {
             description "1593.55 nm/188.128125 THz 3.125GHz spacing";
           }
           enum "1593.53" {
             description "1593.53 nm/188.131250 THz 3.125/6.25GHz spacing";
           }
           enum "1593.50" {
             description "1593.50 nm/188.134375 THz 3.125GHz spacing";
           }
           enum "1593.48" {
             description "1593.48 nm/188.137500 THz 3.125/6.25/12.5GHz spacing";
           }
           enum "1593.45" {
             description "1593.45 nm/188.140625 THz 3.125GHz spacing";
           }
           enum "1593.42" {
             description "1593.42 nm/188.143750 THz 3.125/6.25GHz spacing";
           }
           enum "1593.40" {
             description "1593.40 nm/188.146875 THz 3.125GHz spacing";
           }
           enum "1593.37" {
             description "1593.37 nm/188.150000 THz 3.125/6.25/12.5/50/75GHz spacing";
           }
           enum "1593.34" {
             description "1593.34 nm/188.153125 THz 3.125GHz spacing";
           }
           enum "1593.32" {
             description "1593.32 nm/188.156250 THz 3.125/6.25GHz spacing";
           }
           enum "1593.29" {
             description "1593.29 nm/188.159375 THz 3.125GHz spacing";
           }
           enum "1593.26" {
             description "1593.26 nm/188.162500 THz 3.125/6.25/12.5GHz spacing";
           }
           enum "1593.24" {
             description "1593.24 nm/188.165625 THz 3.125GHz spacing";
           }
           enum "1593.21" {
             description "1593.21 nm/188.168750 THz 3.125/6.25GHz spacing";
           }
           enum "1593.18" {
             description "1593.18 nm/188.171875 THz 3.125GHz spacing";
           }
           enum "1593.16" {
             description "1593.16 nm/188.175000 THz 3.125/6.25/12.5GHz spacing";
           }
           enum "1593.13" {
             description "1593.13 nm/188.178125 THz 3.125GHz spacing";
           }
           enum "1593.10" {
             description "1593.10 nm/188.181250 THz 3.125/6.25GHz spacing";
           }
           enum "1593.08" {
             description "1593.08 nm/188.184375 THz 3.125GHz spacing";
           }
           enum "1593.05" {
             description "1593.05 nm/188.187500 THz 3.125/6.25/12.5GHz spacing";
           }
           enum "1593.03" {
             description "1593.03 nm/188.190625 THz 3.125GHz spacing";
           }
           enum "1593.00" {
             description "1593.00 nm/188.193750 THz 3.125/6.25GHz spacing";
           }
           enum "1592.97" {
             description "1592.97 nm/188.196875 THz 3.125GHz spacing";
           }
           enum "1592.95" {
             description "1592.95 nm/188.200000 THz 3.125/6.25/12.5/100GHz spacing";
           }
           enum "1592.92" {
             description "1592.92 nm/188.203125 THz 3.125GHz spacing";
           }
           enum "1592.89" {
             description "1592.89 nm/188.206250 THz 3.125/6.25GHz spacing";
           }
           enum "1592.87" {
             description "1592.87 nm/188.209375 THz 3.125GHz spacing";
           }
           enum "1592.84" {
             description "1592.84 nm/188.212500 THz 3.125/6.25/12.5GHz spacing";
           }
           enum "1592.81" {
             description "1592.81 nm/188.215625 THz 3.125GHz spacing";
           }
           enum "1592.79" {
             description "1592.79 nm/188.218750 THz 3.125/6.25GHz spacing";
           }
           enum "1592.76" {
             description "1592.76 nm/188.221875 THz 3.125GHz spacing";
           }
           enum "1592.73" {
             description "1592.73 nm/188.225000 THz 3.125/6.25/12.5/75GHz spacing";
           }
           enum "1592.71" {
             description "1592.71 nm/188.228125 THz 3.125GHz spacing";
           }
           enum "1592.68" {
             description "1592.68 nm/188.231250 THz 3.125/6.25GHz spacing";
           }
           enum "1592.66" {
             description "1592.66 nm/188.234375 THz 3.125GHz spacing";
           }
           enum "1592.63" {
             description "1592.63 nm/188.237500 THz 3.125/6.25/12.5GHz spacing";
           }
           enum "1592.60" {
             description "1592.60 nm/188.240625 THz 3.125GHz spacing";
           }
           enum "1592.58" {
             description "1592.58 nm/188.243750 THz 3.125/6.25GHz spacing";
           }
           enum "1592.55" {
             description "1592.55 nm/188.246875 THz 3.125GHz spacing";
           }
           enum "1592.52" {
             description "1592.52 nm/188.250000 THz 3.125/6.25/12.5/50GHz spacing";
           }
           enum "1592.50" {
             description "1592.50 nm/188.253125 THz 3.125GHz spacing";
           }
           enum "1592.47" {
             description "1592.47 nm/188.256250 THz 3.125/6.25GHz spacing";
           }
           enum "1592.44" {
             description "1592.44 nm/188.259375 THz 3.125GHz spacing";
           }
           enum "1592.42" {
             description "1592.42 nm/188.262500 THz 3.125/6.25/12.5GHz spacing";
           }
           enum "1592.39" {
             description "1592.39 nm/188.265625 THz 3.125GHz spacing";
           }
           enum "1592.36" {
             description "1592.36 nm/188.268750 THz 3.125/6.25GHz spacing";
           }
           enum "1592.34" {
             description "1592.34 nm/188.271875 THz 3.125GHz spacing";
           }
           enum "1592.31" {
             description "1592.31 nm/188.275000 THz 3.125/6.25/12.5GHz spacing";
           }
           enum "1592.29" {
             description "1592.29 nm/188.278125 THz 3.125GHz spacing";
           }
           enum "1592.26" {
             description "1592.26 nm/188.281250 THz 3.125/6.25GHz spacing";
           }
           enum "1592.23" {
             description "1592.23 nm/188.284375 THz 3.125GHz spacing";
           }
           enum "1592.21" {
             description "1592.21 nm/188.287500 THz 3.125/6.25/12.5GHz spacing";
           }
           enum "1592.18" {
             description "1592.18 nm/188.290625 THz 3.125GHz spacing";
           }
           enum "1592.15" {
             description "1592.15 nm/188.293750 THz 3.125/6.25GHz spacing";
           }
           enum "1592.13" {
             description "1592.13 nm/188.296875 THz 3.125GHz spacing";
           }
           enum "1592.10" {
             description "1592.10 nm/188.300000 THz 3.125/6.25/12.5/100GHz spacing";
           }
           enum "1592.07" {
             description "1592.07 nm/188.303125 THz 3.125GHz spacing";
           }
           enum "1592.05" {
             description "1592.05 nm/188.306250 THz 3.125/6.25GHz spacing";
           }
           enum "1592.02" {
             description "1592.02 nm/188.309375 THz 3.125GHz spacing";
           }
           enum "1591.99" {
             description "1591.99 nm/188.312500 THz 3.125/6.25/12.5GHz spacing";
           }
           enum "1591.97" {
             description "1591.97 nm/188.315625 THz 3.125GHz spacing";
           }
           enum "1591.94" {
             description "1591.94 nm/188.318750 THz 3.125/6.25GHz spacing";
           }
           enum "1591.92" {
             description "1591.92 nm/188.321875 THz 3.125GHz spacing";
           }
           enum "1591.89" {
             description "1591.89 nm/188.325000 THz 3.125/6.25/12.5GHz spacing";
           }
           enum "1591.86" {
             description "1591.86 nm/188.328125 THz 3.125GHz spacing";
           }
           enum "1591.84" {
             description "1591.84 nm/188.331250 THz 3.125/6.25GHz spacing";
           }
           enum "1591.81" {
             description "1591.81 nm/188.334375 THz 3.125GHz spacing";
           }
           enum "1591.78" {
             description "1591.78 nm/188.337500 THz 3.125/6.25/12.5GHz spacing";
           }
           enum "1591.76" {
             description "1591.76 nm/188.340625 THz 3.125GHz spacing";
           }
           enum "1591.73" {
             description "1591.73 nm/188.343750 THz 3.125/6.25GHz spacing";
           }
           enum "1591.70" {
             description "1591.70 nm/188.346875 THz 3.125GHz spacing";
           }
           enum "1591.68" {
             description "1591.68 nm/188.350000 THz 3.125/6.25/12.5/50GHz spacing";
           }
           enum "1591.65" {
             description "1591.65 nm/188.353125 THz 3.125GHz spacing";
           }
           enum "1591.62" {
             description "1591.62 nm/188.356250 THz 3.125/6.25GHz spacing";
           }
           enum "1591.60" {
             description "1591.60 nm/188.359375 THz 3.125GHz spacing";
           }
           enum "1591.57" {
             description "1591.57 nm/188.362500 THz 3.125/6.25/12.5GHz spacing";
           }
           enum "1591.55" {
             description "1591.55 nm/188.365625 THz 3.125GHz spacing";
           }
           enum "1591.52" {
             description "1591.52 nm/188.368750 THz 3.125/6.25GHz spacing";
           }
           enum "1591.49" {
             description "1591.49 nm/188.371875 THz 3.125GHz spacing";
           }
           enum "1591.47" {
             description "1591.47 nm/188.375000 THz 3.125/6.25/12.5/75GHz spacing";
           }
           enum "1591.44" {
             description "1591.44 nm/188.378125 THz 3.125GHz spacing";
           }
           enum "1591.41" {
             description "1591.41 nm/188.381250 THz 3.125/6.25GHz spacing";
           }
           enum "1591.39" {
             description "1591.39 nm/188.384375 THz 3.125GHz spacing";
           }
           enum "1591.36" {
             description "1591.36 nm/188.387500 THz 3.125/6.25/12.5GHz spacing";
           }
           enum "1591.33" {
             description "1591.33 nm/188.390625 THz 3.125GHz spacing";
           }
           enum "1591.31" {
             description "1591.31 nm/188.393750 THz 3.125/6.25GHz spacing";
           }
           enum "1591.28" {
             description "1591.28 nm/188.396875 THz 3.125GHz spacing";
           }
           enum "1591.26" {
             description "1591.26 nm/188.400000 THz 3.125/6.25/12.5/50/75/100GHz spacing";
           }
           enum "1591.23" {
             description "1591.23 nm/188.403125 THz 3.125GHz spacing";
           }
           enum "1591.20" {
             description "1591.20 nm/188.406250 THz 3.125/6.25GHz spacing";
           }
           enum "1591.18" {
             description "1591.18 nm/188.409375 THz 3.125GHz spacing";
           }
           enum "1591.15" {
             description "1591.15 nm/188.412500 THz 3.125/6.25/12.5GHz spacing";
           }
           enum "1591.12" {
             description "1591.12 nm/188.415625 THz 3.125GHz spacing";
           }
           enum "1591.10" {
             description "1591.10 nm/188.418750 THz 3.125/6.25GHz spacing";
           }
           enum "1591.07" {
             description "1591.07 nm/188.421875 THz 3.125GHz spacing";
           }
           enum "1591.04" {
             description "1591.04 nm/188.425000 THz 3.125/6.25/12.5GHz spacing";
           }
           enum "1591.02" {
             description "1591.02 nm/188.428125 THz 3.125GHz spacing";
           }
           enum "1590.99" {
             description "1590.99 nm/188.431250 THz 3.125/6.25GHz spacing";
           }
           enum "1590.96" {
             description "1590.96 nm/188.434375 THz 3.125GHz spacing";
           }
           enum "1590.94" {
             description "1590.94 nm/188.437500 THz 3.125/6.25/12.5GHz spacing";
           }
           enum "1590.91" {
             description "1590.91 nm/188.440625 THz 3.125GHz spacing";
           }
           enum "1590.89" {
             description "1590.89 nm/188.443750 THz 3.125/6.25GHz spacing";
           }
           enum "1590.86" {
             description "1590.86 nm/188.446875 THz 3.125GHz spacing";
           }
           enum "1590.83" {
             description "1590.83 nm/188.450000 THz 3.125/6.25/12.5/50/75GHz spacing";
           }
           enum "1590.81" {
             description "1590.81 nm/188.453125 THz 3.125GHz spacing";
           }
           enum "1590.78" {
             description "1590.78 nm/188.456250 THz 3.125/6.25GHz spacing";
           }
           enum "1590.75" {
             description "1590.75 nm/188.459375 THz 3.125GHz spacing";
           }
           enum "1590.73" {
             description "1590.73 nm/188.462500 THz 3.125/6.25/12.5GHz spacing";
           }
           enum "1590.70" {
             description "1590.70 nm/188.465625 THz 3.125GHz spacing";
           }
           enum "1590.67" {
             description "1590.67 nm/188.468750 THz 3.125/6.25GHz spacing";
           }
           enum "1590.65" {
             description "1590.65 nm/188.471875 THz 3.125GHz spacing";
           }
           enum "1590.62" {
             description "1590.62 nm/188.475000 THz 3.125/6.25/12.5GHz spacing";
           }
           enum "1590.60" {
             description "1590.60 nm/188.478125 THz 3.125GHz spacing";
           }
           enum "1590.57" {
             description "1590.57 nm/188.481250 THz 3.125/6.25GHz spacing";
           }
           enum "1590.54" {
             description "1590.54 nm/188.484375 THz 3.125GHz spacing";
           }
           enum "1590.52" {
             description "1590.52 nm/188.487500 THz 3.125/6.25/12.5GHz spacing";
           }
           enum "1590.49" {
             description "1590.49 nm/188.490625 THz 3.125GHz spacing";
           }
           enum "1590.46" {
             description "1590.46 nm/188.493750 THz 3.125/6.25GHz spacing";
           }
           enum "1590.44" {
             description "1590.44 nm/188.496875 THz 3.125GHz spacing";
           }
           enum "1590.41" {
             description "1590.41 nm/188.500000 THz 3.125/6.25/12.5/100GHz spacing";
           }
           enum "1590.38" {
             description "1590.38 nm/188.503125 THz 3.125GHz spacing";
           }
           enum "1590.36" {
             description "1590.36 nm/188.506250 THz 3.125/6.25GHz spacing";
           }
           enum "1590.33" {
             description "1590.33 nm/188.509375 THz 3.125GHz spacing";
           }
           enum "1590.31" {
             description "1590.31 nm/188.512500 THz 3.125/6.25/12.5GHz spacing";
           }
           enum "1590.28" {
             description "1590.28 nm/188.515625 THz 3.125GHz spacing";
           }
           enum "1590.25" {
             description "1590.25 nm/188.518750 THz 3.125/6.25GHz spacing";
           }
           enum "1590.23" {
             description "1590.23 nm/188.521875 THz 3.125GHz spacing";
           }
           enum "1590.20" {
             description "1590.20 nm/188.525000 THz 3.125/6.25/12.5/75GHz spacing";
           }
           enum "1590.17" {
             description "1590.17 nm/188.528125 THz 3.125GHz spacing";
           }
           enum "1590.15" {
             description "1590.15 nm/188.531250 THz 3.125/6.25GHz spacing";
           }
           enum "1590.12" {
             description "1590.12 nm/188.534375 THz 3.125GHz spacing";
           }
           enum "1590.09" {
             description "1590.09 nm/188.537500 THz 3.125/6.25/12.5GHz spacing";
           }
           enum "1590.07" {
             description "1590.07 nm/188.540625 THz 3.125GHz spacing";
           }
           enum "1590.04" {
             description "1590.04 nm/188.543750 THz 3.125/6.25GHz spacing";
           }
           enum "1590.02" {
             description "1590.02 nm/188.546875 THz 3.125GHz spacing";
           }
           enum "1589.99" {
             description "1589.99 nm/188.550000 THz 3.125/6.25/12.5/50GHz spacing";
           }
           enum "1589.96" {
             description "1589.96 nm/188.553125 THz 3.125GHz spacing";
           }
           enum "1589.94" {
             description "1589.94 nm/188.556250 THz 3.125/6.25GHz spacing";
           }
           enum "1589.91" {
             description "1589.91 nm/188.559375 THz 3.125GHz spacing";
           }
           enum "1589.88" {
             description "1589.88 nm/188.562500 THz 3.125/6.25/12.5GHz spacing";
           }
           enum "1589.86" {
             description "1589.86 nm/188.565625 THz 3.125GHz spacing";
           }
           enum "1589.83" {
             description "1589.83 nm/188.568750 THz 3.125/6.25GHz spacing";
           }
           enum "1589.80" {
             description "1589.80 nm/188.571875 THz 3.125GHz spacing";
           }
           enum "1589.78" {
             description "1589.78 nm/188.575000 THz 3.125/6.25/12.5GHz spacing";
           }
           enum "1589.75" {
             description "1589.75 nm/188.578125 THz 3.125GHz spacing";
           }
           enum "1589.73" {
             description "1589.73 nm/188.581250 THz 3.125/6.25GHz spacing";
           }
           enum "1589.70" {
             description "1589.70 nm/188.584375 THz 3.125GHz spacing";
           }
           enum "1589.67" {
             description "1589.67 nm/188.587500 THz 3.125/6.25/12.5GHz spacing";
           }
           enum "1589.65" {
             description "1589.65 nm/188.590625 THz 3.125GHz spacing";
           }
           enum "1589.62" {
             description "1589.62 nm/188.593750 THz 3.125/6.25GHz spacing";
           }
           enum "1589.59" {
             description "1589.59 nm/188.596875 THz 3.125GHz spacing";
           }
           enum "1589.57" {
             description "1589.57 nm/188.600000 THz 3.125/6.25/12.5/100GHz spacing";
           }
           enum "1589.54" {
             description "1589.54 nm/188.603125 THz 3.125GHz spacing";
           }
           enum "1589.51" {
             description "1589.51 nm/188.606250 THz 3.125/6.25GHz spacing";
           }
           enum "1589.49" {
             description "1589.49 nm/188.609375 THz 3.125GHz spacing";
           }
           enum "1589.46" {
             description "1589.46 nm/188.612500 THz 3.125/6.25/12.5GHz spacing";
           }
           enum "1589.44" {
             description "1589.44 nm/188.615625 THz 3.125GHz spacing";
           }
           enum "1589.41" {
             description "1589.41 nm/188.618750 THz 3.125/6.25GHz spacing";
           }
           enum "1589.38" {
             description "1589.38 nm/188.621875 THz 3.125GHz spacing";
           }
           enum "1589.36" {
             description "1589.36 nm/188.625000 THz 3.125/6.25/12.5GHz spacing";
           }
           enum "1589.33" {
             description "1589.33 nm/188.628125 THz 3.125GHz spacing";
           }
           enum "1589.30" {
             description "1589.30 nm/188.631250 THz 3.125/6.25GHz spacing";
           }
           enum "1589.28" {
             description "1589.28 nm/188.634375 THz 3.125GHz spacing";
           }
           enum "1589.25" {
             description "1589.25 nm/188.637500 THz 3.125/6.25/12.5GHz spacing";
           }
           enum "1589.23" {
             description "1589.23 nm/188.640625 THz 3.125GHz spacing";
           }
           enum "1589.20" {
             description "1589.20 nm/188.643750 THz 3.125/6.25GHz spacing";
           }
           enum "1589.17" {
             description "1589.17 nm/188.646875 THz 3.125GHz spacing";
           }
           enum "1589.15" {
             description "1589.15 nm/188.650000 THz 3.125/6.25/12.5/50GHz spacing";
           }
           enum "1589.12" {
             description "1589.12 nm/188.653125 THz 3.125GHz spacing";
           }
           enum "1589.09" {
             description "1589.09 nm/188.656250 THz 3.125/6.25GHz spacing";
           }
           enum "1589.07" {
             description "1589.07 nm/188.659375 THz 3.125GHz spacing";
           }
           enum "1589.04" {
             description "1589.04 nm/188.662500 THz 3.125/6.25/12.5GHz spacing";
           }
           enum "1589.01" {
             description "1589.01 nm/188.665625 THz 3.125GHz spacing";
           }
           enum "1588.99" {
             description "1588.99 nm/188.668750 THz 3.125/6.25GHz spacing";
           }
           enum "1588.96" {
             description "1588.96 nm/188.671875 THz 3.125GHz spacing";
           }
           enum "1588.94" {
             description "1588.94 nm/188.675000 THz 3.125/6.25/12.5/75GHz spacing";
           }
           enum "1588.91" {
             description "1588.91 nm/188.678125 THz 3.125GHz spacing";
           }
           enum "1588.88" {
             description "1588.88 nm/188.681250 THz 3.125/6.25GHz spacing";
           }
           enum "1588.86" {
             description "1588.86 nm/188.684375 THz 3.125GHz spacing";
           }
           enum "1588.83" {
             description "1588.83 nm/188.687500 THz 3.125/6.25/12.5GHz spacing";
           }
           enum "1588.80" {
             description "1588.80 nm/188.690625 THz 3.125GHz spacing";
           }
           enum "1588.78" {
             description "1588.78 nm/188.693750 THz 3.125/6.25GHz spacing";
           }
           enum "1588.75" {
             description "1588.75 nm/188.696875 THz 3.125GHz spacing";
           }
           enum "1588.73" {
             description "1588.73 nm/188.700000 THz 3.125/6.25/12.5/50/75/100GHz spacing";
           }
           enum "1588.70" {
             description "1588.70 nm/188.703125 THz 3.125GHz spacing";
           }
           enum "1588.67" {
             description "1588.67 nm/188.706250 THz 3.125/6.25GHz spacing";
           }
           enum "1588.65" {
             description "1588.65 nm/188.709375 THz 3.125GHz spacing";
           }
           enum "1588.62" {
             description "1588.62 nm/188.712500 THz 3.125/6.25/12.5GHz spacing";
           }
           enum "1588.59" {
             description "1588.59 nm/188.715625 THz 3.125GHz spacing";
           }
           enum "1588.57" {
             description "1588.57 nm/188.718750 THz 3.125/6.25GHz spacing";
           }
           enum "1588.54" {
             description "1588.54 nm/188.721875 THz 3.125GHz spacing";
           }
           enum "1588.51" {
             description "1588.51 nm/188.725000 THz 3.125/6.25/12.5GHz spacing";
           }
           enum "1588.49" {
             description "1588.49 nm/188.728125 THz 3.125GHz spacing";
           }
           enum "1588.46" {
             description "1588.46 nm/188.731250 THz 3.125/6.25GHz spacing";
           }
           enum "1588.44" {
             description "1588.44 nm/188.734375 THz 3.125GHz spacing";
           }
           enum "1588.41" {
             description "1588.41 nm/188.737500 THz 3.125/6.25/12.5GHz spacing";
           }
           enum "1588.38" {
             description "1588.38 nm/188.740625 THz 3.125GHz spacing";
           }
           enum "1588.36" {
             description "1588.36 nm/188.743750 THz 3.125/6.25GHz spacing";
           }
           enum "1588.33" {
             description "1588.33 nm/188.746875 THz 3.125GHz spacing";
           }
           enum "1588.30" {
             description "1588.30 nm/188.750000 THz 3.125/6.25/12.5/50/75GHz spacing";
           }
           enum "1588.28" {
             description "1588.28 nm/188.753125 THz 3.125GHz spacing";
           }
           enum "1588.25" {
             description "1588.25 nm/188.756250 THz 3.125/6.25GHz spacing";
           }
           enum "1588.23" {
             description "1588.23 nm/188.759375 THz 3.125GHz spacing";
           }
           enum "1588.20" {
             description "1588.20 nm/188.762500 THz 3.125/6.25/12.5GHz spacing";
           }
           enum "1588.17" {
             description "1588.17 nm/188.765625 THz 3.125GHz spacing";
           }
           enum "1588.15" {
             description "1588.15 nm/188.768750 THz 3.125/6.25GHz spacing";
           }
           enum "1588.12" {
             description "1588.12 nm/188.771875 THz 3.125GHz spacing";
           }
           enum "1588.09" {
             description "1588.09 nm/188.775000 THz 3.125/6.25/12.5GHz spacing";
           }
           enum "1588.07" {
             description "1588.07 nm/188.778125 THz 3.125GHz spacing";
           }
           enum "1588.04" {
             description "1588.04 nm/188.781250 THz 3.125/6.25GHz spacing";
           }
           enum "1588.02" {
             description "1588.02 nm/188.784375 THz 3.125GHz spacing";
           }
           enum "1587.99" {
             description "1587.99 nm/188.787500 THz 3.125/6.25/12.5GHz spacing";
           }
           enum "1587.96" {
             description "1587.96 nm/188.790625 THz 3.125GHz spacing";
           }
           enum "1587.94" {
             description "1587.94 nm/188.793750 THz 3.125/6.25GHz spacing";
           }
           enum "1587.91" {
             description "1587.91 nm/188.796875 THz 3.125GHz spacing";
           }
           enum "1587.88" {
             description "1587.88 nm/188.800000 THz 3.125/6.25/12.5/100GHz spacing";
           }
           enum "1587.86" {
             description "1587.86 nm/188.803125 THz 3.125GHz spacing";
           }
           enum "1587.83" {
             description "1587.83 nm/188.806250 THz 3.125/6.25GHz spacing";
           }
           enum "1587.80" {
             description "1587.80 nm/188.809375 THz 3.125GHz spacing";
           }
           enum "1587.78" {
             description "1587.78 nm/188.812500 THz 3.125/6.25/12.5GHz spacing";
           }
           enum "1587.75" {
             description "1587.75 nm/188.815625 THz 3.125GHz spacing";
           }
           enum "1587.73" {
             description "1587.73 nm/188.818750 THz 3.125/6.25GHz spacing";
           }
           enum "1587.70" {
             description "1587.70 nm/188.821875 THz 3.125GHz spacing";
           }
           enum "1587.67" {
             description "1587.67 nm/188.825000 THz 3.125/6.25/12.5/75GHz spacing";
           }
           enum "1587.65" {
             description "1587.65 nm/188.828125 THz 3.125GHz spacing";
           }
           enum "1587.62" {
             description "1587.62 nm/188.831250 THz 3.125/6.25GHz spacing";
           }
           enum "1587.59" {
             description "1587.59 nm/188.834375 THz 3.125GHz spacing";
           }
           enum "1587.57" {
             description "1587.57 nm/188.837500 THz 3.125/6.25/12.5GHz spacing";
           }
           enum "1587.54" {
             description "1587.54 nm/188.840625 THz 3.125GHz spacing";
           }
           enum "1587.52" {
             description "1587.52 nm/188.843750 THz 3.125/6.25GHz spacing";
           }
           enum "1587.49" {
             description "1587.49 nm/188.846875 THz 3.125GHz spacing";
           }
           enum "1587.46" {
             description "1587.46 nm/188.850000 THz 3.125/6.25/12.5/50GHz spacing";
           }
           enum "1587.44" {
             description "1587.44 nm/188.853125 THz 3.125GHz spacing";
           }
           enum "1587.41" {
             description "1587.41 nm/188.856250 THz 3.125/6.25GHz spacing";
           }
           enum "1587.38" {
             description "1587.38 nm/188.859375 THz 3.125GHz spacing";
           }
           enum "1587.36" {
             description "1587.36 nm/188.862500 THz 3.125/6.25/12.5GHz spacing";
           }
           enum "1587.33" {
             description "1587.33 nm/188.865625 THz 3.125GHz spacing";
           }
           enum "1587.31" {
             description "1587.31 nm/188.868750 THz 3.125/6.25GHz spacing";
           }
           enum "1587.28" {
             description "1587.28 nm/188.871875 THz 3.125GHz spacing";
           }
           enum "1587.25" {
             description "1587.25 nm/188.875000 THz 3.125/6.25/12.5GHz spacing";
           }
           enum "1587.23" {
             description "1587.23 nm/188.878125 THz 3.125GHz spacing";
           }
           enum "1587.20" {
             description "1587.20 nm/188.881250 THz 3.125/6.25GHz spacing";
           }
           enum "1587.17" {
             description "1587.17 nm/188.884375 THz 3.125GHz spacing";
           }
           enum "1587.15" {
             description "1587.15 nm/188.887500 THz 3.125/6.25/12.5GHz spacing";
           }
           enum "1587.12" {
             description "1587.12 nm/188.890625 THz 3.125GHz spacing";
           }
           enum "1587.10" {
             description "1587.10 nm/188.893750 THz 3.125/6.25GHz spacing";
           }
           enum "1587.07" {
             description "1587.07 nm/188.896875 THz 3.125GHz spacing";
           }
           enum "1587.04" {
             description "1587.04 nm/188.900000 THz 3.125/6.25/12.5/100GHz spacing";
           }
           enum "1587.02" {
             description "1587.02 nm/188.903125 THz 3.125GHz spacing";
           }
           enum "1586.99" {
             description "1586.99 nm/188.906250 THz 3.125/6.25GHz spacing";
           }
           enum "1586.96" {
             description "1586.96 nm/188.909375 THz 3.125GHz spacing";
           }
           enum "1586.94" {
             description "1586.94 nm/188.912500 THz 3.125/6.25/12.5GHz spacing";
           }
           enum "1586.91" {
             description "1586.91 nm/188.915625 THz 3.125GHz spacing";
           }
           enum "1586.89" {
             description "1586.89 nm/188.918750 THz 3.125/6.25GHz spacing";
           }
           enum "1586.86" {
             description "1586.86 nm/188.921875 THz 3.125GHz spacing";
           }
           enum "1586.83" {
             description "1586.83 nm/188.925000 THz 3.125/6.25/12.5GHz spacing";
           }
           enum "1586.81" {
             description "1586.81 nm/188.928125 THz 3.125GHz spacing";
           }
           enum "1586.78" {
             description "1586.78 nm/188.931250 THz 3.125/6.25GHz spacing";
           }
           enum "1586.75" {
             description "1586.75 nm/188.934375 THz 3.125GHz spacing";
           }
           enum "1586.73" {
             description "1586.73 nm/188.937500 THz 3.125/6.25/12.5GHz spacing";
           }
           enum "1586.70" {
             description "1586.70 nm/188.940625 THz 3.125GHz spacing";
           }
           enum "1586.68" {
             description "1586.68 nm/188.943750 THz 3.125/6.25GHz spacing";
           }
           enum "1586.65" {
             description "1586.65 nm/188.946875 THz 3.125GHz spacing";
           }
           enum "1586.62" {
             description "1586.62 nm/188.950000 THz 3.125/6.25/12.5/50GHz spacing";
           }
           enum "1586.60" {
             description "1586.60 nm/188.953125 THz 3.125GHz spacing";
           }
           enum "1586.57" {
             description "1586.57 nm/188.956250 THz 3.125/6.25GHz spacing";
           }
           enum "1586.54" {
             description "1586.54 nm/188.959375 THz 3.125GHz spacing";
           }
           enum "1586.52" {
             description "1586.52 nm/188.962500 THz 3.125/6.25/12.5GHz spacing";
           }
           enum "1586.49" {
             description "1586.49 nm/188.965625 THz 3.125GHz spacing";
           }
           enum "1586.47" {
             description "1586.47 nm/188.968750 THz 3.125/6.25GHz spacing";
           }
           enum "1586.44" {
             description "1586.44 nm/188.971875 THz 3.125GHz spacing";
           }
           enum "1586.41" {
             description "1586.41 nm/188.975000 THz 3.125/6.25/12.5/75GHz spacing";
           }
           enum "1586.39" {
             description "1586.39 nm/188.978125 THz 3.125GHz spacing";
           }
           enum "1586.36" {
             description "1586.36 nm/188.981250 THz 3.125/6.25GHz spacing";
           }
           enum "1586.33" {
             description "1586.33 nm/188.984375 THz 3.125GHz spacing";
           }
           enum "1586.31" {
             description "1586.31 nm/188.987500 THz 3.125/6.25/12.5GHz spacing";
           }
           enum "1586.28" {
             description "1586.28 nm/188.990625 THz 3.125GHz spacing";
           }
           enum "1586.26" {
             description "1586.26 nm/188.993750 THz 3.125/6.25GHz spacing";
           }
           enum "1586.23" {
             description "1586.23 nm/188.996875 THz 3.125GHz spacing";
           }
           enum "1586.20" {
             description "1586.20 nm/189.000000 THz 3.125/6.25/12.5/50/75/100GHz spacing";
           }
           enum "1586.18" {
             description "1586.18 nm/189.003125 THz 3.125GHz spacing";
           }
           enum "1586.15" {
             description "1586.15 nm/189.006250 THz 3.125/6.25GHz spacing";
           }
           enum "1586.12" {
             description "1586.12 nm/189.009375 THz 3.125GHz spacing";
           }
           enum "1586.10" {
             description "1586.10 nm/189.012500 THz 3.125/6.25/12.5GHz spacing";
           }
           enum "1586.07" {
             description "1586.07 nm/189.015625 THz 3.125GHz spacing";
           }
           enum "1586.05" {
             description "1586.05 nm/189.018750 THz 3.125/6.25GHz spacing";
           }
           enum "1586.02" {
             description "1586.02 nm/189.021875 THz 3.125GHz spacing";
           }
           enum "1585.99" {
             description "1585.99 nm/189.025000 THz 3.125/6.25/12.5GHz spacing";
           }
           enum "1585.97" {
             description "1585.97 nm/189.028125 THz 3.125GHz spacing";
           }
           enum "1585.94" {
             description "1585.94 nm/189.031250 THz 3.125/6.25GHz spacing";
           }
           enum "1585.92" {
             description "1585.92 nm/189.034375 THz 3.125GHz spacing";
           }
           enum "1585.89" {
             description "1585.89 nm/189.037500 THz 3.125/6.25/12.5GHz spacing";
           }
           enum "1585.86" {
             description "1585.86 nm/189.040625 THz 3.125GHz spacing";
           }
           enum "1585.84" {
             description "1585.84 nm/189.043750 THz 3.125/6.25GHz spacing";
           }
           enum "1585.81" {
             description "1585.81 nm/189.046875 THz 3.125GHz spacing";
           }
           enum "1585.78" {
             description "1585.78 nm/189.050000 THz 3.125/6.25/12.5/50/75GHz spacing";
           }
           enum "1585.76" {
             description "1585.76 nm/189.053125 THz 3.125GHz spacing";
           }
           enum "1585.73" {
             description "1585.73 nm/189.056250 THz 3.125/6.25GHz spacing";
           }
           enum "1585.71" {
             description "1585.71 nm/189.059375 THz 3.125GHz spacing";
           }
           enum "1585.68" {
             description "1585.68 nm/189.062500 THz 3.125/6.25/12.5GHz spacing";
           }
           enum "1585.65" {
             description "1585.65 nm/189.065625 THz 3.125GHz spacing";
           }
           enum "1585.63" {
             description "1585.63 nm/189.068750 THz 3.125/6.25GHz spacing";
           }
           enum "1585.60" {
             description "1585.60 nm/189.071875 THz 3.125GHz spacing";
           }
           enum "1585.57" {
             description "1585.57 nm/189.075000 THz 3.125/6.25/12.5GHz spacing";
           }
           enum "1585.55" {
             description "1585.55 nm/189.078125 THz 3.125GHz spacing";
           }
           enum "1585.52" {
             description "1585.52 nm/189.081250 THz 3.125/6.25GHz spacing";
           }
           enum "1585.50" {
             description "1585.50 nm/189.084375 THz 3.125GHz spacing";
           }
           enum "1585.47" {
             description "1585.47 nm/189.087500 THz 3.125/6.25/12.5GHz spacing";
           }
           enum "1585.44" {
             description "1585.44 nm/189.090625 THz 3.125GHz spacing";
           }
           enum "1585.42" {
             description "1585.42 nm/189.093750 THz 3.125/6.25GHz spacing";
           }
           enum "1585.39" {
             description "1585.39 nm/189.096875 THz 3.125GHz spacing";
           }
           enum "1585.36" {
             description "1585.36 nm/189.100000 THz 3.125/6.25/12.5/100GHz spacing";
           }
           enum "1585.34" {
             description "1585.34 nm/189.103125 THz 3.125GHz spacing";
           }
           enum "1585.31" {
             description "1585.31 nm/189.106250 THz 3.125/6.25GHz spacing";
           }
           enum "1585.29" {
             description "1585.29 nm/189.109375 THz 3.125GHz spacing";
           }
           enum "1585.26" {
             description "1585.26 nm/189.112500 THz 3.125/6.25/12.5GHz spacing";
           }
           enum "1585.23" {
             description "1585.23 nm/189.115625 THz 3.125GHz spacing";
           }
           enum "1585.21" {
             description "1585.21 nm/189.118750 THz 3.125/6.25GHz spacing";
           }
           enum "1585.18" {
             description "1585.18 nm/189.121875 THz 3.125GHz spacing";
           }
           enum "1585.16" {
             description "1585.16 nm/189.125000 THz 3.125/6.25/12.5/75GHz spacing";
           }
           enum "1585.13" {
             description "1585.13 nm/189.128125 THz 3.125GHz spacing";
           }
           enum "1585.10" {
             description "1585.10 nm/189.131250 THz 3.125/6.25GHz spacing";
           }
           enum "1585.08" {
             description "1585.08 nm/189.134375 THz 3.125GHz spacing";
           }
           enum "1585.05" {
             description "1585.05 nm/189.137500 THz 3.125/6.25/12.5GHz spacing";
           }
           enum "1585.02" {
             description "1585.02 nm/189.140625 THz 3.125GHz spacing";
           }
           enum "1585.00" {
             description "1585.00 nm/189.143750 THz 3.125/6.25GHz spacing";
           }
           enum "1584.97" {
             description "1584.97 nm/189.146875 THz 3.125GHz spacing";
           }
           enum "1584.95" {
             description "1584.95 nm/189.150000 THz 3.125/6.25/12.5/50GHz spacing";
           }
           enum "1584.92" {
             description "1584.92 nm/189.153125 THz 3.125GHz spacing";
           }
           enum "1584.89" {
             description "1584.89 nm/189.156250 THz 3.125/6.25GHz spacing";
           }
           enum "1584.87" {
             description "1584.87 nm/189.159375 THz 3.125GHz spacing";
           }
           enum "1584.84" {
             description "1584.84 nm/189.162500 THz 3.125/6.25/12.5GHz spacing";
           }
           enum "1584.81" {
             description "1584.81 nm/189.165625 THz 3.125GHz spacing";
           }
           enum "1584.79" {
             description "1584.79 nm/189.168750 THz 3.125/6.25GHz spacing";
           }
           enum "1584.76" {
             description "1584.76 nm/189.171875 THz 3.125GHz spacing";
           }
           enum "1584.74" {
             description "1584.74 nm/189.175000 THz 3.125/6.25/12.5GHz spacing";
           }
           enum "1584.71" {
             description "1584.71 nm/189.178125 THz 3.125GHz spacing";
           }
           enum "1584.68" {
             description "1584.68 nm/189.181250 THz 3.125/6.25GHz spacing";
           }
           enum "1584.66" {
             description "1584.66 nm/189.184375 THz 3.125GHz spacing";
           }
           enum "1584.63" {
             description "1584.63 nm/189.187500 THz 3.125/6.25/12.5GHz spacing";
           }
           enum "1584.61" {
             description "1584.61 nm/189.190625 THz 3.125GHz spacing";
           }
           enum "1584.58" {
             description "1584.58 nm/189.193750 THz 3.125/6.25GHz spacing";
           }
           enum "1584.55" {
             description "1584.55 nm/189.196875 THz 3.125GHz spacing";
           }
           enum "1584.53" {
             description "1584.53 nm/189.200000 THz 3.125/6.25/12.5/100GHz spacing";
           }
           enum "1584.50" {
             description "1584.50 nm/189.203125 THz 3.125GHz spacing";
           }
           enum "1584.47" {
             description "1584.47 nm/189.206250 THz 3.125/6.25GHz spacing";
           }
           enum "1584.45" {
             description "1584.45 nm/189.209375 THz 3.125GHz spacing";
           }
           enum "1584.42" {
             description "1584.42 nm/189.212500 THz 3.125/6.25/12.5GHz spacing";
           }
           enum "1584.40" {
             description "1584.40 nm/189.215625 THz 3.125GHz spacing";
           }
           enum "1584.37" {
             description "1584.37 nm/189.218750 THz 3.125/6.25GHz spacing";
           }
           enum "1584.34" {
             description "1584.34 nm/189.221875 THz 3.125GHz spacing";
           }
           enum "1584.32" {
             description "1584.32 nm/189.225000 THz 3.125/6.25/12.5GHz spacing";
           }
           enum "1584.29" {
             description "1584.29 nm/189.228125 THz 3.125GHz spacing";
           }
           enum "1584.27" {
             description "1584.27 nm/189.231250 THz 3.125/6.25GHz spacing";
           }
           enum "1584.24" {
             description "1584.24 nm/189.234375 THz 3.125GHz spacing";
           }
           enum "1584.21" {
             description "1584.21 nm/189.237500 THz 3.125/6.25/12.5GHz spacing";
           }
           enum "1584.19" {
             description "1584.19 nm/189.240625 THz 3.125GHz spacing";
           }
           enum "1584.16" {
             description "1584.16 nm/189.243750 THz 3.125/6.25GHz spacing";
           }
           enum "1584.13" {
             description "1584.13 nm/189.246875 THz 3.125GHz spacing";
           }
           enum "1584.11" {
             description "1584.11 nm/189.250000 THz 3.125/6.25/12.5/50GHz spacing";
           }
           enum "1584.08" {
             description "1584.08 nm/189.253125 THz 3.125GHz spacing";
           }
           enum "1584.06" {
             description "1584.06 nm/189.256250 THz 3.125/6.25GHz spacing";
           }
           enum "1584.03" {
             description "1584.03 nm/189.259375 THz 3.125GHz spacing";
           }
           enum "1584.00" {
             description "1584.00 nm/189.262500 THz 3.125/6.25/12.5GHz spacing";
           }
           enum "1583.98" {
             description "1583.98 nm/189.265625 THz 3.125GHz spacing";
           }
           enum "1583.95" {
             description "1583.95 nm/189.268750 THz 3.125/6.25GHz spacing";
           }
           enum "1583.93" {
             description "1583.93 nm/189.271875 THz 3.125GHz spacing";
           }
           enum "1583.90" {
             description "1583.90 nm/189.275000 THz 3.125/6.25/12.5/75GHz spacing";
           }
           enum "1583.87" {
             description "1583.87 nm/189.278125 THz 3.125GHz spacing";
           }
           enum "1583.85" {
             description "1583.85 nm/189.281250 THz 3.125/6.25GHz spacing";
           }
           enum "1583.82" {
             description "1583.82 nm/189.284375 THz 3.125GHz spacing";
           }
           enum "1583.79" {
             description "1583.79 nm/189.287500 THz 3.125/6.25/12.5GHz spacing";
           }
           enum "1583.77" {
             description "1583.77 nm/189.290625 THz 3.125GHz spacing";
           }
           enum "1583.74" {
             description "1583.74 nm/189.293750 THz 3.125/6.25GHz spacing";
           }
           enum "1583.72" {
             description "1583.72 nm/189.296875 THz 3.125GHz spacing";
           }
           enum "1583.69" {
             description "1583.69 nm/189.300000 THz 3.125/6.25/12.5/50/75/100GHz spacing";
           }
           enum "1583.66" {
             description "1583.66 nm/189.303125 THz 3.125GHz spacing";
           }
           enum "1583.64" {
             description "1583.64 nm/189.306250 THz 3.125/6.25GHz spacing";
           }
           enum "1583.61" {
             description "1583.61 nm/189.309375 THz 3.125GHz spacing";
           }
           enum "1583.59" {
             description "1583.59 nm/189.312500 THz 3.125/6.25/12.5GHz spacing";
           }
           enum "1583.56" {
             description "1583.56 nm/189.315625 THz 3.125GHz spacing";
           }
           enum "1583.53" {
             description "1583.53 nm/189.318750 THz 3.125/6.25GHz spacing";
           }
           enum "1583.51" {
             description "1583.51 nm/189.321875 THz 3.125GHz spacing";
           }
           enum "1583.48" {
             description "1583.48 nm/189.325000 THz 3.125/6.25/12.5GHz spacing";
           }
           enum "1583.45" {
             description "1583.45 nm/189.328125 THz 3.125GHz spacing";
           }
           enum "1583.43" {
             description "1583.43 nm/189.331250 THz 3.125/6.25GHz spacing";
           }
           enum "1583.40" {
             description "1583.40 nm/189.334375 THz 3.125GHz spacing";
           }
           enum "1583.38" {
             description "1583.38 nm/189.337500 THz 3.125/6.25/12.5GHz spacing";
           }
           enum "1583.35" {
             description "1583.35 nm/189.340625 THz 3.125GHz spacing";
           }
           enum "1583.32" {
             description "1583.32 nm/189.343750 THz 3.125/6.25GHz spacing";
           }
           enum "1583.30" {
             description "1583.30 nm/189.346875 THz 3.125GHz spacing";
           }
           enum "1583.27" {
             description "1583.27 nm/189.350000 THz 3.125/6.25/12.5/50/75GHz spacing";
           }
           enum "1583.25" {
             description "1583.25 nm/189.353125 THz 3.125GHz spacing";
           }
           enum "1583.22" {
             description "1583.22 nm/189.356250 THz 3.125/6.25GHz spacing";
           }
           enum "1583.19" {
             description "1583.19 nm/189.359375 THz 3.125GHz spacing";
           }
           enum "1583.17" {
             description "1583.17 nm/189.362500 THz 3.125/6.25/12.5GHz spacing";
           }
           enum "1583.14" {
             description "1583.14 nm/189.365625 THz 3.125GHz spacing";
           }
           enum "1583.11" {
             description "1583.11 nm/189.368750 THz 3.125/6.25GHz spacing";
           }
           enum "1583.09" {
             description "1583.09 nm/189.371875 THz 3.125GHz spacing";
           }
           enum "1583.06" {
             description "1583.06 nm/189.375000 THz 3.125/6.25/12.5GHz spacing";
           }
           enum "1583.04" {
             description "1583.04 nm/189.378125 THz 3.125GHz spacing";
           }
           enum "1583.01" {
             description "1583.01 nm/189.381250 THz 3.125/6.25GHz spacing";
           }
           enum "1582.98" {
             description "1582.98 nm/189.384375 THz 3.125GHz spacing";
           }
           enum "1582.96" {
             description "1582.96 nm/189.387500 THz 3.125/6.25/12.5GHz spacing";
           }
           enum "1582.93" {
             description "1582.93 nm/189.390625 THz 3.125GHz spacing";
           }
           enum "1582.91" {
             description "1582.91 nm/189.393750 THz 3.125/6.25GHz spacing";
           }
           enum "1582.88" {
             description "1582.88 nm/189.396875 THz 3.125GHz spacing";
           }
           enum "1582.85" {
             description "1582.85 nm/189.400000 THz 3.125/6.25/12.5/100GHz spacing";
           }
           enum "1582.83" {
             description "1582.83 nm/189.403125 THz 3.125GHz spacing";
           }
           enum "1582.80" {
             description "1582.80 nm/189.406250 THz 3.125/6.25GHz spacing";
           }
           enum "1582.78" {
             description "1582.78 nm/189.409375 THz 3.125GHz spacing";
           }
           enum "1582.75" {
             description "1582.75 nm/189.412500 THz 3.125/6.25/12.5GHz spacing";
           }
           enum "1582.72" {
             description "1582.72 nm/189.415625 THz 3.125GHz spacing";
           }
           enum "1582.70" {
             description "1582.70 nm/189.418750 THz 3.125/6.25GHz spacing";
           }
           enum "1582.67" {
             description "1582.67 nm/189.421875 THz 3.125GHz spacing";
           }
           enum "1582.64" {
             description "1582.64 nm/189.425000 THz 3.125/6.25/12.5/75GHz spacing";
           }
           enum "1582.62" {
             description "1582.62 nm/189.428125 THz 3.125GHz spacing";
           }
           enum "1582.59" {
             description "1582.59 nm/189.431250 THz 3.125/6.25GHz spacing";
           }
           enum "1582.57" {
             description "1582.57 nm/189.434375 THz 3.125GHz spacing";
           }
           enum "1582.54" {
             description "1582.54 nm/189.437500 THz 3.125/6.25/12.5GHz spacing";
           }
           enum "1582.51" {
             description "1582.51 nm/189.440625 THz 3.125GHz spacing";
           }
           enum "1582.49" {
             description "1582.49 nm/189.443750 THz 3.125/6.25GHz spacing";
           }
           enum "1582.46" {
             description "1582.46 nm/189.446875 THz 3.125GHz spacing";
           }
           enum "1582.44" {
             description "1582.44 nm/189.450000 THz 3.125/6.25/12.5/50GHz spacing";
           }
           enum "1582.41" {
             description "1582.41 nm/189.453125 THz 3.125GHz spacing";
           }
           enum "1582.38" {
             description "1582.38 nm/189.456250 THz 3.125/6.25GHz spacing";
           }
           enum "1582.36" {
             description "1582.36 nm/189.459375 THz 3.125GHz spacing";
           }
           enum "1582.33" {
             description "1582.33 nm/189.462500 THz 3.125/6.25/12.5GHz spacing";
           }
           enum "1582.31" {
             description "1582.31 nm/189.465625 THz 3.125GHz spacing";
           }
           enum "1582.28" {
             description "1582.28 nm/189.468750 THz 3.125/6.25GHz spacing";
           }
           enum "1582.25" {
             description "1582.25 nm/189.471875 THz 3.125GHz spacing";
           }
           enum "1582.23" {
             description "1582.23 nm/189.475000 THz 3.125/6.25/12.5GHz spacing";
           }
           enum "1582.20" {
             description "1582.20 nm/189.478125 THz 3.125GHz spacing";
           }
           enum "1582.17" {
             description "1582.17 nm/189.481250 THz 3.125/6.25GHz spacing";
           }
           enum "1582.15" {
             description "1582.15 nm/189.484375 THz 3.125GHz spacing";
           }
           enum "1582.12" {
             description "1582.12 nm/189.487500 THz 3.125/6.25/12.5GHz spacing";
           }
           enum "1582.10" {
             description "1582.10 nm/189.490625 THz 3.125GHz spacing";
           }
           enum "1582.07" {
             description "1582.07 nm/189.493750 THz 3.125/6.25GHz spacing";
           }
           enum "1582.04" {
             description "1582.04 nm/189.496875 THz 3.125GHz spacing";
           }
           enum "1582.02" {
             description "1582.02 nm/189.500000 THz 3.125/6.25/12.5/100GHz spacing";
           }
           enum "1581.99" {
             description "1581.99 nm/189.503125 THz 3.125GHz spacing";
           }
           enum "1581.97" {
             description "1581.97 nm/189.506250 THz 3.125/6.25GHz spacing";
           }
           enum "1581.94" {
             description "1581.94 nm/189.509375 THz 3.125GHz spacing";
           }
           enum "1581.91" {
             description "1581.91 nm/189.512500 THz 3.125/6.25/12.5GHz spacing";
           }
           enum "1581.89" {
             description "1581.89 nm/189.515625 THz 3.125GHz spacing";
           }
           enum "1581.86" {
             description "1581.86 nm/189.518750 THz 3.125/6.25GHz spacing";
           }
           enum "1581.84" {
             description "1581.84 nm/189.521875 THz 3.125GHz spacing";
           }
           enum "1581.81" {
             description "1581.81 nm/189.525000 THz 3.125/6.25/12.5GHz spacing";
           }
           enum "1581.78" {
             description "1581.78 nm/189.528125 THz 3.125GHz spacing";
           }
           enum "1581.76" {
             description "1581.76 nm/189.531250 THz 3.125/6.25GHz spacing";
           }
           enum "1581.73" {
             description "1581.73 nm/189.534375 THz 3.125GHz spacing";
           }
           enum "1581.71" {
             description "1581.71 nm/189.537500 THz 3.125/6.25/12.5GHz spacing";
           }
           enum "1581.68" {
             description "1581.68 nm/189.540625 THz 3.125GHz spacing";
           }
           enum "1581.65" {
             description "1581.65 nm/189.543750 THz 3.125/6.25GHz spacing";
           }
           enum "1581.63" {
             description "1581.63 nm/189.546875 THz 3.125GHz spacing";
           }
           enum "1581.60" {
             description "1581.60 nm/189.550000 THz 3.125/6.25/12.5/50GHz spacing";
           }
           enum "1581.57" {
             description "1581.57 nm/189.553125 THz 3.125GHz spacing";
           }
           enum "1581.55" {
             description "1581.55 nm/189.556250 THz 3.125/6.25GHz spacing";
           }
           enum "1581.52" {
             description "1581.52 nm/189.559375 THz 3.125GHz spacing";
           }
           enum "1581.50" {
             description "1581.50 nm/189.562500 THz 3.125/6.25/12.5GHz spacing";
           }
           enum "1581.47" {
             description "1581.47 nm/189.565625 THz 3.125GHz spacing";
           }
           enum "1581.44" {
             description "1581.44 nm/189.568750 THz 3.125/6.25GHz spacing";
           }
           enum "1581.42" {
             description "1581.42 nm/189.571875 THz 3.125GHz spacing";
           }
           enum "1581.39" {
             description "1581.39 nm/189.575000 THz 3.125/6.25/12.5/75GHz spacing";
           }
           enum "1581.37" {
             description "1581.37 nm/189.578125 THz 3.125GHz spacing";
           }
           enum "1581.34" {
             description "1581.34 nm/189.581250 THz 3.125/6.25GHz spacing";
           }
           enum "1581.31" {
             description "1581.31 nm/189.584375 THz 3.125GHz spacing";
           }
           enum "1581.29" {
             description "1581.29 nm/189.587500 THz 3.125/6.25/12.5GHz spacing";
           }
           enum "1581.26" {
             description "1581.26 nm/189.590625 THz 3.125GHz spacing";
           }
           enum "1581.24" {
             description "1581.24 nm/189.593750 THz 3.125/6.25GHz spacing";
           }
           enum "1581.21" {
             description "1581.21 nm/189.596875 THz 3.125GHz spacing";
           }
           enum "1581.18" {
             description "1581.18 nm/189.600000 THz 3.125/6.25/12.5/50/75/100GHz spacing";
           }
           enum "1581.16" {
             description "1581.16 nm/189.603125 THz 3.125GHz spacing";
           }
           enum "1581.13" {
             description "1581.13 nm/189.606250 THz 3.125/6.25GHz spacing";
           }
           enum "1581.11" {
             description "1581.11 nm/189.609375 THz 3.125GHz spacing";
           }
           enum "1581.08" {
             description "1581.08 nm/189.612500 THz 3.125/6.25/12.5GHz spacing";
           }
           enum "1581.05" {
             description "1581.05 nm/189.615625 THz 3.125GHz spacing";
           }
           enum "1581.03" {
             description "1581.03 nm/189.618750 THz 3.125/6.25GHz spacing";
           }
           enum "1581.00" {
             description "1581.00 nm/189.621875 THz 3.125GHz spacing";
           }
           enum "1580.98" {
             description "1580.98 nm/189.625000 THz 3.125/6.25/12.5GHz spacing";
           }
           enum "1580.95" {
             description "1580.95 nm/189.628125 THz 3.125GHz spacing";
           }
           enum "1580.92" {
             description "1580.92 nm/189.631250 THz 3.125/6.25GHz spacing";
           }
           enum "1580.90" {
             description "1580.90 nm/189.634375 THz 3.125GHz spacing";
           }
           enum "1580.87" {
             description "1580.87 nm/189.637500 THz 3.125/6.25/12.5GHz spacing";
           }
           enum "1580.85" {
             description "1580.85 nm/189.640625 THz 3.125GHz spacing";
           }
           enum "1580.82" {
             description "1580.82 nm/189.643750 THz 3.125/6.25GHz spacing";
           }
           enum "1580.79" {
             description "1580.79 nm/189.646875 THz 3.125GHz spacing";
           }
           enum "1580.77" {
             description "1580.77 nm/189.650000 THz 3.125/6.25/12.5/50/75GHz spacing";
           }
           enum "1580.74" {
             description "1580.74 nm/189.653125 THz 3.125GHz spacing";
           }
           enum "1580.71" {
             description "1580.71 nm/189.656250 THz 3.125/6.25GHz spacing";
           }
           enum "1580.69" {
             description "1580.69 nm/189.659375 THz 3.125GHz spacing";
           }
           enum "1580.66" {
             description "1580.66 nm/189.662500 THz 3.125/6.25/12.5GHz spacing";
           }
           enum "1580.64" {
             description "1580.64 nm/189.665625 THz 3.125GHz spacing";
           }
           enum "1580.61" {
             description "1580.61 nm/189.668750 THz 3.125/6.25GHz spacing";
           }
           enum "1580.58" {
             description "1580.58 nm/189.671875 THz 3.125GHz spacing";
           }
           enum "1580.56" {
             description "1580.56 nm/189.675000 THz 3.125/6.25/12.5GHz spacing";
           }
           enum "1580.53" {
             description "1580.53 nm/189.678125 THz 3.125GHz spacing";
           }
           enum "1580.51" {
             description "1580.51 nm/189.681250 THz 3.125/6.25GHz spacing";
           }
           enum "1580.48" {
             description "1580.48 nm/189.684375 THz 3.125GHz spacing";
           }
           enum "1580.45" {
             description "1580.45 nm/189.687500 THz 3.125/6.25/12.5GHz spacing";
           }
           enum "1580.43" {
             description "1580.43 nm/189.690625 THz 3.125GHz spacing";
           }
           enum "1580.40" {
             description "1580.40 nm/189.693750 THz 3.125/6.25GHz spacing";
           }
           enum "1580.38" {
             description "1580.38 nm/189.696875 THz 3.125GHz spacing";
           }
           enum "1580.35" {
             description "1580.35 nm/189.700000 THz 3.125/6.25/12.5/100GHz spacing";
           }
           enum "1580.32" {
             description "1580.32 nm/189.703125 THz 3.125GHz spacing";
           }
           enum "1580.30" {
             description "1580.30 nm/189.706250 THz 3.125/6.25GHz spacing";
           }
           enum "1580.27" {
             description "1580.27 nm/189.709375 THz 3.125GHz spacing";
           }
           enum "1580.25" {
             description "1580.25 nm/189.712500 THz 3.125/6.25/12.5GHz spacing";
           }
           enum "1580.22" {
             description "1580.22 nm/189.715625 THz 3.125GHz spacing";
           }
           enum "1580.19" {
             description "1580.19 nm/189.718750 THz 3.125/6.25GHz spacing";
           }
           enum "1580.17" {
             description "1580.17 nm/189.721875 THz 3.125GHz spacing";
           }
           enum "1580.14" {
             description "1580.14 nm/189.725000 THz 3.125/6.25/12.5/75GHz spacing";
           }
           enum "1580.12" {
             description "1580.12 nm/189.728125 THz 3.125GHz spacing";
           }
           enum "1580.09" {
             description "1580.09 nm/189.731250 THz 3.125/6.25GHz spacing";
           }
           enum "1580.06" {
             description "1580.06 nm/189.734375 THz 3.125GHz spacing";
           }
           enum "1580.04" {
             description "1580.04 nm/189.737500 THz 3.125/6.25/12.5GHz spacing";
           }
           enum "1580.01" {
             description "1580.01 nm/189.740625 THz 3.125GHz spacing";
           }
           enum "1579.99" {
             description "1579.99 nm/189.743750 THz 3.125/6.25GHz spacing";
           }
           enum "1579.96" {
             description "1579.96 nm/189.746875 THz 3.125GHz spacing";
           }
           enum "1579.93" {
             description "1579.93 nm/189.750000 THz 3.125/6.25/12.5/50GHz spacing";
           }
           enum "1579.91" {
             description "1579.91 nm/189.753125 THz 3.125GHz spacing";
           }
           enum "1579.88" {
             description "1579.88 nm/189.756250 THz 3.125/6.25GHz spacing";
           }
           enum "1579.86" {
             description "1579.86 nm/189.759375 THz 3.125GHz spacing";
           }
           enum "1579.83" {
             description "1579.83 nm/189.762500 THz 3.125/6.25/12.5GHz spacing";
           }
           enum "1579.80" {
             description "1579.80 nm/189.765625 THz 3.125GHz spacing";
           }
           enum "1579.78" {
             description "1579.78 nm/189.768750 THz 3.125/6.25GHz spacing";
           }
           enum "1579.75" {
             description "1579.75 nm/189.771875 THz 3.125GHz spacing";
           }
           enum "1579.73" {
             description "1579.73 nm/189.775000 THz 3.125/6.25/12.5GHz spacing";
           }
           enum "1579.70" {
             description "1579.70 nm/189.778125 THz 3.125GHz spacing";
           }
           enum "1579.67" {
             description "1579.67 nm/189.781250 THz 3.125/6.25GHz spacing";
           }
           enum "1579.65" {
             description "1579.65 nm/189.784375 THz 3.125GHz spacing";
           }
           enum "1579.62" {
             description "1579.62 nm/189.787500 THz 3.125/6.25/12.5GHz spacing";
           }
           enum "1579.60" {
             description "1579.60 nm/189.790625 THz 3.125GHz spacing";
           }
           enum "1579.57" {
             description "1579.57 nm/189.793750 THz 3.125/6.25GHz spacing";
           }
           enum "1579.54" {
             description "1579.54 nm/189.796875 THz 3.125GHz spacing";
           }
           enum "1579.52" {
             description "1579.52 nm/189.800000 THz 3.125/6.25/12.5/100GHz spacing";
           }
           enum "1579.49" {
             description "1579.49 nm/189.803125 THz 3.125GHz spacing";
           }
           enum "1579.47" {
             description "1579.47 nm/189.806250 THz 3.125/6.25GHz spacing";
           }
           enum "1579.44" {
             description "1579.44 nm/189.809375 THz 3.125GHz spacing";
           }
           enum "1579.41" {
             description "1579.41 nm/189.812500 THz 3.125/6.25/12.5GHz spacing";
           }
           enum "1579.39" {
             description "1579.39 nm/189.815625 THz 3.125GHz spacing";
           }
           enum "1579.36" {
             description "1579.36 nm/189.818750 THz 3.125/6.25GHz spacing";
           }
           enum "1579.34" {
             description "1579.34 nm/189.821875 THz 3.125GHz spacing";
           }
           enum "1579.31" {
             description "1579.31 nm/189.825000 THz 3.125/6.25/12.5GHz spacing";
           }
           enum "1579.28" {
             description "1579.28 nm/189.828125 THz 3.125GHz spacing";
           }
           enum "1579.26" {
             description "1579.26 nm/189.831250 THz 3.125/6.25GHz spacing";
           }
           enum "1579.23" {
             description "1579.23 nm/189.834375 THz 3.125GHz spacing";
           }
           enum "1579.21" {
             description "1579.21 nm/189.837500 THz 3.125/6.25/12.5GHz spacing";
           }
           enum "1579.18" {
             description "1579.18 nm/189.840625 THz 3.125GHz spacing";
           }
           enum "1579.15" {
             description "1579.15 nm/189.843750 THz 3.125/6.25GHz spacing";
           }
           enum "1579.13" {
             description "1579.13 nm/189.846875 THz 3.125GHz spacing";
           }
           enum "1579.10" {
             description "1579.10 nm/189.850000 THz 3.125/6.25/12.5/50GHz spacing";
           }
           enum "1579.08" {
             description "1579.08 nm/189.853125 THz 3.125GHz spacing";
           }
           enum "1579.05" {
             description "1579.05 nm/189.856250 THz 3.125/6.25GHz spacing";
           }
           enum "1579.02" {
             description "1579.02 nm/189.859375 THz 3.125GHz spacing";
           }
           enum "1579.00" {
             description "1579.00 nm/189.862500 THz 3.125/6.25/12.5GHz spacing";
           }
           enum "1578.97" {
             description "1578.97 nm/189.865625 THz 3.125GHz spacing";
           }
           enum "1578.95" {
             description "1578.95 nm/189.868750 THz 3.125/6.25GHz spacing";
           }
           enum "1578.92" {
             description "1578.92 nm/189.871875 THz 3.125GHz spacing";
           }
           enum "1578.89" {
             description "1578.89 nm/189.875000 THz 3.125/6.25/12.5/75GHz spacing";
           }
           enum "1578.87" {
             description "1578.87 nm/189.878125 THz 3.125GHz spacing";
           }
           enum "1578.84" {
             description "1578.84 nm/189.881250 THz 3.125/6.25GHz spacing";
           }
           enum "1578.82" {
             description "1578.82 nm/189.884375 THz 3.125GHz spacing";
           }
           enum "1578.79" {
             description "1578.79 nm/189.887500 THz 3.125/6.25/12.5GHz spacing";
           }
           enum "1578.76" {
             description "1578.76 nm/189.890625 THz 3.125GHz spacing";
           }
           enum "1578.74" {
             description "1578.74 nm/189.893750 THz 3.125/6.25GHz spacing";
           }
           enum "1578.71" {
             description "1578.71 nm/189.896875 THz 3.125GHz spacing";
           }
           enum "1578.69" {
             description "1578.69 nm/189.900000 THz 3.125/6.25/12.5/50/75/100GHz spacing";
           }
           enum "1578.66" {
             description "1578.66 nm/189.903125 THz 3.125GHz spacing";
           }
           enum "1578.63" {
             description "1578.63 nm/189.906250 THz 3.125/6.25GHz spacing";
           }
           enum "1578.61" {
             description "1578.61 nm/189.909375 THz 3.125GHz spacing";
           }
           enum "1578.58" {
             description "1578.58 nm/189.912500 THz 3.125/6.25/12.5GHz spacing";
           }
           enum "1578.56" {
             description "1578.56 nm/189.915625 THz 3.125GHz spacing";
           }
           enum "1578.53" {
             description "1578.53 nm/189.918750 THz 3.125/6.25GHz spacing";
           }
           enum "1578.50" {
             description "1578.50 nm/189.921875 THz 3.125GHz spacing";
           }
           enum "1578.48" {
             description "1578.48 nm/189.925000 THz 3.125/6.25/12.5GHz spacing";
           }
           enum "1578.45" {
             description "1578.45 nm/189.928125 THz 3.125GHz spacing";
           }
           enum "1578.43" {
             description "1578.43 nm/189.931250 THz 3.125/6.25GHz spacing";
           }
           enum "1578.40" {
             description "1578.40 nm/189.934375 THz 3.125GHz spacing";
           }
           enum "1578.37" {
             description "1578.37 nm/189.937500 THz 3.125/6.25/12.5GHz spacing";
           }
           enum "1578.35" {
             description "1578.35 nm/189.940625 THz 3.125GHz spacing";
           }
           enum "1578.32" {
             description "1578.32 nm/189.943750 THz 3.125/6.25GHz spacing";
           }
           enum "1578.30" {
             description "1578.30 nm/189.946875 THz 3.125GHz spacing";
           }
           enum "1578.27" {
             description "1578.27 nm/189.950000 THz 3.125/6.25/12.5/50/75GHz spacing";
           }
           enum "1578.24" {
             description "1578.24 nm/189.953125 THz 3.125GHz spacing";
           }
           enum "1578.22" {
             description "1578.22 nm/189.956250 THz 3.125/6.25GHz spacing";
           }
           enum "1578.19" {
             description "1578.19 nm/189.959375 THz 3.125GHz spacing";
           }
           enum "1578.17" {
             description "1578.17 nm/189.962500 THz 3.125/6.25/12.5GHz spacing";
           }
           enum "1578.14" {
             description "1578.14 nm/189.965625 THz 3.125GHz spacing";
           }
           enum "1578.11" {
             description "1578.11 nm/189.968750 THz 3.125/6.25GHz spacing";
           }
           enum "1578.09" {
             description "1578.09 nm/189.971875 THz 3.125GHz spacing";
           }
           enum "1578.06" {
             description "1578.06 nm/189.975000 THz 3.125/6.25/12.5GHz spacing";
           }
           enum "1578.04" {
             description "1578.04 nm/189.978125 THz 3.125GHz spacing";
           }
           enum "1578.01" {
             description "1578.01 nm/189.981250 THz 3.125/6.25GHz spacing";
           }
           enum "1577.98" {
             description "1577.98 nm/189.984375 THz 3.125GHz spacing";
           }
           enum "1577.96" {
             description "1577.96 nm/189.987500 THz 3.125/6.25/12.5GHz spacing";
           }
           enum "1577.93" {
             description "1577.93 nm/189.990625 THz 3.125GHz spacing";
           }
           enum "1577.91" {
             description "1577.91 nm/189.993750 THz 3.125/6.25GHz spacing";
           }
           enum "1577.88" {
             description "1577.88 nm/189.996875 THz 3.125GHz spacing";
           }
           enum "1577.86" {
             description "1577.86 nm/190.000000 THz 3.125/6.25/12.5/100GHz spacing";
           }
           enum "1577.83" {
             description "1577.83 nm/190.003125 THz 3.125GHz spacing";
           }
           enum "1577.80" {
             description "1577.80 nm/190.006250 THz 3.125/6.25GHz spacing";
           }
           enum "1577.78" {
             description "1577.78 nm/190.009375 THz 3.125GHz spacing";
           }
           enum "1577.75" {
             description "1577.75 nm/190.012500 THz 3.125/6.25/12.5GHz spacing";
           }
           enum "1577.73" {
             description "1577.73 nm/190.015625 THz 3.125GHz spacing";
           }
           enum "1577.70" {
             description "1577.70 nm/190.018750 THz 3.125/6.25GHz spacing";
           }
           enum "1577.67" {
             description "1577.67 nm/190.021875 THz 3.125GHz spacing";
           }
           enum "1577.65" {
             description "1577.65 nm/190.025000 THz 3.125/6.25/12.5/75GHz spacing";
           }
           enum "1577.62" {
             description "1577.62 nm/190.028125 THz 3.125GHz spacing";
           }
           enum "1577.60" {
             description "1577.60 nm/190.031250 THz 3.125/6.25GHz spacing";
           }
           enum "1577.57" {
             description "1577.57 nm/190.034375 THz 3.125GHz spacing";
           }
           enum "1577.54" {
             description "1577.54 nm/190.037500 THz 3.125/6.25/12.5GHz spacing";
           }
           enum "1577.52" {
             description "1577.52 nm/190.040625 THz 3.125GHz spacing";
           }
           enum "1577.49" {
             description "1577.49 nm/190.043750 THz 3.125/6.25GHz spacing";
           }
           enum "1577.47" {
             description "1577.47 nm/190.046875 THz 3.125GHz spacing";
           }
           enum "1577.44" {
             description "1577.44 nm/190.050000 THz 3.125/6.25/12.5/50GHz spacing";
           }
           enum "1577.41" {
             description "1577.41 nm/190.053125 THz 3.125GHz spacing";
           }
           enum "1577.39" {
             description "1577.39 nm/190.056250 THz 3.125/6.25GHz spacing";
           }
           enum "1577.36" {
             description "1577.36 nm/190.059375 THz 3.125GHz spacing";
           }
           enum "1577.34" {
             description "1577.34 nm/190.062500 THz 3.125/6.25/12.5GHz spacing";
           }
           enum "1577.31" {
             description "1577.31 nm/190.065625 THz 3.125GHz spacing";
           }
           enum "1577.28" {
             description "1577.28 nm/190.068750 THz 3.125/6.25GHz spacing";
           }
           enum "1577.26" {
             description "1577.26 nm/190.071875 THz 3.125GHz spacing";
           }
           enum "1577.23" {
             description "1577.23 nm/190.075000 THz 3.125/6.25/12.5GHz spacing";
           }
           enum "1577.21" {
             description "1577.21 nm/190.078125 THz 3.125GHz spacing";
           }
           enum "1577.18" {
             description "1577.18 nm/190.081250 THz 3.125/6.25GHz spacing";
           }
           enum "1577.15" {
             description "1577.15 nm/190.084375 THz 3.125GHz spacing";
           }
           enum "1577.13" {
             description "1577.13 nm/190.087500 THz 3.125/6.25/12.5GHz spacing";
           }
           enum "1577.10" {
             description "1577.10 nm/190.090625 THz 3.125GHz spacing";
           }
           enum "1577.08" {
             description "1577.08 nm/190.093750 THz 3.125/6.25GHz spacing";
           }
           enum "1577.05" {
             description "1577.05 nm/190.096875 THz 3.125GHz spacing";
           }
           enum "1577.03" {
             description "1577.03 nm/190.100000 THz 3.125/6.25/12.5/100GHz spacing";
           }
           enum "1577.00" {
             description "1577.00 nm/190.103125 THz 3.125GHz spacing";
           }
           enum "1576.97" {
             description "1576.97 nm/190.106250 THz 3.125/6.25GHz spacing";
           }
           enum "1576.95" {
             description "1576.95 nm/190.109375 THz 3.125GHz spacing";
           }
           enum "1576.92" {
             description "1576.92 nm/190.112500 THz 3.125/6.25/12.5GHz spacing";
           }
           enum "1576.90" {
             description "1576.90 nm/190.115625 THz 3.125GHz spacing";
           }
           enum "1576.87" {
             description "1576.87 nm/190.118750 THz 3.125/6.25GHz spacing";
           }
           enum "1576.84" {
             description "1576.84 nm/190.121875 THz 3.125GHz spacing";
           }
           enum "1576.82" {
             description "1576.82 nm/190.125000 THz 3.125/6.25/12.5GHz spacing";
           }
           enum "1576.79" {
             description "1576.79 nm/190.128125 THz 3.125GHz spacing";
           }
           enum "1576.77" {
             description "1576.77 nm/190.131250 THz 3.125/6.25GHz spacing";
           }
           enum "1576.74" {
             description "1576.74 nm/190.134375 THz 3.125GHz spacing";
           }
           enum "1576.71" {
             description "1576.71 nm/190.137500 THz 3.125/6.25/12.5GHz spacing";
           }
           enum "1576.69" {
             description "1576.69 nm/190.140625 THz 3.125GHz spacing";
           }
           enum "1576.66" {
             description "1576.66 nm/190.143750 THz 3.125/6.25GHz spacing";
           }
           enum "1576.64" {
             description "1576.64 nm/190.146875 THz 3.125GHz spacing";
           }
           enum "1576.61" {
             description "1576.61 nm/190.150000 THz 3.125/6.25/12.5/50GHz spacing";
           }
           enum "1576.58" {
             description "1576.58 nm/190.153125 THz 3.125GHz spacing";
           }
           enum "1576.56" {
             description "1576.56 nm/190.156250 THz 3.125/6.25GHz spacing";
           }
           enum "1576.53" {
             description "1576.53 nm/190.159375 THz 3.125GHz spacing";
           }
           enum "1576.51" {
             description "1576.51 nm/190.162500 THz 3.125/6.25/12.5GHz spacing";
           }
           enum "1576.48" {
             description "1576.48 nm/190.165625 THz 3.125GHz spacing";
           }
           enum "1576.45" {
             description "1576.45 nm/190.168750 THz 3.125/6.25GHz spacing";
           }
           enum "1576.43" {
             description "1576.43 nm/190.171875 THz 3.125GHz spacing";
           }
           enum "1576.40" {
             description "1576.40 nm/190.175000 THz 3.125/6.25/12.5/75GHz spacing";
           }
           enum "1576.38" {
             description "1576.38 nm/190.178125 THz 3.125GHz spacing";
           }
           enum "1576.35" {
             description "1576.35 nm/190.181250 THz 3.125/6.25GHz spacing";
           }
           enum "1576.33" {
             description "1576.33 nm/190.184375 THz 3.125GHz spacing";
           }
           enum "1576.30" {
             description "1576.30 nm/190.187500 THz 3.125/6.25/12.5GHz spacing";
           }
           enum "1576.27" {
             description "1576.27 nm/190.190625 THz 3.125GHz spacing";
           }
           enum "1576.25" {
             description "1576.25 nm/190.193750 THz 3.125/6.25GHz spacing";
           }
           enum "1576.22" {
             description "1576.22 nm/190.196875 THz 3.125GHz spacing";
           }
           enum "1576.20" {
             description "1576.20 nm/190.200000 THz 3.125/6.25/12.5/50/75/100GHz spacing";
           }
           enum "1576.17" {
             description "1576.17 nm/190.203125 THz 3.125GHz spacing";
           }
           enum "1576.14" {
             description "1576.14 nm/190.206250 THz 3.125/6.25GHz spacing";
           }
           enum "1576.12" {
             description "1576.12 nm/190.209375 THz 3.125GHz spacing";
           }
           enum "1576.09" {
             description "1576.09 nm/190.212500 THz 3.125/6.25/12.5GHz spacing";
           }
           enum "1576.07" {
             description "1576.07 nm/190.215625 THz 3.125GHz spacing";
           }
           enum "1576.04" {
             description "1576.04 nm/190.218750 THz 3.125/6.25GHz spacing";
           }
           enum "1576.01" {
             description "1576.01 nm/190.221875 THz 3.125GHz spacing";
           }
           enum "1575.99" {
             description "1575.99 nm/190.225000 THz 3.125/6.25/12.5GHz spacing";
           }
           enum "1575.96" {
             description "1575.96 nm/190.228125 THz 3.125GHz spacing";
           }
           enum "1575.94" {
             description "1575.94 nm/190.231250 THz 3.125/6.25GHz spacing";
           }
           enum "1575.91" {
             description "1575.91 nm/190.234375 THz 3.125GHz spacing";
           }
           enum "1575.89" {
             description "1575.89 nm/190.237500 THz 3.125/6.25/12.5GHz spacing";
           }
           enum "1575.86" {
             description "1575.86 nm/190.240625 THz 3.125GHz spacing";
           }
           enum "1575.83" {
             description "1575.83 nm/190.243750 THz 3.125/6.25GHz spacing";
           }
           enum "1575.81" {
             description "1575.81 nm/190.246875 THz 3.125GHz spacing";
           }
           enum "1575.78" {
             description "1575.78 nm/190.250000 THz 3.125/6.25/12.5/50/75GHz spacing";
           }
           enum "1575.76" {
             description "1575.76 nm/190.253125 THz 3.125GHz spacing";
           }
           enum "1575.73" {
             description "1575.73 nm/190.256250 THz 3.125/6.25GHz spacing";
           }
           enum "1575.70" {
             description "1575.70 nm/190.259375 THz 3.125GHz spacing";
           }
           enum "1575.68" {
             description "1575.68 nm/190.262500 THz 3.125/6.25/12.5GHz spacing";
           }
           enum "1575.65" {
             description "1575.65 nm/190.265625 THz 3.125GHz spacing";
           }
           enum "1575.63" {
             description "1575.63 nm/190.268750 THz 3.125/6.25GHz spacing";
           }
           enum "1575.60" {
             description "1575.60 nm/190.271875 THz 3.125GHz spacing";
           }
           enum "1575.57" {
             description "1575.57 nm/190.275000 THz 3.125/6.25/12.5GHz spacing";
           }
           enum "1575.55" {
             description "1575.55 nm/190.278125 THz 3.125GHz spacing";
           }
           enum "1575.52" {
             description "1575.52 nm/190.281250 THz 3.125/6.25GHz spacing";
           }
           enum "1575.50" {
             description "1575.50 nm/190.284375 THz 3.125GHz spacing";
           }
           enum "1575.47" {
             description "1575.47 nm/190.287500 THz 3.125/6.25/12.5GHz spacing";
           }
           enum "1575.45" {
             description "1575.45 nm/190.290625 THz 3.125GHz spacing";
           }
           enum "1575.42" {
             description "1575.42 nm/190.293750 THz 3.125/6.25GHz spacing";
           }
           enum "1575.39" {
             description "1575.39 nm/190.296875 THz 3.125GHz spacing";
           }
           enum "1575.37" {
             description "1575.37 nm/190.300000 THz 3.125/6.25/12.5/100GHz spacing";
           }
           enum "1575.34" {
             description "1575.34 nm/190.303125 THz 3.125GHz spacing";
           }
           enum "1575.32" {
             description "1575.32 nm/190.306250 THz 3.125/6.25GHz spacing";
           }
           enum "1575.29" {
             description "1575.29 nm/190.309375 THz 3.125GHz spacing";
           }
           enum "1575.26" {
             description "1575.26 nm/190.312500 THz 3.125/6.25/12.5GHz spacing";
           }
           enum "1575.24" {
             description "1575.24 nm/190.315625 THz 3.125GHz spacing";
           }
           enum "1575.21" {
             description "1575.21 nm/190.318750 THz 3.125/6.25GHz spacing";
           }
           enum "1575.19" {
             description "1575.19 nm/190.321875 THz 3.125GHz spacing";
           }
           enum "1575.16" {
             description "1575.16 nm/190.325000 THz 3.125/6.25/12.5/75GHz spacing";
           }
           enum "1575.13" {
             description "1575.13 nm/190.328125 THz 3.125GHz spacing";
           }
           enum "1575.11" {
             description "1575.11 nm/190.331250 THz 3.125/6.25GHz spacing";
           }
           enum "1575.08" {
             description "1575.08 nm/190.334375 THz 3.125GHz spacing";
           }
           enum "1575.06" {
             description "1575.06 nm/190.337500 THz 3.125/6.25/12.5GHz spacing";
           }
           enum "1575.03" {
             description "1575.03 nm/190.340625 THz 3.125GHz spacing";
           }
           enum "1575.01" {
             description "1575.01 nm/190.343750 THz 3.125/6.25GHz spacing";
           }
           enum "1574.98" {
             description "1574.98 nm/190.346875 THz 3.125GHz spacing";
           }
           enum "1574.95" {
             description "1574.95 nm/190.350000 THz 3.125/6.25/12.5/50GHz spacing";
           }
           enum "1574.93" {
             description "1574.93 nm/190.353125 THz 3.125GHz spacing";
           }
           enum "1574.90" {
             description "1574.90 nm/190.356250 THz 3.125/6.25GHz spacing";
           }
           enum "1574.88" {
             description "1574.88 nm/190.359375 THz 3.125GHz spacing";
           }
           enum "1574.85" {
             description "1574.85 nm/190.362500 THz 3.125/6.25/12.5GHz spacing";
           }
           enum "1574.82" {
             description "1574.82 nm/190.365625 THz 3.125GHz spacing";
           }
           enum "1574.80" {
             description "1574.80 nm/190.368750 THz 3.125/6.25GHz spacing";
           }
           enum "1574.77" {
             description "1574.77 nm/190.371875 THz 3.125GHz spacing";
           }
           enum "1574.75" {
             description "1574.75 nm/190.375000 THz 3.125/6.25/12.5GHz spacing";
           }
           enum "1574.72" {
             description "1574.72 nm/190.378125 THz 3.125GHz spacing";
           }
           enum "1574.70" {
             description "1574.70 nm/190.381250 THz 3.125/6.25GHz spacing";
           }
           enum "1574.67" {
             description "1574.67 nm/190.384375 THz 3.125GHz spacing";
           }
           enum "1574.64" {
             description "1574.64 nm/190.387500 THz 3.125/6.25/12.5GHz spacing";
           }
           enum "1574.62" {
             description "1574.62 nm/190.390625 THz 3.125GHz spacing";
           }
           enum "1574.59" {
             description "1574.59 nm/190.393750 THz 3.125/6.25GHz spacing";
           }
           enum "1574.57" {
             description "1574.57 nm/190.396875 THz 3.125GHz spacing";
           }
           enum "1574.54" {
             description "1574.54 nm/190.400000 THz 3.125/6.25/12.5/100GHz spacing";
           }
           enum "1574.51" {
             description "1574.51 nm/190.403125 THz 3.125GHz spacing";
           }
           enum "1574.49" {
             description "1574.49 nm/190.406250 THz 3.125/6.25GHz spacing";
           }
           enum "1574.46" {
             description "1574.46 nm/190.409375 THz 3.125GHz spacing";
           }
           enum "1574.44" {
             description "1574.44 nm/190.412500 THz 3.125/6.25/12.5GHz spacing";
           }
           enum "1574.41" {
             description "1574.41 nm/190.415625 THz 3.125GHz spacing";
           }
           enum "1574.39" {
             description "1574.39 nm/190.418750 THz 3.125/6.25GHz spacing";
           }
           enum "1574.36" {
             description "1574.36 nm/190.421875 THz 3.125GHz spacing";
           }
           enum "1574.33" {
             description "1574.33 nm/190.425000 THz 3.125/6.25/12.5GHz spacing";
           }
           enum "1574.31" {
             description "1574.31 nm/190.428125 THz 3.125GHz spacing";
           }
           enum "1574.28" {
             description "1574.28 nm/190.431250 THz 3.125/6.25GHz spacing";
           }
           enum "1574.26" {
             description "1574.26 nm/190.434375 THz 3.125GHz spacing";
           }
           enum "1574.23" {
             description "1574.23 nm/190.437500 THz 3.125/6.25/12.5GHz spacing";
           }
           enum "1574.20" {
             description "1574.20 nm/190.440625 THz 3.125GHz spacing";
           }
           enum "1574.18" {
             description "1574.18 nm/190.443750 THz 3.125/6.25GHz spacing";
           }
           enum "1574.15" {
             description "1574.15 nm/190.446875 THz 3.125GHz spacing";
           }
           enum "1574.13" {
             description "1574.13 nm/190.450000 THz 3.125/6.25/12.5/50GHz spacing";
           }
           enum "1574.10" {
             description "1574.10 nm/190.453125 THz 3.125GHz spacing";
           }
           enum "1574.08" {
             description "1574.08 nm/190.456250 THz 3.125/6.25GHz spacing";
           }
           enum "1574.05" {
             description "1574.05 nm/190.459375 THz 3.125GHz spacing";
           }
           enum "1574.02" {
             description "1574.02 nm/190.462500 THz 3.125/6.25/12.5GHz spacing";
           }
           enum "1574.00" {
             description "1574.00 nm/190.465625 THz 3.125GHz spacing";
           }
           enum "1573.97" {
             description "1573.97 nm/190.468750 THz 3.125/6.25GHz spacing";
           }
           enum "1573.95" {
             description "1573.95 nm/190.471875 THz 3.125GHz spacing";
           }
           enum "1573.92" {
             description "1573.92 nm/190.475000 THz 3.125/6.25/12.5/75GHz spacing";
           }
           enum "1573.89" {
             description "1573.89 nm/190.478125 THz 3.125GHz spacing";
           }
           enum "1573.87" {
             description "1573.87 nm/190.481250 THz 3.125/6.25GHz spacing";
           }
           enum "1573.84" {
             description "1573.84 nm/190.484375 THz 3.125GHz spacing";
           }
           enum "1573.82" {
             description "1573.82 nm/190.487500 THz 3.125/6.25/12.5GHz spacing";
           }
           enum "1573.79" {
             description "1573.79 nm/190.490625 THz 3.125GHz spacing";
           }
           enum "1573.77" {
             description "1573.77 nm/190.493750 THz 3.125/6.25GHz spacing";
           }
           enum "1573.74" {
             description "1573.74 nm/190.496875 THz 3.125GHz spacing";
           }
           enum "1573.71" {
             description "1573.71 nm/190.500000 THz 3.125/6.25/12.5/50/75/100GHz spacing";
           }
           enum "1573.69" {
             description "1573.69 nm/190.503125 THz 3.125GHz spacing";
           }
           enum "1573.66" {
             description "1573.66 nm/190.506250 THz 3.125/6.25GHz spacing";
           }
           enum "1573.64" {
             description "1573.64 nm/190.509375 THz 3.125GHz spacing";
           }
           enum "1573.61" {
             description "1573.61 nm/190.512500 THz 3.125/6.25/12.5GHz spacing";
           }
           enum "1573.58" {
             description "1573.58 nm/190.515625 THz 3.125GHz spacing";
           }
           enum "1573.56" {
             description "1573.56 nm/190.518750 THz 3.125/6.25GHz spacing";
           }
           enum "1573.53" {
             description "1573.53 nm/190.521875 THz 3.125GHz spacing";
           }
           enum "1573.51" {
             description "1573.51 nm/190.525000 THz 3.125/6.25/12.5GHz spacing";
           }
           enum "1573.48" {
             description "1573.48 nm/190.528125 THz 3.125GHz spacing";
           }
           enum "1573.46" {
             description "1573.46 nm/190.531250 THz 3.125/6.25GHz spacing";
           }
           enum "1573.43" {
             description "1573.43 nm/190.534375 THz 3.125GHz spacing";
           }
           enum "1573.40" {
             description "1573.40 nm/190.537500 THz 3.125/6.25/12.5GHz spacing";
           }
           enum "1573.38" {
             description "1573.38 nm/190.540625 THz 3.125GHz spacing";
           }
           enum "1573.35" {
             description "1573.35 nm/190.543750 THz 3.125/6.25GHz spacing";
           }
           enum "1573.33" {
             description "1573.33 nm/190.546875 THz 3.125GHz spacing";
           }
           enum "1573.30" {
             description "1573.30 nm/190.550000 THz 3.125/6.25/12.5/50/75GHz spacing";
           }
           enum "1573.27" {
             description "1573.27 nm/190.553125 THz 3.125GHz spacing";
           }
           enum "1573.25" {
             description "1573.25 nm/190.556250 THz 3.125/6.25GHz spacing";
           }
           enum "1573.22" {
             description "1573.22 nm/190.559375 THz 3.125GHz spacing";
           }
           enum "1573.20" {
             description "1573.20 nm/190.562500 THz 3.125/6.25/12.5GHz spacing";
           }
           enum "1573.17" {
             description "1573.17 nm/190.565625 THz 3.125GHz spacing";
           }
           enum "1573.15" {
             description "1573.15 nm/190.568750 THz 3.125/6.25GHz spacing";
           }
           enum "1573.12" {
             description "1573.12 nm/190.571875 THz 3.125GHz spacing";
           }
           enum "1573.09" {
             description "1573.09 nm/190.575000 THz 3.125/6.25/12.5GHz spacing";
           }
           enum "1573.07" {
             description "1573.07 nm/190.578125 THz 3.125GHz spacing";
           }
           enum "1573.04" {
             description "1573.04 nm/190.581250 THz 3.125/6.25GHz spacing";
           }
           enum "1573.02" {
             description "1573.02 nm/190.584375 THz 3.125GHz spacing";
           }
           enum "1572.99" {
             description "1572.99 nm/190.587500 THz 3.125/6.25/12.5GHz spacing";
           }
           enum "1572.97" {
             description "1572.97 nm/190.590625 THz 3.125GHz spacing";
           }
           enum "1572.94" {
             description "1572.94 nm/190.593750 THz 3.125/6.25GHz spacing";
           }
           enum "1572.91" {
             description "1572.91 nm/190.596875 THz 3.125GHz spacing";
           }
           enum "1572.89" {
             description "1572.89 nm/190.600000 THz 3.125/6.25/12.5/100GHz spacing";
           }
           enum "1572.86" {
             description "1572.86 nm/190.603125 THz 3.125GHz spacing";
           }
           enum "1572.84" {
             description "1572.84 nm/190.606250 THz 3.125/6.25GHz spacing";
           }
           enum "1572.81" {
             description "1572.81 nm/190.609375 THz 3.125GHz spacing";
           }
           enum "1572.78" {
             description "1572.78 nm/190.612500 THz 3.125/6.25/12.5GHz spacing";
           }
           enum "1572.76" {
             description "1572.76 nm/190.615625 THz 3.125GHz spacing";
           }
           enum "1572.73" {
             description "1572.73 nm/190.618750 THz 3.125/6.25GHz spacing";
           }
           enum "1572.71" {
             description "1572.71 nm/190.621875 THz 3.125GHz spacing";
           }
           enum "1572.68" {
             description "1572.68 nm/190.625000 THz 3.125/6.25/12.5/75GHz spacing";
           }
           enum "1572.66" {
             description "1572.66 nm/190.628125 THz 3.125GHz spacing";
           }
           enum "1572.63" {
             description "1572.63 nm/190.631250 THz 3.125/6.25GHz spacing";
           }
           enum "1572.60" {
             description "1572.60 nm/190.634375 THz 3.125GHz spacing";
           }
           enum "1572.58" {
             description "1572.58 nm/190.637500 THz 3.125/6.25/12.5GHz spacing";
           }
           enum "1572.55" {
             description "1572.55 nm/190.640625 THz 3.125GHz spacing";
           }
           enum "1572.53" {
             description "1572.53 nm/190.643750 THz 3.125/6.25GHz spacing";
           }
           enum "1572.50" {
             description "1572.50 nm/190.646875 THz 3.125GHz spacing";
           }
           enum "1572.48" {
             description "1572.48 nm/190.650000 THz 3.125/6.25/12.5/50GHz spacing";
           }
           enum "1572.45" {
             description "1572.45 nm/190.653125 THz 3.125GHz spacing";
           }
           enum "1572.42" {
             description "1572.42 nm/190.656250 THz 3.125/6.25GHz spacing";
           }
           enum "1572.40" {
             description "1572.40 nm/190.659375 THz 3.125GHz spacing";
           }
           enum "1572.37" {
             description "1572.37 nm/190.662500 THz 3.125/6.25/12.5GHz spacing";
           }
           enum "1572.35" {
             description "1572.35 nm/190.665625 THz 3.125GHz spacing";
           }
           enum "1572.32" {
             description "1572.32 nm/190.668750 THz 3.125/6.25GHz spacing";
           }
           enum "1572.30" {
             description "1572.30 nm/190.671875 THz 3.125GHz spacing";
           }
           enum "1572.27" {
             description "1572.27 nm/190.675000 THz 3.125/6.25/12.5GHz spacing";
           }
           enum "1572.24" {
             description "1572.24 nm/190.678125 THz 3.125GHz spacing";
           }
           enum "1572.22" {
             description "1572.22 nm/190.681250 THz 3.125/6.25GHz spacing";
           }
           enum "1572.19" {
             description "1572.19 nm/190.684375 THz 3.125GHz spacing";
           }
           enum "1572.17" {
             description "1572.17 nm/190.687500 THz 3.125/6.25/12.5GHz spacing";
           }
           enum "1572.14" {
             description "1572.14 nm/190.690625 THz 3.125GHz spacing";
           }
           enum "1572.11" {
             description "1572.11 nm/190.693750 THz 3.125/6.25GHz spacing";
           }
           enum "1572.09" {
             description "1572.09 nm/190.696875 THz 3.125GHz spacing";
           }
           enum "1572.06" {
             description "1572.06 nm/190.700000 THz 3.125/6.25/12.5/100GHz spacing";
           }
           enum "1572.04" {
             description "1572.04 nm/190.703125 THz 3.125GHz spacing";
           }
           enum "1572.01" {
             description "1572.01 nm/190.706250 THz 3.125/6.25GHz spacing";
           }
           enum "1571.99" {
             description "1571.99 nm/190.709375 THz 3.125GHz spacing";
           }
           enum "1571.96" {
             description "1571.96 nm/190.712500 THz 3.125/6.25/12.5GHz spacing";
           }
           enum "1571.93" {
             description "1571.93 nm/190.715625 THz 3.125GHz spacing";
           }
           enum "1571.91" {
             description "1571.91 nm/190.718750 THz 3.125/6.25GHz spacing";
           }
           enum "1571.88" {
             description "1571.88 nm/190.721875 THz 3.125GHz spacing";
           }
           enum "1571.86" {
             description "1571.86 nm/190.725000 THz 3.125/6.25/12.5GHz spacing";
           }
           enum "1571.83" {
             description "1571.83 nm/190.728125 THz 3.125GHz spacing";
           }
           enum "1571.81" {
             description "1571.81 nm/190.731250 THz 3.125/6.25GHz spacing";
           }
           enum "1571.78" {
             description "1571.78 nm/190.734375 THz 3.125GHz spacing";
           }
           enum "1571.75" {
             description "1571.75 nm/190.737500 THz 3.125/6.25/12.5GHz spacing";
           }
           enum "1571.73" {
             description "1571.73 nm/190.740625 THz 3.125GHz spacing";
           }
           enum "1571.70" {
             description "1571.70 nm/190.743750 THz 3.125/6.25GHz spacing";
           }
           enum "1571.68" {
             description "1571.68 nm/190.746875 THz 3.125GHz spacing";
           }
           enum "1571.65" {
             description "1571.65 nm/190.750000 THz 3.125/6.25/12.5/50GHz spacing";
           }
           enum "1571.63" {
             description "1571.63 nm/190.753125 THz 3.125GHz spacing";
           }
           enum "1571.60" {
             description "1571.60 nm/190.756250 THz 3.125/6.25GHz spacing";
           }
           enum "1571.57" {
             description "1571.57 nm/190.759375 THz 3.125GHz spacing";
           }
           enum "1571.55" {
             description "1571.55 nm/190.762500 THz 3.125/6.25/12.5GHz spacing";
           }
           enum "1571.52" {
             description "1571.52 nm/190.765625 THz 3.125GHz spacing";
           }
           enum "1571.50" {
             description "1571.50 nm/190.768750 THz 3.125/6.25GHz spacing";
           }
           enum "1571.47" {
             description "1571.47 nm/190.771875 THz 3.125GHz spacing";
           }
           enum "1571.45" {
             description "1571.45 nm/190.775000 THz 3.125/6.25/12.5/75GHz spacing";
           }
           enum "1571.42" {
             description "1571.42 nm/190.778125 THz 3.125GHz spacing";
           }
           enum "1571.39" {
             description "1571.39 nm/190.781250 THz 3.125/6.25GHz spacing";
           }
           enum "1571.37" {
             description "1571.37 nm/190.784375 THz 3.125GHz spacing";
           }
           enum "1571.34" {
             description "1571.34 nm/190.787500 THz 3.125/6.25/12.5GHz spacing";
           }
           enum "1571.32" {
             description "1571.32 nm/190.790625 THz 3.125GHz spacing";
           }
           enum "1571.29" {
             description "1571.29 nm/190.793750 THz 3.125/6.25GHz spacing";
           }
           enum "1571.27" {
             description "1571.27 nm/190.796875 THz 3.125GHz spacing";
           }
           enum "1571.24" {
             description "1571.24 nm/190.800000 THz 3.125/6.25/12.5/50/75/100GHz spacing";
           }
           enum "1571.21" {
             description "1571.21 nm/190.803125 THz 3.125GHz spacing";
           }
           enum "1571.19" {
             description "1571.19 nm/190.806250 THz 3.125/6.25GHz spacing";
           }
           enum "1571.16" {
             description "1571.16 nm/190.809375 THz 3.125GHz spacing";
           }
           enum "1571.14" {
             description "1571.14 nm/190.812500 THz 3.125/6.25/12.5GHz spacing";
           }
           enum "1571.11" {
             description "1571.11 nm/190.815625 THz 3.125GHz spacing";
           }
           enum "1571.08" {
             description "1571.08 nm/190.818750 THz 3.125/6.25GHz spacing";
           }
           enum "1571.06" {
             description "1571.06 nm/190.821875 THz 3.125GHz spacing";
           }
           enum "1571.03" {
             description "1571.03 nm/190.825000 THz 3.125/6.25/12.5GHz spacing";
           }
           enum "1571.01" {
             description "1571.01 nm/190.828125 THz 3.125GHz spacing";
           }
           enum "1570.98" {
             description "1570.98 nm/190.831250 THz 3.125/6.25GHz spacing";
           }
           enum "1570.96" {
             description "1570.96 nm/190.834375 THz 3.125GHz spacing";
           }
           enum "1570.93" {
             description "1570.93 nm/190.837500 THz 3.125/6.25/12.5GHz spacing";
           }
           enum "1570.90" {
             description "1570.90 nm/190.840625 THz 3.125GHz spacing";
           }
           enum "1570.88" {
             description "1570.88 nm/190.843750 THz 3.125/6.25GHz spacing";
           }
           enum "1570.85" {
             description "1570.85 nm/190.846875 THz 3.125GHz spacing";
           }
           enum "1570.83" {
             description "1570.83 nm/190.850000 THz 3.125/6.25/12.5/50/75GHz spacing";
           }
           enum "1570.80" {
             description "1570.80 nm/190.853125 THz 3.125GHz spacing";
           }
           enum "1570.78" {
             description "1570.78 nm/190.856250 THz 3.125/6.25GHz spacing";
           }
           enum "1570.75" {
             description "1570.75 nm/190.859375 THz 3.125GHz spacing";
           }
           enum "1570.72" {
             description "1570.72 nm/190.862500 THz 3.125/6.25/12.5GHz spacing";
           }
           enum "1570.70" {
             description "1570.70 nm/190.865625 THz 3.125GHz spacing";
           }
           enum "1570.67" {
             description "1570.67 nm/190.868750 THz 3.125/6.25GHz spacing";
           }
           enum "1570.65" {
             description "1570.65 nm/190.871875 THz 3.125GHz spacing";
           }
           enum "1570.62" {
             description "1570.62 nm/190.875000 THz 3.125/6.25/12.5GHz spacing";
           }
           enum "1570.60" {
             description "1570.60 nm/190.878125 THz 3.125GHz spacing";
           }
           enum "1570.57" {
             description "1570.57 nm/190.881250 THz 3.125/6.25GHz spacing";
           }
           enum "1570.54" {
             description "1570.54 nm/190.884375 THz 3.125GHz spacing";
           }
           enum "1570.52" {
             description "1570.52 nm/190.887500 THz 3.125/6.25/12.5GHz spacing";
           }
           enum "1570.49" {
             description "1570.49 nm/190.890625 THz 3.125GHz spacing";
           }
           enum "1570.47" {
             description "1570.47 nm/190.893750 THz 3.125/6.25GHz spacing";
           }
           enum "1570.44" {
             description "1570.44 nm/190.896875 THz 3.125GHz spacing";
           }
           enum "1570.42" {
             description "1570.42 nm/190.900000 THz 3.125/6.25/12.5/100GHz spacing";
           }
           enum "1570.39" {
             description "1570.39 nm/190.903125 THz 3.125GHz spacing";
           }
           enum "1570.36" {
             description "1570.36 nm/190.906250 THz 3.125/6.25GHz spacing";
           }
           enum "1570.34" {
             description "1570.34 nm/190.909375 THz 3.125GHz spacing";
           }
           enum "1570.31" {
             description "1570.31 nm/190.912500 THz 3.125/6.25/12.5GHz spacing";
           }
           enum "1570.29" {
             description "1570.29 nm/190.915625 THz 3.125GHz spacing";
           }
           enum "1570.26" {
             description "1570.26 nm/190.918750 THz 3.125/6.25GHz spacing";
           }
           enum "1570.24" {
             description "1570.24 nm/190.921875 THz 3.125GHz spacing";
           }
           enum "1570.21" {
             description "1570.21 nm/190.925000 THz 3.125/6.25/12.5/75GHz spacing";
           }
           enum "1570.18" {
             description "1570.18 nm/190.928125 THz 3.125GHz spacing";
           }
           enum "1570.16" {
             description "1570.16 nm/190.931250 THz 3.125/6.25GHz spacing";
           }
           enum "1570.13" {
             description "1570.13 nm/190.934375 THz 3.125GHz spacing";
           }
           enum "1570.11" {
             description "1570.11 nm/190.937500 THz 3.125/6.25/12.5GHz spacing";
           }
           enum "1570.08" {
             description "1570.08 nm/190.940625 THz 3.125GHz spacing";
           }
           enum "1570.06" {
             description "1570.06 nm/190.943750 THz 3.125/6.25GHz spacing";
           }
           enum "1570.03" {
             description "1570.03 nm/190.946875 THz 3.125GHz spacing";
           }
           enum "1570.01" {
             description "1570.01 nm/190.950000 THz 3.125/6.25/12.5/50GHz spacing";
           }
           enum "1569.98" {
             description "1569.98 nm/190.953125 THz 3.125GHz spacing";
           }
           enum "1569.95" {
             description "1569.95 nm/190.956250 THz 3.125/6.25GHz spacing";
           }
           enum "1569.93" {
             description "1569.93 nm/190.959375 THz 3.125GHz spacing";
           }
           enum "1569.90" {
             description "1569.90 nm/190.962500 THz 3.125/6.25/12.5GHz spacing";
           }
           enum "1569.88" {
             description "1569.88 nm/190.965625 THz 3.125GHz spacing";
           }
           enum "1569.85" {
             description "1569.85 nm/190.968750 THz 3.125/6.25GHz spacing";
           }
           enum "1569.83" {
             description "1569.83 nm/190.971875 THz 3.125GHz spacing";
           }
           enum "1569.80" {
             description "1569.80 nm/190.975000 THz 3.125/6.25/12.5GHz spacing";
           }
           enum "1569.77" {
             description "1569.77 nm/190.978125 THz 3.125GHz spacing";
           }
           enum "1569.75" {
             description "1569.75 nm/190.981250 THz 3.125/6.25GHz spacing";
           }
           enum "1569.72" {
             description "1569.72 nm/190.984375 THz 3.125GHz spacing";
           }
           enum "1569.70" {
             description "1569.70 nm/190.987500 THz 3.125/6.25/12.5GHz spacing";
           }
           enum "1569.67" {
             description "1569.67 nm/190.990625 THz 3.125GHz spacing";
           }
           enum "1569.65" {
             description "1569.65 nm/190.993750 THz 3.125/6.25GHz spacing";
           }
           enum "1569.62" {
             description "1569.62 nm/190.996875 THz 3.125GHz spacing";
           }
           enum "1569.59" {
             description "1569.59 nm/191.000000 THz 3.125/6.25/12.5/100GHz spacing";
           }
           enum "1568.77" {
             description "1568.77 nm/191.1003 THz 50/100Ghz spacing";
           }
           enum "1568.36" {
             description "1568.36 nm/191.150000 THz 3.125/6.25/12.5/50/75GHz spacing";
           }
           enum "1568.34" {
             description "1568.34 nm/191.153125 THz 3.125GHz spacing";
           }
           enum "1568.31" {
             description "1568.31 nm/191.156250 THz 3.125/6.25GHz spacing";
           }
           enum "1568.29" {
             description "1568.29 nm/191.159375 THz 3.125GHz spacing";
           }
           enum "1568.26" {
             description "1568.26 nm/191.162500 THz 3.125/6.25/12.5GHz spacing";
           }
           enum "1568.23" {
             description "1568.23 nm/191.165625 THz 3.125GHz spacing";
           }
           enum "1568.21" {
             description "1568.21 nm/191.168750 THz 3.125/6.25GHz spacing";
           }
           enum "1568.18" {
             description "1568.18 nm/191.171875 THz 3.125GHz spacing";
           }
           enum "1568.16" {
             description "1568.16 nm/191.175000 THz 3.125/6.25/12.5/75GHz spacing";
           }
           enum "1568.13" {
             description "1568.13 nm/191.178125 THz 3.125GHz spacing";
           }
           enum "1568.11" {
             description "1568.11 nm/191.181250 THz 3.125/6.25GHz spacing";
           }
           enum "1568.08" {
             description "1568.08 nm/191.184375 THz 3.125GHz spacing";
           }
           enum "1568.05" {
             description "1568.05 nm/191.187500 THz 3.125/6.25/12.5GHz spacing";
           }
           enum "1568.03" {
             description "1568.03 nm/191.190625 THz 3.125GHz spacing";
           }
           enum "1568.00" {
             description "1568.00 nm/191.193750 THz 3.125/6.25GHz spacing";
           }
           enum "1567.98" {
             description "1567.98 nm/191.196875 THz 3.125GHz spacing";
           }
           enum "1567.95" {
             description "1567.95 nm/191.200000 THz 3.125/6.25/12.5/100GHz spacing";
           }
           enum "1567.93" {
             description "1567.93 nm/191.203125 THz 3.125GHz spacing";
           }
           enum "1567.90" {
             description "1567.90 nm/191.206250 THz 3.125/6.25GHz spacing";
           }
           enum "1567.88" {
             description "1567.88 nm/191.209375 THz 3.125GHz spacing";
           }
           enum "1567.85" {
             description "1567.85 nm/191.212500 THz 3.125/6.25/12.5GHz spacing";
           }
           enum "1567.82" {
             description "1567.82 nm/191.215625 THz 3.125GHz spacing";
           }
           enum "1567.80" {
             description "1567.80 nm/191.218750 THz 3.125/6.25GHz spacing";
           }
           enum "1567.77" {
             description "1567.77 nm/191.221875 THz 3.125GHz spacing";
           }
           enum "1567.75" {
             description "1567.75 nm/191.225000 THz 3.125/6.25/12.5/75GHz spacing";
           }
           enum "1567.72" {
             description "1567.72 nm/191.228125 THz 3.125GHz spacing";
           }
           enum "1567.70" {
             description "1567.70 nm/191.231250 THz 3.125/6.25GHz spacing";
           }
           enum "1567.67" {
             description "1567.67 nm/191.234375 THz 3.125GHz spacing";
           }
           enum "1567.64" {
             description "1567.64 nm/191.237500 THz 3.125/6.25/12.5GHz spacing";
           }
           enum "1567.62" {
             description "1567.62 nm/191.240625 THz 3.125GHz spacing";
           }
           enum "1567.59" {
             description "1567.59 nm/191.243750 THz 3.125/6.25GHz spacing";
           }
           enum "1567.57" {
             description "1567.57 nm/191.246875 THz 3.125GHz spacing";
           }
           enum "1567.54" {
             description "1567.54 nm/191.250000 THz 3.125/6.25/12.5/50/75GHz spacing";
           }
           enum "1567.52" {
             description "1567.52 nm/191.253125 THz 3.125GHz spacing";
           }
           enum "1567.49" {
             description "1567.49 nm/191.256250 THz 3.125/6.25GHz spacing";
           }
           enum "1567.47" {
             description "1567.47 nm/191.259375 THz 3.125GHz spacing";
           }
           enum "1567.44" {
             description "1567.44 nm/191.262500 THz 3.125/6.25/12.5GHz spacing";
           }
           enum "1567.41" {
             description "1567.41 nm/191.265625 THz 3.125GHz spacing";
           }
           enum "1567.39" {
             description "1567.39 nm/191.268750 THz 3.125/6.25GHz spacing";
           }
           enum "1567.36" {
             description "1567.36 nm/191.271875 THz 3.125GHz spacing";
           }
           enum "1567.34" {
             description "1567.34 nm/191.275000 THz 3.125/6.25/12.5GHz spacing";
           }
           enum "1567.31" {
             description "1567.31 nm/191.278125 THz 3.125GHz spacing";
           }
           enum "1567.29" {
             description "1567.29 nm/191.281250 THz 3.125/6.25GHz spacing";
           }
           enum "1567.26" {
             description "1567.26 nm/191.284375 THz 3.125GHz spacing";
           }
           enum "1567.23" {
             description "1567.23 nm/191.287500 THz 3.125/6.25/12.5GHz spacing";
           }
           enum "1567.21" {
             description "1567.21 nm/191.290625 THz 3.125GHz spacing";
           }
           enum "1567.18" {
             description "1567.18 nm/191.293750 THz 3.125/6.25GHz spacing";
           }
           enum "1567.16" {
             description "1567.16 nm/191.296875 THz 3.125GHz spacing";
           }
           enum "1567.13" {
             description "1567.13 nm/191.300000 THz 3.125/6.25/12.5/100GHz spacing";
           }
           enum "1567.11" {
             description "1567.11 nm/191.303125 THz 3.125GHz spacing";
           }
           enum "1567.08" {
             description "1567.08 nm/191.306250 THz 3.125/6.25GHz spacing";
           }
           enum "1567.06" {
             description "1567.06 nm/191.309375 THz 3.125GHz spacing";
           }
           enum "1567.03" {
             description "1567.03 nm/191.312500 THz 3.125/6.25/12.5GHz spacing";
           }
           enum "1567.00" {
             description "1567.00 nm/191.315625 THz 3.125GHz spacing";
           }
           enum "1566.98" {
             description "1566.98 nm/191.318750 THz 3.125/6.25GHz spacing";
           }
           enum "1566.95" {
             description "1566.95 nm/191.321875 THz 3.125GHz spacing";
           }
           enum "1566.93" {
             description "1566.93 nm/191.325000 THz 3.125/6.25/12.5/75GHz spacing";
           }
           enum "1566.90" {
             description "1566.90 nm/191.328125 THz 3.125GHz spacing";
           }
           enum "1566.88" {
             description "1566.88 nm/191.331250 THz 3.125/6.25GHz spacing";
           }
           enum "1566.85" {
             description "1566.85 nm/191.334375 THz 3.125GHz spacing";
           }
           enum "1566.83" {
             description "1566.83 nm/191.337500 THz 3.125/6.25/12.5GHz spacing";
           }
           enum "1566.80" {
             description "1566.80 nm/191.340625 THz 3.125GHz spacing";
           }
           enum "1566.77" {
             description "1566.77 nm/191.343750 THz 3.125/6.25GHz spacing";
           }
           enum "1566.75" {
             description "1566.75 nm/191.346875 THz 3.125GHz spacing";
           }
           enum "1566.72" {
             description "1566.72 nm/191.350000 THz 3.125/6.25/12.5/50GHz spacing";
           }
           enum "1566.70" {
             description "1566.70 nm/191.353125 THz 3.125GHz spacing";
           }
           enum "1566.67" {
             description "1566.67 nm/191.356250 THz 3.125/6.25GHz spacing";
           }
           enum "1566.65" {
             description "1566.65 nm/191.359375 THz 3.125GHz spacing";
           }
           enum "1566.62" {
             description "1566.62 nm/191.362500 THz 3.125/6.25/12.5GHz spacing";
           }
           enum "1566.60" {
             description "1566.60 nm/191.365625 THz 3.125GHz spacing";
           }
           enum "1566.57" {
             description "1566.57 nm/191.368750 THz 3.125/6.25GHz spacing";
           }
           enum "1566.54" {
             description "1566.54 nm/191.371875 THz 3.125GHz spacing";
           }
           enum "1566.52" {
             description "1566.52 nm/191.375000 THz 3.125/6.25/12.5GHz spacing";
           }
           enum "1566.49" {
             description "1566.49 nm/191.378125 THz 3.125GHz spacing";
           }
           enum "1566.47" {
             description "1566.47 nm/191.381250 THz 3.125/6.25GHz spacing";
           }
           enum "1566.44" {
             description "1566.44 nm/191.384375 THz 3.125GHz spacing";
           }
           enum "1566.42" {
             description "1566.42 nm/191.387500 THz 3.125/6.25/12.5GHz spacing";
           }
           enum "1566.39" {
             description "1566.39 nm/191.390625 THz 3.125GHz spacing";
           }
           enum "1566.36" {
             description "1566.36 nm/191.393750 THz 3.125/6.25GHz spacing";
           }
           enum "1566.34" {
             description "1566.34 nm/191.396875 THz 3.125GHz spacing";
           }
           enum "1566.31" {
             description "1566.31 nm/191.400000 THz 3.125/6.25/12.5/50/75/100GHz spacing";
           }
           enum "1566.29" {
             description "1566.29 nm/191.403125 THz 3.125GHz spacing";
           }
           enum "1566.26" {
             description "1566.26 nm/191.406250 THz 3.125/6.25GHz spacing";
           }
           enum "1566.24" {
             description "1566.24 nm/191.409375 THz 3.125GHz spacing";
           }
           enum "1566.21" {
             description "1566.21 nm/191.412500 THz 3.125/6.25/12.5GHz spacing";
           }
           enum "1566.19" {
             description "1566.19 nm/191.415625 THz 3.125GHz spacing";
           }
           enum "1566.16" {
             description "1566.16 nm/191.418750 THz 3.125/6.25GHz spacing";
           }
           enum "1566.13" {
             description "1566.13 nm/191.421875 THz 3.125GHz spacing";
           }
           enum "1566.11" {
             description "1566.11 nm/191.425000 THz 3.125/6.25/12.5GHz spacing";
           }
           enum "1566.08" {
             description "1566.08 nm/191.428125 THz 3.125GHz spacing";
           }
           enum "1566.06" {
             description "1566.06 nm/191.431250 THz 3.125/6.25GHz spacing";
           }
           enum "1566.03" {
             description "1566.03 nm/191.434375 THz 3.125GHz spacing";
           }
           enum "1566.01" {
             description "1566.01 nm/191.437500 THz 3.125/6.25/12.5GHz spacing";
           }
           enum "1565.98" {
             description "1565.98 nm/191.440625 THz 3.125GHz spacing";
           }
           enum "1565.96" {
             description "1565.96 nm/191.443750 THz 3.125/6.25GHz spacing";
           }
           enum "1565.93" {
             description "1565.93 nm/191.446875 THz 3.125GHz spacing";
           }
           enum "1565.90" {
             description "1565.90 nm/191.450000 THz 3.125/6.25/12.5/50GHz spacing";
           }
           enum "1565.88" {
             description "1565.88 nm/191.453125 THz 3.125GHz spacing";
           }
           enum "1565.85" {
             description "1565.85 nm/191.456250 THz 3.125/6.25GHz spacing";
           }
           enum "1565.83" {
             description "1565.83 nm/191.459375 THz 3.125GHz spacing";
           }
           enum "1565.80" {
             description "1565.80 nm/191.462500 THz 3.125/6.25/12.5GHz spacing";
           }
           enum "1565.78" {
             description "1565.78 nm/191.465625 THz 3.125GHz spacing";
           }
           enum "1565.75" {
             description "1565.75 nm/191.468750 THz 3.125/6.25GHz spacing";
           }
           enum "1565.73" {
             description "1565.73 nm/191.471875 THz 3.125GHz spacing";
           }
           enum "1565.70" {
             description "1565.70 nm/191.475000 THz 3.125/6.25/12.5/75GHz spacing";
           }
           enum "1565.67" {
             description "1565.67 nm/191.478125 THz 3.125GHz spacing";
           }
           enum "1565.65" {
             description "1565.65 nm/191.481250 THz 3.125/6.25GHz spacing";
           }
           enum "1565.62" {
             description "1565.62 nm/191.484375 THz 3.125GHz spacing";
           }
           enum "1565.60" {
             description "1565.60 nm/191.487500 THz 3.125/6.25/12.5GHz spacing";
           }
           enum "1565.57" {
             description "1565.57 nm/191.490625 THz 3.125GHz spacing";
           }
           enum "1565.55" {
             description "1565.55 nm/191.493750 THz 3.125/6.25GHz spacing";
           }
           enum "1565.52" {
             description "1565.52 nm/191.496875 THz 3.125GHz spacing";
           }
           enum "1565.50" {
             description "1565.50 nm/191.500000 THz 3.125/6.25/12.5/100GHz spacing";
           }
           enum "1565.47" {
             description "1565.47 nm/191.503125 THz 3.125GHz spacing";
           }
           enum "1565.44" {
             description "1565.44 nm/191.506250 THz 3.125/6.25GHz spacing";
           }
           enum "1565.42" {
             description "1565.42 nm/191.509375 THz 3.125GHz spacing";
           }
           enum "1565.39" {
             description "1565.39 nm/191.512500 THz 3.125/6.25/12.5GHz spacing";
           }
           enum "1565.37" {
             description "1565.37 nm/191.515625 THz 3.125GHz spacing";
           }
           enum "1565.34" {
             description "1565.34 nm/191.518750 THz 3.125/6.25GHz spacing";
           }
           enum "1565.32" {
             description "1565.32 nm/191.521875 THz 3.125GHz spacing";
           }
           enum "1565.29" {
             description "1565.29 nm/191.525000 THz 3.125/6.25/12.5GHz spacing";
           }
           enum "1565.27" {
             description "1565.27 nm/191.528125 THz 3.125GHz spacing";
           }
           enum "1565.24" {
             description "1565.24 nm/191.531250 THz 3.125/6.25GHz spacing";
           }
           enum "1565.21" {
             description "1565.21 nm/191.534375 THz 3.125GHz spacing";
           }
           enum "1565.19" {
             description "1565.19 nm/191.537500 THz 3.125/6.25/12.5GHz spacing";
           }
           enum "1565.16" {
             description "1565.16 nm/191.540625 THz 3.125GHz spacing";
           }
           enum "1565.14" {
             description "1565.14 nm/191.543750 THz 3.125/6.25GHz spacing";
           }
           enum "1565.11" {
             description "1565.11 nm/191.546875 THz 3.125GHz spacing";
           }
           enum "1565.09" {
             description "1565.09 nm/191.550000 THz 3.125/6.25/12.5/50/75GHz spacing";
           }
           enum "1565.06" {
             description "1565.06 nm/191.553125 THz 3.125GHz spacing";
           }
           enum "1565.04" {
             description "1565.04 nm/191.556250 THz 3.125/6.25GHz spacing";
           }
           enum "1565.01" {
             description "1565.01 nm/191.559375 THz 3.125GHz spacing";
           }
           enum "1564.99" {
             description "1564.99 nm/191.562500 THz 3.125/6.25/12.5GHz spacing";
           }
           enum "1564.96" {
             description "1564.96 nm/191.565625 THz 3.125GHz spacing";
           }
           enum "1564.93" {
             description "1564.93 nm/191.568750 THz 3.125/6.25GHz spacing";
           }
           enum "1564.91" {
             description "1564.91 nm/191.571875 THz 3.125GHz spacing";
           }
           enum "1564.88" {
             description "1564.88 nm/191.575000 THz 3.125/6.25/12.5GHz spacing";
           }
           enum "1564.86" {
             description "1564.86 nm/191.578125 THz 3.125GHz spacing";
           }
           enum "1564.83" {
             description "1564.83 nm/191.581250 THz 3.125/6.25GHz spacing";
           }
           enum "1564.81" {
             description "1564.81 nm/191.584375 THz 3.125GHz spacing";
           }
           enum "1564.78" {
             description "1564.78 nm/191.587500 THz 3.125/6.25/12.5GHz spacing";
           }
           enum "1564.76" {
             description "1564.76 nm/191.590625 THz 3.125GHz spacing";
           }
           enum "1564.73" {
             description "1564.73 nm/191.593750 THz 3.125/6.25GHz spacing";
           }
           enum "1564.70" {
             description "1564.70 nm/191.596875 THz 3.125GHz spacing";
           }
           enum "1564.68" {
             description "1564.68 nm/191.600000 THz 3.125/6.25/12.5/100GHz spacing";
           }
           enum "1564.65" {
             description "1564.65 nm/191.603125 THz 3.125GHz spacing";
           }
           enum "1564.63" {
             description "1564.63 nm/191.606250 THz 3.125/6.25GHz spacing";
           }
           enum "1564.60" {
             description "1564.60 nm/191.609375 THz 3.125GHz spacing";
           }
           enum "1564.58" {
             description "1564.58 nm/191.612500 THz 3.125/6.25/12.5GHz spacing";
           }
           enum "1564.55" {
             description "1564.55 nm/191.615625 THz 3.125GHz spacing";
           }
           enum "1564.53" {
             description "1564.53 nm/191.618750 THz 3.125/6.25GHz spacing";
           }
           enum "1564.50" {
             description "1564.50 nm/191.621875 THz 3.125GHz spacing";
           }
           enum "1564.47" {
             description "1564.47 nm/191.625000 THz 3.125/6.25/12.5/75GHz spacing";
           }
           enum "1564.45" {
             description "1564.45 nm/191.628125 THz 3.125GHz spacing";
           }
           enum "1564.42" {
             description "1564.42 nm/191.631250 THz 3.125/6.25GHz spacing";
           }
           enum "1564.40" {
             description "1564.40 nm/191.634375 THz 3.125GHz spacing";
           }
           enum "1564.37" {
             description "1564.37 nm/191.637500 THz 3.125/6.25/12.5GHz spacing";
           }
           enum "1564.35" {
             description "1564.35 nm/191.640625 THz 3.125GHz spacing";
           }
           enum "1564.32" {
             description "1564.32 nm/191.643750 THz 3.125/6.25GHz spacing";
           }
           enum "1564.30" {
             description "1564.30 nm/191.646875 THz 3.125GHz spacing";
           }
           enum "1564.27" {
             description "1564.27 nm/191.650000 THz 3.125/6.25/12.5/50GHz spacing";
           }
           enum "1564.25" {
             description "1564.25 nm/191.653125 THz 3.125GHz spacing";
           }
           enum "1564.22" {
             description "1564.22 nm/191.656250 THz 3.125/6.25GHz spacing";
           }
           enum "1564.19" {
             description "1564.19 nm/191.659375 THz 3.125GHz spacing";
           }
           enum "1564.17" {
             description "1564.17 nm/191.662500 THz 3.125/6.25/12.5GHz spacing";
           }
           enum "1564.14" {
             description "1564.14 nm/191.665625 THz 3.125GHz spacing";
           }
           enum "1564.12" {
             description "1564.12 nm/191.668750 THz 3.125/6.25GHz spacing";
           }
           enum "1564.09" {
             description "1564.09 nm/191.671875 THz 3.125GHz spacing";
           }
           enum "1564.07" {
             description "1564.07 nm/191.675000 THz 3.125/6.25/12.5GHz spacing";
           }
           enum "1564.04" {
             description "1564.04 nm/191.678125 THz 3.125GHz spacing";
           }
           enum "1564.02" {
             description "1564.02 nm/191.681250 THz 3.125/6.25GHz spacing";
           }
           enum "1563.99" {
             description "1563.99 nm/191.684375 THz 3.125GHz spacing";
           }
           enum "1563.96" {
             description "1563.96 nm/191.687500 THz 3.125/6.25/12.5GHz spacing";
           }
           enum "1563.94" {
             description "1563.94 nm/191.690625 THz 3.125GHz spacing";
           }
           enum "1563.91" {
             description "1563.91 nm/191.693750 THz 3.125/6.25GHz spacing";
           }
           enum "1563.89" {
             description "1563.89 nm/191.696875 THz 3.125GHz spacing";
           }
           enum "1563.86" {
             description "1563.86 nm/191.700000 THz 3.125/6.25/12.5/50/75/100GHz spacing";
           }
           enum "1563.84" {
             description "1563.84 nm/191.703125 THz 3.125GHz spacing";
           }
           enum "1563.81" {
             description "1563.81 nm/191.706250 THz 3.125/6.25GHz spacing";
           }
           enum "1563.79" {
             description "1563.79 nm/191.709375 THz 3.125GHz spacing";
           }
           enum "1563.76" {
             description "1563.76 nm/191.712500 THz 3.125/6.25/12.5GHz spacing";
           }
           enum "1563.74" {
             description "1563.74 nm/191.715625 THz 3.125GHz spacing";
           }
           enum "1563.71" {
             description "1563.71 nm/191.718750 THz 3.125/6.25GHz spacing";
           }
           enum "1563.68" {
             description "1563.68 nm/191.721875 THz 3.125GHz spacing";
           }
           enum "1563.66" {
             description "1563.66 nm/191.725000 THz 3.125/6.25/12.5GHz spacing";
           }
           enum "1563.63" {
             description "1563.63 nm/191.728125 THz 3.125GHz spacing";
           }
           enum "1563.61" {
             description "1563.61 nm/191.731250 THz 3.125/6.25GHz spacing";
           }
           enum "1563.58" {
             description "1563.58 nm/191.734375 THz 3.125GHz spacing";
           }
           enum "1563.56" {
             description "1563.56 nm/191.737500 THz 3.125/6.25/12.5GHz spacing";
           }
           enum "1563.53" {
             description "1563.53 nm/191.740625 THz 3.125GHz spacing";
           }
           enum "1563.51" {
             description "1563.51 nm/191.743750 THz 3.125/6.25GHz spacing";
           }
           enum "1563.48" {
             description "1563.48 nm/191.746875 THz 3.125GHz spacing";
           }
           enum "1563.45" {
             description "1563.45 nm/191.750000 THz 3.125/6.25/12.5/50GHz spacing";
           }
           enum "1563.43" {
             description "1563.43 nm/191.753125 THz 3.125GHz spacing";
           }
           enum "1563.40" {
             description "1563.40 nm/191.756250 THz 3.125/6.25GHz spacing";
           }
           enum "1563.38" {
             description "1563.38 nm/191.759375 THz 3.125GHz spacing";
           }
           enum "1563.35" {
             description "1563.35 nm/191.762500 THz 3.125/6.25/12.5GHz spacing";
           }
           enum "1563.33" {
             description "1563.33 nm/191.765625 THz 3.125GHz spacing";
           }
           enum "1563.30" {
             description "1563.30 nm/191.768750 THz 3.125/6.25GHz spacing";
           }
           enum "1563.28" {
             description "1563.28 nm/191.771875 THz 3.125GHz spacing";
           }
           enum "1563.25" {
             description "1563.25 nm/191.775000 THz 3.125/6.25/12.5/75GHz spacing";
           }
           enum "1563.23" {
             description "1563.23 nm/191.778125 THz 3.125GHz spacing";
           }
           enum "1563.20" {
             description "1563.20 nm/191.781250 THz 3.125/6.25GHz spacing";
           }
           enum "1563.17" {
             description "1563.17 nm/191.784375 THz 3.125GHz spacing";
           }
           enum "1563.15" {
             description "1563.15 nm/191.787500 THz 3.125/6.25/12.5GHz spacing";
           }
           enum "1563.12" {
             description "1563.12 nm/191.790625 THz 3.125GHz spacing";
           }
           enum "1563.10" {
             description "1563.10 nm/191.793750 THz 3.125/6.25GHz spacing";
           }
           enum "1563.07" {
             description "1563.07 nm/191.796875 THz 3.125GHz spacing";
           }
           enum "1563.05" {
             description "1563.05 nm/191.800000 THz 3.125/6.25/12.5/100GHz spacing";
           }
           enum "1563.02" {
             description "1563.02 nm/191.803125 THz 3.125GHz spacing";
           }
           enum "1563.00" {
             description "1563.00 nm/191.806250 THz 3.125/6.25GHz spacing";
           }
           enum "1562.97" {
             description "1562.97 nm/191.809375 THz 3.125GHz spacing";
           }
           enum "1562.95" {
             description "1562.95 nm/191.812500 THz 3.125/6.25/12.5GHz spacing";
           }
           enum "1562.92" {
             description "1562.92 nm/191.815625 THz 3.125GHz spacing";
           }
           enum "1562.89" {
             description "1562.89 nm/191.818750 THz 3.125/6.25GHz spacing";
           }
           enum "1562.87" {
             description "1562.87 nm/191.821875 THz 3.125GHz spacing";
           }
           enum "1562.84" {
             description "1562.84 nm/191.825000 THz 3.125/6.25/12.5GHz spacing";
           }
           enum "1562.82" {
             description "1562.82 nm/191.828125 THz 3.125GHz spacing";
           }
           enum "1562.79" {
             description "1562.79 nm/191.831250 THz 3.125/6.25GHz spacing";
           }
           enum "1562.77" {
             description "1562.77 nm/191.834375 THz 3.125GHz spacing";
           }
           enum "1562.74" {
             description "1562.74 nm/191.837500 THz 3.125/6.25/12.5GHz spacing";
           }
           enum "1562.72" {
             description "1562.72 nm/191.840625 THz 3.125GHz spacing";
           }
           enum "1562.69" {
             description "1562.69 nm/191.843750 THz 3.125/6.25GHz spacing";
           }
           enum "1562.67" {
             description "1562.67 nm/191.846875 THz 3.125GHz spacing";
           }
           enum "1562.64" {
             description "1562.64 nm/191.850000 THz 3.125/6.25/12.5/50/75GHz spacing";
           }
           enum "1562.61" {
             description "1562.61 nm/191.853125 THz 3.125GHz spacing";
           }
           enum "1562.59" {
             description "1562.59 nm/191.856250 THz 3.125/6.25GHz spacing";
           }
           enum "1562.56" {
             description "1562.56 nm/191.859375 THz 3.125GHz spacing";
           }
           enum "1562.54" {
             description "1562.54 nm/191.862500 THz 3.125/6.25/12.5GHz spacing";
           }
           enum "1562.51" {
             description "1562.51 nm/191.865625 THz 3.125GHz spacing";
           }
           enum "1562.49" {
             description "1562.49 nm/191.868750 THz 3.125/6.25GHz spacing";
           }
           enum "1562.46" {
             description "1562.46 nm/191.871875 THz 3.125GHz spacing";
           }
           enum "1562.44" {
             description "1562.44 nm/191.875000 THz 3.125/6.25/12.5GHz spacing";
           }
           enum "1562.41" {
             description "1562.41 nm/191.878125 THz 3.125GHz spacing";
           }
           enum "1562.39" {
             description "1562.39 nm/191.881250 THz 3.125/6.25GHz spacing";
           }
           enum "1562.36" {
             description "1562.36 nm/191.884375 THz 3.125GHz spacing";
           }
           enum "1562.33" {
             description "1562.33 nm/191.887500 THz 3.125/6.25/12.5GHz spacing";
           }
           enum "1562.31" {
             description "1562.31 nm/191.890625 THz 3.125GHz spacing";
           }
           enum "1562.28" {
             description "1562.28 nm/191.893750 THz 3.125/6.25GHz spacing";
           }
           enum "1562.26" {
             description "1562.26 nm/191.896875 THz 3.125GHz spacing";
           }
           enum "1562.23" {
             description "1562.23 nm/191.900000 THz 3.125/6.25/12.5/100GHz spacing";
           }
           enum "1562.21" {
             description "1562.21 nm/191.903125 THz 3.125GHz spacing";
           }
           enum "1562.18" {
             description "1562.18 nm/191.906250 THz 3.125/6.25GHz spacing";
           }
           enum "1562.16" {
             description "1562.16 nm/191.909375 THz 3.125GHz spacing";
           }
           enum "1562.13" {
             description "1562.13 nm/191.912500 THz 3.125/6.25/12.5GHz spacing";
           }
           enum "1562.11" {
             description "1562.11 nm/191.915625 THz 3.125GHz spacing";
           }
           enum "1562.08" {
             description "1562.08 nm/191.918750 THz 3.125/6.25GHz spacing";
           }
           enum "1562.05" {
             description "1562.05 nm/191.921875 THz 3.125GHz spacing";
           }
           enum "1562.03" {
             description "1562.03 nm/191.925000 THz 3.125/6.25/12.5/75GHz spacing";
           }
           enum "1562.00" {
             description "1562.00 nm/191.928125 THz 3.125GHz spacing";
           }
           enum "1561.98" {
             description "1561.98 nm/191.931250 THz 3.125/6.25GHz spacing";
           }
           enum "1561.95" {
             description "1561.95 nm/191.934375 THz 3.125GHz spacing";
           }
           enum "1561.93" {
             description "1561.93 nm/191.937500 THz 3.125/6.25/12.5GHz spacing";
           }
           enum "1561.90" {
             description "1561.90 nm/191.940625 THz 3.125GHz spacing";
           }
           enum "1561.88" {
             description "1561.88 nm/191.943750 THz 3.125/6.25GHz spacing";
           }
           enum "1561.85" {
             description "1561.85 nm/191.946875 THz 3.125GHz spacing";
           }
           enum "1561.83" {
             description "1561.83 nm/191.950000 THz 3.125/6.25/12.5/50GHz spacing";
           }
           enum "1561.80" {
             description "1561.80 nm/191.953125 THz 3.125GHz spacing";
           }
           enum "1561.77" {
             description "1561.77 nm/191.956250 THz 3.125/6.25GHz spacing";
           }
           enum "1561.75" {
             description "1561.75 nm/191.959375 THz 3.125GHz spacing";
           }
           enum "1561.72" {
             description "1561.72 nm/191.962500 THz 3.125/6.25/12.5GHz spacing";
           }
           enum "1561.70" {
             description "1561.70 nm/191.965625 THz 3.125GHz spacing";
           }
           enum "1561.67" {
             description "1561.67 nm/191.968750 THz 3.125/6.25GHz spacing";
           }
           enum "1561.65" {
             description "1561.65 nm/191.971875 THz 3.125GHz spacing";
           }
           enum "1561.62" {
             description "1561.62 nm/191.975000 THz 3.125/6.25/12.5GHz spacing";
           }
           enum "1561.60" {
             description "1561.60 nm/191.978125 THz 3.125GHz spacing";
           }
           enum "1561.57" {
             description "1561.57 nm/191.981250 THz 3.125/6.25GHz spacing";
           }
           enum "1561.55" {
             description "1561.55 nm/191.984375 THz 3.125GHz spacing";
           }
           enum "1561.52" {
             description "1561.52 nm/191.987500 THz 3.125/6.25/12.5GHz spacing";
           }
           enum "1561.50" {
             description "1561.50 nm/191.990625 THz 3.125GHz spacing";
           }
           enum "1561.47" {
             description "1561.47 nm/191.993750 THz 3.125/6.25GHz spacing";
           }
           enum "1561.44" {
             description "1561.44 nm/191.996875 THz 3.125GHz spacing";
           }
           enum "1561.42" {
             description "1561.42 nm/192.000000 THz 3.125/6.25/12.5/50/75/100GHz spacing";
           }
           enum "1561.39" {
             description "1561.39 nm/192.003125 THz 3.125GHz spacing";
           }
           enum "1561.37" {
             description "1561.37 nm/192.006250 THz 3.125/6.25GHz spacing";
           }
           enum "1561.34" {
             description "1561.34 nm/192.009375 THz 3.125GHz spacing";
           }
           enum "1561.32" {
             description "1561.32 nm/192.012500 THz 3.125/6.25/12.5GHz spacing";
           }
           enum "1561.29" {
             description "1561.29 nm/192.015625 THz 3.125GHz spacing";
           }
           enum "1561.27" {
             description "1561.27 nm/192.018750 THz 3.125/6.25GHz spacing";
           }
           enum "1561.24" {
             description "1561.24 nm/192.021875 THz 3.125GHz spacing";
           }
           enum "1561.22" {
             description "1561.22 nm/192.025000 THz 3.125/6.25/12.5GHz spacing";
           }
           enum "1561.19" {
             description "1561.19 nm/192.028125 THz 3.125GHz spacing";
           }
           enum "1561.16" {
             description "1561.16 nm/192.031250 THz 3.125/6.25GHz spacing";
           }
           enum "1561.14" {
             description "1561.14 nm/192.034375 THz 3.125GHz spacing";
           }
           enum "1561.11" {
             description "1561.11 nm/192.037500 THz 3.125/6.25/12.5GHz spacing";
           }
           enum "1561.09" {
             description "1561.09 nm/192.040625 THz 3.125GHz spacing";
           }
           enum "1561.06" {
             description "1561.06 nm/192.043750 THz 3.125/6.25GHz spacing";
           }
           enum "1561.04" {
             description "1561.04 nm/192.046875 THz 3.125GHz spacing";
           }
           enum "1561.01" {
             description "1561.01 nm/192.050000 THz 3.125/6.25/12.5/50GHz spacing";
           }
           enum "1560.99" {
             description "1560.99 nm/192.053125 THz 3.125GHz spacing";
           }
           enum "1560.96" {
             description "1560.96 nm/192.056250 THz 3.125/6.25GHz spacing";
           }
           enum "1560.94" {
             description "1560.94 nm/192.059375 THz 3.125GHz spacing";
           }
           enum "1560.91" {
             description "1560.91 nm/192.062500 THz 3.125/6.25/12.5GHz spacing";
           }
           enum "1560.89" {
             description "1560.89 nm/192.065625 THz 3.125GHz spacing";
           }
           enum "1560.86" {
             description "1560.86 nm/192.068750 THz 3.125/6.25GHz spacing";
           }
           enum "1560.83" {
             description "1560.83 nm/192.071875 THz 3.125GHz spacing";
           }
           enum "1560.81" {
             description "1560.81 nm/192.075000 THz 3.125/6.25/12.5/75GHz spacing";
           }
           enum "1560.78" {
             description "1560.78 nm/192.078125 THz 3.125GHz spacing";
           }
           enum "1560.76" {
             description "1560.76 nm/192.081250 THz 3.125/6.25GHz spacing";
           }
           enum "1560.73" {
             description "1560.73 nm/192.084375 THz 3.125GHz spacing";
           }
           enum "1560.71" {
             description "1560.71 nm/192.087500 THz 3.125/6.25/12.5GHz spacing";
           }
           enum "1560.68" {
             description "1560.68 nm/192.090625 THz 3.125GHz spacing";
           }
           enum "1560.66" {
             description "1560.66 nm/192.093750 THz 3.125/6.25GHz spacing";
           }
           enum "1560.63" {
             description "1560.63 nm/192.096875 THz 3.125GHz spacing";
           }
           enum "1560.61" {
             description "1560.61 nm/192.100000 THz 3.125/6.25/12.5/100GHz spacing";
           }
           enum "1560.58" {
             description "1560.58 nm/192.103125 THz 3.125GHz spacing";
           }
           enum "1560.56" {
             description "1560.56 nm/192.106250 THz 3.125/6.25GHz spacing";
           }
           enum "1560.53" {
             description "1560.53 nm/192.109375 THz 3.125GHz spacing";
           }
           enum "1560.50" {
             description "1560.50 nm/192.112500 THz 3.125/6.25/12.5GHz spacing";
           }
           enum "1560.48" {
             description "1560.48 nm/192.115625 THz 3.125GHz spacing";
           }
           enum "1560.45" {
             description "1560.45 nm/192.118750 THz 3.125/6.25GHz spacing";
           }
           enum "1560.43" {
             description "1560.43 nm/192.121875 THz 3.125GHz spacing";
           }
           enum "1560.40" {
             description "1560.40 nm/192.125000 THz 3.125/6.25/12.5GHz spacing";
           }
           enum "1560.38" {
             description "1560.38 nm/192.128125 THz 3.125GHz spacing";
           }
           enum "1560.35" {
             description "1560.35 nm/192.131250 THz 3.125/6.25GHz spacing";
           }
           enum "1560.33" {
             description "1560.33 nm/192.134375 THz 3.125GHz spacing";
           }
           enum "1560.30" {
             description "1560.30 nm/192.137500 THz 3.125/6.25/12.5GHz spacing";
           }
           enum "1560.28" {
             description "1560.28 nm/192.140625 THz 3.125GHz spacing";
           }
           enum "1560.25" {
             description "1560.25 nm/192.143750 THz 3.125/6.25GHz spacing";
           }
           enum "1560.23" {
             description "1560.23 nm/192.146875 THz 3.125GHz spacing";
           }
           enum "1560.20" {
             description "1560.20 nm/192.150000 THz 3.125/6.25/12.5/50/75GHz spacing";
           }
           enum "1560.17" {
             description "1560.17 nm/192.153125 THz 3.125GHz spacing";
           }
           enum "1560.15" {
             description "1560.15 nm/192.156250 THz 3.125/6.25GHz spacing";
           }
           enum "1560.12" {
             description "1560.12 nm/192.159375 THz 3.125GHz spacing";
           }
           enum "1560.10" {
             description "1560.10 nm/192.162500 THz 3.125/6.25/12.5GHz spacing";
           }
           enum "1560.07" {
             description "1560.07 nm/192.165625 THz 3.125GHz spacing";
           }
           enum "1560.05" {
             description "1560.05 nm/192.168750 THz 3.125/6.25GHz spacing";
           }
           enum "1560.02" {
             description "1560.02 nm/192.171875 THz 3.125GHz spacing";
           }
           enum "1560.00" {
             description "1560.00 nm/192.175000 THz 3.125/6.25/12.5GHz spacing";
           }
           enum "1559.97" {
             description "1559.97 nm/192.178125 THz 3.125GHz spacing";
           }
           enum "1559.95" {
             description "1559.95 nm/192.181250 THz 3.125/6.25GHz spacing";
           }
           enum "1559.92" {
             description "1559.92 nm/192.184375 THz 3.125GHz spacing";
           }
           enum "1559.90" {
             description "1559.90 nm/192.187500 THz 3.125/6.25/12.5GHz spacing";
           }
           enum "1559.87" {
             description "1559.87 nm/192.190625 THz 3.125GHz spacing";
           }
           enum "1559.84" {
             description "1559.84 nm/192.193750 THz 3.125/6.25GHz spacing";
           }
           enum "1559.82" {
             description "1559.82 nm/192.196875 THz 3.125GHz spacing";
           }
           enum "1559.79" {
             description "1559.79 nm/192.200000 THz 3.125/6.25/12.5/100GHz spacing";
           }
           enum "1559.77" {
             description "1559.77 nm/192.203125 THz 3.125GHz spacing";
           }
           enum "1559.74" {
             description "1559.74 nm/192.206250 THz 3.125/6.25GHz spacing";
           }
           enum "1559.72" {
             description "1559.72 nm/192.209375 THz 3.125GHz spacing";
           }
           enum "1559.69" {
             description "1559.69 nm/192.212500 THz 3.125/6.25/12.5GHz spacing";
           }
           enum "1559.67" {
             description "1559.67 nm/192.215625 THz 3.125GHz spacing";
           }
           enum "1559.64" {
             description "1559.64 nm/192.218750 THz 3.125/6.25GHz spacing";
           }
           enum "1559.62" {
             description "1559.62 nm/192.221875 THz 3.125GHz spacing";
           }
           enum "1559.59" {
             description "1559.59 nm/192.225000 THz 3.125/6.25/12.5/75GHz spacing";
           }
           enum "1559.57" {
             description "1559.57 nm/192.228125 THz 3.125GHz spacing";
           }
           enum "1559.54" {
             description "1559.54 nm/192.231250 THz 3.125/6.25GHz spacing";
           }
           enum "1559.52" {
             description "1559.52 nm/192.234375 THz 3.125GHz spacing";
           }
           enum "1559.49" {
             description "1559.49 nm/192.237500 THz 3.125/6.25/12.5GHz spacing";
           }
           enum "1559.46" {
             description "1559.46 nm/192.240625 THz 3.125GHz spacing";
           }
           enum "1559.44" {
             description "1559.44 nm/192.243750 THz 3.125/6.25GHz spacing";
           }
           enum "1559.41" {
             description "1559.41 nm/192.246875 THz 3.125GHz spacing";
           }
           enum "1559.39" {
             description "1559.39 nm/192.250000 THz 3.125/6.25/12.5/50GHz spacing";
           }
           enum "1559.36" {
             description "1559.36 nm/192.253125 THz 3.125GHz spacing";
           }
           enum "1559.34" {
             description "1559.34 nm/192.256250 THz 3.125/6.25GHz spacing";
           }
           enum "1559.31" {
             description "1559.31 nm/192.259375 THz 3.125GHz spacing";
           }
           enum "1559.29" {
             description "1559.29 nm/192.262500 THz 3.125/6.25/12.5GHz spacing";
           }
           enum "1559.26" {
             description "1559.26 nm/192.265625 THz 3.125GHz spacing";
           }
           enum "1559.24" {
             description "1559.24 nm/192.268750 THz 3.125/6.25GHz spacing";
           }
           enum "1559.21" {
             description "1559.21 nm/192.271875 THz 3.125GHz spacing";
           }
           enum "1559.19" {
             description "1559.19 nm/192.275000 THz 3.125/6.25/12.5GHz spacing";
           }
           enum "1559.16" {
             description "1559.16 nm/192.278125 THz 3.125GHz spacing";
           }
           enum "1559.14" {
             description "1559.14 nm/192.281250 THz 3.125/6.25GHz spacing";
           }
           enum "1559.11" {
             description "1559.11 nm/192.284375 THz 3.125GHz spacing";
           }
           enum "1559.08" {
             description "1559.08 nm/192.287500 THz 3.125/6.25/12.5GHz spacing";
           }
           enum "1559.06" {
             description "1559.06 nm/192.290625 THz 3.125GHz spacing";
           }
           enum "1559.03" {
             description "1559.03 nm/192.293750 THz 3.125/6.25GHz spacing";
           }
           enum "1559.01" {
             description "1559.01 nm/192.296875 THz 3.125GHz spacing";
           }
           enum "1558.98" {
             description "1558.98 nm/192.300000 THz 3.125/6.25/12.5/50/75/100GHz spacing";
           }
           enum "1558.96" {
             description "1558.96 nm/192.303125 THz 3.125GHz spacing";
           }
           enum "1558.93" {
             description "1558.93 nm/192.306250 THz 3.125/6.25GHz spacing";
           }
           enum "1558.91" {
             description "1558.91 nm/192.309375 THz 3.125GHz spacing";
           }
           enum "1558.88" {
             description "1558.88 nm/192.312500 THz 3.125/6.25/12.5GHz spacing";
           }
           enum "1558.86" {
             description "1558.86 nm/192.315625 THz 3.125GHz spacing";
           }
           enum "1558.83" {
             description "1558.83 nm/192.318750 THz 3.125/6.25GHz spacing";
           }
           enum "1558.81" {
             description "1558.81 nm/192.321875 THz 3.125GHz spacing";
           }
           enum "1558.78" {
             description "1558.78 nm/192.325000 THz 3.125/6.25/12.5GHz spacing";
           }
           enum "1558.76" {
             description "1558.76 nm/192.328125 THz 3.125GHz spacing";
           }
           enum "1558.73" {
             description "1558.73 nm/192.331250 THz 3.125/6.25GHz spacing";
           }
           enum "1558.70" {
             description "1558.70 nm/192.334375 THz 3.125GHz spacing";
           }
           enum "1558.68" {
             description "1558.68 nm/192.337500 THz 3.125/6.25/12.5GHz spacing";
           }
           enum "1558.65" {
             description "1558.65 nm/192.340625 THz 3.125GHz spacing";
           }
           enum "1558.63" {
             description "1558.63 nm/192.343750 THz 3.125/6.25GHz spacing";
           }
           enum "1558.60" {
             description "1558.60 nm/192.346875 THz 3.125GHz spacing";
           }
           enum "1558.58" {
             description "1558.58 nm/192.350000 THz 3.125/6.25/12.5/50GHz spacing";
           }
           enum "1558.55" {
             description "1558.55 nm/192.353125 THz 3.125GHz spacing";
           }
           enum "1558.53" {
             description "1558.53 nm/192.356250 THz 3.125/6.25GHz spacing";
           }
           enum "1558.50" {
             description "1558.50 nm/192.359375 THz 3.125GHz spacing";
           }
           enum "1558.48" {
             description "1558.48 nm/192.362500 THz 3.125/6.25/12.5GHz spacing";
           }
           enum "1558.45" {
             description "1558.45 nm/192.365625 THz 3.125GHz spacing";
           }
           enum "1558.43" {
             description "1558.43 nm/192.368750 THz 3.125/6.25GHz spacing";
           }
           enum "1558.40" {
             description "1558.40 nm/192.371875 THz 3.125GHz spacing";
           }
           enum "1558.38" {
             description "1558.38 nm/192.375000 THz 3.125/6.25/12.5/75GHz spacing";
           }
           enum "1558.35" {
             description "1558.35 nm/192.378125 THz 3.125GHz spacing";
           }
           enum "1558.32" {
             description "1558.32 nm/192.381250 THz 3.125/6.25GHz spacing";
           }
           enum "1558.30" {
             description "1558.30 nm/192.384375 THz 3.125GHz spacing";
           }
           enum "1558.27" {
             description "1558.27 nm/192.387500 THz 3.125/6.25/12.5GHz spacing";
           }
           enum "1558.25" {
             description "1558.25 nm/192.390625 THz 3.125GHz spacing";
           }
           enum "1558.22" {
             description "1558.22 nm/192.393750 THz 3.125/6.25GHz spacing";
           }
           enum "1558.20" {
             description "1558.20 nm/192.396875 THz 3.125GHz spacing";
           }
           enum "1558.17" {
             description "1558.17 nm/192.400000 THz 3.125/6.25/12.5/100GHz spacing";
           }
           enum "1558.15" {
             description "1558.15 nm/192.403125 THz 3.125GHz spacing";
           }
           enum "1558.12" {
             description "1558.12 nm/192.406250 THz 3.125/6.25GHz spacing";
           }
           enum "1558.10" {
             description "1558.10 nm/192.409375 THz 3.125GHz spacing";
           }
           enum "1558.07" {
             description "1558.07 nm/192.412500 THz 3.125/6.25/12.5GHz spacing";
           }
           enum "1558.05" {
             description "1558.05 nm/192.415625 THz 3.125GHz spacing";
           }
           enum "1558.02" {
             description "1558.02 nm/192.418750 THz 3.125/6.25GHz spacing";
           }
           enum "1558.00" {
             description "1558.00 nm/192.421875 THz 3.125GHz spacing";
           }
           enum "1557.97" {
             description "1557.97 nm/192.425000 THz 3.125/6.25/12.5GHz spacing";
           }
           enum "1557.95" {
             description "1557.95 nm/192.428125 THz 3.125GHz spacing";
           }
           enum "1557.92" {
             description "1557.92 nm/192.431250 THz 3.125/6.25GHz spacing";
           }
           enum "1557.89" {
             description "1557.89 nm/192.434375 THz 3.125GHz spacing";
           }
           enum "1557.87" {
             description "1557.87 nm/192.437500 THz 3.125/6.25/12.5GHz spacing";
           }
           enum "1557.84" {
             description "1557.84 nm/192.440625 THz 3.125GHz spacing";
           }
           enum "1557.82" {
             description "1557.82 nm/192.443750 THz 3.125/6.25GHz spacing";
           }
           enum "1557.79" {
             description "1557.79 nm/192.446875 THz 3.125GHz spacing";
           }
           enum "1557.77" {
             description "1557.77 nm/192.450000 THz 3.125/6.25/12.5/50/75GHz spacing";
           }
           enum "1557.74" {
             description "1557.74 nm/192.453125 THz 3.125GHz spacing";
           }
           enum "1557.72" {
             description "1557.72 nm/192.456250 THz 3.125/6.25GHz spacing";
           }
           enum "1557.69" {
             description "1557.69 nm/192.459375 THz 3.125GHz spacing";
           }
           enum "1557.67" {
             description "1557.67 nm/192.462500 THz 3.125/6.25/12.5GHz spacing";
           }
           enum "1557.64" {
             description "1557.64 nm/192.465625 THz 3.125GHz spacing";
           }
           enum "1557.62" {
             description "1557.62 nm/192.468750 THz 3.125/6.25GHz spacing";
           }
           enum "1557.59" {
             description "1557.59 nm/192.471875 THz 3.125GHz spacing";
           }
           enum "1557.57" {
             description "1557.57 nm/192.475000 THz 3.125/6.25/12.5GHz spacing";
           }
           enum "1557.54" {
             description "1557.54 nm/192.478125 THz 3.125GHz spacing";
           }
           enum "1557.52" {
             description "1557.52 nm/192.481250 THz 3.125/6.25GHz spacing";
           }
           enum "1557.49" {
             description "1557.49 nm/192.484375 THz 3.125GHz spacing";
           }
           enum "1557.46" {
             description "1557.46 nm/192.487500 THz 3.125/6.25/12.5GHz spacing";
           }
           enum "1557.44" {
             description "1557.44 nm/192.490625 THz 3.125GHz spacing";
           }
           enum "1557.41" {
             description "1557.41 nm/192.493750 THz 3.125/6.25GHz spacing";
           }
           enum "1557.39" {
             description "1557.39 nm/192.496875 THz 3.125GHz spacing";
           }
           enum "1557.36" {
             description "1557.36 nm/192.500000 THz 3.125/6.25/12.5/100GHz spacing";
           }
           enum "1557.34" {
             description "1557.34 nm/192.503125 THz 3.125GHz spacing";
           }
           enum "1557.31" {
             description "1557.31 nm/192.506250 THz 3.125/6.25GHz spacing";
           }
           enum "1557.29" {
             description "1557.29 nm/192.509375 THz 3.125GHz spacing";
           }
           enum "1557.26" {
             description "1557.26 nm/192.512500 THz 3.125/6.25/12.5GHz spacing";
           }
           enum "1557.24" {
             description "1557.24 nm/192.515625 THz 3.125GHz spacing";
           }
           enum "1557.21" {
             description "1557.21 nm/192.518750 THz 3.125/6.25GHz spacing";
           }
           enum "1557.19" {
             description "1557.19 nm/192.521875 THz 3.125GHz spacing";
           }
           enum "1557.16" {
             description "1557.16 nm/192.525000 THz 3.125/6.25/12.5/75GHz spacing";
           }
           enum "1557.14" {
             description "1557.14 nm/192.528125 THz 3.125GHz spacing";
           }
           enum "1557.11" {
             description "1557.11 nm/192.531250 THz 3.125/6.25GHz spacing";
           }
           enum "1557.09" {
             description "1557.09 nm/192.534375 THz 3.125GHz spacing";
           }
           enum "1557.06" {
             description "1557.06 nm/192.537500 THz 3.125/6.25/12.5GHz spacing";
           }
           enum "1557.03" {
             description "1557.03 nm/192.540625 THz 3.125GHz spacing";
           }
           enum "1557.01" {
             description "1557.01 nm/192.543750 THz 3.125/6.25GHz spacing";
           }
           enum "1556.98" {
             description "1556.98 nm/192.546875 THz 3.125GHz spacing";
           }
           enum "1556.96" {
             description "1556.96 nm/192.550000 THz 3.125/6.25/12.5/50GHz spacing";
           }
           enum "1556.93" {
             description "1556.93 nm/192.553125 THz 3.125GHz spacing";
           }
           enum "1556.91" {
             description "1556.91 nm/192.556250 THz 3.125/6.25GHz spacing";
           }
           enum "1556.88" {
             description "1556.88 nm/192.559375 THz 3.125GHz spacing";
           }
           enum "1556.86" {
             description "1556.86 nm/192.562500 THz 3.125/6.25/12.5GHz spacing";
           }
           enum "1556.83" {
             description "1556.83 nm/192.565625 THz 3.125GHz spacing";
           }
           enum "1556.81" {
             description "1556.81 nm/192.568750 THz 3.125/6.25GHz spacing";
           }
           enum "1556.78" {
             description "1556.78 nm/192.571875 THz 3.125GHz spacing";
           }
           enum "1556.76" {
             description "1556.76 nm/192.575000 THz 3.125/6.25/12.5GHz spacing";
           }
           enum "1556.73" {
             description "1556.73 nm/192.578125 THz 3.125GHz spacing";
           }
           enum "1556.71" {
             description "1556.71 nm/192.581250 THz 3.125/6.25GHz spacing";
           }
           enum "1556.68" {
             description "1556.68 nm/192.584375 THz 3.125GHz spacing";
           }
           enum "1556.66" {
             description "1556.66 nm/192.587500 THz 3.125/6.25/12.5GHz spacing";
           }
           enum "1556.63" {
             description "1556.63 nm/192.590625 THz 3.125GHz spacing";
           }
           enum "1556.61" {
             description "1556.61 nm/192.593750 THz 3.125/6.25GHz spacing";
           }
           enum "1556.58" {
             description "1556.58 nm/192.596875 THz 3.125GHz spacing";
           }
           enum "1556.55" {
             description "1556.55 nm/192.600000 THz 3.125/6.25/12.5/50/75/100GHz spacing";
           }
           enum "1556.53" {
             description "1556.53 nm/192.603125 THz 3.125GHz spacing";
           }
           enum "1556.50" {
             description "1556.50 nm/192.606250 THz 3.125/6.25GHz spacing";
           }
           enum "1556.48" {
             description "1556.48 nm/192.609375 THz 3.125GHz spacing";
           }
           enum "1556.45" {
             description "1556.45 nm/192.612500 THz 3.125/6.25/12.5GHz spacing";
           }
           enum "1556.43" {
             description "1556.43 nm/192.615625 THz 3.125GHz spacing";
           }
           enum "1556.40" {
             description "1556.40 nm/192.618750 THz 3.125/6.25GHz spacing";
           }
           enum "1556.38" {
             description "1556.38 nm/192.621875 THz 3.125GHz spacing";
           }
           enum "1556.35" {
             description "1556.35 nm/192.625000 THz 3.125/6.25/12.5GHz spacing";
           }
           enum "1556.33" {
             description "1556.33 nm/192.628125 THz 3.125GHz spacing";
           }
           enum "1556.30" {
             description "1556.30 nm/192.631250 THz 3.125/6.25GHz spacing";
           }
           enum "1556.28" {
             description "1556.28 nm/192.634375 THz 3.125GHz spacing";
           }
           enum "1556.25" {
             description "1556.25 nm/192.637500 THz 3.125/6.25/12.5GHz spacing";
           }
           enum "1556.23" {
             description "1556.23 nm/192.640625 THz 3.125GHz spacing";
           }
           enum "1556.20" {
             description "1556.20 nm/192.643750 THz 3.125/6.25GHz spacing";
           }
           enum "1556.18" {
             description "1556.18 nm/192.646875 THz 3.125GHz spacing";
           }
           enum "1556.15" {
             description "1556.15 nm/192.650000 THz 3.125/6.25/12.5/50GHz spacing";
           }
           enum "1556.13" {
             description "1556.13 nm/192.653125 THz 3.125GHz spacing";
           }
           enum "1556.10" {
             description "1556.10 nm/192.656250 THz 3.125/6.25GHz spacing";
           }
           enum "1556.08" {
             description "1556.08 nm/192.659375 THz 3.125GHz spacing";
           }
           enum "1556.05" {
             description "1556.05 nm/192.662500 THz 3.125/6.25/12.5GHz spacing";
           }
           enum "1556.02" {
             description "1556.02 nm/192.665625 THz 3.125GHz spacing";
           }
           enum "1556.00" {
             description "1556.00 nm/192.668750 THz 3.125/6.25GHz spacing";
           }
           enum "1555.97" {
             description "1555.97 nm/192.671875 THz 3.125GHz spacing";
           }
           enum "1555.95" {
             description "1555.95 nm/192.675000 THz 3.125/6.25/12.5/75GHz spacing";
           }
           enum "1555.92" {
             description "1555.92 nm/192.678125 THz 3.125GHz spacing";
           }
           enum "1555.90" {
             description "1555.90 nm/192.681250 THz 3.125/6.25GHz spacing";
           }
           enum "1555.87" {
             description "1555.87 nm/192.684375 THz 3.125GHz spacing";
           }
           enum "1555.85" {
             description "1555.85 nm/192.687500 THz 3.125/6.25/12.5GHz spacing";
           }
           enum "1555.82" {
             description "1555.82 nm/192.690625 THz 3.125GHz spacing";
           }
           enum "1555.80" {
             description "1555.80 nm/192.693750 THz 3.125/6.25GHz spacing";
           }
           enum "1555.77" {
             description "1555.77 nm/192.696875 THz 3.125GHz spacing";
           }
           enum "1555.75" {
             description "1555.75 nm/192.700000 THz 3.125/6.25/12.5/100GHz spacing";
           }
           enum "1555.72" {
             description "1555.72 nm/192.703125 THz 3.125GHz spacing";
           }
           enum "1555.70" {
             description "1555.70 nm/192.706250 THz 3.125/6.25GHz spacing";
           }
           enum "1555.67" {
             description "1555.67 nm/192.709375 THz 3.125GHz spacing";
           }
           enum "1555.65" {
             description "1555.65 nm/192.712500 THz 3.125/6.25/12.5GHz spacing";
           }
           enum "1555.62" {
             description "1555.62 nm/192.715625 THz 3.125GHz spacing";
           }
           enum "1555.60" {
             description "1555.60 nm/192.718750 THz 3.125/6.25GHz spacing";
           }
           enum "1555.57" {
             description "1555.57 nm/192.721875 THz 3.125GHz spacing";
           }
           enum "1555.55" {
             description "1555.55 nm/192.725000 THz 3.125/6.25/12.5GHz spacing";
           }
           enum "1555.52" {
             description "1555.52 nm/192.728125 THz 3.125GHz spacing";
           }
           enum "1555.49" {
             description "1555.49 nm/192.731250 THz 3.125/6.25GHz spacing";
           }
           enum "1555.47" {
             description "1555.47 nm/192.734375 THz 3.125GHz spacing";
           }
           enum "1555.44" {
             description "1555.44 nm/192.737500 THz 3.125/6.25/12.5GHz spacing";
           }
           enum "1555.42" {
             description "1555.42 nm/192.740625 THz 3.125GHz spacing";
           }
           enum "1555.39" {
             description "1555.39 nm/192.743750 THz 3.125/6.25GHz spacing";
           }
           enum "1555.37" {
             description "1555.37 nm/192.746875 THz 3.125GHz spacing";
           }
           enum "1555.34" {
             description "1555.34 nm/192.750000 THz 3.125/6.25/12.5/50/75GHz spacing";
           }
           enum "1555.32" {
             description "1555.32 nm/192.753125 THz 3.125GHz spacing";
           }
           enum "1555.29" {
             description "1555.29 nm/192.756250 THz 3.125/6.25GHz spacing";
           }
           enum "1555.27" {
             description "1555.27 nm/192.759375 THz 3.125GHz spacing";
           }
           enum "1555.24" {
             description "1555.24 nm/192.762500 THz 3.125/6.25/12.5GHz spacing";
           }
           enum "1555.22" {
             description "1555.22 nm/192.765625 THz 3.125GHz spacing";
           }
           enum "1555.19" {
             description "1555.19 nm/192.768750 THz 3.125/6.25GHz spacing";
           }
           enum "1555.17" {
             description "1555.17 nm/192.771875 THz 3.125GHz spacing";
           }
           enum "1555.14" {
             description "1555.14 nm/192.775000 THz 3.125/6.25/12.5GHz spacing";
           }
           enum "1555.12" {
             description "1555.12 nm/192.778125 THz 3.125GHz spacing";
           }
           enum "1555.09" {
             description "1555.09 nm/192.781250 THz 3.125/6.25GHz spacing";
           }
           enum "1555.07" {
             description "1555.07 nm/192.784375 THz 3.125GHz spacing";
           }
           enum "1555.04" {
             description "1555.04 nm/192.787500 THz 3.125/6.25/12.5GHz spacing";
           }
           enum "1555.02" {
             description "1555.02 nm/192.790625 THz 3.125GHz spacing";
           }
           enum "1554.99" {
             description "1554.99 nm/192.793750 THz 3.125/6.25GHz spacing";
           }
           enum "1554.97" {
             description "1554.97 nm/192.796875 THz 3.125GHz spacing";
           }
           enum "1554.94" {
             description "1554.94 nm/192.800000 THz 3.125/6.25/12.5/100GHz spacing";
           }
           enum "1554.91" {
             description "1554.91 nm/192.803125 THz 3.125GHz spacing";
           }
           enum "1554.89" {
             description "1554.89 nm/192.806250 THz 3.125/6.25GHz spacing";
           }
           enum "1554.86" {
             description "1554.86 nm/192.809375 THz 3.125GHz spacing";
           }
           enum "1554.84" {
             description "1554.84 nm/192.812500 THz 3.125/6.25/12.5GHz spacing";
           }
           enum "1554.81" {
             description "1554.81 nm/192.815625 THz 3.125GHz spacing";
           }
           enum "1554.79" {
             description "1554.79 nm/192.818750 THz 3.125/6.25GHz spacing";
           }
           enum "1554.76" {
             description "1554.76 nm/192.821875 THz 3.125GHz spacing";
           }
           enum "1554.74" {
             description "1554.74 nm/192.825000 THz 3.125/6.25/12.5/75GHz spacing";
           }
           enum "1554.71" {
             description "1554.71 nm/192.828125 THz 3.125GHz spacing";
           }
           enum "1554.69" {
             description "1554.69 nm/192.831250 THz 3.125/6.25GHz spacing";
           }
           enum "1554.66" {
             description "1554.66 nm/192.834375 THz 3.125GHz spacing";
           }
           enum "1554.64" {
             description "1554.64 nm/192.837500 THz 3.125/6.25/12.5GHz spacing";
           }
           enum "1554.61" {
             description "1554.61 nm/192.840625 THz 3.125GHz spacing";
           }
           enum "1554.59" {
             description "1554.59 nm/192.843750 THz 3.125/6.25GHz spacing";
           }
           enum "1554.56" {
             description "1554.56 nm/192.846875 THz 3.125GHz spacing";
           }
           enum "1554.54" {
             description "1554.54 nm/192.850000 THz 3.125/6.25/12.5/50GHz spacing";
           }
           enum "1554.51" {
             description "1554.51 nm/192.853125 THz 3.125GHz spacing";
           }
           enum "1554.49" {
             description "1554.49 nm/192.856250 THz 3.125/6.25GHz spacing";
           }
           enum "1554.46" {
             description "1554.46 nm/192.859375 THz 3.125GHz spacing";
           }
           enum "1554.44" {
             description "1554.44 nm/192.862500 THz 3.125/6.25/12.5GHz spacing";
           }
           enum "1554.41" {
             description "1554.41 nm/192.865625 THz 3.125GHz spacing";
           }
           enum "1554.39" {
             description "1554.39 nm/192.868750 THz 3.125/6.25GHz spacing";
           }
           enum "1554.36" {
             description "1554.36 nm/192.871875 THz 3.125GHz spacing";
           }
           enum "1554.34" {
             description "1554.34 nm/192.875000 THz 3.125/6.25/12.5GHz spacing";
           }
           enum "1554.31" {
             description "1554.31 nm/192.878125 THz 3.125GHz spacing";
           }
           enum "1554.29" {
             description "1554.29 nm/192.881250 THz 3.125/6.25GHz spacing";
           }
           enum "1554.26" {
             description "1554.26 nm/192.884375 THz 3.125GHz spacing";
           }
           enum "1554.23" {
             description "1554.23 nm/192.887500 THz 3.125/6.25/12.5GHz spacing";
           }
           enum "1554.21" {
             description "1554.21 nm/192.890625 THz 3.125GHz spacing";
           }
           enum "1554.18" {
             description "1554.18 nm/192.893750 THz 3.125/6.25GHz spacing";
           }
           enum "1554.16" {
             description "1554.16 nm/192.896875 THz 3.125GHz spacing";
           }
           enum "1554.13" {
             description "1554.13 nm/192.900000 THz 3.125/6.25/12.5/50/75/100GHz spacing";
           }
           enum "1554.11" {
             description "1554.11 nm/192.903125 THz 3.125GHz spacing";
           }
           enum "1554.08" {
             description "1554.08 nm/192.906250 THz 3.125/6.25GHz spacing";
           }
           enum "1554.06" {
             description "1554.06 nm/192.909375 THz 3.125GHz spacing";
           }
           enum "1554.03" {
             description "1554.03 nm/192.912500 THz 3.125/6.25/12.5GHz spacing";
           }
           enum "1554.01" {
             description "1554.01 nm/192.915625 THz 3.125GHz spacing";
           }
           enum "1553.98" {
             description "1553.98 nm/192.918750 THz 3.125/6.25GHz spacing";
           }
           enum "1553.96" {
             description "1553.96 nm/192.921875 THz 3.125GHz spacing";
           }
           enum "1553.93" {
             description "1553.93 nm/192.925000 THz 3.125/6.25/12.5GHz spacing";
           }
           enum "1553.91" {
             description "1553.91 nm/192.928125 THz 3.125GHz spacing";
           }
           enum "1553.88" {
             description "1553.88 nm/192.931250 THz 3.125/6.25GHz spacing";
           }
           enum "1553.86" {
             description "1553.86 nm/192.934375 THz 3.125GHz spacing";
           }
           enum "1553.83" {
             description "1553.83 nm/192.937500 THz 3.125/6.25/12.5GHz spacing";
           }
           enum "1553.81" {
             description "1553.81 nm/192.940625 THz 3.125GHz spacing";
           }
           enum "1553.78" {
             description "1553.78 nm/192.943750 THz 3.125/6.25GHz spacing";
           }
           enum "1553.76" {
             description "1553.76 nm/192.946875 THz 3.125GHz spacing";
           }
           enum "1553.73" {
             description "1553.73 nm/192.950000 THz 3.125/6.25/12.5/50GHz spacing";
           }
           enum "1553.71" {
             description "1553.71 nm/192.953125 THz 3.125GHz spacing";
           }
           enum "1553.68" {
             description "1553.68 nm/192.956250 THz 3.125/6.25GHz spacing";
           }
           enum "1553.66" {
             description "1553.66 nm/192.959375 THz 3.125GHz spacing";
           }
           enum "1553.63" {
             description "1553.63 nm/192.962500 THz 3.125/6.25/12.5GHz spacing";
           }
           enum "1553.61" {
             description "1553.61 nm/192.965625 THz 3.125GHz spacing";
           }
           enum "1553.58" {
             description "1553.58 nm/192.968750 THz 3.125/6.25GHz spacing";
           }
           enum "1553.56" {
             description "1553.56 nm/192.971875 THz 3.125GHz spacing";
           }
           enum "1553.53" {
             description "1553.53 nm/192.975000 THz 3.125/6.25/12.5/75GHz spacing";
           }
           enum "1553.50" {
             description "1553.50 nm/192.978125 THz 3.125GHz spacing";
           }
           enum "1553.48" {
             description "1553.48 nm/192.981250 THz 3.125/6.25GHz spacing";
           }
           enum "1553.45" {
             description "1553.45 nm/192.984375 THz 3.125GHz spacing";
           }
           enum "1553.43" {
             description "1553.43 nm/192.987500 THz 3.125/6.25/12.5GHz spacing";
           }
           enum "1553.40" {
             description "1553.40 nm/192.990625 THz 3.125GHz spacing";
           }
           enum "1553.38" {
             description "1553.38 nm/192.993750 THz 3.125/6.25GHz spacing";
           }
           enum "1553.35" {
             description "1553.35 nm/192.996875 THz 3.125GHz spacing";
           }
           enum "1553.33" {
             description "1553.33 nm/193.000000 THz 3.125/6.25/12.5/100GHz spacing";
           }
           enum "1553.30" {
             description "1553.30 nm/193.003125 THz 3.125GHz spacing";
           }
           enum "1553.28" {
             description "1553.28 nm/193.006250 THz 3.125/6.25GHz spacing";
           }
           enum "1553.25" {
             description "1553.25 nm/193.009375 THz 3.125GHz spacing";
           }
           enum "1553.23" {
             description "1553.23 nm/193.012500 THz 3.125/6.25/12.5GHz spacing";
           }
           enum "1553.20" {
             description "1553.20 nm/193.015625 THz 3.125GHz spacing";
           }
           enum "1553.18" {
             description "1553.18 nm/193.018750 THz 3.125/6.25GHz spacing";
           }
           enum "1553.15" {
             description "1553.15 nm/193.021875 THz 3.125GHz spacing";
           }
           enum "1553.13" {
             description "1553.13 nm/193.025000 THz 3.125/6.25/12.5GHz spacing";
           }
           enum "1553.10" {
             description "1553.10 nm/193.028125 THz 3.125GHz spacing";
           }
           enum "1553.08" {
             description "1553.08 nm/193.031250 THz 3.125/6.25GHz spacing";
           }
           enum "1553.05" {
             description "1553.05 nm/193.034375 THz 3.125GHz spacing";
           }
           enum "1553.03" {
             description "1553.03 nm/193.037500 THz 3.125/6.25/12.5GHz spacing";
           }
           enum "1553.00" {
             description "1553.00 nm/193.040625 THz 3.125GHz spacing";
           }
           enum "1552.98" {
             description "1552.98 nm/193.043750 THz 3.125/6.25GHz spacing";
           }
           enum "1552.95" {
             description "1552.95 nm/193.046875 THz 3.125GHz spacing";
           }
           enum "1552.93" {
             description "1552.93 nm/193.050000 THz 3.125/6.25/12.5/50/75GHz spacing";
           }
           enum "1552.90" {
             description "1552.90 nm/193.053125 THz 3.125GHz spacing";
           }
           enum "1552.88" {
             description "1552.88 nm/193.056250 THz 3.125/6.25GHz spacing";
           }
           enum "1552.85" {
             description "1552.85 nm/193.059375 THz 3.125GHz spacing";
           }
           enum "1552.83" {
             description "1552.83 nm/193.062500 THz 3.125/6.25/12.5GHz spacing";
           }
           enum "1552.80" {
             description "1552.80 nm/193.065625 THz 3.125GHz spacing";
           }
           enum "1552.78" {
             description "1552.78 nm/193.068750 THz 3.125/6.25GHz spacing";
           }
           enum "1552.75" {
             description "1552.75 nm/193.071875 THz 3.125GHz spacing";
           }
           enum "1552.73" {
             description "1552.73 nm/193.075000 THz 3.125/6.25/12.5GHz spacing";
           }
           enum "1552.70" {
             description "1552.70 nm/193.078125 THz 3.125GHz spacing";
           }
           enum "1552.68" {
             description "1552.68 nm/193.081250 THz 3.125/6.25GHz spacing";
           }
           enum "1552.65" {
             description "1552.65 nm/193.084375 THz 3.125GHz spacing";
           }
           enum "1552.62" {
             description "1552.62 nm/193.087500 THz 3.125/6.25/12.5GHz spacing";
           }
           enum "1552.60" {
             description "1552.60 nm/193.090625 THz 3.125GHz spacing";
           }
           enum "1552.57" {
             description "1552.57 nm/193.093750 THz 3.125/6.25GHz spacing";
           }
           enum "1552.55" {
             description "1552.55 nm/193.096875 THz 3.125GHz spacing";
           }
           enum "1552.52" {
             description "1552.52 nm/193.100000 THz 3.125/6.25/12.5/100GHz spacing";
           }
           enum "1552.50" {
             description "1552.50 nm/193.103125 THz 3.125GHz spacing";
           }
           enum "1552.47" {
             description "1552.47 nm/193.106250 THz 3.125/6.25GHz spacing";
           }
           enum "1552.45" {
             description "1552.45 nm/193.109375 THz 3.125GHz spacing";
           }
           enum "1552.42" {
             description "1552.42 nm/193.112500 THz 3.125/6.25/12.5GHz spacing";
           }
           enum "1552.40" {
             description "1552.40 nm/193.115625 THz 3.125GHz spacing";
           }
           enum "1552.37" {
             description "1552.37 nm/193.118750 THz 3.125/6.25GHz spacing";
           }
           enum "1552.35" {
             description "1552.35 nm/193.121875 THz 3.125GHz spacing";
           }
           enum "1552.32" {
             description "1552.32 nm/193.125000 THz 3.125/6.25/12.5/75GHz spacing";
           }
           enum "1552.30" {
             description "1552.30 nm/193.128125 THz 3.125GHz spacing";
           }
           enum "1552.27" {
             description "1552.27 nm/193.131250 THz 3.125/6.25GHz spacing";
           }
           enum "1552.25" {
             description "1552.25 nm/193.134375 THz 3.125GHz spacing";
           }
           enum "1552.22" {
             description "1552.22 nm/193.137500 THz 3.125/6.25/12.5GHz spacing";
           }
           enum "1552.20" {
             description "1552.20 nm/193.140625 THz 3.125GHz spacing";
           }
           enum "1552.17" {
             description "1552.17 nm/193.143750 THz 3.125/6.25GHz spacing";
           }
           enum "1552.15" {
             description "1552.15 nm/193.146875 THz 3.125GHz spacing";
           }
           enum "1552.12" {
             description "1552.12 nm/193.150000 THz 3.125/6.25/12.5/50GHz spacing";
           }
           enum "1552.10" {
             description "1552.10 nm/193.153125 THz 3.125GHz spacing";
           }
           enum "1552.07" {
             description "1552.07 nm/193.156250 THz 3.125/6.25GHz spacing";
           }
           enum "1552.05" {
             description "1552.05 nm/193.159375 THz 3.125GHz spacing";
           }
           enum "1552.02" {
             description "1552.02 nm/193.162500 THz 3.125/6.25/12.5GHz spacing";
           }
           enum "1552.00" {
             description "1552.00 nm/193.165625 THz 3.125GHz spacing";
           }
           enum "1551.97" {
             description "1551.97 nm/193.168750 THz 3.125/6.25GHz spacing";
           }
           enum "1551.95" {
             description "1551.95 nm/193.171875 THz 3.125GHz spacing";
           }
           enum "1551.92" {
             description "1551.92 nm/193.175000 THz 3.125/6.25/12.5GHz spacing";
           }
           enum "1551.90" {
             description "1551.90 nm/193.178125 THz 3.125GHz spacing";
           }
           enum "1551.87" {
             description "1551.87 nm/193.181250 THz 3.125/6.25GHz spacing";
           }
           enum "1551.85" {
             description "1551.85 nm/193.184375 THz 3.125GHz spacing";
           }
           enum "1551.82" {
             description "1551.82 nm/193.187500 THz 3.125/6.25/12.5GHz spacing";
           }
           enum "1551.80" {
             description "1551.80 nm/193.190625 THz 3.125GHz spacing";
           }
           enum "1551.77" {
             description "1551.77 nm/193.193750 THz 3.125/6.25GHz spacing";
           }
           enum "1551.75" {
             description "1551.75 nm/193.196875 THz 3.125GHz spacing";
           }
           enum "1551.72" {
             description "1551.72 nm/193.200000 THz 3.125/6.25/12.5/50/75/100GHz spacing";
           }
           enum "1551.70" {
             description "1551.70 nm/193.203125 THz 3.125GHz spacing";
           }
           enum "1551.67" {
             description "1551.67 nm/193.206250 THz 3.125/6.25GHz spacing";
           }
           enum "1551.65" {
             description "1551.65 nm/193.209375 THz 3.125GHz spacing";
           }
           enum "1551.62" {
             description "1551.62 nm/193.212500 THz 3.125/6.25/12.5GHz spacing";
           }
           enum "1551.60" {
             description "1551.60 nm/193.215625 THz 3.125GHz spacing";
           }
           enum "1551.57" {
             description "1551.57 nm/193.218750 THz 3.125/6.25GHz spacing";
           }
           enum "1551.55" {
             description "1551.55 nm/193.221875 THz 3.125GHz spacing";
           }
           enum "1551.52" {
             description "1551.52 nm/193.225000 THz 3.125/6.25/12.5GHz spacing";
           }
           enum "1551.49" {
             description "1551.49 nm/193.228125 THz 3.125GHz spacing";
           }
           enum "1551.47" {
             description "1551.47 nm/193.231250 THz 3.125/6.25GHz spacing";
           }
           enum "1551.44" {
             description "1551.44 nm/193.234375 THz 3.125GHz spacing";
           }
           enum "1551.42" {
             description "1551.42 nm/193.237500 THz 3.125/6.25/12.5GHz spacing";
           }
           enum "1551.39" {
             description "1551.39 nm/193.240625 THz 3.125GHz spacing";
           }
           enum "1551.37" {
             description "1551.37 nm/193.243750 THz 3.125/6.25GHz spacing";
           }
           enum "1551.34" {
             description "1551.34 nm/193.246875 THz 3.125GHz spacing";
           }
           enum "1551.32" {
             description "1551.32 nm/193.250000 THz 3.125/6.25/12.5/50GHz spacing";
           }
           enum "1551.29" {
             description "1551.29 nm/193.253125 THz 3.125GHz spacing";
           }
           enum "1551.27" {
             description "1551.27 nm/193.256250 THz 3.125/6.25GHz spacing";
           }
           enum "1551.24" {
             description "1551.24 nm/193.259375 THz 3.125GHz spacing";
           }
           enum "1551.22" {
             description "1551.22 nm/193.262500 THz 3.125/6.25/12.5GHz spacing";
           }
           enum "1551.19" {
             description "1551.19 nm/193.265625 THz 3.125GHz spacing";
           }
           enum "1551.17" {
             description "1551.17 nm/193.268750 THz 3.125/6.25GHz spacing";
           }
           enum "1551.14" {
             description "1551.14 nm/193.271875 THz 3.125GHz spacing";
           }
           enum "1551.12" {
             description "1551.12 nm/193.275000 THz 3.125/6.25/12.5/75GHz spacing";
           }
           enum "1551.09" {
             description "1551.09 nm/193.278125 THz 3.125GHz spacing";
           }
           enum "1551.07" {
             description "1551.07 nm/193.281250 THz 3.125/6.25GHz spacing";
           }
           enum "1551.04" {
             description "1551.04 nm/193.284375 THz 3.125GHz spacing";
           }
           enum "1551.02" {
             description "1551.02 nm/193.287500 THz 3.125/6.25/12.5GHz spacing";
           }
           enum "1550.99" {
             description "1550.99 nm/193.290625 THz 3.125GHz spacing";
           }
           enum "1550.97" {
             description "1550.97 nm/193.293750 THz 3.125/6.25GHz spacing";
           }
           enum "1550.94" {
             description "1550.94 nm/193.296875 THz 3.125GHz spacing";
           }
           enum "1550.92" {
             description "1550.92 nm/193.300000 THz 3.125/6.25/12.5/100GHz spacing";
           }
           enum "1550.89" {
             description "1550.89 nm/193.303125 THz 3.125GHz spacing";
           }
           enum "1550.87" {
             description "1550.87 nm/193.306250 THz 3.125/6.25GHz spacing";
           }
           enum "1550.84" {
             description "1550.84 nm/193.309375 THz 3.125GHz spacing";
           }
           enum "1550.82" {
             description "1550.82 nm/193.312500 THz 3.125/6.25/12.5GHz spacing";
           }
           enum "1550.79" {
             description "1550.79 nm/193.315625 THz 3.125GHz spacing";
           }
           enum "1550.77" {
             description "1550.77 nm/193.318750 THz 3.125/6.25GHz spacing";
           }
           enum "1550.74" {
             description "1550.74 nm/193.321875 THz 3.125GHz spacing";
           }
           enum "1550.72" {
             description "1550.72 nm/193.325000 THz 3.125/6.25/12.5GHz spacing";
           }
           enum "1550.69" {
             description "1550.69 nm/193.328125 THz 3.125GHz spacing";
           }
           enum "1550.67" {
             description "1550.67 nm/193.331250 THz 3.125/6.25GHz spacing";
           }
           enum "1550.64" {
             description "1550.64 nm/193.334375 THz 3.125GHz spacing";
           }
           enum "1550.62" {
             description "1550.62 nm/193.337500 THz 3.125/6.25/12.5GHz spacing";
           }
           enum "1550.59" {
             description "1550.59 nm/193.340625 THz 3.125GHz spacing";
           }
           enum "1550.57" {
             description "1550.57 nm/193.343750 THz 3.125/6.25GHz spacing";
           }
           enum "1550.54" {
             description "1550.54 nm/193.346875 THz 3.125GHz spacing";
           }
           enum "1550.52" {
             description "1550.52 nm/193.350000 THz 3.125/6.25/12.5/50/75GHz spacing";
           }
           enum "1550.49" {
             description "1550.49 nm/193.353125 THz 3.125GHz spacing";
           }
           enum "1550.47" {
             description "1550.47 nm/193.356250 THz 3.125/6.25GHz spacing";
           }
           enum "1550.44" {
             description "1550.44 nm/193.359375 THz 3.125GHz spacing";
           }
           enum "1550.42" {
             description "1550.42 nm/193.362500 THz 3.125/6.25/12.5GHz spacing";
           }
           enum "1550.39" {
             description "1550.39 nm/193.365625 THz 3.125GHz spacing";
           }
           enum "1550.37" {
             description "1550.37 nm/193.368750 THz 3.125/6.25GHz spacing";
           }
           enum "1550.34" {
             description "1550.34 nm/193.371875 THz 3.125GHz spacing";
           }
           enum "1550.32" {
             description "1550.32 nm/193.375000 THz 3.125/6.25/12.5GHz spacing";
           }
           enum "1550.29" {
             description "1550.29 nm/193.378125 THz 3.125GHz spacing";
           }
           enum "1550.27" {
             description "1550.27 nm/193.381250 THz 3.125/6.25GHz spacing";
           }
           enum "1550.24" {
             description "1550.24 nm/193.384375 THz 3.125GHz spacing";
           }
           enum "1550.22" {
             description "1550.22 nm/193.387500 THz 3.125/6.25/12.5GHz spacing";
           }
           enum "1550.19" {
             description "1550.19 nm/193.390625 THz 3.125GHz spacing";
           }
           enum "1550.17" {
             description "1550.17 nm/193.393750 THz 3.125/6.25GHz spacing";
           }
           enum "1550.14" {
             description "1550.14 nm/193.396875 THz 3.125GHz spacing";
           }
           enum "1550.12" {
             description "1550.12 nm/193.400000 THz 3.125/6.25/12.5/100GHz spacing";
           }
           enum "1550.09" {
             description "1550.09 nm/193.403125 THz 3.125GHz spacing";
           }
           enum "1550.07" {
             description "1550.07 nm/193.406250 THz 3.125/6.25GHz spacing";
           }
           enum "1550.04" {
             description "1550.04 nm/193.409375 THz 3.125GHz spacing";
           }
           enum "1550.02" {
             description "1550.02 nm/193.412500 THz 3.125/6.25/12.5GHz spacing";
           }
           enum "1549.99" {
             description "1549.99 nm/193.415625 THz 3.125GHz spacing";
           }
           enum "1549.97" {
             description "1549.97 nm/193.418750 THz 3.125/6.25GHz spacing";
           }
           enum "1549.94" {
             description "1549.94 nm/193.421875 THz 3.125GHz spacing";
           }
           enum "1549.92" {
             description "1549.92 nm/193.425000 THz 3.125/6.25/12.5/75GHz spacing";
           }
           enum "1549.89" {
             description "1549.89 nm/193.428125 THz 3.125GHz spacing";
           }
           enum "1549.87" {
             description "1549.87 nm/193.431250 THz 3.125/6.25GHz spacing";
           }
           enum "1549.84" {
             description "1549.84 nm/193.434375 THz 3.125GHz spacing";
           }
           enum "1549.82" {
             description "1549.82 nm/193.437500 THz 3.125/6.25/12.5GHz spacing";
           }
           enum "1549.79" {
             description "1549.79 nm/193.440625 THz 3.125GHz spacing";
           }
           enum "1549.77" {
             description "1549.77 nm/193.443750 THz 3.125/6.25GHz spacing";
           }
           enum "1549.74" {
             description "1549.74 nm/193.446875 THz 3.125GHz spacing";
           }
           enum "1549.72" {
             description "1549.72 nm/193.450000 THz 3.125/6.25/12.5/50GHz spacing";
           }
           enum "1549.69" {
             description "1549.69 nm/193.453125 THz 3.125GHz spacing";
           }
           enum "1549.67" {
             description "1549.67 nm/193.456250 THz 3.125/6.25GHz spacing";
           }
           enum "1549.64" {
             description "1549.64 nm/193.459375 THz 3.125GHz spacing";
           }
           enum "1549.62" {
             description "1549.62 nm/193.462500 THz 3.125/6.25/12.5GHz spacing";
           }
           enum "1549.59" {
             description "1549.59 nm/193.465625 THz 3.125GHz spacing";
           }
           enum "1549.57" {
             description "1549.57 nm/193.468750 THz 3.125/6.25GHz spacing";
           }
           enum "1549.54" {
             description "1549.54 nm/193.471875 THz 3.125GHz spacing";
           }
           enum "1549.52" {
             description "1549.52 nm/193.475000 THz 3.125/6.25/12.5GHz spacing";
           }
           enum "1549.49" {
             description "1549.49 nm/193.478125 THz 3.125GHz spacing";
           }
           enum "1549.47" {
             description "1549.47 nm/193.481250 THz 3.125/6.25GHz spacing";
           }
           enum "1549.44" {
             description "1549.44 nm/193.484375 THz 3.125GHz spacing";
           }
           enum "1549.42" {
             description "1549.42 nm/193.487500 THz 3.125/6.25/12.5GHz spacing";
           }
           enum "1549.39" {
             description "1549.39 nm/193.490625 THz 3.125GHz spacing";
           }
           enum "1549.37" {
             description "1549.37 nm/193.493750 THz 3.125/6.25GHz spacing";
           }
           enum "1549.34" {
             description "1549.34 nm/193.496875 THz 3.125GHz spacing";
           }
           enum "1549.32" {
             description "1549.32 nm/193.500000 THz 3.125/6.25/12.5/50/75/100GHz spacing";
           }
           enum "1549.29" {
             description "1549.29 nm/193.503125 THz 3.125GHz spacing";
           }
           enum "1549.26" {
             description "1549.26 nm/193.506250 THz 3.125/6.25GHz spacing";
           }
           enum "1549.24" {
             description "1549.24 nm/193.509375 THz 3.125GHz spacing";
           }
           enum "1549.21" {
             description "1549.21 nm/193.512500 THz 3.125/6.25/12.5GHz spacing";
           }
           enum "1549.19" {
             description "1549.19 nm/193.515625 THz 3.125GHz spacing";
           }
           enum "1549.16" {
             description "1549.16 nm/193.518750 THz 3.125/6.25GHz spacing";
           }
           enum "1549.14" {
             description "1549.14 nm/193.521875 THz 3.125GHz spacing";
           }
           enum "1549.11" {
             description "1549.11 nm/193.525000 THz 3.125/6.25/12.5GHz spacing";
           }
           enum "1549.09" {
             description "1549.09 nm/193.528125 THz 3.125GHz spacing";
           }
           enum "1549.06" {
             description "1549.06 nm/193.531250 THz 3.125/6.25GHz spacing";
           }
           enum "1549.04" {
             description "1549.04 nm/193.534375 THz 3.125GHz spacing";
           }
           enum "1549.01" {
             description "1549.01 nm/193.537500 THz 3.125/6.25/12.5GHz spacing";
           }
           enum "1548.99" {
             description "1548.99 nm/193.540625 THz 3.125GHz spacing";
           }
           enum "1548.96" {
             description "1548.96 nm/193.543750 THz 3.125/6.25GHz spacing";
           }
           enum "1548.94" {
             description "1548.94 nm/193.546875 THz 3.125GHz spacing";
           }
           enum "1548.91" {
             description "1548.91 nm/193.550000 THz 3.125/6.25/12.5/50GHz spacing";
           }
           enum "1548.89" {
             description "1548.89 nm/193.553125 THz 3.125GHz spacing";
           }
           enum "1548.86" {
             description "1548.86 nm/193.556250 THz 3.125/6.25GHz spacing";
           }
           enum "1548.84" {
             description "1548.84 nm/193.559375 THz 3.125GHz spacing";
           }
           enum "1548.81" {
             description "1548.81 nm/193.562500 THz 3.125/6.25/12.5GHz spacing";
           }
           enum "1548.79" {
             description "1548.79 nm/193.565625 THz 3.125GHz spacing";
           }
           enum "1548.76" {
             description "1548.76 nm/193.568750 THz 3.125/6.25GHz spacing";
           }
           enum "1548.74" {
             description "1548.74 nm/193.571875 THz 3.125GHz spacing";
           }
           enum "1548.71" {
             description "1548.71 nm/193.575000 THz 3.125/6.25/12.5/75GHz spacing";
           }
           enum "1548.69" {
             description "1548.69 nm/193.578125 THz 3.125GHz spacing";
           }
           enum "1548.66" {
             description "1548.66 nm/193.581250 THz 3.125/6.25GHz spacing";
           }
           enum "1548.64" {
             description "1548.64 nm/193.584375 THz 3.125GHz spacing";
           }
           enum "1548.61" {
             description "1548.61 nm/193.587500 THz 3.125/6.25/12.5GHz spacing";
           }
           enum "1548.59" {
             description "1548.59 nm/193.590625 THz 3.125GHz spacing";
           }
           enum "1548.56" {
             description "1548.56 nm/193.593750 THz 3.125/6.25GHz spacing";
           }
           enum "1548.54" {
             description "1548.54 nm/193.596875 THz 3.125GHz spacing";
           }
           enum "1548.51" {
             description "1548.51 nm/193.600000 THz 3.125/6.25/12.5/100GHz spacing";
           }
           enum "1548.49" {
             description "1548.49 nm/193.603125 THz 3.125GHz spacing";
           }
           enum "1548.46" {
             description "1548.46 nm/193.606250 THz 3.125/6.25GHz spacing";
           }
           enum "1548.44" {
             description "1548.44 nm/193.609375 THz 3.125GHz spacing";
           }
           enum "1548.41" {
             description "1548.41 nm/193.612500 THz 3.125/6.25/12.5GHz spacing";
           }
           enum "1548.39" {
             description "1548.39 nm/193.615625 THz 3.125GHz spacing";
           }
           enum "1548.36" {
             description "1548.36 nm/193.618750 THz 3.125/6.25GHz spacing";
           }
           enum "1548.34" {
             description "1548.34 nm/193.621875 THz 3.125GHz spacing";
           }
           enum "1548.31" {
             description "1548.31 nm/193.625000 THz 3.125/6.25/12.5GHz spacing";
           }
           enum "1548.29" {
             description "1548.29 nm/193.628125 THz 3.125GHz spacing";
           }
           enum "1548.26" {
             description "1548.26 nm/193.631250 THz 3.125/6.25GHz spacing";
           }
           enum "1548.24" {
             description "1548.24 nm/193.634375 THz 3.125GHz spacing";
           }
           enum "1548.21" {
             description "1548.21 nm/193.637500 THz 3.125/6.25/12.5GHz spacing";
           }
           enum "1548.19" {
             description "1548.19 nm/193.640625 THz 3.125GHz spacing";
           }
           enum "1548.16" {
             description "1548.16 nm/193.643750 THz 3.125/6.25GHz spacing";
           }
           enum "1548.14" {
             description "1548.14 nm/193.646875 THz 3.125GHz spacing";
           }
           enum "1548.11" {
             description "1548.11 nm/193.650000 THz 3.125/6.25/12.5/50/75GHz spacing";
           }
           enum "1548.09" {
             description "1548.09 nm/193.653125 THz 3.125GHz spacing";
           }
           enum "1548.06" {
             description "1548.06 nm/193.656250 THz 3.125/6.25GHz spacing";
           }
           enum "1548.04" {
             description "1548.04 nm/193.659375 THz 3.125GHz spacing";
           }
           enum "1548.02" {
             description "1548.02 nm/193.662500 THz 3.125/6.25/12.5GHz spacing";
           }
           enum "1547.99" {
             description "1547.99 nm/193.665625 THz 3.125GHz spacing";
           }
           enum "1547.97" {
             description "1547.97 nm/193.668750 THz 3.125/6.25GHz spacing";
           }
           enum "1547.94" {
             description "1547.94 nm/193.671875 THz 3.125GHz spacing";
           }
           enum "1547.92" {
             description "1547.92 nm/193.675000 THz 3.125/6.25/12.5GHz spacing";
           }
           enum "1547.89" {
             description "1547.89 nm/193.678125 THz 3.125GHz spacing";
           }
           enum "1547.87" {
             description "1547.87 nm/193.681250 THz 3.125/6.25GHz spacing";
           }
           enum "1547.84" {
             description "1547.84 nm/193.684375 THz 3.125GHz spacing";
           }
           enum "1547.82" {
             description "1547.82 nm/193.687500 THz 3.125/6.25/12.5GHz spacing";
           }
           enum "1547.79" {
             description "1547.79 nm/193.690625 THz 3.125GHz spacing";
           }
           enum "1547.77" {
             description "1547.77 nm/193.693750 THz 3.125/6.25GHz spacing";
           }
           enum "1547.74" {
             description "1547.74 nm/193.696875 THz 3.125GHz spacing";
           }
           enum "1547.72" {
             description "1547.72 nm/193.700000 THz 3.125/6.25/12.5/100GHz spacing";
           }
           enum "1547.69" {
             description "1547.69 nm/193.703125 THz 3.125GHz spacing";
           }
           enum "1547.67" {
             description "1547.67 nm/193.706250 THz 3.125/6.25GHz spacing";
           }
           enum "1547.64" {
             description "1547.64 nm/193.709375 THz 3.125GHz spacing";
           }
           enum "1547.62" {
             description "1547.62 nm/193.712500 THz 3.125/6.25/12.5GHz spacing";
           }
           enum "1547.59" {
             description "1547.59 nm/193.715625 THz 3.125GHz spacing";
           }
           enum "1547.57" {
             description "1547.57 nm/193.718750 THz 3.125/6.25GHz spacing";
           }
           enum "1547.54" {
             description "1547.54 nm/193.721875 THz 3.125GHz spacing";
           }
           enum "1547.52" {
             description "1547.52 nm/193.725000 THz 3.125/6.25/12.5/75GHz spacing";
           }
           enum "1547.49" {
             description "1547.49 nm/193.728125 THz 3.125GHz spacing";
           }
           enum "1547.47" {
             description "1547.47 nm/193.731250 THz 3.125/6.25GHz spacing";
           }
           enum "1547.44" {
             description "1547.44 nm/193.734375 THz 3.125GHz spacing";
           }
           enum "1547.42" {
             description "1547.42 nm/193.737500 THz 3.125/6.25/12.5GHz spacing";
           }
           enum "1547.39" {
             description "1547.39 nm/193.740625 THz 3.125GHz spacing";
           }
           enum "1547.37" {
             description "1547.37 nm/193.743750 THz 3.125/6.25GHz spacing";
           }
           enum "1547.34" {
             description "1547.34 nm/193.746875 THz 3.125GHz spacing";
           }
           enum "1547.32" {
             description "1547.32 nm/193.750000 THz 3.125/6.25/12.5/50GHz spacing";
           }
           enum "1547.29" {
             description "1547.29 nm/193.753125 THz 3.125GHz spacing";
           }
           enum "1547.27" {
             description "1547.27 nm/193.756250 THz 3.125/6.25GHz spacing";
           }
           enum "1547.24" {
             description "1547.24 nm/193.759375 THz 3.125GHz spacing";
           }
           enum "1547.22" {
             description "1547.22 nm/193.762500 THz 3.125/6.25/12.5GHz spacing";
           }
           enum "1547.19" {
             description "1547.19 nm/193.765625 THz 3.125GHz spacing";
           }
           enum "1547.17" {
             description "1547.17 nm/193.768750 THz 3.125/6.25GHz spacing";
           }
           enum "1547.14" {
             description "1547.14 nm/193.771875 THz 3.125GHz spacing";
           }
           enum "1547.12" {
             description "1547.12 nm/193.775000 THz 3.125/6.25/12.5GHz spacing";
           }
           enum "1547.09" {
             description "1547.09 nm/193.778125 THz 3.125GHz spacing";
           }
           enum "1547.07" {
             description "1547.07 nm/193.781250 THz 3.125/6.25GHz spacing";
           }
           enum "1547.04" {
             description "1547.04 nm/193.784375 THz 3.125GHz spacing";
           }
           enum "1547.02" {
             description "1547.02 nm/193.787500 THz 3.125/6.25/12.5GHz spacing";
           }
           enum "1546.99" {
             description "1546.99 nm/193.790625 THz 3.125GHz spacing";
           }
           enum "1546.97" {
             description "1546.97 nm/193.793750 THz 3.125/6.25GHz spacing";
           }
           enum "1546.94" {
             description "1546.94 nm/193.796875 THz 3.125GHz spacing";
           }
           enum "1546.92" {
             description "1546.92 nm/193.800000 THz 3.125/6.25/12.5/50/75/100GHz spacing";
           }
           enum "1546.89" {
             description "1546.89 nm/193.803125 THz 3.125GHz spacing";
           }
           enum "1546.87" {
             description "1546.87 nm/193.806250 THz 3.125/6.25GHz spacing";
           }
           enum "1546.84" {
             description "1546.84 nm/193.809375 THz 3.125GHz spacing";
           }
           enum "1546.82" {
             description "1546.82 nm/193.812500 THz 3.125/6.25/12.5GHz spacing";
           }
           enum "1546.79" {
             description "1546.79 nm/193.815625 THz 3.125GHz spacing";
           }
           enum "1546.77" {
             description "1546.77 nm/193.818750 THz 3.125/6.25GHz spacing";
           }
           enum "1546.74" {
             description "1546.74 nm/193.821875 THz 3.125GHz spacing";
           }
           enum "1546.72" {
             description "1546.72 nm/193.825000 THz 3.125/6.25/12.5GHz spacing";
           }
           enum "1546.69" {
             description "1546.69 nm/193.828125 THz 3.125GHz spacing";
           }
           enum "1546.67" {
             description "1546.67 nm/193.831250 THz 3.125/6.25GHz spacing";
           }
           enum "1546.64" {
             description "1546.64 nm/193.834375 THz 3.125GHz spacing";
           }
           enum "1546.62" {
             description "1546.62 nm/193.837500 THz 3.125/6.25/12.5GHz spacing";
           }
           enum "1546.59" {
             description "1546.59 nm/193.840625 THz 3.125GHz spacing";
           }
           enum "1546.57" {
             description "1546.57 nm/193.843750 THz 3.125/6.25GHz spacing";
           }
           enum "1546.54" {
             description "1546.54 nm/193.846875 THz 3.125GHz spacing";
           }
           enum "1546.52" {
             description "1546.52 nm/193.850000 THz 3.125/6.25/12.5/50GHz spacing";
           }
           enum "1546.49" {
             description "1546.49 nm/193.853125 THz 3.125GHz spacing";
           }
           enum "1546.47" {
             description "1546.47 nm/193.856250 THz 3.125/6.25GHz spacing";
           }
           enum "1546.44" {
             description "1546.44 nm/193.859375 THz 3.125GHz spacing";
           }
           enum "1546.42" {
             description "1546.42 nm/193.862500 THz 3.125/6.25/12.5GHz spacing";
           }
           enum "1546.39" {
             description "1546.39 nm/193.865625 THz 3.125GHz spacing";
           }
           enum "1546.37" {
             description "1546.37 nm/193.868750 THz 3.125/6.25GHz spacing";
           }
           enum "1546.34" {
             description "1546.34 nm/193.871875 THz 3.125GHz spacing";
           }
           enum "1546.32" {
             description "1546.32 nm/193.875000 THz 3.125/6.25/12.5/75GHz spacing";
           }
           enum "1546.29" {
             description "1546.29 nm/193.878125 THz 3.125GHz spacing";
           }
           enum "1546.27" {
             description "1546.27 nm/193.881250 THz 3.125/6.25GHz spacing";
           }
           enum "1546.24" {
             description "1546.24 nm/193.884375 THz 3.125GHz spacing";
           }
           enum "1546.22" {
             description "1546.22 nm/193.887500 THz 3.125/6.25/12.5GHz spacing";
           }
           enum "1546.19" {
             description "1546.19 nm/193.890625 THz 3.125GHz spacing";
           }
           enum "1546.17" {
             description "1546.17 nm/193.893750 THz 3.125/6.25GHz spacing";
           }
           enum "1546.14" {
             description "1546.14 nm/193.896875 THz 3.125GHz spacing";
           }
           enum "1546.12" {
             description "1546.12 nm/193.900000 THz 3.125/6.25/12.5/100GHz spacing";
           }
           enum "1546.09" {
             description "1546.09 nm/193.903125 THz 3.125GHz spacing";
           }
           enum "1546.07" {
             description "1546.07 nm/193.906250 THz 3.125/6.25GHz spacing";
           }
           enum "1546.04" {
             description "1546.04 nm/193.909375 THz 3.125GHz spacing";
           }
           enum "1546.02" {
             description "1546.02 nm/193.912500 THz 3.125/6.25/12.5GHz spacing";
           }
           enum "1545.99" {
             description "1545.99 nm/193.915625 THz 3.125GHz spacing";
           }
           enum "1545.97" {
             description "1545.97 nm/193.918750 THz 3.125/6.25GHz spacing";
           }
           enum "1545.94" {
             description "1545.94 nm/193.921875 THz 3.125GHz spacing";
           }
           enum "1545.92" {
             description "1545.92 nm/193.925000 THz 3.125/6.25/12.5GHz spacing";
           }
           enum "1545.89" {
             description "1545.89 nm/193.928125 THz 3.125GHz spacing";
           }
           enum "1545.87" {
             description "1545.87 nm/193.931250 THz 3.125/6.25GHz spacing";
           }
           enum "1545.84" {
             description "1545.84 nm/193.934375 THz 3.125GHz spacing";
           }
           enum "1545.82" {
             description "1545.82 nm/193.937500 THz 3.125/6.25/12.5GHz spacing";
           }
           enum "1545.80" {
             description "1545.80 nm/193.940625 THz 3.125GHz spacing";
           }
           enum "1545.77" {
             description "1545.77 nm/193.943750 THz 3.125/6.25GHz spacing";
           }
           enum "1545.75" {
             description "1545.75 nm/193.946875 THz 3.125GHz spacing";
           }
           enum "1545.72" {
             description "1545.72 nm/193.950000 THz 3.125/6.25/12.5/50/75GHz spacing";
           }
           enum "1545.70" {
             description "1545.70 nm/193.953125 THz 3.125GHz spacing";
           }
           enum "1545.67" {
             description "1545.67 nm/193.956250 THz 3.125/6.25GHz spacing";
           }
           enum "1545.65" {
             description "1545.65 nm/193.959375 THz 3.125GHz spacing";
           }
           enum "1545.62" {
             description "1545.62 nm/193.962500 THz 3.125/6.25/12.5GHz spacing";
           }
           enum "1545.60" {
             description "1545.60 nm/193.965625 THz 3.125GHz spacing";
           }
           enum "1545.57" {
             description "1545.57 nm/193.968750 THz 3.125/6.25GHz spacing";
           }
           enum "1545.55" {
             description "1545.55 nm/193.971875 THz 3.125GHz spacing";
           }
           enum "1545.52" {
             description "1545.52 nm/193.975000 THz 3.125/6.25/12.5GHz spacing";
           }
           enum "1545.50" {
             description "1545.50 nm/193.978125 THz 3.125GHz spacing";
           }
           enum "1545.47" {
             description "1545.47 nm/193.981250 THz 3.125/6.25GHz spacing";
           }
           enum "1545.45" {
             description "1545.45 nm/193.984375 THz 3.125GHz spacing";
           }
           enum "1545.42" {
             description "1545.42 nm/193.987500 THz 3.125/6.25/12.5GHz spacing";
           }
           enum "1545.40" {
             description "1545.40 nm/193.990625 THz 3.125GHz spacing";
           }
           enum "1545.37" {
             description "1545.37 nm/193.993750 THz 3.125/6.25GHz spacing";
           }
           enum "1545.35" {
             description "1545.35 nm/193.996875 THz 3.125GHz spacing";
           }
           enum "1545.32" {
             description "1545.32 nm/194.000000 THz 3.125/6.25/12.5/100GHz spacing";
           }
           enum "1545.30" {
             description "1545.30 nm/194.003125 THz 3.125GHz spacing";
           }
           enum "1545.27" {
             description "1545.27 nm/194.006250 THz 3.125/6.25GHz spacing";
           }
           enum "1545.25" {
             description "1545.25 nm/194.009375 THz 3.125GHz spacing";
           }
           enum "1545.22" {
             description "1545.22 nm/194.012500 THz 3.125/6.25/12.5GHz spacing";
           }
           enum "1545.20" {
             description "1545.20 nm/194.015625 THz 3.125GHz spacing";
           }
           enum "1545.17" {
             description "1545.17 nm/194.018750 THz 3.125/6.25GHz spacing";
           }
           enum "1545.15" {
             description "1545.15 nm/194.021875 THz 3.125GHz spacing";
           }
           enum "1545.12" {
             description "1545.12 nm/194.025000 THz 3.125/6.25/12.5/75GHz spacing";
           }
           enum "1545.10" {
             description "1545.10 nm/194.028125 THz 3.125GHz spacing";
           }
           enum "1545.07" {
             description "1545.07 nm/194.031250 THz 3.125/6.25GHz spacing";
           }
           enum "1545.05" {
             description "1545.05 nm/194.034375 THz 3.125GHz spacing";
           }
           enum "1545.02" {
             description "1545.02 nm/194.037500 THz 3.125/6.25/12.5GHz spacing";
           }
           enum "1545.00" {
             description "1545.00 nm/194.040625 THz 3.125GHz spacing";
           }
           enum "1544.97" {
             description "1544.97 nm/194.043750 THz 3.125/6.25GHz spacing";
           }
           enum "1544.95" {
             description "1544.95 nm/194.046875 THz 3.125GHz spacing";
           }
           enum "1544.92" {
             description "1544.92 nm/194.050000 THz 3.125/6.25/12.5/50GHz spacing";
           }
           enum "1544.90" {
             description "1544.90 nm/194.053125 THz 3.125GHz spacing";
           }
           enum "1544.87" {
             description "1544.87 nm/194.056250 THz 3.125/6.25GHz spacing";
           }
           enum "1544.85" {
             description "1544.85 nm/194.059375 THz 3.125GHz spacing";
           }
           enum "1544.82" {
             description "1544.82 nm/194.062500 THz 3.125/6.25/12.5GHz spacing";
           }
           enum "1544.80" {
             description "1544.80 nm/194.065625 THz 3.125GHz spacing";
           }
           enum "1544.77" {
             description "1544.77 nm/194.068750 THz 3.125/6.25GHz spacing";
           }
           enum "1544.75" {
             description "1544.75 nm/194.071875 THz 3.125GHz spacing";
           }
           enum "1544.72" {
             description "1544.72 nm/194.075000 THz 3.125/6.25/12.5GHz spacing";
           }
           enum "1544.70" {
             description "1544.70 nm/194.078125 THz 3.125GHz spacing";
           }
           enum "1544.68" {
             description "1544.68 nm/194.081250 THz 3.125/6.25GHz spacing";
           }
           enum "1544.65" {
             description "1544.65 nm/194.084375 THz 3.125GHz spacing";
           }
           enum "1544.63" {
             description "1544.63 nm/194.087500 THz 3.125/6.25/12.5GHz spacing";
           }
           enum "1544.60" {
             description "1544.60 nm/194.090625 THz 3.125GHz spacing";
           }
           enum "1544.58" {
             description "1544.58 nm/194.093750 THz 3.125/6.25GHz spacing";
           }
           enum "1544.55" {
             description "1544.55 nm/194.096875 THz 3.125GHz spacing";
           }
           enum "1544.53" {
             description "1544.53 nm/194.100000 THz 3.125/6.25/12.5/50/75/100GHz spacing";
           }
           enum "1544.50" {
             description "1544.50 nm/194.103125 THz 3.125GHz spacing";
           }
           enum "1544.48" {
             description "1544.48 nm/194.106250 THz 3.125/6.25GHz spacing";
           }
           enum "1544.45" {
             description "1544.45 nm/194.109375 THz 3.125GHz spacing";
           }
           enum "1544.43" {
             description "1544.43 nm/194.112500 THz 3.125/6.25/12.5GHz spacing";
           }
           enum "1544.40" {
             description "1544.40 nm/194.115625 THz 3.125GHz spacing";
           }
           enum "1544.38" {
             description "1544.38 nm/194.118750 THz 3.125/6.25GHz spacing";
           }
           enum "1544.35" {
             description "1544.35 nm/194.121875 THz 3.125GHz spacing";
           }
           enum "1544.33" {
             description "1544.33 nm/194.125000 THz 3.125/6.25/12.5GHz spacing";
           }
           enum "1544.30" {
             description "1544.30 nm/194.128125 THz 3.125GHz spacing";
           }
           enum "1544.28" {
             description "1544.28 nm/194.131250 THz 3.125/6.25GHz spacing";
           }
           enum "1544.25" {
             description "1544.25 nm/194.134375 THz 3.125GHz spacing";
           }
           enum "1544.23" {
             description "1544.23 nm/194.137500 THz 3.125/6.25/12.5GHz spacing";
           }
           enum "1544.20" {
             description "1544.20 nm/194.140625 THz 3.125GHz spacing";
           }
           enum "1544.18" {
             description "1544.18 nm/194.143750 THz 3.125/6.25GHz spacing";
           }
           enum "1544.15" {
             description "1544.15 nm/194.146875 THz 3.125GHz spacing";
           }
           enum "1544.13" {
             description "1544.13 nm/194.150000 THz 3.125/6.25/12.5/50GHz spacing";
           }
           enum "1544.10" {
             description "1544.10 nm/194.153125 THz 3.125GHz spacing";
           }
           enum "1544.08" {
             description "1544.08 nm/194.156250 THz 3.125/6.25GHz spacing";
           }
           enum "1544.05" {
             description "1544.05 nm/194.159375 THz 3.125GHz spacing";
           }
           enum "1544.03" {
             description "1544.03 nm/194.162500 THz 3.125/6.25/12.5GHz spacing";
           }
           enum "1544.00" {
             description "1544.00 nm/194.165625 THz 3.125GHz spacing";
           }
           enum "1543.98" {
             description "1543.98 nm/194.168750 THz 3.125/6.25GHz spacing";
           }
           enum "1543.95" {
             description "1543.95 nm/194.171875 THz 3.125GHz spacing";
           }
           enum "1543.93" {
             description "1543.93 nm/194.175000 THz 3.125/6.25/12.5/75GHz spacing";
           }
           enum "1543.90" {
             description "1543.90 nm/194.178125 THz 3.125GHz spacing";
           }
           enum "1543.88" {
             description "1543.88 nm/194.181250 THz 3.125/6.25GHz spacing";
           }
           enum "1543.85" {
             description "1543.85 nm/194.184375 THz 3.125GHz spacing";
           }
           enum "1543.83" {
             description "1543.83 nm/194.187500 THz 3.125/6.25/12.5GHz spacing";
           }
           enum "1543.81" {
             description "1543.81 nm/194.190625 THz 3.125GHz spacing";
           }
           enum "1543.78" {
             description "1543.78 nm/194.193750 THz 3.125/6.25GHz spacing";
           }
           enum "1543.76" {
             description "1543.76 nm/194.196875 THz 3.125GHz spacing";
           }
           enum "1543.73" {
             description "1543.73 nm/194.200000 THz 3.125/6.25/12.5/100GHz spacing";
           }
           enum "1543.71" {
             description "1543.71 nm/194.203125 THz 3.125GHz spacing";
           }
           enum "1543.68" {
             description "1543.68 nm/194.206250 THz 3.125/6.25GHz spacing";
           }
           enum "1543.66" {
             description "1543.66 nm/194.209375 THz 3.125GHz spacing";
           }
           enum "1543.63" {
             description "1543.63 nm/194.212500 THz 3.125/6.25/12.5GHz spacing";
           }
           enum "1543.61" {
             description "1543.61 nm/194.215625 THz 3.125GHz spacing";
           }
           enum "1543.58" {
             description "1543.58 nm/194.218750 THz 3.125/6.25GHz spacing";
           }
           enum "1543.56" {
             description "1543.56 nm/194.221875 THz 3.125GHz spacing";
           }
           enum "1543.53" {
             description "1543.53 nm/194.225000 THz 3.125/6.25/12.5GHz spacing";
           }
           enum "1543.51" {
             description "1543.51 nm/194.228125 THz 3.125GHz spacing";
           }
           enum "1543.48" {
             description "1543.48 nm/194.231250 THz 3.125/6.25GHz spacing";
           }
           enum "1543.46" {
             description "1543.46 nm/194.234375 THz 3.125GHz spacing";
           }
           enum "1543.43" {
             description "1543.43 nm/194.237500 THz 3.125/6.25/12.5GHz spacing";
           }
           enum "1543.41" {
             description "1543.41 nm/194.240625 THz 3.125GHz spacing";
           }
           enum "1543.38" {
             description "1543.38 nm/194.243750 THz 3.125/6.25GHz spacing";
           }
           enum "1543.36" {
             description "1543.36 nm/194.246875 THz 3.125GHz spacing";
           }
           enum "1543.33" {
             description "1543.33 nm/194.250000 THz 3.125/6.25/12.5/50/75GHz spacing";
           }
           enum "1543.31" {
             description "1543.31 nm/194.253125 THz 3.125GHz spacing";
           }
           enum "1543.28" {
             description "1543.28 nm/194.256250 THz 3.125/6.25GHz spacing";
           }
           enum "1543.26" {
             description "1543.26 nm/194.259375 THz 3.125GHz spacing";
           }
           enum "1543.23" {
             description "1543.23 nm/194.262500 THz 3.125/6.25/12.5GHz spacing";
           }
           enum "1543.21" {
             description "1543.21 nm/194.265625 THz 3.125GHz spacing";
           }
           enum "1543.18" {
             description "1543.18 nm/194.268750 THz 3.125/6.25GHz spacing";
           }
           enum "1543.16" {
             description "1543.16 nm/194.271875 THz 3.125GHz spacing";
           }
           enum "1543.13" {
             description "1543.13 nm/194.275000 THz 3.125/6.25/12.5GHz spacing";
           }
           enum "1543.11" {
             description "1543.11 nm/194.278125 THz 3.125GHz spacing";
           }
           enum "1543.08" {
             description "1543.08 nm/194.281250 THz 3.125/6.25GHz spacing";
           }
           enum "1543.06" {
             description "1543.06 nm/194.284375 THz 3.125GHz spacing";
           }
           enum "1543.04" {
             description "1543.04 nm/194.287500 THz 3.125/6.25/12.5GHz spacing";
           }
           enum "1543.01" {
             description "1543.01 nm/194.290625 THz 3.125GHz spacing";
           }
           enum "1542.99" {
             description "1542.99 nm/194.293750 THz 3.125/6.25GHz spacing";
           }
           enum "1542.96" {
             description "1542.96 nm/194.296875 THz 3.125GHz spacing";
           }
           enum "1542.94" {
             description "1542.94 nm/194.300000 THz 3.125/6.25/12.5/100GHz spacing";
           }
           enum "1542.91" {
             description "1542.91 nm/194.303125 THz 3.125GHz spacing";
           }
           enum "1542.89" {
             description "1542.89 nm/194.306250 THz 3.125/6.25GHz spacing";
           }
           enum "1542.86" {
             description "1542.86 nm/194.309375 THz 3.125GHz spacing";
           }
           enum "1542.84" {
             description "1542.84 nm/194.312500 THz 3.125/6.25/12.5GHz spacing";
           }
           enum "1542.81" {
             description "1542.81 nm/194.315625 THz 3.125GHz spacing";
           }
           enum "1542.79" {
             description "1542.79 nm/194.318750 THz 3.125/6.25GHz spacing";
           }
           enum "1542.76" {
             description "1542.76 nm/194.321875 THz 3.125GHz spacing";
           }
           enum "1542.74" {
             description "1542.74 nm/194.325000 THz 3.125/6.25/12.5/75GHz spacing";
           }
           enum "1542.71" {
             description "1542.71 nm/194.328125 THz 3.125GHz spacing";
           }
           enum "1542.69" {
             description "1542.69 nm/194.331250 THz 3.125/6.25GHz spacing";
           }
           enum "1542.66" {
             description "1542.66 nm/194.334375 THz 3.125GHz spacing";
           }
           enum "1542.64" {
             description "1542.64 nm/194.337500 THz 3.125/6.25/12.5GHz spacing";
           }
           enum "1542.61" {
             description "1542.61 nm/194.340625 THz 3.125GHz spacing";
           }
           enum "1542.59" {
             description "1542.59 nm/194.343750 THz 3.125/6.25GHz spacing";
           }
           enum "1542.56" {
             description "1542.56 nm/194.346875 THz 3.125GHz spacing";
           }
           enum "1542.54" {
             description "1542.54 nm/194.350000 THz 3.125/6.25/12.5/50GHz spacing";
           }
           enum "1542.51" {
             description "1542.51 nm/194.353125 THz 3.125GHz spacing";
           }
           enum "1542.49" {
             description "1542.49 nm/194.356250 THz 3.125/6.25GHz spacing";
           }
           enum "1542.46" {
             description "1542.46 nm/194.359375 THz 3.125GHz spacing";
           }
           enum "1542.44" {
             description "1542.44 nm/194.362500 THz 3.125/6.25/12.5GHz spacing";
           }
           enum "1542.42" {
             description "1542.42 nm/194.365625 THz 3.125GHz spacing";
           }
           enum "1542.39" {
             description "1542.39 nm/194.368750 THz 3.125/6.25GHz spacing";
           }
           enum "1542.37" {
             description "1542.37 nm/194.371875 THz 3.125GHz spacing";
           }
           enum "1542.34" {
             description "1542.34 nm/194.375000 THz 3.125/6.25/12.5GHz spacing";
           }
           enum "1542.32" {
             description "1542.32 nm/194.378125 THz 3.125GHz spacing";
           }
           enum "1542.29" {
             description "1542.29 nm/194.381250 THz 3.125/6.25GHz spacing";
           }
           enum "1542.27" {
             description "1542.27 nm/194.384375 THz 3.125GHz spacing";
           }
           enum "1542.24" {
             description "1542.24 nm/194.387500 THz 3.125/6.25/12.5GHz spacing";
           }
           enum "1542.22" {
             description "1542.22 nm/194.390625 THz 3.125GHz spacing";
           }
           enum "1542.19" {
             description "1542.19 nm/194.393750 THz 3.125/6.25GHz spacing";
           }
           enum "1542.17" {
             description "1542.17 nm/194.396875 THz 3.125GHz spacing";
           }
           enum "1542.14" {
             description "1542.14 nm/194.400000 THz 3.125/6.25/12.5/50/75/100GHz spacing";
           }
           enum "1542.12" {
             description "1542.12 nm/194.403125 THz 3.125GHz spacing";
           }
           enum "1542.09" {
             description "1542.09 nm/194.406250 THz 3.125/6.25GHz spacing";
           }
           enum "1542.07" {
             description "1542.07 nm/194.409375 THz 3.125GHz spacing";
           }
           enum "1542.04" {
             description "1542.04 nm/194.412500 THz 3.125/6.25/12.5GHz spacing";
           }
           enum "1542.02" {
             description "1542.02 nm/194.415625 THz 3.125GHz spacing";
           }
           enum "1541.99" {
             description "1541.99 nm/194.418750 THz 3.125/6.25GHz spacing";
           }
           enum "1541.97" {
             description "1541.97 nm/194.421875 THz 3.125GHz spacing";
           }
           enum "1541.94" {
             description "1541.94 nm/194.425000 THz 3.125/6.25/12.5GHz spacing";
           }
           enum "1541.92" {
             description "1541.92 nm/194.428125 THz 3.125GHz spacing";
           }
           enum "1541.89" {
             description "1541.89 nm/194.431250 THz 3.125/6.25GHz spacing";
           }
           enum "1541.87" {
             description "1541.87 nm/194.434375 THz 3.125GHz spacing";
           }
           enum "1541.84" {
             description "1541.84 nm/194.437500 THz 3.125/6.25/12.5GHz spacing";
           }
           enum "1541.82" {
             description "1541.82 nm/194.440625 THz 3.125GHz spacing";
           }
           enum "1541.80" {
             description "1541.80 nm/194.443750 THz 3.125/6.25GHz spacing";
           }
           enum "1541.77" {
             description "1541.77 nm/194.446875 THz 3.125GHz spacing";
           }
           enum "1541.75" {
             description "1541.75 nm/194.450000 THz 3.125/6.25/12.5/50GHz spacing";
           }
           enum "1541.72" {
             description "1541.72 nm/194.453125 THz 3.125GHz spacing";
           }
           enum "1541.70" {
             description "1541.70 nm/194.456250 THz 3.125/6.25GHz spacing";
           }
           enum "1541.67" {
             description "1541.67 nm/194.459375 THz 3.125GHz spacing";
           }
           enum "1541.65" {
             description "1541.65 nm/194.462500 THz 3.125/6.25/12.5GHz spacing";
           }
           enum "1541.62" {
             description "1541.62 nm/194.465625 THz 3.125GHz spacing";
           }
           enum "1541.60" {
             description "1541.60 nm/194.468750 THz 3.125/6.25GHz spacing";
           }
           enum "1541.57" {
             description "1541.57 nm/194.471875 THz 3.125GHz spacing";
           }
           enum "1541.55" {
             description "1541.55 nm/194.475000 THz 3.125/6.25/12.5/75GHz spacing";
           }
           enum "1541.52" {
             description "1541.52 nm/194.478125 THz 3.125GHz spacing";
           }
           enum "1541.50" {
             description "1541.50 nm/194.481250 THz 3.125/6.25GHz spacing";
           }
           enum "1541.47" {
             description "1541.47 nm/194.484375 THz 3.125GHz spacing";
           }
           enum "1541.45" {
             description "1541.45 nm/194.487500 THz 3.125/6.25/12.5GHz spacing";
           }
           enum "1541.42" {
             description "1541.42 nm/194.490625 THz 3.125GHz spacing";
           }
           enum "1541.40" {
             description "1541.40 nm/194.493750 THz 3.125/6.25GHz spacing";
           }
           enum "1541.37" {
             description "1541.37 nm/194.496875 THz 3.125GHz spacing";
           }
           enum "1541.35" {
             description "1541.35 nm/194.500000 THz 3.125/6.25/12.5/100GHz spacing";
           }
           enum "1541.32" {
             description "1541.32 nm/194.503125 THz 3.125GHz spacing";
           }
           enum "1541.30" {
             description "1541.30 nm/194.506250 THz 3.125/6.25GHz spacing";
           }
           enum "1541.28" {
             description "1541.28 nm/194.509375 THz 3.125GHz spacing";
           }
           enum "1541.25" {
             description "1541.25 nm/194.512500 THz 3.125/6.25/12.5GHz spacing";
           }
           enum "1541.23" {
             description "1541.23 nm/194.515625 THz 3.125GHz spacing";
           }
           enum "1541.20" {
             description "1541.20 nm/194.518750 THz 3.125/6.25GHz spacing";
           }
           enum "1541.18" {
             description "1541.18 nm/194.521875 THz 3.125GHz spacing";
           }
           enum "1541.15" {
             description "1541.15 nm/194.525000 THz 3.125/6.25/12.5GHz spacing";
           }
           enum "1541.13" {
             description "1541.13 nm/194.528125 THz 3.125GHz spacing";
           }
           enum "1541.10" {
             description "1541.10 nm/194.531250 THz 3.125/6.25GHz spacing";
           }
           enum "1541.08" {
             description "1541.08 nm/194.534375 THz 3.125GHz spacing";
           }
           enum "1541.05" {
             description "1541.05 nm/194.537500 THz 3.125/6.25/12.5GHz spacing";
           }
           enum "1541.03" {
             description "1541.03 nm/194.540625 THz 3.125GHz spacing";
           }
           enum "1541.00" {
             description "1541.00 nm/194.543750 THz 3.125/6.25GHz spacing";
           }
           enum "1540.98" {
             description "1540.98 nm/194.546875 THz 3.125GHz spacing";
           }
           enum "1540.95" {
             description "1540.95 nm/194.550000 THz 3.125/6.25/12.5/50/75GHz spacing";
           }
           enum "1540.93" {
             description "1540.93 nm/194.553125 THz 3.125GHz spacing";
           }
           enum "1540.90" {
             description "1540.90 nm/194.556250 THz 3.125/6.25GHz spacing";
           }
           enum "1540.88" {
             description "1540.88 nm/194.559375 THz 3.125GHz spacing";
           }
           enum "1540.85" {
             description "1540.85 nm/194.562500 THz 3.125/6.25/12.5GHz spacing";
           }
           enum "1540.83" {
             description "1540.83 nm/194.565625 THz 3.125GHz spacing";
           }
           enum "1540.80" {
             description "1540.80 nm/194.568750 THz 3.125/6.25GHz spacing";
           }
           enum "1540.78" {
             description "1540.78 nm/194.571875 THz 3.125GHz spacing";
           }
           enum "1540.76" {
             description "1540.76 nm/194.575000 THz 3.125/6.25/12.5GHz spacing";
           }
           enum "1540.73" {
             description "1540.73 nm/194.578125 THz 3.125GHz spacing";
           }
           enum "1540.71" {
             description "1540.71 nm/194.581250 THz 3.125/6.25GHz spacing";
           }
           enum "1540.68" {
             description "1540.68 nm/194.584375 THz 3.125GHz spacing";
           }
           enum "1540.66" {
             description "1540.66 nm/194.587500 THz 3.125/6.25/12.5GHz spacing";
           }
           enum "1540.63" {
             description "1540.63 nm/194.590625 THz 3.125GHz spacing";
           }
           enum "1540.61" {
             description "1540.61 nm/194.593750 THz 3.125/6.25GHz spacing";
           }
           enum "1540.58" {
             description "1540.58 nm/194.596875 THz 3.125GHz spacing";
           }
           enum "1540.56" {
             description "1540.56 nm/194.600000 THz 3.125/6.25/12.5/100GHz spacing";
           }
           enum "1540.53" {
             description "1540.53 nm/194.603125 THz 3.125GHz spacing";
           }
           enum "1540.51" {
             description "1540.51 nm/194.606250 THz 3.125/6.25GHz spacing";
           }
           enum "1540.48" {
             description "1540.48 nm/194.609375 THz 3.125GHz spacing";
           }
           enum "1540.46" {
             description "1540.46 nm/194.612500 THz 3.125/6.25/12.5GHz spacing";
           }
           enum "1540.43" {
             description "1540.43 nm/194.615625 THz 3.125GHz spacing";
           }
           enum "1540.41" {
             description "1540.41 nm/194.618750 THz 3.125/6.25GHz spacing";
           }
           enum "1540.38" {
             description "1540.38 nm/194.621875 THz 3.125GHz spacing";
           }
           enum "1540.36" {
             description "1540.36 nm/194.625000 THz 3.125/6.25/12.5/75GHz spacing";
           }
           enum "1540.33" {
             description "1540.33 nm/194.628125 THz 3.125GHz spacing";
           }
           enum "1540.31" {
             description "1540.31 nm/194.631250 THz 3.125/6.25GHz spacing";
           }
           enum "1540.29" {
             description "1540.29 nm/194.634375 THz 3.125GHz spacing";
           }
           enum "1540.26" {
             description "1540.26 nm/194.637500 THz 3.125/6.25/12.5GHz spacing";
           }
           enum "1540.24" {
             description "1540.24 nm/194.640625 THz 3.125GHz spacing";
           }
           enum "1540.21" {
             description "1540.21 nm/194.643750 THz 3.125/6.25GHz spacing";
           }
           enum "1540.19" {
             description "1540.19 nm/194.646875 THz 3.125GHz spacing";
           }
           enum "1540.16" {
             description "1540.16 nm/194.650000 THz 3.125/6.25/12.5/50GHz spacing";
           }
           enum "1540.14" {
             description "1540.14 nm/194.653125 THz 3.125GHz spacing";
           }
           enum "1540.11" {
             description "1540.11 nm/194.656250 THz 3.125/6.25GHz spacing";
           }
           enum "1540.09" {
             description "1540.09 nm/194.659375 THz 3.125GHz spacing";
           }
           enum "1540.06" {
             description "1540.06 nm/194.662500 THz 3.125/6.25/12.5GHz spacing";
           }
           enum "1540.04" {
             description "1540.04 nm/194.665625 THz 3.125GHz spacing";
           }
           enum "1540.01" {
             description "1540.01 nm/194.668750 THz 3.125/6.25GHz spacing";
           }
           enum "1539.99" {
             description "1539.99 nm/194.671875 THz 3.125GHz spacing";
           }
           enum "1539.96" {
             description "1539.96 nm/194.675000 THz 3.125/6.25/12.5/75GHz spacing";
           }
           enum "1539.94" {
             description "1539.94 nm/194.678125 THz 3.125GHz spacing";
           }
           enum "1539.91" {
             description "1539.91 nm/194.681250 THz 3.125/6.25GHz spacing";
           }
           enum "1539.89" {
             description "1539.89 nm/194.684375 THz 3.125GHz spacing";
           }
           enum "1539.86" {
             description "1539.86 nm/194.687500 THz 3.125/6.25/12.5GHz spacing";
           }
           enum "1539.84" {
             description "1539.84 nm/194.690625 THz 3.125GHz spacing";
           }
           enum "1539.82" {
             description "1539.82 nm/194.693750 THz 3.125/6.25GHz spacing";
           }
           enum "1539.79" {
             description "1539.79 nm/194.696875 THz 3.125GHz spacing";
           }
           enum "1539.77" {
             description "1539.77 nm/194.700000 THz 3.125/6.25/12.5/50/75/100GHz spacing";
           }
           enum "1539.74" {
             description "1539.74 nm/194.703125 THz 3.125GHz spacing";
           }
           enum "1539.72" {
             description "1539.72 nm/194.706250 THz 3.125/6.25GHz spacing";
           }
           enum "1539.69" {
             description "1539.69 nm/194.709375 THz 3.125GHz spacing";
           }
           enum "1539.67" {
             description "1539.67 nm/194.712500 THz 3.125/6.25/12.5GHz spacing";
           }
           enum "1539.64" {
             description "1539.64 nm/194.715625 THz 3.125GHz spacing";
           }
           enum "1539.62" {
             description "1539.62 nm/194.718750 THz 3.125/6.25GHz spacing";
           }
           enum "1539.59" {
             description "1539.59 nm/194.721875 THz 3.125GHz spacing";
           }
           enum "1539.57" {
             description "1539.57 nm/194.725000 THz 3.125/6.25/12.5GHz spacing";
           }
           enum "1539.54" {
             description "1539.54 nm/194.728125 THz 3.125GHz spacing";
           }
           enum "1539.52" {
             description "1539.52 nm/194.731250 THz 3.125/6.25GHz spacing";
           }
           enum "1539.49" {
             description "1539.49 nm/194.734375 THz 3.125GHz spacing";
           }
           enum "1539.47" {
             description "1539.47 nm/194.737500 THz 3.125/6.25/12.5GHz spacing";
           }
           enum "1539.44" {
             description "1539.44 nm/194.740625 THz 3.125GHz spacing";
           }
           enum "1539.42" {
             description "1539.42 nm/194.743750 THz 3.125/6.25GHz spacing";
           }
           enum "1539.40" {
             description "1539.40 nm/194.746875 THz 3.125GHz spacing";
           }
           enum "1539.37" {
             description "1539.37 nm/194.750000 THz 3.125/6.25/12.5/50GHz spacing";
           }
           enum "1539.35" {
             description "1539.35 nm/194.753125 THz 3.125GHz spacing";
           }
           enum "1539.32" {
             description "1539.32 nm/194.756250 THz 3.125/6.25GHz spacing";
           }
           enum "1539.30" {
             description "1539.30 nm/194.759375 THz 3.125GHz spacing";
           }
           enum "1539.27" {
             description "1539.27 nm/194.762500 THz 3.125/6.25/12.5GHz spacing";
           }
           enum "1539.25" {
             description "1539.25 nm/194.765625 THz 3.125GHz spacing";
           }
           enum "1539.22" {
             description "1539.22 nm/194.768750 THz 3.125/6.25GHz spacing";
           }
           enum "1539.20" {
             description "1539.20 nm/194.771875 THz 3.125GHz spacing";
           }
           enum "1539.17" {
             description "1539.17 nm/194.775000 THz 3.125/6.25/12.5/75GHz spacing";
           }
           enum "1539.15" {
             description "1539.15 nm/194.778125 THz 3.125GHz spacing";
           }
           enum "1539.12" {
             description "1539.12 nm/194.781250 THz 3.125/6.25GHz spacing";
           }
           enum "1539.10" {
             description "1539.10 nm/194.784375 THz 3.125GHz spacing";
           }
           enum "1539.07" {
             description "1539.07 nm/194.787500 THz 3.125/6.25/12.5GHz spacing";
           }
           enum "1539.05" {
             description "1539.05 nm/194.790625 THz 3.125GHz spacing";
           }
           enum "1539.03" {
             description "1539.03 nm/194.793750 THz 3.125/6.25GHz spacing";
           }
           enum "1539.00" {
             description "1539.00 nm/194.796875 THz 3.125GHz spacing";
           }
           enum "1538.98" {
             description "1538.98 nm/194.800000 THz 3.125/6.25/12.5/100GHz spacing";
           }
           enum "1538.95" {
             description "1538.95 nm/194.803125 THz 3.125GHz spacing";
           }
           enum "1538.93" {
             description "1538.93 nm/194.806250 THz 3.125/6.25GHz spacing";
           }
           enum "1538.90" {
             description "1538.90 nm/194.809375 THz 3.125GHz spacing";
           }
           enum "1538.88" {
             description "1538.88 nm/194.812500 THz 3.125/6.25/12.5GHz spacing";
           }
           enum "1538.85" {
             description "1538.85 nm/194.815625 THz 3.125GHz spacing";
           }
           enum "1538.83" {
             description "1538.83 nm/194.818750 THz 3.125/6.25GHz spacing";
           }
           enum "1538.80" {
             description "1538.80 nm/194.821875 THz 3.125GHz spacing";
           }
           enum "1538.78" {
             description "1538.78 nm/194.825000 THz 3.125/6.25/12.5GHz spacing";
           }
           enum "1538.75" {
             description "1538.75 nm/194.828125 THz 3.125GHz spacing";
           }
           enum "1538.73" {
             description "1538.73 nm/194.831250 THz 3.125/6.25GHz spacing";
           }
           enum "1538.70" {
             description "1538.70 nm/194.834375 THz 3.125GHz spacing";
           }
           enum "1538.68" {
             description "1538.68 nm/194.837500 THz 3.125/6.25/12.5GHz spacing";
           }
           enum "1538.65" {
             description "1538.65 nm/194.840625 THz 3.125GHz spacing";
           }
           enum "1538.63" {
             description "1538.63 nm/194.843750 THz 3.125/6.25GHz spacing";
           }
           enum "1538.61" {
             description "1538.61 nm/194.846875 THz 3.125GHz spacing";
           }
           enum "1538.58" {
             description "1538.58 nm/194.850000 THz 3.125/6.25/12.5/50/75GHz spacing";
           }
           enum "1538.56" {
             description "1538.56 nm/194.853125 THz 3.125GHz spacing";
           }
           enum "1538.53" {
             description "1538.53 nm/194.856250 THz 3.125/6.25GHz spacing";
           }
           enum "1538.51" {
             description "1538.51 nm/194.859375 THz 3.125GHz spacing";
           }
           enum "1538.48" {
             description "1538.48 nm/194.862500 THz 3.125/6.25/12.5GHz spacing";
           }
           enum "1538.46" {
             description "1538.46 nm/194.865625 THz 3.125GHz spacing";
           }
           enum "1538.43" {
             description "1538.43 nm/194.868750 THz 3.125/6.25GHz spacing";
           }
           enum "1538.41" {
             description "1538.41 nm/194.871875 THz 3.125GHz spacing";
           }
           enum "1538.38" {
             description "1538.38 nm/194.875000 THz 3.125/6.25/12.5GHz spacing";
           }
           enum "1538.36" {
             description "1538.36 nm/194.878125 THz 3.125GHz spacing";
           }
           enum "1538.33" {
             description "1538.33 nm/194.881250 THz 3.125/6.25GHz spacing";
           }
           enum "1538.31" {
             description "1538.31 nm/194.884375 THz 3.125GHz spacing";
           }
           enum "1538.28" {
             description "1538.28 nm/194.887500 THz 3.125/6.25/12.5GHz spacing";
           }
           enum "1538.26" {
             description "1538.26 nm/194.890625 THz 3.125GHz spacing";
           }
           enum "1538.24" {
             description "1538.24 nm/194.893750 THz 3.125/6.25GHz spacing";
           }
           enum "1538.21" {
             description "1538.21 nm/194.896875 THz 3.125GHz spacing";
           }
           enum "1538.19" {
             description "1538.19 nm/194.900000 THz 3.125/6.25/12.5/100GHz spacing";
           }
           enum "1538.16" {
             description "1538.16 nm/194.903125 THz 3.125GHz spacing";
           }
           enum "1538.14" {
             description "1538.14 nm/194.906250 THz 3.125/6.25GHz spacing";
           }
           enum "1538.11" {
             description "1538.11 nm/194.909375 THz 3.125GHz spacing";
           }
           enum "1538.09" {
             description "1538.09 nm/194.912500 THz 3.125/6.25/12.5GHz spacing";
           }
           enum "1538.06" {
             description "1538.06 nm/194.915625 THz 3.125GHz spacing";
           }
           enum "1538.04" {
             description "1538.04 nm/194.918750 THz 3.125/6.25GHz spacing";
           }
           enum "1538.01" {
             description "1538.01 nm/194.921875 THz 3.125GHz spacing";
           }
           enum "1537.99" {
             description "1537.99 nm/194.925000 THz 3.125/6.25/12.5/75GHz spacing";
           }
           enum "1537.96" {
             description "1537.96 nm/194.928125 THz 3.125GHz spacing";
           }
           enum "1537.94" {
             description "1537.94 nm/194.931250 THz 3.125/6.25GHz spacing";
           }
           enum "1537.91" {
             description "1537.91 nm/194.934375 THz 3.125GHz spacing";
           }
           enum "1537.89" {
             description "1537.89 nm/194.937500 THz 3.125/6.25/12.5GHz spacing";
           }
           enum "1537.87" {
             description "1537.87 nm/194.940625 THz 3.125GHz spacing";
           }
           enum "1537.84" {
             description "1537.84 nm/194.943750 THz 3.125/6.25GHz spacing";
           }
           enum "1537.82" {
             description "1537.82 nm/194.946875 THz 3.125GHz spacing";
           }
           enum "1537.79" {
             description "1537.79 nm/194.950000 THz 3.125/6.25/12.5/50GHz spacing";
           }
           enum "1537.77" {
             description "1537.77 nm/194.953125 THz 3.125GHz spacing";
           }
           enum "1537.74" {
             description "1537.74 nm/194.956250 THz 3.125/6.25GHz spacing";
           }
           enum "1537.72" {
             description "1537.72 nm/194.959375 THz 3.125GHz spacing";
           }
           enum "1537.69" {
             description "1537.69 nm/194.962500 THz 3.125/6.25/12.5GHz spacing";
           }
           enum "1537.67" {
             description "1537.67 nm/194.965625 THz 3.125GHz spacing";
           }
           enum "1537.64" {
             description "1537.64 nm/194.968750 THz 3.125/6.25GHz spacing";
           }
           enum "1537.62" {
             description "1537.62 nm/194.971875 THz 3.125GHz spacing";
           }
           enum "1537.59" {
             description "1537.59 nm/194.975000 THz 3.125/6.25/12.5GHz spacing";
           }
           enum "1537.57" {
             description "1537.57 nm/194.978125 THz 3.125GHz spacing";
           }
           enum "1537.55" {
             description "1537.55 nm/194.981250 THz 3.125/6.25GHz spacing";
           }
           enum "1537.52" {
             description "1537.52 nm/194.984375 THz 3.125GHz spacing";
           }
           enum "1537.50" {
             description "1537.50 nm/194.987500 THz 3.125/6.25/12.5GHz spacing";
           }
           enum "1537.47" {
             description "1537.47 nm/194.990625 THz 3.125GHz spacing";
           }
           enum "1537.45" {
             description "1537.45 nm/194.993750 THz 3.125/6.25GHz spacing";
           }
           enum "1537.42" {
             description "1537.42 nm/194.996875 THz 3.125GHz spacing";
           }
           enum "1537.40" {
             description "1537.40 nm/195.000000 THz 3.125/6.25/12.5/50/75/100GHz spacing";
           }
           enum "1537.37" {
             description "1537.37 nm/195.003125 THz 3.125GHz spacing";
           }
           enum "1537.35" {
             description "1537.35 nm/195.006250 THz 3.125/6.25GHz spacing";
           }
           enum "1537.32" {
             description "1537.32 nm/195.009375 THz 3.125GHz spacing";
           }
           enum "1537.30" {
             description "1537.30 nm/195.012500 THz 3.125/6.25/12.5GHz spacing";
           }
           enum "1537.27" {
             description "1537.27 nm/195.015625 THz 3.125GHz spacing";
           }
           enum "1537.25" {
             description "1537.25 nm/195.018750 THz 3.125/6.25GHz spacing";
           }
           enum "1537.22" {
             description "1537.22 nm/195.021875 THz 3.125GHz spacing";
           }
           enum "1537.20" {
             description "1537.20 nm/195.025000 THz 3.125/6.25/12.5GHz spacing";
           }
           enum "1537.18" {
             description "1537.18 nm/195.028125 THz 3.125GHz spacing";
           }
           enum "1537.15" {
             description "1537.15 nm/195.031250 THz 3.125/6.25GHz spacing";
           }
           enum "1537.13" {
             description "1537.13 nm/195.034375 THz 3.125GHz spacing";
           }
           enum "1537.10" {
             description "1537.10 nm/195.037500 THz 3.125/6.25/12.5GHz spacing";
           }
           enum "1537.08" {
             description "1537.08 nm/195.040625 THz 3.125GHz spacing";
           }
           enum "1537.05" {
             description "1537.05 nm/195.043750 THz 3.125/6.25GHz spacing";
           }
           enum "1537.03" {
             description "1537.03 nm/195.046875 THz 3.125GHz spacing";
           }
           enum "1537.00" {
             description "1537.00 nm/195.050000 THz 3.125/6.25/12.5/50GHz spacing";
           }
           enum "1536.98" {
             description "1536.98 nm/195.053125 THz 3.125GHz spacing";
           }
           enum "1536.95" {
             description "1536.95 nm/195.056250 THz 3.125/6.25GHz spacing";
           }
           enum "1536.93" {
             description "1536.93 nm/195.059375 THz 3.125GHz spacing";
           }
           enum "1536.90" {
             description "1536.90 nm/195.062500 THz 3.125/6.25/12.5GHz spacing";
           }
           enum "1536.88" {
             description "1536.88 nm/195.065625 THz 3.125GHz spacing";
           }
           enum "1536.86" {
             description "1536.86 nm/195.068750 THz 3.125/6.25GHz spacing";
           }
           enum "1536.83" {
             description "1536.83 nm/195.071875 THz 3.125GHz spacing";
           }
           enum "1536.81" {
             description "1536.81 nm/195.075000 THz 3.125/6.25/12.5/75GHz spacing";
           }
           enum "1536.78" {
             description "1536.78 nm/195.078125 THz 3.125GHz spacing";
           }
           enum "1536.76" {
             description "1536.76 nm/195.081250 THz 3.125/6.25GHz spacing";
           }
           enum "1536.73" {
             description "1536.73 nm/195.084375 THz 3.125GHz spacing";
           }
           enum "1536.71" {
             description "1536.71 nm/195.087500 THz 3.125/6.25/12.5GHz spacing";
           }
           enum "1536.68" {
             description "1536.68 nm/195.090625 THz 3.125GHz spacing";
           }
           enum "1536.66" {
             description "1536.66 nm/195.093750 THz 3.125/6.25GHz spacing";
           }
           enum "1536.63" {
             description "1536.63 nm/195.096875 THz 3.125GHz spacing";
           }
           enum "1536.61" {
             description "1536.61 nm/195.100000 THz 3.125/6.25/12.5/100GHz spacing";
           }
           enum "1536.58" {
             description "1536.58 nm/195.103125 THz 3.125GHz spacing";
           }
           enum "1536.56" {
             description "1536.56 nm/195.106250 THz 3.125/6.25GHz spacing";
           }
           enum "1536.54" {
             description "1536.54 nm/195.109375 THz 3.125GHz spacing";
           }
           enum "1536.51" {
             description "1536.51 nm/195.112500 THz 3.125/6.25/12.5GHz spacing";
           }
           enum "1536.49" {
             description "1536.49 nm/195.115625 THz 3.125GHz spacing";
           }
           enum "1536.46" {
             description "1536.46 nm/195.118750 THz 3.125/6.25GHz spacing";
           }
           enum "1536.44" {
             description "1536.44 nm/195.121875 THz 3.125GHz spacing";
           }
           enum "1536.41" {
             description "1536.41 nm/195.125000 THz 3.125/6.25/12.5GHz spacing";
           }
           enum "1536.39" {
             description "1536.39 nm/195.128125 THz 3.125GHz spacing";
           }
           enum "1536.36" {
             description "1536.36 nm/195.131250 THz 3.125/6.25GHz spacing";
           }
           enum "1536.34" {
             description "1536.34 nm/195.134375 THz 3.125GHz spacing";
           }
           enum "1536.31" {
             description "1536.31 nm/195.137500 THz 3.125/6.25/12.5GHz spacing";
           }
           enum "1536.29" {
             description "1536.29 nm/195.140625 THz 3.125GHz spacing";
           }
           enum "1536.26" {
             description "1536.26 nm/195.143750 THz 3.125/6.25GHz spacing";
           }
           enum "1536.24" {
             description "1536.24 nm/195.146875 THz 3.125GHz spacing";
           }
           enum "1536.22" {
             description "1536.22 nm/195.150000 THz 3.125/6.25/12.5/50/75GHz spacing";
           }
           enum "1536.19" {
             description "1536.19 nm/195.153125 THz 3.125GHz spacing";
           }
           enum "1536.17" {
             description "1536.17 nm/195.156250 THz 3.125/6.25GHz spacing";
           }
           enum "1536.14" {
             description "1536.14 nm/195.159375 THz 3.125GHz spacing";
           }
           enum "1536.12" {
             description "1536.12 nm/195.162500 THz 3.125/6.25/12.5GHz spacing";
           }
           enum "1536.09" {
             description "1536.09 nm/195.165625 THz 3.125GHz spacing";
           }
           enum "1536.07" {
             description "1536.07 nm/195.168750 THz 3.125/6.25GHz spacing";
           }
           enum "1536.04" {
             description "1536.04 nm/195.171875 THz 3.125GHz spacing";
           }
           enum "1536.02" {
             description "1536.02 nm/195.175000 THz 3.125/6.25/12.5GHz spacing";
           }
           enum "1535.99" {
             description "1535.99 nm/195.178125 THz 3.125GHz spacing";
           }
           enum "1535.97" {
             description "1535.97 nm/195.181250 THz 3.125/6.25GHz spacing";
           }
           enum "1535.94" {
             description "1535.94 nm/195.184375 THz 3.125GHz spacing";
           }
           enum "1535.92" {
             description "1535.92 nm/195.187500 THz 3.125/6.25/12.5GHz spacing";
           }
           enum "1535.90" {
             description "1535.90 nm/195.190625 THz 3.125GHz spacing";
           }
           enum "1535.87" {
             description "1535.87 nm/195.193750 THz 3.125/6.25GHz spacing";
           }
           enum "1535.85" {
             description "1535.85 nm/195.196875 THz 3.125GHz spacing";
           }
           enum "1535.82" {
             description "1535.82 nm/195.200000 THz 3.125/6.25/12.5/100GHz spacing";
           }
           enum "1535.80" {
             description "1535.80 nm/195.203125 THz 3.125GHz spacing";
           }
           enum "1535.77" {
             description "1535.77 nm/195.206250 THz 3.125/6.25GHz spacing";
           }
           enum "1535.75" {
             description "1535.75 nm/195.209375 THz 3.125GHz spacing";
           }
           enum "1535.72" {
             description "1535.72 nm/195.212500 THz 3.125/6.25/12.5GHz spacing";
           }
           enum "1535.70" {
             description "1535.70 nm/195.215625 THz 3.125GHz spacing";
           }
           enum "1535.67" {
             description "1535.67 nm/195.218750 THz 3.125/6.25GHz spacing";
           }
           enum "1535.65" {
             description "1535.65 nm/195.221875 THz 3.125GHz spacing";
           }
           enum "1535.63" {
             description "1535.63 nm/195.225000 THz 3.125/6.25/12.5/75GHz spacing";
           }
           enum "1535.60" {
             description "1535.60 nm/195.228125 THz 3.125GHz spacing";
           }
           enum "1535.58" {
             description "1535.58 nm/195.231250 THz 3.125/6.25GHz spacing";
           }
           enum "1535.55" {
             description "1535.55 nm/195.234375 THz 3.125GHz spacing";
           }
           enum "1535.53" {
             description "1535.53 nm/195.237500 THz 3.125/6.25/12.5GHz spacing";
           }
           enum "1535.50" {
             description "1535.50 nm/195.240625 THz 3.125GHz spacing";
           }
           enum "1535.48" {
             description "1535.48 nm/195.243750 THz 3.125/6.25GHz spacing";
           }
           enum "1535.45" {
             description "1535.45 nm/195.246875 THz 3.125GHz spacing";
           }
           enum "1535.43" {
             description "1535.43 nm/195.250000 THz 3.125/6.25/12.5/50GHz spacing";
           }
           enum "1535.40" {
             description "1535.40 nm/195.253125 THz 3.125GHz spacing";
           }
           enum "1535.38" {
             description "1535.38 nm/195.256250 THz 3.125/6.25GHz spacing";
           }
           enum "1535.36" {
             description "1535.36 nm/195.259375 THz 3.125GHz spacing";
           }
           enum "1535.33" {
             description "1535.33 nm/195.262500 THz 3.125/6.25/12.5GHz spacing";
           }
           enum "1535.31" {
             description "1535.31 nm/195.265625 THz 3.125GHz spacing";
           }
           enum "1535.28" {
             description "1535.28 nm/195.268750 THz 3.125/6.25GHz spacing";
           }
           enum "1535.26" {
             description "1535.26 nm/195.271875 THz 3.125GHz spacing";
           }
           enum "1535.23" {
             description "1535.23 nm/195.275000 THz 3.125/6.25/12.5GHz spacing";
           }
           enum "1535.21" {
             description "1535.21 nm/195.278125 THz 3.125GHz spacing";
           }
           enum "1535.18" {
             description "1535.18 nm/195.281250 THz 3.125/6.25GHz spacing";
           }
           enum "1535.16" {
             description "1535.16 nm/195.284375 THz 3.125GHz spacing";
           }
           enum "1535.13" {
             description "1535.13 nm/195.287500 THz 3.125/6.25/12.5GHz spacing";
           }
           enum "1535.11" {
             description "1535.11 nm/195.290625 THz 3.125GHz spacing";
           }
           enum "1535.08" {
             description "1535.08 nm/195.293750 THz 3.125/6.25GHz spacing";
           }
           enum "1535.06" {
             description "1535.06 nm/195.296875 THz 3.125GHz spacing";
           }
           enum "1535.04" {
             description "1535.04 nm/195.300000 THz 3.125/6.25/12.5/50/75/100GHz spacing";
           }
           enum "1535.01" {
             description "1535.01 nm/195.303125 THz 3.125GHz spacing";
           }
           enum "1534.99" {
             description "1534.99 nm/195.306250 THz 3.125/6.25GHz spacing";
           }
           enum "1534.96" {
             description "1534.96 nm/195.309375 THz 3.125GHz spacing";
           }
           enum "1534.94" {
             description "1534.94 nm/195.312500 THz 3.125/6.25/12.5GHz spacing";
           }
           enum "1534.91" {
             description "1534.91 nm/195.315625 THz 3.125GHz spacing";
           }
           enum "1534.89" {
             description "1534.89 nm/195.318750 THz 3.125/6.25GHz spacing";
           }
           enum "1534.86" {
             description "1534.86 nm/195.321875 THz 3.125GHz spacing";
           }
           enum "1534.84" {
             description "1534.84 nm/195.325000 THz 3.125/6.25/12.5GHz spacing";
           }
           enum "1534.81" {
             description "1534.81 nm/195.328125 THz 3.125GHz spacing";
           }
           enum "1534.79" {
             description "1534.79 nm/195.331250 THz 3.125/6.25GHz spacing";
           }
           enum "1534.77" {
             description "1534.77 nm/195.334375 THz 3.125GHz spacing";
           }
           enum "1534.74" {
             description "1534.74 nm/195.337500 THz 3.125/6.25/12.5GHz spacing";
           }
           enum "1534.72" {
             description "1534.72 nm/195.340625 THz 3.125GHz spacing";
           }
           enum "1534.69" {
             description "1534.69 nm/195.343750 THz 3.125/6.25GHz spacing";
           }
           enum "1534.67" {
             description "1534.67 nm/195.346875 THz 3.125GHz spacing";
           }
           enum "1534.64" {
             description "1534.64 nm/195.350000 THz 3.125/6.25/12.5/50GHz spacing";
           }
           enum "1534.62" {
             description "1534.62 nm/195.353125 THz 3.125GHz spacing";
           }
           enum "1534.59" {
             description "1534.59 nm/195.356250 THz 3.125/6.25GHz spacing";
           }
           enum "1534.57" {
             description "1534.57 nm/195.359375 THz 3.125GHz spacing";
           }
           enum "1534.54" {
             description "1534.54 nm/195.362500 THz 3.125/6.25/12.5GHz spacing";
           }
           enum "1534.52" {
             description "1534.52 nm/195.365625 THz 3.125GHz spacing";
           }
           enum "1534.50" {
             description "1534.50 nm/195.368750 THz 3.125/6.25GHz spacing";
           }
           enum "1534.47" {
             description "1534.47 nm/195.371875 THz 3.125GHz spacing";
           }
           enum "1534.45" {
             description "1534.45 nm/195.375000 THz 3.125/6.25/12.5/75GHz spacing";
           }
           enum "1534.42" {
             description "1534.42 nm/195.378125 THz 3.125GHz spacing";
           }
           enum "1534.40" {
             description "1534.40 nm/195.381250 THz 3.125/6.25GHz spacing";
           }
           enum "1534.37" {
             description "1534.37 nm/195.384375 THz 3.125GHz spacing";
           }
           enum "1534.35" {
             description "1534.35 nm/195.387500 THz 3.125/6.25/12.5GHz spacing";
           }
           enum "1534.32" {
             description "1534.32 nm/195.390625 THz 3.125GHz spacing";
           }
           enum "1534.30" {
             description "1534.30 nm/195.393750 THz 3.125/6.25GHz spacing";
           }
           enum "1534.27" {
             description "1534.27 nm/195.396875 THz 3.125GHz spacing";
           }
           enum "1534.25" {
             description "1534.25 nm/195.400000 THz 3.125/6.25/12.5/100GHz spacing";
           }
           enum "1534.23" {
             description "1534.23 nm/195.403125 THz 3.125GHz spacing";
           }
           enum "1534.20" {
             description "1534.20 nm/195.406250 THz 3.125/6.25GHz spacing";
           }
           enum "1534.18" {
             description "1534.18 nm/195.409375 THz 3.125GHz spacing";
           }
           enum "1534.15" {
             description "1534.15 nm/195.412500 THz 3.125/6.25/12.5GHz spacing";
           }
           enum "1534.13" {
             description "1534.13 nm/195.415625 THz 3.125GHz spacing";
           }
           enum "1534.10" {
             description "1534.10 nm/195.418750 THz 3.125/6.25GHz spacing";
           }
           enum "1534.08" {
             description "1534.08 nm/195.421875 THz 3.125GHz spacing";
           }
           enum "1534.05" {
             description "1534.05 nm/195.425000 THz 3.125/6.25/12.5GHz spacing";
           }
           enum "1534.03" {
             description "1534.03 nm/195.428125 THz 3.125GHz spacing";
           }
           enum "1534.00" {
             description "1534.00 nm/195.431250 THz 3.125/6.25GHz spacing";
           }
           enum "1533.98" {
             description "1533.98 nm/195.434375 THz 3.125GHz spacing";
           }
           enum "1533.96" {
             description "1533.96 nm/195.437500 THz 3.125/6.25/12.5GHz spacing";
           }
           enum "1533.93" {
             description "1533.93 nm/195.440625 THz 3.125GHz spacing";
           }
           enum "1533.91" {
             description "1533.91 nm/195.443750 THz 3.125/6.25GHz spacing";
           }
           enum "1533.88" {
             description "1533.88 nm/195.446875 THz 3.125GHz spacing";
           }
           enum "1533.86" {
             description "1533.86 nm/195.450000 THz 3.125/6.25/12.5/50/75GHz spacing";
           }
           enum "1533.83" {
             description "1533.83 nm/195.453125 THz 3.125GHz spacing";
           }
           enum "1533.81" {
             description "1533.81 nm/195.456250 THz 3.125/6.25GHz spacing";
           }
           enum "1533.78" {
             description "1533.78 nm/195.459375 THz 3.125GHz spacing";
           }
           enum "1533.76" {
             description "1533.76 nm/195.462500 THz 3.125/6.25/12.5GHz spacing";
           }
           enum "1533.73" {
             description "1533.73 nm/195.465625 THz 3.125GHz spacing";
           }
           enum "1533.71" {
             description "1533.71 nm/195.468750 THz 3.125/6.25GHz spacing";
           }
           enum "1533.69" {
             description "1533.69 nm/195.471875 THz 3.125GHz spacing";
           }
           enum "1533.66" {
             description "1533.66 nm/195.475000 THz 3.125/6.25/12.5GHz spacing";
           }
           enum "1533.64" {
             description "1533.64 nm/195.478125 THz 3.125GHz spacing";
           }
           enum "1533.61" {
             description "1533.61 nm/195.481250 THz 3.125/6.25GHz spacing";
           }
           enum "1533.59" {
             description "1533.59 nm/195.484375 THz 3.125GHz spacing";
           }
           enum "1533.56" {
             description "1533.56 nm/195.487500 THz 3.125/6.25/12.5GHz spacing";
           }
           enum "1533.54" {
             description "1533.54 nm/195.490625 THz 3.125GHz spacing";
           }
           enum "1533.51" {
             description "1533.51 nm/195.493750 THz 3.125/6.25GHz spacing";
           }
           enum "1533.49" {
             description "1533.49 nm/195.496875 THz 3.125GHz spacing";
           }
           enum "1533.47" {
             description "1533.47 nm/195.500000 THz 3.125/6.25/12.5/100GHz spacing";
           }
           enum "1533.44" {
             description "1533.44 nm/195.503125 THz 3.125GHz spacing";
           }
           enum "1533.42" {
             description "1533.42 nm/195.506250 THz 3.125/6.25GHz spacing";
           }
           enum "1533.39" {
             description "1533.39 nm/195.509375 THz 3.125GHz spacing";
           }
           enum "1533.37" {
             description "1533.37 nm/195.512500 THz 3.125/6.25/12.5GHz spacing";
           }
           enum "1533.34" {
             description "1533.34 nm/195.515625 THz 3.125GHz spacing";
           }
           enum "1533.32" {
             description "1533.32 nm/195.518750 THz 3.125/6.25GHz spacing";
           }
           enum "1533.29" {
             description "1533.29 nm/195.521875 THz 3.125GHz spacing";
           }
           enum "1533.27" {
             description "1533.27 nm/195.525000 THz 3.125/6.25/12.5/75GHz spacing";
           }
           enum "1533.24" {
             description "1533.24 nm/195.528125 THz 3.125GHz spacing";
           }
           enum "1533.22" {
             description "1533.22 nm/195.531250 THz 3.125/6.25GHz spacing";
           }
           enum "1533.20" {
             description "1533.20 nm/195.534375 THz 3.125GHz spacing";
           }
           enum "1533.17" {
             description "1533.17 nm/195.537500 THz 3.125/6.25/12.5GHz spacing";
           }
           enum "1533.15" {
             description "1533.15 nm/195.540625 THz 3.125GHz spacing";
           }
           enum "1533.12" {
             description "1533.12 nm/195.543750 THz 3.125/6.25GHz spacing";
           }
           enum "1533.10" {
             description "1533.10 nm/195.546875 THz 3.125GHz spacing";
           }
           enum "1533.07" {
             description "1533.07 nm/195.550000 THz 3.125/6.25/12.5/50GHz spacing";
           }
           enum "1533.05" {
             description "1533.05 nm/195.553125 THz 3.125GHz spacing";
           }
           enum "1533.02" {
             description "1533.02 nm/195.556250 THz 3.125/6.25GHz spacing";
           }
           enum "1533.00" {
             description "1533.00 nm/195.559375 THz 3.125GHz spacing";
           }
           enum "1532.98" {
             description "1532.98 nm/195.562500 THz 3.125/6.25/12.5GHz spacing";
           }
           enum "1532.95" {
             description "1532.95 nm/195.565625 THz 3.125GHz spacing";
           }
           enum "1532.93" {
             description "1532.93 nm/195.568750 THz 3.125/6.25GHz spacing";
           }
           enum "1532.90" {
             description "1532.90 nm/195.571875 THz 3.125GHz spacing";
           }
           enum "1532.88" {
             description "1532.88 nm/195.575000 THz 3.125/6.25/12.5GHz spacing";
           }
           enum "1532.85" {
             description "1532.85 nm/195.578125 THz 3.125GHz spacing";
           }
           enum "1532.83" {
             description "1532.83 nm/195.581250 THz 3.125/6.25GHz spacing";
           }
           enum "1532.80" {
             description "1532.80 nm/195.584375 THz 3.125GHz spacing";
           }
           enum "1532.78" {
             description "1532.78 nm/195.587500 THz 3.125/6.25/12.5GHz spacing";
           }
           enum "1532.75" {
             description "1532.75 nm/195.590625 THz 3.125GHz spacing";
           }
           enum "1532.73" {
             description "1532.73 nm/195.593750 THz 3.125/6.25GHz spacing";
           }
           enum "1532.71" {
             description "1532.71 nm/195.596875 THz 3.125GHz spacing";
           }
           enum "1532.68" {
             description "1532.68 nm/195.600000 THz 3.125/6.25/12.5/50/75/100GHz spacing";
           }
           enum "1532.66" {
             description "1532.66 nm/195.603125 THz 3.125GHz spacing";
           }
           enum "1532.63" {
             description "1532.63 nm/195.606250 THz 3.125/6.25GHz spacing";
           }
           enum "1532.61" {
             description "1532.61 nm/195.609375 THz 3.125GHz spacing";
           }
           enum "1532.58" {
             description "1532.58 nm/195.612500 THz 3.125/6.25/12.5GHz spacing";
           }
           enum "1532.56" {
             description "1532.56 nm/195.615625 THz 3.125GHz spacing";
           }
           enum "1532.53" {
             description "1532.53 nm/195.618750 THz 3.125/6.25GHz spacing";
           }
           enum "1532.51" {
             description "1532.51 nm/195.621875 THz 3.125GHz spacing";
           }
           enum "1532.49" {
             description "1532.49 nm/195.625000 THz 3.125/6.25/12.5GHz spacing";
           }
           enum "1532.46" {
             description "1532.46 nm/195.628125 THz 3.125GHz spacing";
           }
           enum "1532.44" {
             description "1532.44 nm/195.631250 THz 3.125/6.25GHz spacing";
           }
           enum "1532.41" {
             description "1532.41 nm/195.634375 THz 3.125GHz spacing";
           }
           enum "1532.39" {
             description "1532.39 nm/195.637500 THz 3.125/6.25/12.5GHz spacing";
           }
           enum "1532.36" {
             description "1532.36 nm/195.640625 THz 3.125GHz spacing";
           }
           enum "1532.34" {
             description "1532.34 nm/195.643750 THz 3.125/6.25GHz spacing";
           }
           enum "1532.31" {
             description "1532.31 nm/195.646875 THz 3.125GHz spacing";
           }
           enum "1532.29" {
             description "1532.29 nm/195.650000 THz 3.125/6.25/12.5/50GHz spacing";
           }
           enum "1532.27" {
             description "1532.27 nm/195.653125 THz 3.125GHz spacing";
           }
           enum "1532.24" {
             description "1532.24 nm/195.656250 THz 3.125/6.25GHz spacing";
           }
           enum "1532.22" {
             description "1532.22 nm/195.659375 THz 3.125GHz spacing";
           }
           enum "1532.19" {
             description "1532.19 nm/195.662500 THz 3.125/6.25/12.5GHz spacing";
           }
           enum "1532.17" {
             description "1532.17 nm/195.665625 THz 3.125GHz spacing";
           }
           enum "1532.14" {
             description "1532.14 nm/195.668750 THz 3.125/6.25GHz spacing";
           }
           enum "1532.12" {
             description "1532.12 nm/195.671875 THz 3.125GHz spacing";
           }
           enum "1532.09" {
             description "1532.09 nm/195.675000 THz 3.125/6.25/12.5/75GHz spacing";
           }
           enum "1532.07" {
             description "1532.07 nm/195.678125 THz 3.125GHz spacing";
           }
           enum "1532.04" {
             description "1532.04 nm/195.681250 THz 3.125/6.25GHz spacing";
           }
           enum "1532.02" {
             description "1532.02 nm/195.684375 THz 3.125GHz spacing";
           }
           enum "1532.00" {
             description "1532.00 nm/195.687500 THz 3.125/6.25/12.5GHz spacing";
           }
           enum "1531.97" {
             description "1531.97 nm/195.690625 THz 3.125GHz spacing";
           }
           enum "1531.95" {
             description "1531.95 nm/195.693750 THz 3.125/6.25GHz spacing";
           }
           enum "1531.92" {
             description "1531.92 nm/195.696875 THz 3.125GHz spacing";
           }
           enum "1531.90" {
             description "1531.90 nm/195.700000 THz 3.125/6.25/12.5/100GHz spacing";
           }
           enum "1531.87" {
             description "1531.87 nm/195.703125 THz 3.125GHz spacing";
           }
           enum "1531.85" {
             description "1531.85 nm/195.706250 THz 3.125/6.25GHz spacing";
           }
           enum "1531.82" {
             description "1531.82 nm/195.709375 THz 3.125GHz spacing";
           }
           enum "1531.80" {
             description "1531.80 nm/195.712500 THz 3.125/6.25/12.5GHz spacing";
           }
           enum "1531.78" {
             description "1531.78 nm/195.715625 THz 3.125GHz spacing";
           }
           enum "1531.75" {
             description "1531.75 nm/195.718750 THz 3.125/6.25GHz spacing";
           }
           enum "1531.73" {
             description "1531.73 nm/195.721875 THz 3.125GHz spacing";
           }
           enum "1531.70" {
             description "1531.70 nm/195.725000 THz 3.125/6.25/12.5GHz spacing";
           }
           enum "1531.68" {
             description "1531.68 nm/195.728125 THz 3.125GHz spacing";
           }
           enum "1531.65" {
             description "1531.65 nm/195.731250 THz 3.125/6.25GHz spacing";
           }
           enum "1531.63" {
             description "1531.63 nm/195.734375 THz 3.125GHz spacing";
           }
           enum "1531.60" {
             description "1531.60 nm/195.737500 THz 3.125/6.25/12.5GHz spacing";
           }
           enum "1531.58" {
             description "1531.58 nm/195.740625 THz 3.125GHz spacing";
           }
           enum "1531.56" {
             description "1531.56 nm/195.743750 THz 3.125/6.25GHz spacing";
           }
           enum "1531.53" {
             description "1531.53 nm/195.746875 THz 3.125GHz spacing";
           }
           enum "1531.51" {
             description "1531.51 nm/195.750000 THz 3.125/6.25/12.5/50/75GHz spacing";
           }
           enum "1531.48" {
             description "1531.48 nm/195.753125 THz 3.125GHz spacing";
           }
           enum "1531.46" {
             description "1531.46 nm/195.756250 THz 3.125/6.25GHz spacing";
           }
           enum "1531.43" {
             description "1531.43 nm/195.759375 THz 3.125GHz spacing";
           }
           enum "1531.41" {
             description "1531.41 nm/195.762500 THz 3.125/6.25/12.5GHz spacing";
           }
           enum "1531.38" {
             description "1531.38 nm/195.765625 THz 3.125GHz spacing";
           }
           enum "1531.36" {
             description "1531.36 nm/195.768750 THz 3.125/6.25GHz spacing";
           }
           enum "1531.34" {
             description "1531.34 nm/195.771875 THz 3.125GHz spacing";
           }
           enum "1531.31" {
             description "1531.31 nm/195.775000 THz 3.125/6.25/12.5GHz spacing";
           }
           enum "1531.29" {
             description "1531.29 nm/195.778125 THz 3.125GHz spacing";
           }
           enum "1531.26" {
             description "1531.26 nm/195.781250 THz 3.125/6.25GHz spacing";
           }
           enum "1531.24" {
             description "1531.24 nm/195.784375 THz 3.125GHz spacing";
           }
           enum "1531.21" {
             description "1531.21 nm/195.787500 THz 3.125/6.25/12.5GHz spacing";
           }
           enum "1531.19" {
             description "1531.19 nm/195.790625 THz 3.125GHz spacing";
           }
           enum "1531.16" {
             description "1531.16 nm/195.793750 THz 3.125/6.25GHz spacing";
           }
           enum "1531.14" {
             description "1531.14 nm/195.796875 THz 3.125GHz spacing";
           }
           enum "1531.12" {
             description "1531.12 nm/195.800000 THz 3.125/6.25/12.5/100GHz spacing";
           }
           enum "1531.09" {
             description "1531.09 nm/195.803125 THz 3.125GHz spacing";
           }
           enum "1531.07" {
             description "1531.07 nm/195.806250 THz 3.125/6.25GHz spacing";
           }
           enum "1531.04" {
             description "1531.04 nm/195.809375 THz 3.125GHz spacing";
           }
           enum "1531.02" {
             description "1531.02 nm/195.812500 THz 3.125/6.25/12.5GHz spacing";
           }
           enum "1530.99" {
             description "1530.99 nm/195.815625 THz 3.125GHz spacing";
           }
           enum "1530.97" {
             description "1530.97 nm/195.818750 THz 3.125/6.25GHz spacing";
           }
           enum "1530.94" {
             description "1530.94 nm/195.821875 THz 3.125GHz spacing";
           }
           enum "1530.92" {
             description "1530.92 nm/195.825000 THz 3.125/6.25/12.5/75GHz spacing";
           }
           enum "1530.90" {
             description "1530.90 nm/195.828125 THz 3.125GHz spacing";
           }
           enum "1530.87" {
             description "1530.87 nm/195.831250 THz 3.125/6.25GHz spacing";
           }
           enum "1530.85" {
             description "1530.85 nm/195.834375 THz 3.125GHz spacing";
           }
           enum "1530.82" {
             description "1530.82 nm/195.837500 THz 3.125/6.25/12.5GHz spacing";
           }
           enum "1530.80" {
             description "1530.80 nm/195.840625 THz 3.125GHz spacing";
           }
           enum "1530.77" {
             description "1530.77 nm/195.843750 THz 3.125/6.25GHz spacing";
           }
           enum "1530.75" {
             description "1530.75 nm/195.846875 THz 3.125GHz spacing";
           }
           enum "1530.72" {
             description "1530.72 nm/195.850000 THz 3.125/6.25/12.5/50GHz spacing";
           }
           enum "1530.70" {
             description "1530.70 nm/195.853125 THz 3.125GHz spacing";
           }
           enum "1530.68" {
             description "1530.68 nm/195.856250 THz 3.125/6.25GHz spacing";
           }
           enum "1530.65" {
             description "1530.65 nm/195.859375 THz 3.125GHz spacing";
           }
           enum "1530.63" {
             description "1530.63 nm/195.862500 THz 3.125/6.25/12.5GHz spacing";
           }
           enum "1530.60" {
             description "1530.60 nm/195.865625 THz 3.125GHz spacing";
           }
           enum "1530.58" {
             description "1530.58 nm/195.868750 THz 3.125/6.25GHz spacing";
           }
           enum "1530.55" {
             description "1530.55 nm/195.871875 THz 3.125GHz spacing";
           }
           enum "1530.53" {
             description "1530.53 nm/195.875000 THz 3.125/6.25/12.5GHz spacing";
           }
           enum "1530.51" {
             description "1530.51 nm/195.878125 THz 3.125GHz spacing";
           }
           enum "1530.48" {
             description "1530.48 nm/195.881250 THz 3.125/6.25GHz spacing";
           }
           enum "1530.46" {
             description "1530.46 nm/195.884375 THz 3.125GHz spacing";
           }
           enum "1530.43" {
             description "1530.43 nm/195.887500 THz 3.125/6.25/12.5GHz spacing";
           }
           enum "1530.41" {
             description "1530.41 nm/195.890625 THz 3.125GHz spacing";
           }
           enum "1530.38" {
             description "1530.38 nm/195.893750 THz 3.125/6.25GHz spacing";
           }
           enum "1530.36" {
             description "1530.36 nm/195.896875 THz 3.125GHz spacing";
           }
           enum "1530.33" {
             description "1530.33 nm/195.900000 THz 3.125/6.25/12.5/50/75/100GHz spacing";
           }
           enum "1530.31" {
             description "1530.31 nm/195.903125 THz 3.125GHz spacing";
           }
           enum "1530.29" {
             description "1530.29 nm/195.906250 THz 3.125/6.25GHz spacing";
           }
           enum "1530.26" {
             description "1530.26 nm/195.909375 THz 3.125GHz spacing";
           }
           enum "1530.24" {
             description "1530.24 nm/195.912500 THz 3.125/6.25/12.5GHz spacing";
           }
           enum "1530.21" {
             description "1530.21 nm/195.915625 THz 3.125GHz spacing";
           }
           enum "1530.19" {
             description "1530.19 nm/195.918750 THz 3.125/6.25GHz spacing";
           }
           enum "1530.16" {
             description "1530.16 nm/195.921875 THz 3.125GHz spacing";
           }
           enum "1530.14" {
             description "1530.14 nm/195.925000 THz 3.125/6.25/12.5GHz spacing";
           }
           enum "1530.11" {
             description "1530.11 nm/195.928125 THz 3.125GHz spacing";
           }
           enum "1530.09" {
             description "1530.09 nm/195.931250 THz 3.125/6.25GHz spacing";
           }
           enum "1530.07" {
             description "1530.07 nm/195.934375 THz 3.125GHz spacing";
           }
           enum "1530.04" {
             description "1530.04 nm/195.937500 THz 3.125/6.25/12.5GHz spacing";
           }
           enum "1530.02" {
             description "1530.02 nm/195.940625 THz 3.125GHz spacing";
           }
           enum "1529.99" {
             description "1529.99 nm/195.943750 THz 3.125/6.25GHz spacing";
           }
           enum "1529.97" {
             description "1529.97 nm/195.946875 THz 3.125GHz spacing";
           }
           enum "1529.94" {
             description "1529.94 nm/195.950000 THz 3.125/6.25/12.5/50GHz spacing";
           }
           enum "1529.92" {
             description "1529.92 nm/195.953125 THz 3.125GHz spacing";
           }
           enum "1529.89" {
             description "1529.89 nm/195.956250 THz 3.125/6.25GHz spacing";
           }
           enum "1529.87" {
             description "1529.87 nm/195.959375 THz 3.125GHz spacing";
           }
           enum "1529.85" {
             description "1529.85 nm/195.962500 THz 3.125/6.25/12.5GHz spacing";
           }
           enum "1529.82" {
             description "1529.82 nm/195.965625 THz 3.125GHz spacing";
           }
           enum "1529.80" {
             description "1529.80 nm/195.968750 THz 3.125/6.25GHz spacing";
           }
           enum "1529.77" {
             description "1529.77 nm/195.971875 THz 3.125GHz spacing";
           }
           enum "1529.75" {
             description "1529.75 nm/195.975000 THz 3.125/6.25/12.5/75GHz spacing";
           }
           enum "1529.72" {
             description "1529.72 nm/195.978125 THz 3.125GHz spacing";
           }
           enum "1529.70" {
             description "1529.70 nm/195.981250 THz 3.125/6.25GHz spacing";
           }
           enum "1529.68" {
             description "1529.68 nm/195.984375 THz 3.125GHz spacing";
           }
           enum "1529.65" {
             description "1529.65 nm/195.987500 THz 3.125/6.25/12.5GHz spacing";
           }
           enum "1529.63" {
             description "1529.63 nm/195.990625 THz 3.125GHz spacing";
           }
           enum "1529.60" {
             description "1529.60 nm/195.993750 THz 3.125/6.25GHz spacing";
           }
           enum "1529.58" {
             description "1529.58 nm/195.996875 THz 3.125GHz spacing";
           }
           enum "1529.55" {
             description "1529.55 nm/196.000000 THz 3.125/6.25/12.5/100GHz spacing";
           }
           enum "1529.53" {
             description "1529.53 nm/196.003125 THz 3.125GHz spacing";
           }
           enum "1529.50" {
             description "1529.50 nm/196.006250 THz 3.125/6.25GHz spacing";
           }
           enum "1529.48" {
             description "1529.48 nm/196.009375 THz 3.125GHz spacing";
           }
           enum "1529.46" {
             description "1529.46 nm/196.012500 THz 3.125/6.25/12.5GHz spacing";
           }
           enum "1529.43" {
             description "1529.43 nm/196.015625 THz 3.125GHz spacing";
           }
           enum "1529.41" {
             description "1529.41 nm/196.018750 THz 3.125/6.25GHz spacing";
           }
           enum "1529.38" {
             description "1529.38 nm/196.021875 THz 3.125GHz spacing";
           }
           enum "1529.36" {
             description "1529.36 nm/196.025000 THz 3.125/6.25/12.5GHz spacing";
           }
           enum "1529.33" {
             description "1529.33 nm/196.028125 THz 3.125GHz spacing";
           }
           enum "1529.31" {
             description "1529.31 nm/196.031250 THz 3.125/6.25GHz spacing";
           }
           enum "1529.29" {
             description "1529.29 nm/196.034375 THz 3.125GHz spacing";
           }
           enum "1529.26" {
             description "1529.26 nm/196.037500 THz 3.125/6.25/12.5GHz spacing";
           }
           enum "1529.24" {
             description "1529.24 nm/196.040625 THz 3.125GHz spacing";
           }
           enum "1529.21" {
             description "1529.21 nm/196.043750 THz 3.125/6.25GHz spacing";
           }
           enum "1529.19" {
             description "1529.19 nm/196.046875 THz 3.125GHz spacing";
           }
           enum "1529.16" {
             description "1529.16 nm/196.050000 THz 3.125/6.25/12.5/50/75GHz spacing";
           }
           enum "1529.14" {
             description "1529.14 nm/196.053125 THz 3.125GHz spacing";
           }
           enum "1529.11" {
             description "1529.11 nm/196.056250 THz 3.125/6.25GHz spacing";
           }
           enum "1529.09" {
             description "1529.09 nm/196.059375 THz 3.125GHz spacing";
           }
           enum "1529.07" {
             description "1529.07 nm/196.062500 THz 3.125/6.25/12.5GHz spacing";
           }
           enum "1529.04" {
             description "1529.04 nm/196.065625 THz 3.125GHz spacing";
           }
           enum "1529.02" {
             description "1529.02 nm/196.068750 THz 3.125/6.25GHz spacing";
           }
           enum "1528.99" {
             description "1528.99 nm/196.071875 THz 3.125GHz spacing";
           }
           enum "1528.97" {
             description "1528.97 nm/196.075000 THz 3.125/6.25/12.5GHz spacing";
           }
           enum "1528.94" {
             description "1528.94 nm/196.078125 THz 3.125GHz spacing";
           }
           enum "1528.92" {
             description "1528.92 nm/196.081250 THz 3.125/6.25GHz spacing";
           }
           enum "1528.90" {
             description "1528.90 nm/196.084375 THz 3.125GHz spacing";
           }
           enum "1528.87" {
             description "1528.87 nm/196.087500 THz 3.125/6.25/12.5GHz spacing";
           }
           enum "1528.85" {
             description "1528.85 nm/196.090625 THz 3.125GHz spacing";
           }
           enum "1528.82" {
             description "1528.82 nm/196.093750 THz 3.125/6.25GHz spacing";
           }
           enum "1528.80" {
             description "1528.80 nm/196.096875 THz 3.125GHz spacing";
           }
           enum "1528.77" {
             description "1528.77 nm/196.100000 THz 3.125/6.25/12.5/50/75/100GHz spacing";
           }
           enum "1528.75" {
             description "1528.75 nm/196.103125 THz 3.125GHz spacing";
           }
           enum "1528.72" {
             description "1528.72 nm/196.106250 THz 3.125/6.25GHz spacing";
           }
           enum "1528.70" {
             description "1528.70 nm/196.109375 THz 3.125GHz spacing";
           }
           enum "1528.68" {
             description "1528.68 nm/196.112500 THz 3.125/6.25/12.5GHz spacing";
           }
           enum "1528.65" {
             description "1528.65 nm/196.115625 THz 3.125GHz spacing";
           }
           enum "1528.63" {
             description "1528.63 nm/196.118750 THz 3.125/6.25GHz spacing";
           }
           enum "1528.60" {
             description "1528.60 nm/196.121875 THz 3.125GHz spacing";
           }
           enum "1528.58" {
             description "1528.58 nm/196.125000 THz 3.125/6.25/12.5/75GHz spacing";
           }
           enum "1528.55" {
             description "1528.55 nm/196.128125 THz 3.125GHz spacing";
           }
           enum "1528.53" {
             description "1528.53 nm/196.131250 THz 3.125/6.25GHz spacing";
           }
           enum "1528.51" {
             description "1528.51 nm/196.134375 THz 3.125GHz spacing";
           }
           enum "1528.48" {
             description "1528.48 nm/196.137500 THz 3.125/6.25/12.5GHz spacing";
           }
           enum "1528.46" {
             description "1528.46 nm/196.140625 THz 3.125GHz spacing";
           }
           enum "1528.43" {
             description "1528.43 nm/196.143750 THz 3.125/6.25GHz spacing";
           }
           enum "1528.41" {
             description "1528.41 nm/196.146875 THz 3.125GHz spacing";
           }
           enum "1528.38" {
             description "1528.38 nm/196.15040 THz 50Ghz spacing";
           }
         }
       }
       leaf tx-power {
         description "Transmit laser output power";
         units "dBm";
         type string {
           junos:posix-pattern "^[+-]?[0-9]+(\\.[0-9]+)?$";
           junos:pattern-message "numerical value must be specified with optional leading sign and optional decimal point";
         }
       }
       container loopback {
         presence "enable loopback";
         description "Put the optics in loopback mode";
         uses apply-advanced;
         leaf loopbacktype {
           description "Set loopback type";
           type enumeration {
             enum "media-side-out" {
               description "Loop media side output back to input";
             }
             enum "media-side-in" {
               description "Loop media side input back to output";
             }
             enum "host-side-out" {
               description "Loop host side output back to input";
             }
             enum "host-side-in" {
               description "Loop host side input back to output";
             }
           }
         }
       }
       leaf los-warning-threshold {
         description "LOS warning threshold";
         units "dBm";
         type string;
       }
       leaf los-alarm-threshold {
         description "LOS alarm threshold";
         units "dBm";
         type string;
       }
       leaf modulation-format {
         description "Type of Modulation Format";
         type enumeration {
           enum "16qam" {
             description "16-QAM Modulation Format";
           }
           enum "8qam" {
             description "8-QAM MOdulation Format";
           }
           enum "qpsk" {
             description "QPSK Modulation Format";
           }
         }
       }
       choice laser-enable-choice {
         leaf laser-enable {
           description "Enable Laser";
           type empty;
         }
         leaf no-laser-enable {
           description "Don't enable Laser";
           type empty;
         }
       }
       choice is-ma-choice {
         leaf is-ma {
           description "Link is enabled with alarms masked";
           type empty;
         }
         leaf no-is-ma {
           description "Don't link is enabled with alarms masked";
           type empty;
         }
       }
       leaf encoding {
         description "Line encoding";
         type enumeration {
           enum "differential" {
             description "Differential phase line encoding";
           }
           enum "non-differential" {
             description "Non-differential phase line encoding";
           }
         }
       }
       leaf fec {
         description "Forward Error Correction mode";
         type enumeration {
           enum "sdfec" {
             description "Sky-Compatible Soft Decision Forward Error Correction";
           }
           enum "sdfec25" {
             description "Denali-Compatible Soft Decision Forward Error Correction with 25 percent overhead";
           }
           enum "hgfec" {
             description "High Gain Forward Error Correction";
           }
           enum "sdfec15" {
             description "Soft Decision Forward Error Correction with 15 percent overhead";
           }
         }
       }
       leaf high-polarization {
         description "High polarization tracking mode";
         type empty;
       }
       container application {
         description "Config Host and Media Code";
         uses apply-advanced;
         leaf hostid {
           description "Enter Host Code";
           type union {
             type string {
               pattern "<.*>|$.*";
             }
             type uint32 {
               range "1 .. 255";
             }
           }
         }
         leaf mediaid {
           description "Enter Media Code";
           type union {
             type string {
               pattern "<.*>|$.*";
             }
             type uint32 {
               range "1 .. 255";
             }
           }
         }
         leaf domainid {
           description "Enter Domain ID";
           type union {
             type string {
               pattern "<.*>|$.*";
             }
             type uint32 {
               range "0 .. 255";
             }
           }
         }
       }
       container cd {
         description "Config CD value mapped with media-id";
         uses apply-advanced;
         leaf cd-val {
           description "Enter cd value";
           type decimal64 {
             fraction-digits 9;
           }
         }
       }
       container appselid {
         description "Config AppSel ID";
         uses apply-advanced;
         leaf id {
           type union {
             type string {
               pattern "<.*>|$.*";
             }
             type uint32 {
               range "1 .. 240";
             }
           }
         }
       }
       container signal-degrade {
         description "Signal degrade thresholds";
         uses apply-advanced;
         leaf interval {
           description "Time interval";
           default "10";
           units "milliseconds";
           type union {
             type string {
               pattern "<.*>|$.*";
             }
             type uint32 {
               range "1 .. 1000";
             }
           }
         }
         leaf ber-threshold-clear {
           description "Ber threshold for signal degrade clear (format: xe-n, example: 4.5e-3)";
           type string {
             junos:posix-pattern "^[0-9]+(.[0-9]+)?e-[0-9]$";
             junos:pattern-message "Ber threshold value in format: xe-n, x is an integer or decimal number, n = 0..9";
           }
         }
         leaf ber-threshold-signal-degrade {
           description "Ber threshold for signal-degrade (format: xe-n, example: 4.5e-3)";
           type string {
             junos:posix-pattern "^[0-9]+(.[0-9]+)?e-[0-9]$";
             junos:pattern-message "Ber threshold value in format: xe-n, x is an integer or decimal number, n = 0..9";
           }
         }
         leaf q-threshold-signal-degrade-clear {
           description "Q threshold for signal-degrade clear (e.g. 14.26)";
           units "dB";
           type string;
         }
         leaf q-threshold-signal-degrade {
           description "Q threshold for signal-degrade (e.g. 9.26)";
           units "dB";
           type string;
         }
       }
       list alarm {
         key name;
         ordered-by user;
         description "Set optic alarms";
         leaf name {
           junos:cli-feature "nokeyword";
           type enumeration {
             enum "low-light-alarm" {
               description "Enable low light alarm";
             }
           }
         }
         uses apply-advanced;
         choice actiontype {
           case case_1 {
             leaf syslog {
               type empty;
             }
           }
           case case_2 {
             leaf link-down {
               type empty;
             }
           }
         }
       }
       container tca {
         description "Set tca for optic alarms";
         uses apply-advanced;
         container tx-power-high-tca {
           description "Tx power high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
               junos:posix-pattern "^[+-]?[0-9]+(\\.[0-9]+)?$";
               junos:pattern-message "numerical value must be specified with optional leading sign and optional decimal point";
             }
           }
           leaf threshold-24hrs {
             description "TCA Threshold for 24-hour interval in dBm";
             type string {
               junos:posix-pattern "^[+-]?[0-9]+(\\.[0-9]+)?$";
               junos:pattern-message "numerical value must be specified with optional leading sign and optional decimal point";
             }
           }
         }
         container tx-power-low-tca {
           description "Tx power low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
               junos:posix-pattern "^[+-]?[0-9]+(\\.[0-9]+)?$";
               junos:pattern-message "numerical value must be specified with optional leading sign and optional decimal point";
             }
           }
           leaf threshold-24hrs {
             description "TCA Threshold for 24-hour interval in dBm";
             type string {
               junos:posix-pattern "^[+-]?[0-9]+(\\.[0-9]+)?$";
               junos:pattern-message "numerical value must be specified with optional leading sign and optional decimal point";
             }
           }
         }
         container rx-power-high-tca {
           description "Rx power high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
               junos:posix-pattern "^[+-]?[0-9]+(\\.[0-9]+)?$";
               junos:pattern-message "numerical value must be specified with optional leading sign and optional decimal point";
             }
           }
           leaf threshold-24hrs {
             description "TCA Threshold for 24-hour interval in dBm";
             type string {
               junos:posix-pattern "^[+-]?[0-9]+(\\.[0-9]+)?$";
               junos:pattern-message "numerical value must be specified with optional leading sign and optional decimal point";
             }
           }
         }
         container rx-power-low-tca {
           description "Rx power low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
               junos:posix-pattern "^[+-]?[0-9]+(\\.[0-9]+)?$";
               junos:pattern-message "numerical value must be specified with optional leading sign and optional decimal point";
             }
           }
           leaf threshold-24hrs {
             description "TCA Threshold for 24-hour interval in dBm";
             type string {
               junos:posix-pattern "^[+-]?[0-9]+(\\.[0-9]+)?$";
               junos:pattern-message "numerical value must be specified with optional leading sign and optional decimal point";
             }
           }
         }
         container rx-signal-power-high-tca {
           description "Rx signal power high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
               junos:posix-pattern "^[+-]?[0-9]+(\\.[0-9]+)?$";
               junos:pattern-message "numerical value must be specified with optional leading sign and optional decimal point";
             }
           }
           leaf threshold-24hrs {
             description "TCA Threshold for 24-hour interval in dBm";
             type string {
               junos:posix-pattern "^[+-]?[0-9]+(\\.[0-9]+)?$";
               junos:pattern-message "numerical value must be specified with optional leading sign and optional decimal point";
             }
           }
         }
         container rx-signal-power-low-tca {
           description "Rx signal power low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
               junos:posix-pattern "^[+-]?[0-9]+(\\.[0-9]+)?$";
               junos:pattern-message "numerical value must be specified with optional leading sign and optional decimal point";
             }
           }
           leaf threshold-24hrs {
             description "TCA Threshold for 24-hour interval in dBm";
             type string {
               junos:posix-pattern "^[+-]?[0-9]+(\\.[0-9]+)?$";
               junos:pattern-message "numerical value must be specified with optional leading sign and optional decimal point";
             }
           }
         }
         container temperature-high-tca {
           description "Temperature high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in celsius";
             type string {
               junos:posix-pattern "^[+-]?[0-9]+(\\.[0-9]+)?$";
               junos:pattern-message "numerical value must be specified with optional leading sign and optional decimal point";
             }
           }
           leaf threshold-24hrs {
             description "TCA Threshold for 24-hour interval in celsius";
             type string {
               junos:posix-pattern "^[+-]?[0-9]+(\\.[0-9]+)?$";
               junos:pattern-message "numerical value must be specified with optional leading sign and optional decimal point";
             }
           }
         }
         container temperature-low-tca {
           description "Temperature low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in celsius";
             type string {
               junos:posix-pattern "^[+-]?[0-9]+(\\.[0-9]+)?$";
               junos:pattern-message "numerical value must be specified with optional leading sign and optional decimal point";
             }
           }
           leaf threshold-24hrs {
             description "TCA Threshold for 24-hour interval in celsius";
             type string {
               junos:posix-pattern "^[+-]?[0-9]+(\\.[0-9]+)?$";
               junos:pattern-message "numerical value must be specified with optional leading sign and optional decimal point";
             }
           }
         }
         container carrier-frequency-offset-high-tca {
           description "Carrier frequency offset high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in MHz";
             type string {
               junos:posix-pattern "^[+-]?[0-9]+(\\.[0-9]+)?$";
               junos:pattern-message "numerical value must be specified with optional leading sign and optional decimal point";
             }
           }
           leaf threshold-24hrs {
             description "TCA Threshold for 24-hour interval in MHz";
             type string {
               junos:posix-pattern "^[+-]?[0-9]+(\\.[0-9]+)?$";
               junos:pattern-message "numerical value must be specified with optional leading sign and optional decimal point";
             }
           }
         }
         container carrier-frequency-offset-low-tca {
           description "Carrier frequency offset low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in MHz";
             type string {
               junos:posix-pattern "^[+-]?[0-9]+(\\.[0-9]+)?$";
               junos:pattern-message "numerical value must be specified with optional leading sign and optional decimal point";
             }
           }
           leaf threshold-24hrs {
             description "TCA Threshold for 24-hour interval in MHz";
             type string {
               junos:posix-pattern "^[+-]?[0-9]+(\\.[0-9]+)?$";
               junos:pattern-message "numerical value must be specified with optional leading sign and optional decimal point";
             }
           }
         }
         container fec-ber {
           junos:cli-feature "oneliner";
           description "Optics Errored Seconds Threshold crossing defect trigger";
           choice enable-tca-choice {
             leaf enable-tca {
               description "Enable the Optics errored seconds threshold crossing alert";
               type empty;
             }
             leaf no-enable-tca {
               description "Don't enable the Optics errored seconds threshold crossing alert";
               type empty;
             }
           }
           leaf threshold {
             description "TCA Threshold for user-configurable interval (default 15-minutes) in exponential format";
             default "10e-3";
             type string {
               junos:posix-pattern "^[0-9]+(\\.[0-9]+)?e-[0-9]$";
               junos:pattern-message "exponential value must be in format xe-n, x is a decimal number, n = 0..9";
             }
           }
           leaf threshold-24hrs {
             description "TCA Threshold for 24-hour interval in exponential format";
             default "10e-3";
             type string {
               junos:posix-pattern "^[0-9]+(\\.[0-9]+)?e-[0-9]$";
               junos:pattern-message "exponential value must be in format xe-n, x is a decimal number, n = 0..9";
             }
           }
         }
         container tec-current-high-tca {
           description "TEC Current high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in mA";
             type string {
               junos:posix-pattern "^[+-]?[0-9]+(\\.[0-9]+)?$";
               junos:pattern-message "numerical value must be specified with optional leading sign and optional decimal point";
             }
           }
           leaf threshold-24hrs {
             description "TCA Threshold for 24-hour interval in mA";
             type string {
               junos:posix-pattern "^[+-]?[0-9]+(\\.[0-9]+)?$";
               junos:pattern-message "numerical value must be specified with optional leading sign and optional decimal point";
             }
           }
         }
         container tec-current-low-tca {
           description "TEC Current low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in mA";
             type string {
               junos:posix-pattern "^[+-]?[0-9]+(\\.[0-9]+)?$";
               junos:pattern-message "numerical value must be specified with optional leading sign and optional decimal point";
             }
           }
           leaf threshold-24hrs {
             description "TCA Threshold for 24-hour interval in mA";
             type string {
               junos:posix-pattern "^[+-]?[0-9]+(\\.[0-9]+)?$";
               junos:pattern-message "numerical value must be specified with optional leading sign and optional decimal point";
             }
           }
         }
         container residual-isi-high-tca {
           description "Residual ISI high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in ps/nm";
             type string {
               junos:posix-pattern "^[+-]?[0-9]+(\\.[0-9]+)?$";
               junos:pattern-message "numerical value must be specified with optional leading sign and optional decimal point";
             }
           }
           leaf threshold-24hrs {
             description "TCA Threshold for 24-hour interval in ps/nm";
             type string {
               junos:posix-pattern "^[+-]?[0-9]+(\\.[0-9]+)?$";
               junos:pattern-message "numerical value must be specified with optional leading sign and optional decimal point";
             }
           }
         }
         container residual-isi-low-tca {
           description "Residual ISI low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in ps/nm";
             type string {
               junos:posix-pattern "^[+-]?[0-9]+(\\.[0-9]+)?$";
               junos:pattern-message "numerical value must be specified with optional leading sign and optional decimal point";
             }
           }
           leaf threshold-24hrs {
             description "TCA Threshold for 24-hour interval in ps/nm";
             type string {
               junos:posix-pattern "^[+-]?[0-9]+(\\.[0-9]+)?$";
               junos:pattern-message "numerical value must be specified with optional leading sign and optional decimal point";
             }
           }
         }
         container pam-histogram-high-tca {
           description "PAM Histogram high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes)";
             type string {
               junos:posix-pattern "^[0-9]+$";
               junos:pattern-message "must be an unsigned integer";
             }
           }
           leaf threshold-24hrs {
             description "TCA Threshold for 24-hour interval";
             type string {
               junos:posix-pattern "^[0-9]+$";
               junos:pattern-message "must be an unsigned integer";
             }
           }
         }
         container snr-low-tca {
           description "SNR low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm ";
             type string {
               junos:posix-pattern "^[+-]?[0-9]+(\\.[0-9]+)?$";
               junos:pattern-message "numerical value must be specified with optional leading sign and optional decimal point";
             }
           }
           leaf threshold-24hrs {
             description "TCA Threshold for 24-hour interval in dBm";
             type string {
               junos:posix-pattern "^[+-]?[0-9]+(\\.[0-9]+)?$";
               junos:pattern-message "numerical value must be specified with optional leading sign and optional decimal point";
             }
           }
         }
         container fec-corrected-errors-high-tca {
           description "FEC Corrected Error High Threshold crossing defect trigger";
           uses apply-advanced;
           choice enable-tca-choice {
             leaf enable-tca {
               description "Enable the FEC Corrected Errors threshold crossing alert";
               type empty;
             }
             leaf no-enable-tca {
               description "Don't enable the FEC Corrected Errors threshold crossing alert";
               type empty;
             }
           }
           leaf threshold {
             description "TCA Threshold for user-configurable interval (default 15-minutes) in exponential format";
             default "10e-3";
             type string {
               junos:posix-pattern "^[0-9]+(\\.[0-9]+)?e-[0-9]$";
               junos:pattern-message "exponential value must be in format xe-n, x is a decimal number, n = 0..9";
             }
           }
           leaf threshold-24hrs {
             description "TCA Threshold for 24-hour interval in exponential format";
             default "10e-3";
             type string {
               junos:posix-pattern "^[0-9]+(\\.[0-9]+)?e-[0-9]$";
               junos:pattern-message "exponential value must be in format xe-n, x is a decimal number, n = 0..9";
             }
           }
         }
         container fec-ucorrected-words-high-tca {
           description "FEC UCorrected Words High Threshold crossing defect trigger";
           uses apply-advanced;
           choice enable-tca-choice {
             leaf enable-tca {
               description "Enable the FEC UCorrected Words threshold crossing alert";
               type empty;
             }
             leaf no-enable-tca {
               description "Don't enable the FEC UCorrected Words threshold crossing alert";
               type empty;
             }
           }
           leaf threshold {
             description "TCA Threshold for user-configurable interval (default 15-minutes) in exponential format";
             default "10e-3";
             type string {
               junos:posix-pattern "^[0-9]+(\\.[0-9]+)?e-[0-9]$";
               junos:pattern-message "exponential value must be in format xe-n, x is a decimal number, n = 0..9";
             }
           }
           leaf threshold-24hrs {
             description "TCA Threshold for 24-hour interval in exponential format";
             default "10e-3";
             type string {
               junos:posix-pattern "^[0-9]+(\\.[0-9]+)?e-[0-9]$";
               junos:pattern-message "exponential value must be in format xe-n, x is a decimal number, n = 0..9";
             }
           }
         }
         container laser-frequency-error-high-tca {
           description "Laser frequency error high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in MHz";
             type string {
               junos:posix-pattern "^[+-]?[0-9]+(\\.[0-9]+)?$";
               junos:pattern-message "numerical value must be specified with optional leading sign and optional decimal point";
             }
           }
           leaf threshold-24hrs {
             description "TCA Threshold for 24-hour interval in MHz";
             type string {
               junos:posix-pattern "^[+-]?[0-9]+(\\.[0-9]+)?$";
               junos:pattern-message "numerical value must be specified with optional leading sign and optional decimal point";
             }
           }
         }
         container laser-frequency-error-low-tca {
           description "Laser frequency error low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in MHz";
             type string {
               junos:posix-pattern "^[+-]?[0-9]+(\\.[0-9]+)?$";
               junos:pattern-message "numerical value must be specified with optional leading sign and optional decimal point";
             }
           }
           leaf threshold-24hrs {
             description "TCA Threshold for 24-hour interval in MHz";
             type string {
               junos:posix-pattern "^[+-]?[0-9]+(\\.[0-9]+)?$";
               junos:pattern-message "numerical value must be specified with optional leading sign and optional decimal point";
             }
           }
         }
       }
       list warning {
         key name;
         ordered-by user;
         description "Set optic warnings";
         leaf name {
           junos:cli-feature "nokeyword";
           type enumeration {
             enum "low-light-warning" {
               description "Enable low light warning";
             }
           }
         }
         uses apply-advanced;
         choice actiontype {
           case case_1 {
             leaf syslog {
               description "Set action as syslog";
               type empty;
             }
           }
           case case_2 {
             leaf link-down {
               description "Set action as link-down";
               type empty;
             }
           }
         }
       }
       leaf low-power-mode {
         description "Force optics to low power mode";
         type empty;
       }
       leaf high-power-mode {
         description "High power optic mode";
         type empty;
       }
       leaf host-side-fec {
         description "Host side optics FEC ON/OFF";
         type enumeration {
           enum "off" {
             description "Host side FEC OFF for optics";
           }
           enum "on" {
             description "Host side FEC ON for optics";
           }
         }
       }
       leaf media-side-fec {
         description "Media side FEC ON/OFF";
         type enumeration {
           enum "off" {
             description "Media side FEC OFF for optics";
           }
           enum "on" {
             description "Media side FEC ON for optics";
           }
         }
       }
       choice lane-info {
         case case_1 {
           list lane {
             key name;
             description "Media lane number";
             leaf name {
               description "Lane number";
               junos:cli-feature "nokeyword";
               type union {
                 type string {
                   pattern "<.*>|$.*";
                 }
                 type uint32 {
                   range "0 .. 7";
                 }
               }
             }
             uses apply-advanced;
             leaf tx-laser {
               description "Transmit Laser ON/OFF";
               junos:must "(!(\"interfaces ${interface} disable\"))";
               junos:must-message "tx-laser cannot be applied when interface is disabled";
               type enumeration {
                 enum "off" {
                   description "Transmit laser OFF for optics";
                 }
                 enum "on" {
                   description "Transmit laser ON for optics";
                 }
               }
             }
             leaf rx-output {
               description "Receive output ON/OFF";
               type enumeration {
                 enum "off" {
                   description "Receive output OFF for optics";
                 }
                 enum "on" {
                   description "Receive output ON for optics";
                 }
               }
             }
             leaf tx-cdr {
               description "Transmit Clock and Data Recovery ON/OFF";
               type enumeration {
                 enum "off" {
                   description "Transmit Clock and Data Recovery OFF for optics";
                 }
                 enum "on" {
                   description "Transmit Clock and Data Recovery ON for optics";
                 }
               }
             }
             leaf rx-cdr {
               description "Receive Clock and Data Recovery ON/OFF";
               type enumeration {
                 enum "off" {
                   description "Receive Clock and Data Recovery OFF for optics";
                 }
                 enum "on" {
                   description "Receive Clock and Data Recovery ON for optics";
                 }
               }
             }
             leaf tx-input-equalization-adaptive {
               description "Transmit adaptive equalization ON/OFF";
               type enumeration {
                 enum "off" {
                   description "Transmit adaptive equalization OFF for optics";
                 }
                 enum "on" {
                   description "Transmit adaptive equalization ON for optics";
                 }
               }
             }
             leaf tx-input-equalization-manual {
               description "Transmit manual equalization for optics";
               units "dB";
               junos:must "(!(\".. tx-input-equalization-adaptive on\"))";
               junos:must-message "Manual equalization not possible when adaptive is enabled";
               type union {
                 type string {
                   pattern "<.*>|$.*";
                 }
                 type int32 {
                   range "0 .. 15";
                 }
               }
             }
             leaf rx-output-emphasis {
               description "Receive output emphasis for optics";
               units "dB";
               type union {
                 type string {
                   pattern "<.*>|$.*";
                 }
                 type int32 {
                   range "0 .. 15";
                 }
               }
             }
             leaf rx-output-amplitude {
               description "Receive output amplitude setting";
               type enumeration {
                 enum "400mV" {
                   description "No equalization for 100mV - 400mV amplitude";
                 }
                 enum "600mV" {
                   description "No equalization for 300mV - 600mV amplitude";
                 }
                 enum "800mV" {
                   description "No equalization for 400mV - 800mV amplitude";
                 }
                 enum "1200mV" {
                   description "No equalization for 600mV - 1200mV amplitude";
                 }
               }
             }
             leaf tx-squelch {
               description "Transmit squelch ON/OFF";
               type enumeration {
                 enum "off" {
                   description "Transmit squelch OFF for optics";
                 }
                 enum "on" {
                   description "Transmit squelch ON for optics";
                 }
               }
             }
             leaf rx-squelch {
               description "Receive squelch ON/OFF";
               type enumeration {
                 enum "off" {
                   description "Receive squelch OFF for optics";
                 }
                 enum "on" {
                   description "Receive squelch ON for optics";
                 }
               }
             }
             leaf tx-rate-select {
               description "Transmit rate select for optics";
               type union {
                 type string {
                   pattern "<.*>|$.*";
                 }
                 type int32 {
                   range "0 .. 3";
                 }
               }
             }
             leaf rx-rate-select {
               description "Receive rate select for optics";
               type union {
                 type string {
                   pattern "<.*>|$.*";
                 }
                 type int32 {
                   range "0 .. 3";
                 }
               }
             }
           }
         }
         case case_2 {
           container lane-all {
             presence "enable lane-all";
             description "Apply settings to all lane";
             uses apply-advanced;
             leaf tx-laser {
               description "Transmit Laser ON/OFF";
               junos:must "(!(\"interfaces ${interface} disable\"))";
               junos:must-message "tx-laser cannot be applied when interface is disabled";
               type enumeration {
                 enum "off" {
                   description "Transmit laser OFF for optics";
                 }
                 enum "on" {
                   description "Transmit laser ON for optics";
                 }
               }
             }
             leaf rx-output {
               description "Receive output ON/OFF";
               type enumeration {
                 enum "off" {
                   description "Receive output OFF for optics";
                 }
                 enum "on" {
                   description "Receive output ON for optics";
                 }
               }
             }
             leaf tx-cdr {
               description "Transmit Clock and Data Recovery ON/OFF";
               type enumeration {
                 enum "off" {
                   description "Transmit Clock and Data Recovery OFF for optics";
                 }
                 enum "on" {
                   description "Transmit Clock and Data Recovery ON for optics";
                 }
               }
             }
             leaf rx-cdr {
               description "Receive Clock and Data Recovery ON/OFF";
               type enumeration {
                 enum "off" {
                   description "Receive Clock and Data Recovery OFF for optics";
                 }
                 enum "on" {
                   description "Receive Clock and Data Recovery ON for optics";
                 }
               }
             }
             leaf tx-input-equalization-adaptive {
               description "Transmit adaptive equalization ON/OFF";
               type enumeration {
                 enum "off" {
                   description "Transmit adaptive equalization OFF for optics";
                 }
                 enum "on" {
                   description "Transmit adaptive equalization ON for optics";
                 }
               }
             }
             leaf tx-input-equalization-manual {
               description "Transmit manual equalization for optics";
               units "dB";
               junos:must "(!(\".. tx-input-equalization-adaptive on\"))";
               junos:must-message "Manual equalization not possible when adaptive is enabled";
               type union {
                 type string {
                   pattern "<.*>|$.*";
                 }
                 type int32 {
                   range "0 .. 15";
                 }
               }
             }
             leaf rx-output-emphasis {
               description "Receive output emphasis for optics";
               units "dB";
               type union {
                 type string {
                   pattern "<.*>|$.*";
                 }
                 type int32 {
                   range "0 .. 15";
                 }
               }
             }
             leaf rx-output-amplitude {
               description "Receive output amplitude setting";
               type enumeration {
                 enum "400mV" {
                   description "No equalization for 100mV - 400mV amplitude";
                 }
                 enum "600mV" {
                   description "No equalization for 300mV - 600mV amplitude";
                 }
                 enum "800mV" {
                   description "No equalization for 400mV - 800mV amplitude";
                 }
                 enum "1200mV" {
                   description "No equalization for 600mV - 1200mV amplitude";
                 }
               }
             }
             leaf tx-squelch {
               description "Transmit squelch ON/OFF";
               type enumeration {
                 enum "off" {
                   description "Transmit squelch OFF for optics";
                 }
                 enum "on" {
                   description "Transmit squelch ON for optics";
                 }
               }
             }
             leaf rx-squelch {
               description "Receive squelch ON/OFF";
               type enumeration {
                 enum "off" {
                   description "Receive squelch OFF for optics";
                 }
                 enum "on" {
                   description "Receive squelch ON for optics";
                 }
               }
             }
             leaf tx-rate-select {
               description "Transmit rate select for optics";
               type union {
                 type string {
                   pattern "<.*>|$.*";
                 }
                 type int32 {
                   range "0 .. 3";
                 }
               }
             }
             leaf rx-rate-select {
               description "Receive rate select for optics";
               type union {
                 type string {
                   pattern "<.*>|$.*";
                 }
                 type int32 {
                   range "0 .. 3";
                 }
               }
             }
           }
         }
       }
     }
     container otn-options {
       description "Optical Transmission Network interface-specific options";
       uses otn_options_type;
     }
     container och-options {
       description "Optical channel configuration options";
       uses och-attributes;
     }
     container otu-options {
       description "Optical transmission unit configuration options";
       uses otu-attributes;
     }
     container odu-options {
       description "Optical data unit configuration options";
       uses odu-attributes;
     }
     container ett-options {
       description "Transport ethernet client configuration options";
       uses ett-attributes;
     }
     container fastether-options {
       description "Fast Ethernet interface-specific options";
       uses apply-advanced;
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       leaf ingress-rate-limit {
         description "Ingress rate at port";
         units "megabits per second";
         type union {
           type string {
             pattern "<.*>|$.*";
           }
           type uint32 {
             range "1 .. 100";
           }
         }
       }
       list source-address-filter {
         key name;
         ordered-by user;
         junos:cli-feature "homogeneous";
         junos:cli-feature "oneliner";
         description "Source address filters";
         leaf name {
           description "Remote MAC address";
           junos:cli-feature "nokeyword";
           type jt:mac-addr;
         }
       }
       container ieee-802.3ad {
         junos:must "(!(\"system autoinstallation\"))";
         junos:must-message "incompatible with 'system autoinstallation'";
         junos:cli-feature "oneliner-plus";
         description "IEEE 802.3ad";
         uses apply-advanced;
         container lacp {
           description "Link Aggregation Control Protocol configuration";
           uses apply-advanced;
           leaf port-priority {
             description "Priority of the port (0 ... 65535)";
             type union {
               type uint16;
               type string {
                 pattern "<.*>|$.*";
               }
             }
           }
         }
         leaf bundle {
           description "Join an aggregated Ethernet interface";
           junos:cli-feature "nokeyword";
           junos:must "(!(any \"class-of-service interfaces ${interface} unit <*> rewrite-rules\"))";
           junos:must-message "rewrite config can not be applied on ae child";
           junos:must "(!(any \"class-of-service interfaces ${interface} unit <*> classifiers\"))";
           junos:must-message "classifier config can not be applied on ae child";
           junos:must "(!(any \"class-of-service interfaces ${interface} unit <*> output-traffic-control-profile\"))";
           junos:must-message "output-traffic-control-profile config can not be applied on ae child";
           junos:must "(!(\"class-of-service interfaces ${interface} output-traffic-control-profile\"))";
           junos:must-message "output-traffic-control-profile config can not be applied on ae child";
           junos:must "(!(\"class-of-service interfaces ${interface} shaping-rate\"))";
           junos:must-message "shaping-rate config can not be applied on ae child";
           junos:must "(!(\"class-of-service interfaces ${interface} scheduler-map\"))";
           junos:must-message "scheduler-map config can not be applied on ae child";
           junos:must "(!(\".. .. .. vlan-offload\"))";
           junos:must-message "ae child device vlan-offload is not allowed";
           junos:must "(!(\".. .. .. flow-control\"))";
           junos:must-message "Setting flow-control on ae child device is not allowed";
           junos:must "(!(\".. .. .. mtu\"))";
           junos:must-message "Setting mtu on ae child device is not allowed";
           junos:must "(!(\".. .. .. vlan-vci-tagging\"))";
           junos:must-message "ae child device vlan-vci-tagging is not allowed";
           junos:must "(!(\".. .. .. stacked-vlan-tagging\"))";
           junos:must-message "ae child device stacked-vlan-tagging is not allowed";
           junos:must "(!(\".. .. .. flexible-vlan-tagging\"))";
           junos:must-message "ae child device flexible-vlan-tagging is not allowed";
           junos:must "(!(\".. .. .. vlan-tagging\"))";
           junos:must-message "ae child device vlan-tagging is not allowed";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
       }
       container mpls {
         description "MPLS options";
         uses mpls_ifd_options;
       }
       leaf ignore-l3-incompletes {
         description "Ignore L3 incomplete errors";
         type empty;
       }
     }
     container aggregated-ether-options {
       description "Aggregated Ethernet interface-specific options";
       uses apply-advanced;
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       leaf autostate-exclude {
         description "Interface will not contribute to IRB state";
         type empty;
       }
       container link-protection {
         presence "enable link-protection";
         description "Enable link protection mode";
         uses apply-advanced;
         leaf revertive {
           description "Revert back from active backup link to primary, if primary is UP";
           junos:must "(!(\"interfaces ${interface} aggregated-ether-options link-protection non-revertive\"))";
           junos:must-message "link-protection revertive and non-revertive are mutually exclusive";
           junos:must "(!(\"chassis aggregated-devices ethernet lacp\"))";
           junos:must-message "link-protection revertive and LACP are mutually exclusive";
           junos:must "(!(\"interfaces ${interface} aggregated-ether-options lacp\"))";
           junos:must-message "link-protection revertive and LACP are mutually exclusive";
           type empty;
         }
         leaf non-revertive {
           description "Do not revert back (default mode) from active backup link to primary, if primary is UP";
           junos:must "(!(\"interfaces ${interface} aggregated-ether-options link-protection revertive\"))";
           junos:must-message "link-protection revertive and non-revertive are mutually exclusive";
           junos:must "(!(\"chassis aggregated-devices ethernet lacp\"))";
           junos:must-message "link-protection revertive and LACP are mutually exclusive";
           junos:must "(!(\"interfaces ${interface} aggregated-ether-options lacp\"))";
           junos:must-message "link-protection revertive and LACP are mutually exclusive";
           type empty;
         }
         leaf backup-state {
           description "Link protection backup link state";
           default "accept-data";
           type enumeration {
             enum "accept-data" {
               description "Accept data on receive channel of backup link";
             }
             enum "discard-data" {
               description "Discard data on receive channel of backup link";
             }
             enum "down" {
               description "Backup link is marked down";
               junos:must "(!(\"chassis aggregated-devices ethernet lacp\"))";
               junos:must-message "backup-state down and LACP are mutually exclusive";
               junos:must "(!(\"interfaces ${interface} aggregated-ether-options lacp\"))";
               junos:must-message "backup-state down and LACP are mutually exclusive";
             }
           }
         }
         container rtg-config {
           presence "enable rtg-config";
           description "RTG enable on AE";
           uses apply-advanced;
           leaf preempt-cutover-timer {
             description "RTG preempt-cutover-timer in seconds";
             default "1";
             type union {
               type string {
                 pattern "<.*>|$.*";
               }
               type uint32 {
                 range "0 .. 255";
               }
             }
           }
         }
       }
       choice fcoe-lag-choice {
         leaf fcoe-lag {
           description "Enable FIP/FCoE LAG";
           type empty;
         }
         leaf no-fcoe-lag {
           description "Don't enable FIP/FCoE LAG";
           type empty;
         }
       }
       list source-address-filter {
         key name;
         ordered-by user;
         junos:cli-feature "homogeneous";
         junos:cli-feature "oneliner";
         description "Source address filters";
         leaf name {
           description "Remote MAC address";
           junos:cli-feature "nokeyword";
           type jt:mac-addr;
         }
       }
       container configured-flow-control {
         presence "enable configured-flow-control";
         junos:must "(!((\".. flow-control\" || \".. no-flow-control\")))";
         junos:must-message "flow-control and configured-flow-control are not allowed together";
         description "Enable flow control";
         uses apply-advanced;
         leaf rx-buffers {
           description "Enable/Disable Rx buffers";
           type enumeration {
             enum "on" {
               description "Enable Rx buffers";
             }
             enum "off" {
               description "Disable Rx buffers";
             }
           }
         }
         leaf tx-buffers {
           description "Enable/Disable Tx buffers";
           type enumeration {
             enum "on" {
               description "Enable Tx buffers";
             }
             enum "off" {
               description "Disable Tx buffers";
             }
           }
         }
       }
       container load-balance {
         uses aggregate-load-balance;
       }
       container bfd-liveness-detection {
         junos:must "(!(\".. lacp fast-failover\"))";
         junos:must-message "BFD not supported with lacp with fast-failover mode";
         junos:must "(!(\".. lacp link-protection\"))";
         junos:must-message "BFD not supported with lacp link protection";
         junos:must "(!(\".. link-protection\"))";
         junos:must-message "BFD not supported with link protection";
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             junos:must "(\".. algorithm\")";
             junos:must-message "May not be configured without algorithm";
             junos:must "(\"security authentication-key-chains key-chain $$\")";
             junos:must-message "Referenced key-chain must be defined";
             type string;
           }
           leaf algorithm {
             description "Algorithm name";
             junos:must "(\".. key-chain\")";
             junos:must-message "May not be configured without key-chain";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         container damping {
           description "BFD flap damping parameters";
           uses apply-advanced;
           leaf suppress {
             description "Suppress threshold for figure-of-merit value";
             default "5000";
             type union {
               type string {
                 pattern "<.*>|$.*";
               }
               type uint32 {
                 range "1000 .. 200000";
               }
             }
           }
           leaf reuse {
             description "Reuse threshold for figure-of-merit value";
             default "1000";
             type union {
               type string {
                 pattern "<.*>|$.*";
               }
               type uint32 {
                 range "1000 .. 200000";
               }
             }
           }
           leaf max-suppress-time {
             description "Maximum hold-down time";
             default "600";
             units "seconds";
             type union {
               type string {
                 pattern "<.*>|$.*";
               }
               type uint32 {
                 range "1 .. 20000";
               }
             }
           }
           leaf half-life-interval {
             description "Decay half life interval";
             default "30";
             units "seconds";
             type union {
               type string {
                 pattern "<.*>|$.*";
               }
               type uint32 {
                 range "1 .. 600";
               }
             }
           }
           leaf increment {
             description "Increments applied to figure-of-merit value for every flap";
             default "1000";
             type union {
               type string {
                 pattern "<.*>|$.*";
               }
               type uint32 {
                 range "1000 .. 20000";
               }
             }
           }
         }
         leaf neighbor {
           description "BFD neighbor address";
           type jt:ipaddr;
         }
         leaf local-address {
           description "BFD local address";
           type jt:ipaddr;
         }
         leaf holddown-interval {
           description "Time to hold the session-UP notification to the client";
           units "milliseconds";
           type union {
             type string {
               pattern "<.*>|$.*";
             }
             type uint32 {
               range "0 .. 255000";
             }
           }
         }
       }
       leaf minimum-links {
         description "Minimum number of aggregated links";
         junos:must "(!(\"interfaces ${interface} aggregated-ether-options link-speed mixed\"))";
         junos:must-message "Minimum-links option is not compatible with link-speed mixed";
         type union {
           type string {
             pattern "<.*>|$.*";
           }
           type uint16;
         }
       }
       leaf no-unsecure-links {
         description "Don't allow MACSEC unsecure links under AE";
         type empty;
       }
       container minimum-bandwidth {
         presence "enable minimum-bandwidth";
         junos:must "(!(\"interfaces ${interface}  aggregated-ether-options optimize-aggregate-frr\"))";
         junos:must-message "Minimum-bandwidth and optimize-aggregate-frr are mutually exclusive";
         junos:must "(!(\"interfaces ${interface}  aggregated-ether-options minimum-links\"))";
         junos:must-message "Minimum-bandwidth and minimum-links are mutually exclusive";
         description "Minimum bandwidth configured for aggregated bundle";
         uses apply-advanced;
         leaf bw-value {
           description "Bandwidth value";
           default "1";
           type union {
             type uint64;
             type string {
               pattern "<.*>|$.*";
             }
           }
         }
         leaf bw-unit {
           description "Bandwidth unit";
           type enumeration {
             enum "bps" {
               description "Links are in bits per sec";
             }
             enum "kbps" {
               description "Links are in kilo bits per sec";
             }
             enum "mbps" {
               description "Links are in mega bits per sec";
             }
             enum "gbps" {
               description "Links are in giga bits per sec ";
             }
           }
         }
       }
       choice redundancy_choice {
         case case_1 {
         }
         case case_2 {
         }
       }
       container rebalance-periodic {
         uses apply-advanced;
       }
       leaf link-speed {
         description "Link speed of individual interface that joins the AE";
         type enumeration {
           enum "10m" {
             description "Links are 10M";
           }
           enum "100m" {
             description "Links are 100M";
           }
           enum "1g" {
             description "Links are 1G";
           }
           enum "2.5g" {
             description "Links are 2.5G";
           }
           enum "5g" {
             description "Links are 5G";
           }
           enum "8g" {
             description "Links are 8G";
           }
           enum "10g" {
             description "Links are 10G";
           }
           enum "25g" {
             description "Links are 25G";
           }
           enum "40g" {
             description "Links are 40G";
           }
           enum "50g" {
             description "Links are 50G";
           }
           enum "80g" {
             description "Links are 80G";
           }
           enum "100g" {
             description "Links are 100G";
           }
           enum "200g" {
             description "Links are 200G";
           }
           enum "400g" {
             description "Links are 400G";
           }
           enum "800g" {
             description "Links are 800G";
           }
           enum "oc192" {
             description "Links are OC-192";
           }
           enum "mixed" {
             description "Links are various speeds";
             junos:must "(!(\"interfaces ${interface} per-unit-scheduler\"))";
             junos:must-message "per-unit-scheduler is incompatible with link-speed mixed";
             junos:must "(!(\".. resilient-hash\"))";
             junos:must-message "Mixed-rate AE is not supported along with Resilient Hashing  mode";
             junos:must "(!(\".. load-balance adaptive\"))";
             junos:must-message "Mixed-rate AE is not supported along with Adaptive Load balance mode";
           }
         }
       }
       container local-bias {
         presence "enable local-bias";
         description "Turn on local bias functionality";
         uses apply-advanced;
         leaf disable {
           description "Disable local-bias";
           type empty;
         }
       }
       leaf local-minimum-links-threshold {
         description "Specify threshold for minimum links per VC/VCF member";
         type union {
           type string {
             pattern "<.*>|$.*";
           }
           type uint16 {
             range "1 .. 100";
           }
         }
       }
       leaf resilient-hash {
         description "Turn on resilient-hash";
         junos:must "(!(\".. dlb\"))";
         junos:must-message "Resilient-hash AE is not supported along with Dynamic Load Balancing AE";
         junos:must "(!(\"link-speed mixed\"))";
         junos:must-message "Resilient-hash AE is not supported along with Mixed-rate mode";
         junos:must "(!(\"load-balance per-packet\"))";
         junos:must-message "Resilient-hash AE is not supported along with Per-Packet Load balance mode";
         junos:must "(!(\"load-balance adaptive\"))";
         junos:must-message "Resilient-hash AE is not supported along with Adaptive Load balance mode";
         type empty;
       }
       container dlb {
         junos:must "(!(\"virtual-chassis\"))";
         junos:must-message "DLB not supported on VC";
         junos:must "(!(\".. resilient-hash\"))";
         junos:must-message "Dynamic Load Balancing AE is not supported along with resilient hash";
         description "Enable DLB on LAG";
         uses apply-advanced;
         choice mode {
           case case_1 {
             leaf per-packet {
               description "Per-packet link assignment";
               type empty;
             }
           }
           case case_2 {
             leaf assigned-flow {
               description "Fixed link assignment";
               type empty;
             }
           }
           case case_3 {
             container flowlet {
               presence "enable flowlet";
               description "Inactivity-based link assignment";
               uses apply-advanced;
               leaf inactivity-interval {
                 description " Minimum inactivity interval in micro-seconds for link re-assignment";
                 default "256";
                 type union {
                   type string {
                     pattern "<.*>|$.*";
                   }
                   type uint32;
                 }
               }
             }
           }
         }
       }
       container lacp {
         description "Link Aggregation Control Protocol configuration";
         uses apply-advanced;
         choice mode {
           case case_1 {
             leaf active {
               description "Initiate transmission of LACP packets";
               type empty;
             }
           }
           case case_2 {
             leaf passive {
               description "Respond to LACP packets";
               type empty;
             }
           }
         }
         leaf periodic {
           description "Timer interval for periodic transmission of LACP packets";
           type enumeration {
             enum "fast" {
               description "Receive packets every second";
             }
             enum "slow" {
               description "Receive packets every 30 seconds";
             }
           }
         }
         leaf multiplier {
           description "LACP timeout detection multiplier";
           type union {
             type string {
               pattern "<.*>|$.*";
             }
             type uint32 {
               range "3 .. 30";
             }
           }
         }
         leaf fast-failover {
           description "To turn on LACP fast-failover";
           type empty;
         }
         container link-protection {
           presence "enable link-protection";
           junos:must "(!(\".. .. link-protection\"))";
           junos:must-message "LACP and non LACP based link-protection not allowed together";
           uses apply-advanced;
           leaf disable {
             description "To turn off LACP link-protection";
             type empty;
           }
           choice mode {
             case case_1 {
               leaf revertive {
                 description "Switch links when better priority link comes up";
                 type empty;
               }
             }
             case case_2 {
               leaf non-revertive {
                 description "Do not switch links when better priority link comes up";
                 type empty;
               }
             }
           }
           container rtg-config {
             presence "enable rtg-config";
             description "RTG Feature enable on AE";
             uses apply-advanced;
             leaf preempt-cutover-timer {
               description "RTG preempt-cutover-timer in seconds";
               default "1";
               type union {
                 type string {
                   pattern "<.*>|$.*";
                 }
                 type uint32 {
                   range "0 .. 255";
                 }
               }
             }
           }
         }
         leaf sync-reset {
           description "On minimum-link failure notify out of sync to peer";
           type enumeration {
             enum "disable" {
               description "To disable minimum-link failure handling at LACP level";
             }
             enum "enable" {
               description "To enable minimum-link failure handling at LACP level";
             }
           }
         }
         leaf system-priority {
           description "Priority of the system (0 ... 65535)";
           type string;
         }
         leaf system-id {
           description "Node's System ID, encoded as a MAC address";
           type jt:mac-addr;
         }
         leaf admin-key {
           description "Node's administrative key";
           type union {
             type uint16;
             type string {
               pattern "<.*>|$.*";
             }
           }
         }
         container hold-time {
           junos:cli-feature "oneliner";
           description "Hold time for link up and link down for AE link members";
           leaf up {
             description "Link up hold time for the AE link members";
             units "seconds";
             type union {
               type string {
                 pattern "<.*>|$.*";
               }
               type uint16 {
                 range "1 .. 6000";
               }
             }
           }
         }
         leaf aggregate-wait-time {
           description "Aggregate wait time for the AE";
           units "seconds";
           type union {
             type string {
               pattern "<.*>|$.*";
             }
             type uint16 {
               range "0 .. 1800";
             }
           }
         }
         leaf force-up {
           description "Forceup AE interface with LACP";
           type empty;
         }
         leaf no-peer-loopback-validation {
           description "Skip MCLAG peer loop back validation for LACP PDUs on Forceup AE interface";
           junos:must "(\".. force-up\")";
           junos:must-message "LACP force-up must be configured for no-peer-loopback-validation";
           junos:must "(\".. .. mc-ae\")";
           junos:must-message "MC-AE must be configured for no-peer-loopback-validation";
           type empty;
         }
       }
       list link-protection-sub-group {
         key name;
         ordered-by user;
         description "Link Protection subgroup configuration";
         leaf name {
           description "Name of the subgroup";
           junos:cli-feature "nokeyword";
           type string {
             length "2 .. 64";
           }
         }
         uses apply-advanced;
         choice type {
           case case_1 {
             leaf primary {
               description "Primary subgroup for N:N link-protection mode";
               type empty;
             }
           }
           case case_2 {
             leaf backup {
               description "Backup subgroup for N:N link-protection mode";
               type empty;
             }
           }
         }
       }
       container ethernet-switch-profile {
         description "Ethernet virtual LAN/media access control-level options";
         uses apply-advanced;
         leaf-list tag-protocol-id {
           ordered-by user;
           description "IEEE 802.1q Tag Protocol Identifier values for VLAN-tagged frames";
           type string;
         }
         container storm-control {
           junos:cli-feature "oneliner-plus";
           description "Storm control profile name to bind";
           uses apply-advanced;
           leaf profile-name {
             description "Profile name";
             junos:cli-feature "nokeyword";
             junos:must "(\"forwarding-options storm-control-profiles $$\")";
             junos:must-message "Storm profile name must be defined in the [edit forwarding-options storm-control-profiles] hierarchy";
             type string;
           }
         }
         container recovery-timeout {
           junos:cli-feature "oneliner";
           description "Recovery timeout for this interface";
           leaf time-in-seconds {
             junos:cli-feature "nokeyword";
             units "seconds";
             type union {
               type string {
                 pattern "<.*>|$.*";
               }
               type uint32 {
                 range "10 .. 3600";
               }
             }
           }
         }
         leaf mac-learn-enable {
           description "Learn MAC addresses dynamically";
           type empty;
         }
       }
       container mc-ae {
         junos:must "(!((\".. link-protection\" || \".. lacp link-protection\")))";
         junos:must-message "MC-AE and link-protection on AE can not co-exist";
         junos:must "(\".. lacp admin-key\")";
         junos:must-message "LACP admin-key must be configured for MC-AE";
         junos:must "(\".. lacp system-id\")";
         junos:must-message "LACP system-id must be configured for MC-AE";
         junos:must "(!(\".. .. encapsulation vlan-ccc\"))";
         junos:must-message "Encapsulation vlan-ccc is not supported with MC-AE";
         description "Multi-chassis aggregation (MC-AE) network device configuration";
         uses apply-advanced;
         leaf mc-ae-id {
           description "MC-AE group id";
           junos:must "(unique \"interfaces <*>  aggregated-ether-options mc-ae mc-ae-id $$\")";
           junos:must-message "MC-AE id alredy being used";
           type union {
             type string {
               pattern "<.*>|$.*";
             }
             type uint16 {
               range "1 .. 65535";
             }
           }
         }
         leaf redundancy-group {
           description "Redundancy group id";
           default "1";
           junos:must "((any \"protocols iccp peer <*> redundancy-group-id-list $$\" || any \"logical-systems <*> protocols iccp peer <*> redundancy-group-id-list $$\"))";
           junos:must-message "The redundancy group must match with one defined at <protocols iccp peer redundancy-group-id-list>";
           type union {
             type string {
               pattern "<.*>|$.*";
             }
             type uint32 {
               range "1 .. 4294967294";
             }
           }
         }
         leaf chassis-id {
           description "Chassis id of MC-AE network device";
           type union {
             type string {
               pattern "<.*>|$.*";
             }
             type uint16 {
               range "0 .. 1";
             }
           }
         }
         leaf mode {
           description "Mode of the MC-AE";
           type enumeration {
             enum "active-active" {
               description "MC-AE in active-active mode";
               junos:must "(!(any \"interfaces ${interface} unit <*> family inet6\"))";
               junos:must-message "family inet6 is not supported with MC-AE active-active";
               junos:must "(!(any \"interfaces ${interface} unit <*> family inet\"))";
               junos:must-message "family inet is not supported with MC-AE active-active";
             }
           }
         }
         leaf status-control {
           description "Status of the MC-AE chassis";
           type enumeration {
             enum "active" {
               description "Chassis is Active";
             }
             enum "standby" {
               description "Chassis is Standby";
             }
           }
         }
         leaf switchover-mode {
           description "Switchover mode";
           type enumeration {
             enum "revertive" {
               description "Switch mcae node when preferred link comes up";
               junos:must "(\".. .. mc-ae mode active-standby\")";
               junos:must-message "Only Supported in Active-Standby mode.";
               junos:must "(!(\".. .. mc-ae status-control standby\"))";
               junos:must-message "Supported only when status control is Active";
             }
             enum "non-revertive" {
               description "Do not switch mcae node when preferred link comes up";
               junos:must "(\".. .. mc-ae mode active-standby\")";
               junos:must-message "Only Supported in Active-Standby mode.";
               junos:must "(\".. .. mc-ae status-control active\")";
               junos:must-message "Supported only when status control is Active";
             }
           }
         }
         leaf revert-time {
           description "Wait interval before performing switchover";
           default "3";
           units "minute";
           junos:must "(\".. .. mc-ae mode active-standby\")";
           junos:must-message "Only Supported in Active-Standby mode.";
           junos:must "(\".. .. mc-ae status-control active\")";
           junos:must-message "Supported only when status control is Active";
           type union {
             type string {
               pattern "<.*>|$.*";
             }
             type uint32 {
               range "1 .. 10";
             }
           }
         }
         leaf init-delay-time {
           description "Init delay timer for mcae sm for min traffic loss";
           units "seconds";
           type union {
             type string {
               pattern "<.*>|$.*";
             }
             type uint16 {
               range "1 .. 6000";
             }
           }
         }
         leaf recovery-delay-time {
           description "Delay timer for bringing up ICL, ICCP";
           units "seconds";
           type union {
             type string {
               pattern "<.*>|$.*";
             }
             type uint16 {
               range "1 .. 6000";
             }
           }
         }
         leaf enhanced-convergence {
           description "Optimized convergence time for mcae";
           junos:must "(\".. .. mc-ae mode active-active\")";
           junos:must-message "Only Supported in MCAE active-active mode.";
           type empty;
         }
         container events {
           presence "enable events";
           description "MCAE related events";
           uses apply-advanced;
           container iccp-peer-down {
             presence "enable iccp-peer-down";
             description "Define behavior in the event of ICCP peer down";
             uses apply-advanced;
             leaf force-icl-down {
               description "Bring down ICL logical interface";
               type empty;
             }
             leaf prefer-status-control-active {
               description "Keep this node up (recommended only on status-control active)";
               type empty;
             }
           }
         }
       }
     }
     container es-options {
       description "ES PIC interface-specific options";
       uses apply-advanced;
       leaf backup-interface {
         description "Name of backup interface";
         type union {
           type jt:interface-device;
           type string {
             pattern "<.*>|$.*";
           }
         }
       }
     }
     container vdsl-options {
       description "VDSL interface-specific options";
       uses apply-advanced;
       leaf vdsl-profile {
         description "VDSL profile";
         type enumeration {
           enum "auto" {
             description "Auto";
           }
           enum "8a" {
             description "Profile 8a";
           }
           enum "8b" {
             description "Profile 8b";
           }
           enum "8c" {
             description "Profile 8c";
           }
           enum "8d" {
             description "Profile 8d";
           }
           enum "12a" {
             description "Profile 12a";
           }
           enum "12b" {
             description "Profile 12b";
           }
           enum "17a" {
             description "Profile 17a";
           }
         }
       }
       leaf sra {
         description "DSL SRA";
         default "disable";
         type enumeration {
           enum "enable" {
             description "Enable SRA";
           }
           enum "disable" {
             description "Disable SRA";
           }
         }
       }
       leaf v43 {
         description "DSL V43 tones";
         default "enable";
         type enumeration {
           enum "enable" {
             description "Enable V43";
           }
           enum "disable" {
             description "Disable V43";
           }
         }
       }
       leaf sos {
         description "Enable SOS";
         type empty;
       }
     }
     container dsl-sfp-options {
       description "DSL SFP options";
       uses apply-advanced;
       container adsl-options {
         description "ADSL options";
         uses apply-advanced;
         leaf vpi {
           description "Virtual path identifier";
           junos:must "(\".. vci\")";
           junos:must-message "vci must be specified";
           type union {
             type string {
               pattern "<.*>|$.*";
             }
             type uint32 {
               range "0 .. 255";
             }
           }
         }
         leaf vci {
           description "Virtual circuit identifier";
           junos:must "(\".. vpi\")";
           junos:must-message "vpi must be specified";
           type union {
             type string {
               pattern "<.*>|$.*";
             }
             type uint32 {
               range "32 .. 65535";
             }
           }
         }
         leaf encap {
           description "Encapsulation";
           junos:must "((\".. vci\" && \".. vpi\"))";
           junos:must-message "vci and vpi must be specified";
           type enumeration {
             enum "bypass" {
               description "Bypass";
             }
             enum "llcsnap-bridged-802dot1q" {
               description "LLCSNAP bridged 802.1q";
             }
             enum "llcsnap-routed-ip" {
               description "LLCSNAP routed ip";
             }
             enum "vc-mux-bridged" {
               description "VC MUX bridged";
             }
             enum "vc-mux-routed-ip" {
               description "VC MUX routed ip";
             }
             enum "generic" {
               description "Generic";
             }
           }
         }
         leaf annex {
           description "Annex type";
           junos:must "((\".. vci\" && \".. vpi\"))";
           junos:must-message "vci and vpi must be specified";
           type enumeration {
             enum "auto" {
               description "Annex type auto";
             }
             enum "annexj-off" {
               description "Annex type annexj turn off";
             }
           }
         }
       }
       container vdsl-options {
         description "VDSL options";
         uses apply-advanced;
         leaf profile {
           description "VDSL profile";
           type enumeration {
             enum "auto" {
               description "Automatic";
             }
             enum "8a" {
               description "Profile 8a";
             }
             enum "8b" {
               description "Profile 8b";
             }
             enum "8c" {
               description "Profile 8c";
             }
             enum "8d" {
               description "Profile 8d";
             }
             enum "12a" {
               description "Profile 12a";
             }
             enum "12b" {
               description "Profile 12b";
             }
             enum "17a" {
               description "Profile 17a";
             }
             enum "30a" {
               description "Profile 30a";
             }
           }
         }
         leaf carrier {
           description "Carrier setting";
           type enumeration {
             enum "auto" {
               description "Automatic";
             }
             enum "a43" {
               description "Carrier A43";
             }
             enum "b43" {
               description "Carrier B43";
             }
           }
         }
       }
       container gfast-options {
         description "G.fast options";
         uses apply-advanced;
         leaf carrier {
           description "Carrier setting";
           type enumeration {
             enum "a43" {
               description "Carrier A43";
             }
             enum "a43c" {
               description "Carrier A43C";
             }
             enum "b43" {
               description "Carrier B43";
             }
             enum "b43c" {
               description "Carrier B43C";
             }
           }
         }
       }
     }
     container shdsl-options {
       junos:must "(!(\"interfaces ${interface} vdsl-options\"))";
       junos:must-message "VDSL options cannot co-exist with SHDSL options on the same interface";
       junos:must "(!(\"interfaces ${interface} dsl-options\"))";
       junos:must-message "DSL options cannot co-exist with SHDSL options on the same interface";
       description "SHDSL interface-specific options";
       uses apply-advanced;
       leaf annex {
         description "Type of SHDSL annex";
         default "annex-b";
         type enumeration {
           enum "annex-a" {
             description "Annex-a PIC";
           }
           enum "annex-b" {
             description "Annex-b PIC";
           }
           enum "annex-f" {
             description "Annex-f PIC";
           }
           enum "annex-g" {
             description "Annex-g PIC";
           }
           enum "annex-auto" {
             description "Annex-auto PIC";
           }
         }
       }
       leaf line-rate {
         description "SHDSL line rate";
         type string;
       }
       leaf loopback {
         description "Loopback mode";
         type enumeration {
           enum "local" {
             description "Local loopback";
           }
           enum "remote" {
             description "Remote loopback";
           }
         }
       }
       container snr-margin {
         presence "enable snr-margin";
         description "Signal to noise ratio margin";
         uses apply-advanced;
         leaf current {
           description "Current signal to noise ratio margin";
           units "dB";
           type string;
         }
         leaf snext {
           description "SNEXT signal to noise ratio margin";
           units "dB";
           type string;
         }
       }
     }
     container container-options {
       description "Container interface specific options";
       uses apply-advanced;
       container container-type {
         presence "enable container-type";
         description "Protocol type of the container interface";
         uses apply-advanced;
         choice container-type-choice {
           case case_1 {
             container aps {
               description "APS options on the container";
               presence "enable aps";
               junos:must "((\".. .. member-interface-type sonet\" || (\".. .. member-interface-type atm\" || (\".. .. member-interface-type channelized-sonet\" || \".. .. member-interface-type channelized-sdh\"))))";
               junos:must-message "APS can be enabled on Sonet, Channelized-Sonet, Channelized-SDH  or ATM interfaces only";
               uses aps_type;
             }
           }
         }
       }
       container member-interface-type {
         description "Link type of members of container";
         uses apply-advanced;
         choice member_interface_type_choice {
           case case_1 {
             container sonet {
               uses apply-advanced;
               leaf member-interface-speed {
                 description "Link speed of members of container";
                 type enumeration {
                   enum "oc3" {
                     description "Links are OC-3";
                   }
                   enum "oc12" {
                     description "Links are OC-12";
                   }
                   enum "oc48" {
                     description "Links are OC-48";
                   }
                   enum "oc192" {
                     description "Links are OC-192";
                   }
                   enum "oc768" {
                     description "Links are OC-768";
                   }
                   enum "mixed" {
                     description "Links are of different speeds";
                   }
                 }
               }
             }
           }
           case case_2 {
             container atm {
               uses apply-advanced;
               leaf member-interface-speed {
                 description "Link speed of members of container";
                 type enumeration {
                   enum "oc3" {
                     description "Links are OC-3";
                   }
                   enum "oc12" {
                     description "Links are OC-12";
                   }
                   enum "oc48" {
                     description "Links are OC-48";
                   }
                 }
               }
             }
           }
           case case_3 {
             container channelized-sonet {
               uses apply-advanced;
               leaf member-interface-speed {
                 description "Link speed of members of container";
                 type enumeration {
                   enum "coc3" {
                     description "Links are COC-3";
                   }
                   enum "coc12" {
                     description "Links are COC-12";
                   }
                   enum "coc48" {
                     description "Links are COC-48";
                   }
                   enum "coc192" {
                     description "Links are COC-192";
                   }
                   enum "coc768" {
                     description "Links are COC-768";
                   }
                 }
               }
             }
           }
           case case_4 {
             container channelized-sdh {
               uses apply-advanced;
               leaf member-interface-speed {
                 description "Link speed of members of container";
                 type enumeration {
                   enum "cstm1" {
                     description "Links are cstm-1";
                   }
                   enum "cstm4" {
                     description "Links are cstm-4";
                   }
                   enum "cstm16" {
                     description "Links are cstm-16";
                   }
                   enum "coc64" {
                     description "Links are cstm-64";
                   }
                   enum "cstm256" {
                     description "Links are cstm256";
                   }
                 }
               }
             }
           }
         }
       }
       container redundancy {
         description "Container interface redundancy options";
         uses apply-advanced;
         container hold-time {
           junos:cli-feature "oneliner";
           description "Hold time for link up and link down";
           leaf up {
             description "Link up hold time";
             units "milliseconds";
             type union {
               type string {
                 pattern "<.*>|$.*";
               }
               type uint32 {
                 range "0 .. 65534";
               }
             }
           }
           leaf down {
             description "Link down hold time";
             units "milliseconds";
             type union {
               type string {
                 pattern "<.*>|$.*";
               }
               type uint32 {
                 range "0 .. 65534";
               }
             }
           }
         }
       }
       leaf-list container-list {
         ordered-by user;
         description "List of container interfaces this member link is associated to";
         type union {
           type jt:interface-device;
           type string {
             pattern "<.*>|$.*";
           }
         }
       }
       choice redundancy-type {
         case case_1 {
           choice aps-redundancy {
             case case_1 {
               leaf primary {
                 description "This member link is primary interface of the container";
                 type empty;
               }
             }
             case case_2 {
               leaf standby {
                 description "This member link is standby interface of the container";
                 type empty;
               }
             }
           }
         }
       }
       leaf fast-aps {
         description "Fast APS switch";
         type empty;
       }
       leaf allow-configuration-override {
         description "Allow physical configuration of member link to override container configuration";
         type empty;
       }
     }
     container layer2-policer {
       description "Layer2 policing for interface";
       uses apply-advanced;
       choice layer2-input-policer-choice {
         case case_1 {
           leaf input-policer {
             description "Two-color policer for received packets";
             junos:must "(!(\"firewall policer $$ then forwarding-class\"))";
             junos:must-message "Forwarding class cannot be modified for Layer 2 policer";
             junos:must "(!(\"firewall policer $$ then loss-priority medium-low\"))";
             junos:must-message "Loss priority 'medium-low' is not valid for Layer 2 policer";
             junos:must "(!(\"firewall policer $$ then loss-priority low\"))";
             junos:must-message "Loss priority 'low' is not valid for Layer 2 policer";
             junos:must "(\"firewall policer $$ physical-interface-policer\")";
             junos:must-message "Layer 2 policer must be a physical interface policer";
             type string;
           }
         }
         case case_2 {
           leaf input-hierarchical-policer {
             description "Hierarchical policer for received packets";
             type string;
           }
         }
       }
     }
     list unit {
       key name;
       description "Logical interface";
       leaf name {
         junos:cli-feature "nokeyword";
         type string;
       }
       uses apply-advanced;
       leaf interface-tag {
         description "Interface tag name";
         type string {
           length "1 .. 64";
           junos:posix-pattern "^[A-Za-z0-9][_0-9A-Za-z-]*$";
           junos:pattern-message "Must be a non-reserved string of 64 characters or less";
         }
       }
       container policer-overhead {
         description "Policer overhead adjustment for this unit";
         uses apply-advanced;
         leaf policer-overhead-value {
           description "Policer overhead bytes to be accounted in ingress and egress";
           junos:cli-feature "nokeyword";
           units "bytes";
           junos:must "((!(\".. ingress\") && !(\".. egress\")))";
           junos:must-message "Do not use the options ingress or egress when adjust values are specified";
           type union {
             type string {
               pattern "<.*>|$.*";
             }
             type int32;
           }
         }
         leaf ingress {
           description "Ingress value in bytes";
           units "bytes";
           type union {
             type string {
               pattern "<.*>|$.*";
             }
             type int32 {
               range "-64 .. 64";
             }
           }
         }
         leaf egress {
           description "Egress value in bytes";
           units "bytes";
           type union {
             type string {
               pattern "<.*>|$.*";
             }
             type int32 {
               range "-64 .. 64";
             }
           }
         }
       }
       leaf alias {
         description "Interface alias";
         junos:must "(!(\"interfaces interface-range $$\"))";
         junos:must-message "Interface alias cannot be an existing interface range name";
         type string;
       }
       leaf enhanced-convergence {
         description "Optimize convergence time for L3";
         type empty;
       }
       leaf proxy-macip-advertisement {
         description "Proxy advertisement of type 2 MAC+IP route for EVPN";
         type empty;
       }
       leaf virtual-gateway-accept-data {
         description "Accept packets destined for virtual gateway address";
         type empty;
       }
       container peer-psd {
         presence "enable peer-psd";
         junos:cli-feature "oneliner";
         description "Peer psd";
         leaf psd-name {
           description "Peer psd name";
           junos:cli-feature "nokeyword";
           junos:must "(\".. .. peer-interface\")";
           junos:must-message "peer-interface must be configured on this interface";
           type string;
         }
       }
       container peer-interface {
         presence "enable peer-interface";
         junos:cli-feature "oneliner-plus";
         description "Peer interface";
         uses apply-advanced;
         leaf interface-name {
           description "Peer interface name";
           junos:cli-feature "nokeyword";
           junos:must "((\".. .. peer-psd\" || \"interfaces $$-IFL peer-interface\"))";
           junos:must-message "Peer interface or peer psd must be configured";
           type union {
             type jt:interface-unit;
             type string {
               pattern "<.*>|$.*";
             }
           }
         }
       }
       container interface-shared-with {
         presence "enable interface-shared-with";
         junos:must "(\"chassis system-domains\")";
         junos:must-message "Chassis system-domains must be configured";
         junos:cli-feature "oneliner-plus";
         description "Specify which PSD owns this logical interface";
         uses apply-advanced;
         leaf psd-name {
           description "Name of protected system domain (psd[1-31], ex. psd2)";
           junos:cli-feature "nokeyword";
           type string {
             junos:posix-pattern "^psd([1-9]|[1-2][0-9]|[3][0-1])$";
             junos:pattern-message "Protected system domain name is a string consisting of \'psd\' follows by the PSD ID (1-31), ex. psd2";
           }
         }
       }
       choice enable-disable {
         case case_1 {
           leaf disable {
             description "Disable this logical interface";
             type empty;
           }
         }
       }
       leaf extended-telemetry {
         description "Enable extended telemetry";
         type empty;
       }
       leaf passive-monitor-mode {
         description "Use interface to tap packets from another router";
         type empty;
       }
       container account-layer2-overhead {
         presence "enable account-layer2-overhead";
         description "Account layer2 overhead in IFL byte statistics";
         uses apply-advanced;
         leaf overhead-value {
           description "Layer2 overhead bytes to be accounted in ingress and egress";
           junos:cli-feature "nokeyword";
           units "bytes";
           junos:must "((!(\".. ingress\") && !(\".. egress\")))";
           junos:must-message "Do not use the options ingress or egress when adjust values are specified";
           type union {
             type string {
               pattern "<.*>|$.*";
             }
             type int8 {
               range "-128 .. 127";
             }
           }
         }
         leaf ingress {
           description "Layer2 overhead bytes to be accounted in ingress";
           units "bytes";
           type union {
             type string {
               pattern "<.*>|$.*";
             }
             type int8 {
               range "-128 .. 127";
             }
           }
         }
         leaf egress {
           description "Layer2 overhead bytes to be accounted in egress";
           units "bytes";
           type union {
             type string {
               pattern "<.*>|$.*";
             }
             type int8 {
               range "-128 .. 127";
             }
           }
         }
       }
       leaf clear-dont-fragment-bit {
         description "Clear DF bit in packet (AS PIC and J-series only as well as MIF)";
         type empty;
       }
       leaf description {
         description "Text description of interface";
         type string;
       }
       leaf metadata {
         description "Text metadata attached to interface";
         type string;
       }
       leaf encapsulation {
         description "Logical link-layer encapsulation";
         type enumeration {
           enum "atm-nlpid" {
             description "ATM NLPID encapsulation";
           }
           enum "atm-cisco-nlpid" {
             description "Cisco-compatible ATM NLPID encapsulation";
           }
           enum "atm-snap" {
             description "ATM LLC/SNAP encapsulation";
           }
           enum "atm-vc-mux" {
             description "ATM VC multiplexing";
           }
           enum "atm-ccc-vc-mux" {
             description "ATM VC for CCC";
           }
           enum "atm-tcc-vc-mux" {
             description "ATM VC for translational cross-connect";
           }
           enum "atm-tcc-snap" {
             description "ATM LLC/SNAP for translational cross-connect";
           }
           enum "atm-ccc-cell-relay" {
             description "ATM cell relay for CCC";
           }
           enum "vlan-vci-ccc" {
             description "CCC for VLAN Q-in-Q and ATM VPI/VCI interworking";
           }
           enum "ether-over-atm-llc" {
             description "Ethernet over ATM (LLC/SNAP) encapsulation";
           }
           enum "ether-vpls-over-atm-llc" {
             description "Ethernet VPLS over ATM (bridging) encapsulation";
           }
           enum "ppp-over-ether-over-atm-llc" {
             description "PPPoE over ATM (LLC/SNAP) encapsulation";
           }
           enum "ppp-over-ether" {
             description "PPPoE encapsulation";
             junos:must "(!(\".. family\"))";
             junos:must-message "Can't configure protocol family with encapsulation ppp-over-ether";
           }
           enum "atm-ppp-vc-mux" {
             description "ATM PPP over raw AAL5";
           }
           enum "atm-ppp-llc" {
             description "ATM PPP over AAL5/LLC";
           }
           enum "atm-ppp-funi" {
             description "ATM PPP over FUNI";
           }
           enum "atm-mlppp-llc" {
             description "ATM MLPPP over AAL5/LLC";
           }
           enum "frame-relay-ppp" {
             description "PPP over Frame Relay";
             junos:must "(!(\".. family inet6\"))";
             junos:must-message "family inet6 is not supported on encapsulation frame-relay-ppp";
             junos:must "(!(\".. family inet\"))";
             junos:must-message "family inet is not supported on encapsulation frame-relay-ppp";
             junos:must "(\".. .. encapsulation frame-relay\")";
             junos:must-message "Physical link-layer encapsulation must be frame-relay";
           }
           enum "frame-relay-ccc" {
             description "Frame Relay DLCI for CCC";
           }
           enum "frame-relay" {
             description "Frame Relay DLCI";
           }
           enum "frame-relay-tcc" {
             description "Frame Relay DLCI for translational cross-connect";
           }
           enum "frame-relay-ether-type" {
             description "Cisco-compatible Frame Relay Encapsulation DLCI";
             junos:must "((\".. .. encapsulation flexible-frame-relay\" || (\".. .. encapsulation frame-relay-ether-type\" || \".. .. encapsulation frame-relay-ether-type-tcc\")))";
             junos:must-message "Interface encapsulation must be cisco-compatible or flexible frame relay";
           }
           enum "frame-relay-ether-type-tcc" {
             description "Cisco-compatible Frame Relay Encapsulation DLCI for TCC";
           }
           enum "ether-vpls-fr" {
             description "Ethernet VPLS over Frame Relay (bridging) encapsulation";
           }
           enum "vlan-ccc" {
             description "802.1q tagging for a cross-connect";
           }
           enum "ethernet-ccc" {
             description "Ethernet for a cross-connect";
           }
           enum "vlan-vpls" {
             description "VLAN virtual private LAN service";
           }
           enum "vlan-bridge" {
             description "VLAN layer-2 bridging";
           }
           enum "ethernet-tcc" {
             description "Ethernet translational cross-connect";
           }
           enum "dix" {
             description "Ethernet DIXv2 (RFC 894)";
           }
           enum "ethernet" {
             description "Ethernet II (RFC 894)";
           }
           enum "ethernet-vpls" {
             description "Ethernet II virtual private LAN service";
           }
           enum "ethernet-bridge" {
             description "Ethernet II bridging";
           }
           enum "vlan" {
             description "802.1q-tagged Ethernet";
           }
           enum "vlan-tcc" {
             description "802.1q tagging for a translational cross-connect";
           }
           enum "multilink-ppp" {
             description "Multilink PPP";
           }
           enum "multilink-frame-relay-end-to-end" {
             description "Multilink Frame Relay end-to-end (FRF.15)";
           }
           enum "ppp-ccc" {
             description "Serial PPP device for a cross-connect";
           }
         }
       }
       leaf mtu {
         description "Maximum transmission unit packet size";
         type union {
           type string {
             pattern "<.*>|$.*";
           }
           type uint32;
         }
       }
       choice pointedness {
         case case_1 {
           leaf point-to-point {
             description "Point-to-point connection";
             type empty;
           }
         }
         case case_2 {
           leaf multipoint {
             description "Multipoint connection";
             type empty;
           }
         }
       }
       leaf bandwidth {
         description "Logical unit bandwidth (informational only)";
         type string;
       }
       leaf global-layer2-domainid {
         description "Global Layer-2 Identifier for this interface";
         type union {
           type string {
             pattern "<.*>|$.*";
           }
           type uint32 {
             range "5 .. 4094";
           }
         }
       }
       choice traps-choice {
         leaf traps {
           description "Enable SNMP notifications on state changes";
           type empty;
         }
         leaf no-traps {
           description "Don't enable SNMP notifications on state changes";
           type empty;
         }
       }
       choice routing-services-choice {
         leaf routing-services {
           description "Enable routing services";
           status deprecated;
           type empty;
         }
         leaf no-routing-services {
           description "Don't enable routing services";
           status deprecated;
           type empty;
         }
       }
       container routing-service {
         description "Routing Services on this interface";
         uses apply-advanced;
         choice enable-disable {
           case case_1 {
             leaf enable {
               description "Enable Routing Service";
               type empty;
             }
           }
           case case_2 {
             leaf disable {
               description "Disable Routing Service";
               type empty;
             }
           }
         }
       }
       container arp-resp {
         presence "enable arp-resp";
         junos:cli-feature "oneliner";
         description "Knob to control ARP response on the interface, default is restricted";
         choice arp-response-options {
           case case_1 {
             leaf unrestricted {
               description "Enable unrestricted ARP respone on the interface";
               type empty;
             }
           }
           case case_2 {
             leaf restricted {
               description "Enable restricted proxy ARP response on the interface";
               type empty;
             }
           }
         }
       }
       container proxy-arp {
         presence "enable proxy-arp";
         junos:must "(!(\"switch-options no-arp-trap \"))";
         junos:must-message "Cannot enable proxy ARP with no-arp-trap";
         junos:cli-feature "oneliner";
         description "Enable proxy ARP on the interface, default is unrestricted";
         choice proxyarp-options {
           case case_1 {
             leaf unrestricted {
               description "Enable unrestricted proxy ARP on the interface";
               type empty;
             }
           }
           case case_2 {
             leaf restricted {
               description "Enable restricted proxy ARP on the interface";
               type empty;
             }
           }
         }
       }
       choice vlan_choice {
         case case_1 {
           leaf vlan-id {
             description "Virtual LAN identifier value for 802.1q VLAN tags";
             junos:must "(!(\"interfaces ${interface} stacked-vlan-tagging\"))";
             junos:must-message "vlan-id is not supported on stacked-vlan-tagging mode";
             type string;
           }
         }
         case case_2 {
           leaf vlan-id-range {
             description "Virtual LAN identifier range of form vid1-vid2";
             junos:must "((\"interfaces ${interface} vlan-tagging\" || \"interfaces ${interface} flexible-vlan-tagging\"))";
             junos:must-message "valid only with vlan-tagging or flexible-vlan-tagging mode";
             type jt:vlan-range;
           }
         }
         case case_3 {
           leaf-list inner-vlan-id-swap-ranges {
             description "Inner vlan-id swap range(s) of form vid1-vid2 for dynamic L2 VLANs";
             type jt:vlan-range;
           }
         }
         case case_4 {
           leaf-list vlan-id-list {
             description "List of VLAN identifiers";
             junos:must "((\" .. encapsulation vlan-ccc\" || (\"interfaces ${interface} encapsulation extended-vlan-ccc\" || (\" .. encapsulation vlan-vpls\" || (\"interfaces ${interface} encapsulation extended-vlan-vpls\" || (\" .. encapsulation vlan-bridge\" || \"interfaces ${interface} encapsulation extended-vlan-bridge\"))))))";
             junos:must-message "valid only with ccc/vpls/bridge encapsulation";
             junos:must "((\"interfaces ${interface} vlan-tagging\" || \"interfaces ${interface} flexible-vlan-tagging\"))";
             junos:must-message "valid only with vlan-tagging or flexible-vlan-tagging mode";
             type jt:vlan-range;
           }
         }
         case case_5 {
           leaf-list vlan-tag {
             ordered-by user;
             description "IEEE 802.1q tag list for VLAN tagged frames";
             status deprecated;
             type string;
           }
         }
         case case_6 {
           container vlan-tags {
             presence "enable vlan-tags";
             junos:must "((!(\"interfaces ${interface} vlan-tagging\") || !((\". inner\" || (\". inner-range\" || \". inner-list\")))))";
             junos:must-message "inner/inner-range/inner-list is valid only on stacked-vlan-tagging and flexible-vlan-tagging mode";
             junos:must "((!(\"interfaces ${interface} stacked-vlan-tagging\") || (\". inner\" || (\". inner-range\" || \". inner-list\"))))";
             junos:must-message "inner/inner-range/inner-list must be defined for stacked-vlan-tagging mode";
             junos:must "((\".. demux-options\" || (\"interfaces ${interface} vlan-tagging\" || (\"interfaces ${interface} stacked-vlan-tagging\" || \"interfaces ${interface} flexible-vlan-tagging\"))))";
             junos:must-message "valid only with vlan-tagging, stacked-vlan-tagging or flexible-vlan-tagging mode";
             junos:cli-feature "oneliner";
             description "IEEE 802.1q tags";
             leaf outer {
               description "[tpid.]vlan-id, tpid format is 0xNNNN and is optional";
               type string;
             }
             choice inner_choice {
               case case_1 {
                 leaf inner {
                   description "[tpid.]vlan-id, tpid format is 0xNNNN and is optional";
                   type string;
                 }
               }
               case case_2 {
                 leaf inner-range {
                   description "[tpid.]vid1-vid2, tpid format is 0xNNNN and is optional";
                   type string {
                     junos:posix-pattern "^((0[Xx][0-9A-Fa-f]{4}.){0,1}([1-9][0-9]{0,2}|[1-3][0-9]{3}|40[0-8][0-9]|409[0-4])-([1-9][0-9]{0,2}|[1-3][0-9]{3}|40[0-8][0-9]|409[0-4]))$";
                     junos:pattern-message "vid in vlan-tag ([0xNNNN.]vid1-vid2) must be 1 to 4094";
                   }
                 }
               }
               case case_3 {
                 leaf-list inner-list {
                   description "List of VLAN identifiers";
                   junos:must "((\" .. .. encapsulation vlan-ccc\" || (\"interfaces ${interface} encapsulation extended-vlan-ccc\" || (\" .. .. encapsulation vlan-vpls\" || (\"interfaces ${interface} encapsulation extended-vlan-vpls\" || (\" .. .. encapsulation vlan-bridge\" || \"interfaces ${interface} encapsulation extended-vlan-bridge\"))))))";
                   junos:must-message "valid only with ccc/vpls/bridge encapsulation";
                   type jt:vlan-range;
                 }
               }
             }
           }
         }
       }
       leaf native-inner-vlan-id {
         description "Native virtual LAN identifier for singly tagged frames";
         junos:must "((\".. vlan-tags\" || \".. family bridge inner-vlan-id-list\"))";
         junos:must-message "native-inner-vlan-id can be specified only on a dual vlan tagged unit";
         junos:must "(\"interfaces ${interface} flexible-vlan-tagging\")";
         junos:must-message "native-inner-vlan-id can be specified only with flexible-vlan-tagging mode";
         type union {
           type string {
             pattern "<.*>|$.*";
           }
           type uint32 {
             range "0 .. 4094";
           }
         }
       }
       container accept-source-mac {
         junos:must "(\".. family ethernet-switching\")";
         junos:must-message "source mac filters are allowed only on interfaces with family ethernet-switching";
         description "Remote media access control address to/from which to accept traffic";
         uses apply-advanced;
         list mac-address {
           key name;
           description "Remote MAC address";
           uses mac_list;
         }
       }
       container input-vlan-map {
         description "VLAN map operation on input";
         junos:cli-feature "oneliner-plus";
         uses vlan_map;
       }
       container output-vlan-map {
         description "VLAN map operation on output";
         junos:cli-feature "oneliner-plus";
         uses vlan_map;
       }
       leaf swap-by-poppush {
         description "Pop original vlan tag and then push a new vlan tag";
         type empty;
       }
       leaf receive-lsp {
         description "Name of incoming label-switched path";
         type string;
       }
       leaf transmit-lsp {
         description "Name of outgoing label-switched path";
         type string;
       }
       leaf dlci {
         description "Frame Relay data-link control identifier";
         type union {
           type string {
             pattern "<.*>|$.*";
           }
           type uint32 {
             range "1 .. 1022";
           }
         }
       }
       leaf multicast-dlci {
         description "Frame Relay data-link control identifier for multicast packets";
         type union {
           type string {
             pattern "<.*>|$.*";
           }
           type uint32 {
             range "1 .. 1022";
           }
         }
       }
       choice vci_type {
         case case_1 {
           leaf vci {
             description "ATM point-to-point virtual circuit identifier ([vpi.]vci)";
             junos:must "(!(\".. encapsulation vlan-vci-ccc\"))";
             junos:must-message "'vci-range' must be used with encapsulation vlan-vci-ccc";
             type jt:atm-vci;
           }
         }
         case case_2 {
           leaf allow-any-vci {
             description "Allow all VCIs to open in atm-ccc-cell-relay mode";
             type empty;
           }
         }
         case case_3 {
           leaf vpi {
             description "ATM point-to-point virtual path identifier (vpi)";
             type union {
               type string {
                 pattern "<.*>|$.*";
               }
               type uint32 {
                 range "0 .. 255";
               }
             }
           }
         }
         case case_4 {
           leaf trunk-id {
             description "ATM trunk identifier";
             type union {
               type string {
                 pattern "<.*>|$.*";
               }
               type uint32 {
                 range "0 .. 31";
               }
             }
           }
         }
       }
       leaf no-vpivci-swapping {
         description "Do not swap VPI/VCI for Cell Relay";
         junos:must "(\".. encapsulation atm-ccc-cell-relay\")";
         junos:must-message "encapsulation must be atm-ccc-cell-relay";
         type empty;
       }
       choice psn_vci_type {
         case case_1 {
           leaf psn-vci {
             description "PSN VCI";
             junos:must "(\".. encapsulation atm-ccc-cell-relay\")";
             junos:must-message "encapsulation must be atm-ccc-cell-relay";
             junos:must "(!(\".. no-vpivci-swapping\"))";
             junos:must-message "no-vpivci-swapping must not be configured";
             type jt:atm-vci;
           }
         }
         case case_2 {
           leaf psn-vpi {
             description "PSN VPI";
             junos:must "(\".. encapsulation atm-ccc-cell-relay\")";
             junos:must-message "encapsulation must be atm-ccc-cell-relay";
             junos:must "(!(\".. no-vpivci-swapping\"))";
             junos:must-message "no-vpivci-swapping must not be configured";
             type union {
               type string {
                 pattern "<.*>|$.*";
               }
               type uint32 {
                 range "0 .. 255";
               }
             }
           }
         }
       }
       container atm-l2circuit-mode {
         junos:cli-feature "oneliner";
         description "Select ATM Layer 2 circuit transport mode";
         choice mode_choice {
           case case_1 {
             leaf cell {
               description "ATM Layer 2 circuit cell mode";
               type empty;
             }
           }
           case case_2 {
             leaf aal5 {
               description "ATM Layer 2 circuit AAL5 mode";
               type empty;
             }
           }
         }
       }
       container vci-range {
         junos:must "(!(\".. vci\"))";
         junos:must-message "'vci-range' and 'vci' statements cannot co-exist";
         junos:cli-feature "oneliner";
         description "ATM VCI range start <start-vci> end <end-vci>";
         leaf start {
           description "ATM VCI range's start value";
           type union {
             type string {
               pattern "<.*>|$.*";
             }
             type uint16 {
               range "32 .. 4094";
             }
           }
         }
         leaf end {
           description "ATM VCI range's end value";
           type union {
             type string {
               pattern "<.*>|$.*";
             }
             type uint16 {
               range "32 .. 4094";
             }
           }
         }
       }
       leaf trunk-bandwidth {
         description "ATM trunk bandwidth";
         units "bits per second";
         type string;
       }
       leaf multicast-vci {
         description "ATM virtual circuit identifier for multicast packets";
         type jt:atm-vci;
       }
       container shaping {
         description "Virtual circuit traffic-shaping options";
         uses dcd_shaping_config;
       }
       container oam-period {
         junos:cli-feature "oneliner";
         description "OAM cell period";
         choice oam_period_choices {
           case case_1 {
             leaf oam-period {
               description "OAM cell period";
               junos:cli-feature "nokeyword";
               units "seconds";
               type union {
                 type string {
                   pattern "<.*>|$.*";
                 }
                 type uint32 {
                   range "1 .. 900";
                 }
               }
             }
           }
           case case_2 {
             container disable {
               presence "enable disable";
               junos:cli-feature "oneliner";
               description "Disable F5 OAM loopback";
             }
           }
         }
       }
       container oam-liveness {
         description "OAM virtual circuit liveness parameters";
         uses apply-advanced;
         leaf up-count {
           description "Number of OAM cells to consider VC up";
           type union {
             type string {
               pattern "<.*>|$.*";
             }
             type uint32 {
               range "1 .. 255";
             }
           }
         }
         leaf down-count {
           description "Number of OAM cells to consider VC down";
           type union {
             type string {
               pattern "<.*>|$.*";
             }
             type uint32 {
               range "1 .. 255";
             }
           }
         }
       }
       container ppp-options {
         description "Point-to-Point Protocol interface-specific options";
         uses ppp_options_type;
       }
       container pppoe-options {
         description "PPP over Ethernet interface-specific options";
         uses pppoe_options_type;
       }
       choice keepalive_choices {
         case case_1 {
           container keepalives {
             description "Send or demand keepalive messages";
             presence "enable keepalives";
             junos:cli-feature "oneliner";
             uses keepalives_type;
           }
         }
         case case_2 {
           leaf no-keepalives {
             description "Do not send or demand keepalive messages";
             type empty;
           }
         }
       }
       leaf inverse-arp {
         description "Enable inverse ARP";
         type empty;
       }
       leaf transmit-weight {
         description "ATM2 transmit weight for VC under VP tunnel";
         type union {
           type string {
             pattern "<.*>|$.*";
           }
           type uint16 {
             range "1 .. 32767";
           }
         }
       }
       container epd-threshold {
         description "Early packet discard threshold for ATM2";
         junos:cli-feature "oneliner";
         uses epd_threshold_config;
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf atm-scheduler-map {
         description "Assign ATM2 CoS scheduling map";
         type union {
           type string {
             pattern "default";
           }
           type string;
         }
       }
       leaf mrru {
         description "Maximum received reconstructed unit";
         units "bytes";
         type union {
           type string {
             pattern "<.*>|$.*";
           }
           type uint16 {
             range "1500 .. 4500";
           }
         }
       }
       leaf short-sequence {
         description "Short sequence number header format (MLPPP only)";
         type empty;
       }
       leaf fragment-threshold {
         description "Fragmentation threshold";
         units "bytes";
         type union {
           type string {
             pattern "<.*>|$.*";
           }
           type uint32 {
             range "64 .. 4500";
           }
         }
       }
       leaf drop-timeout {
         description "Drop timeout";
         units "milliseconds";
         type union {
           type string {
             pattern "<.*>|$.*";
           }
           type uint16 {
             range "0 .. 2000";
           }
         }
       }
       leaf disable-mlppp-inner-ppp-pfc {
         description "Disable compression for inner PPP header in MLPPP payload";
         type empty;
       }
       leaf minimum-links {
         description "Minimum number of links to sustain the bundle";
         type union {
           type string {
             pattern "<.*>|$.*";
           }
           type uint16;
         }
       }
       leaf multilink-max-classes {
         description "Number of multilink classes";
         type union {
           type string {
             pattern "<.*>|$.*";
           }
           type uint16;
         }
       }
       leaf interleave-fragments {
         description "Interleave long packets with high priority ones";
         type empty;
       }
       leaf link-layer-overhead {
         description "Link layer bit stuffing overhead (0.0 .. 50.0 percent)";
         type jt:unsigned-float;
       }
       leaf accounting-profile {
         description "Accounting profile name";
         junos:must "((\"accounting-options interface-profile $$\" || \"accounting-options flat-file-profile $$\"))";
         junos:must-message "referenced accounting profile must be defined";
         type string;
       }
       leaf peer-unit {
         description "Peer unit number";
         type union {
           type string {
             pattern "<.*>|$.*";
           }
           type uint32 {
             range "0 .. 16385";
           }
         }
       }
       container tunnel {
         description "Tunnel parameters";
         uses apply-advanced;
         container encapsulation {
           presence "enable encapsulation";
           junos:cli-feature "homogeneous";
           description "Encapsulation over tunnel";
           container vxlan-gpe {
             presence "enable vxlan-gpe";
             junos:must "((!(\".. udp\") && !(\".. ipip\")))";
             junos:must-message "Only one encapsulation can  be set per IFL";
             uses apply-advanced;
             container source {
               uses apply-advanced;
               leaf address {
                 description "Interface address prefix";
                 junos:must "(!(\".. interface\"))";
                 junos:must-message "To configure address interface must be not set";
                 type jt:ipv4addr;
               }
               leaf mac-address {
                 description "Interface source mac address";
                 junos:must "((\".. interface\" || \".. address\"))";
                 junos:must-message "Either address or interface must be set";
                 type jt:mac-addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
               leaf mac-address {
                 description "Interface destination mac address";
                 junos:must "(\".. address\")";
                 junos:must-message "destination address must be set";
                 type jt:mac-addr;
               }
             }
             leaf tunnel-endpoint {
               description "Tunnel end point type";
               type enumeration {
                 enum "vxlan" {
                   description "To configure vxlan tunnel-end-point";
                 }
               }
             }
             container source-udp-port-range {
               junos:cli-feature "oneliner";
               description "Value range for source-udp-port";
               leaf min {
                 description "Minimum range value";
                 type union {
                   type string {
                     pattern "<.*>|$.*";
                   }
                   type uint32 {
                     range "1 .. 65535";
                   }
                 }
               }
               leaf max {
                 description "Maximum range value";
                 type union {
                   type string {
                     pattern "<.*>|$.*";
                   }
                   type uint32 {
                     range "1 .. 65535";
                   }
                 }
               }
             }
             leaf destination-udp-port {
               description "Value to write to the destination-udp-port field";
               type union {
                 type string {
                   pattern "<.*>|$.*";
                 }
                 type uint32 {
                   range "1 .. 65535";
                 }
               }
             }
             leaf vni {
               description "Value to write to the vni field";
               type union {
                 type string {
                   pattern "<.*>|$.*";
                 }
                 type uint32 {
                   range "0 .. 16777214";
                 }
               }
             }
           }
           container udp {
             presence "enable udp";
             junos:must "((!(\".. .. .. family ccc\") && !(\".. .. .. family tcc\")))";
             junos:must-message "Only inet, inet6, mpls, iso families allowed for udp tunnel in encap mode";
             junos:must "((!(\".. vxlan-gpe\") && (!(\".. ipip\") && !(\"..gre\"))))";
             junos:must-message "Only one encapsulation can  be set per IFL";
             description "Family for tunnel encapsulation udp";
             uses apply-advanced;
             container source {
               uses apply-advanced;
               leaf address {
                 description "Interface address prefix";
                 junos:must "(!(\".. interface\"))";
                 junos:must-message "To configure address interface must be not set";
                 type jt:ipv4addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
             }
           }
           container ipip {
             presence "enable ipip";
             junos:must "((!(\".. .. .. family ccc\") && (!(\".. .. .. family tcc\") && !(\".. .. .. family iso\"))))";
             junos:must-message "Only inet, inet6, mpls families allowed for ipip tunnel in decap/encap mode";
             junos:must "((!(\".. udp\") && (!(\".. vxlan-gpe\") && !(\".. gre\"))))";
             junos:must-message "Only one encapsulation can  be set per IFL";
             description "Family for tunnel encapsulation ipip";
             uses apply-advanced;
             container source {
               uses apply-advanced;
               leaf address {
                 description "Interface address prefix";
                 junos:must "(!(\".. interface\"))";
                 junos:must-message "To configure address interface must be not set";
                 type jt:ipv4addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
             }
           }
           container virtual-loop {
             presence "enable virtual-loop";
             junos:must "((!(\".. .. .. family ccc\") && (!(\".. .. .. family tcc\") && (!(\".. .. .. family mpls\") && !(\".. .. .. family iso\")))))";
             junos:must-message "Only inet, and inet6 families allowed for virtual-loop tunnel encapsulation mode";
             junos:must "((!(\".. vxlan-gpe\") && (!(\".. ipip\") && (!(\"..gre\") && !(\"..udp\")))))";
             junos:must-message "Only one encapsulation is allowed per IFL";
             description "Family for tunnel encapsulation virtual-loop";
           }
         }
         choice source_type {
           case case_1 {
             leaf source {
               description "Tunnel source address";
               type jt:ipaddr;
             }
           }
           case case_2 {
           }
           case case_3 {
           }
         }
         choice destination_type {
           case case_1 {
             leaf destination {
               description "Tunnel destination address";
               type jt:ipaddr;
             }
           }
           case case_2 {
           }
         }
         leaf backup-destination {
           description "Backup tunnel destination";
           junos:must "(!(\".. destination $$\"))";
           junos:must-message "Backup and primary tunnel destinations must be different";
           type jt:ipaddr;
         }
         choice fragmentation {
           case case_1 {
             leaf allow-fragmentation {
               description "Do not set DF bit on packets";
               type empty;
             }
           }
           case case_2 {
             leaf do-not-fragment {
               description "Set DF bit on packets";
               type empty;
             }
           }
         }
         leaf ttl {
           description "Time to live";
           type union {
             type string {
               pattern "<.*>|$.*";
             }
             type uint32 {
               range "1 .. 255";
             }
           }
         }
         leaf traffic-class {
           description "TOS/Traffic class field of IP-header";
           type union {
             type string {
               pattern "<.*>|$.*";
             }
             type uint32 {
               range "0 .. 255";
             }
           }
         }
         leaf flow-label {
           description "Flow label field of IP6-header";
           type union {
             type string {
               pattern "<.*>|$.*";
             }
             type uint32 {
               range "0 .. 1048575";
             }
           }
         }
         choice path-mtu-discovery-choice {
           leaf path-mtu-discovery {
             description "Enable path MTU discovery for tunnels";
             type empty;
           }
           leaf no-path-mtu-discovery {
             description "Don't enable path MTU discovery for tunnels";
             type empty;
           }
         }
         container routing-instance {
           description "Routing instance to which tunnel ends belong";
           uses apply-advanced;
           leaf destination {
             description "Routing instance of tunnel destination";
             junos:must "((\"routing-instances $$\" || any \"tenants <*> routing-instances $$\"))";
             junos:must-message "referenced routing-instance must be defined";
             type string {
               junos:posix-pattern "!^((__.*__)|(all)|(.*[ ].*)|(\"\")|(.{129,}))$";
               junos:pattern-message "Must be a non-reserved string of 128 characters or less with no spaces.";
             }
           }
         }
       }
       leaf compression-device {
         description "Logical interface used for compression";
         type union {
           type jt:interface-unit;
           type string {
             pattern "<.*>|$.*";
           }
         }
       }
       container atm-policer {
         junos:must "(\".. family\")";
         junos:must-message "Family must be defined for a unit with atm-policer";
         description "ATM policing for logical interface";
         uses apply-advanced;
         leaf input-atm-policer {
           description "Input atm policer";
           type string;
         }
       }
       container layer2-policer {
         junos:must "(\".. family\")";
         junos:must-message "Family must be defined for a unit with layer2-policer";
         description "Layer2 policing for logical interface";
         uses apply-advanced;
         choice layer2-input-policer-choice {
           case case_1 {
             leaf input-policer {
               description "Two-color policer for received packets";
               type string;
             }
           }
           case case_2 {
           }
           case case_3 {
             leaf input-three-color {
               description "Color-blind three-color policer for received packets";
               type string;
             }
           }
         }
         choice layer2-output-policer-choice {
           case case_1 {
             leaf output-policer {
               description "Two-color policer for transmitted packets";
               type string;
             }
           }
           case case_2 {
             leaf output-three-color {
               description "Three-color policer for transmitted packets";
               type string;
             }
           }
         }
       }
       container filter {
         description "Filters to apply to all families configured under this logical interface";
         uses apply-advanced;
         choice chain_choice {
           case case_1 {
           }
         }
         choice input_choice {
           case case_1 {
             container input {
               junos:cli-feature "oneliner";
               description "Name of filter to be applied to received packets";
               leaf filter-name {
                 description "Name of the filter";
                 junos:cli-feature "nokeyword";
                 junos:must "((!(any \"firewall family any filter $$ term <*> from gbp-dst-tag\") || !(any \"firewall family any filter $$ term <*> then next-ip6\")))";
                 junos:must-message "GBP enforcement filter with next-ip6 action not supported on interface input.";
                 junos:must "((!(any \"firewall family any filter $$ term <*> from gbp-src-tag\") || !(any \"firewall family any filter $$ term <*> then next-ip6\")))";
                 junos:must-message "GBP enforcement filter with next-ip6 action not supported on interface input.";
                 junos:must "((!(any \"firewall family any filter $$ term <*> from gbp-dst-tag\") || !(any \"firewall family any filter $$ term <*> then next-ip\")))";
                 junos:must-message "GBP enforcement filter with next-ip action not supported on interface input.";
                 junos:must "((!(any \"firewall family any filter $$ term <*> from gbp-src-tag\") || !(any \"firewall family any filter $$ term <*> then next-ip\")))";
                 junos:must-message "GBP enforcement filter with next-ip action not supported on interface input.";
                 type string;
               }
               leaf shared-name {
                 description "Filter shared-name of instances of interface-shared filter";
                 type string;
               }
               leaf precedence {
                 description "Precedence of the filter";
                 type union {
                   type string {
                     pattern "<.*>|$.*";
                   }
                   type uint32 {
                     range "0 .. 255";
                   }
                 }
               }
             }
           }
         }
         choice output_choice {
           case case_1 {
             container output {
               junos:cli-feature "oneliner";
               description "Name of filter to be applied to transmitted packets";
               leaf filter-name {
                 description "Name of the filter";
                 junos:cli-feature "nokeyword";
                 junos:must "((!(any \"firewall family any filter $$ term <*> from gbp-dst-tag\") || !(any \"firewall family any filter $$ term <*> then next-ip6\")))";
                 junos:must-message "GBP enforcement filter with next-ip6 action not supported on interface output.";
                 junos:must "((!(any \"firewall family any filter $$ term <*> from gbp-src-tag\") || !(any \"firewall family any filter $$ term <*> then next-ip6\")))";
                 junos:must-message "GBP enforcement filter with next-ip6 action not supported on interface output.";
                 junos:must "((!(any \"firewall family any filter $$ term <*> from gbp-dst-tag\") || !(any \"firewall family any filter $$ term <*> then next-ip\")))";
                 junos:must-message "GBP enforcement filter with next-ip action not supported on interface output.";
                 junos:must "((!(any \"firewall family any filter $$ term <*> from gbp-src-tag\") || !(any \"firewall family any filter $$ term <*> then next-ip\")))";
                 junos:must-message "GBP enforcement filter with next-ip action not supported on interface output.";
                 type string;
               }
               leaf shared-name {
                 description "Filter shared-name of instances of interface-shared filter";
                 type string;
               }
               leaf precedence {
                 description "Precedence of the filter";
                 type union {
                   type string {
                     pattern "<.*>|$.*";
                   }
                   type uint32 {
                     range "0 .. 255";
                   }
                 }
               }
             }
           }
         }
       }
       list multi-chassis-protection {
         key name;
         description "Inter-Chassis protection configuration";
         junos:must "(\"interfaces ${interface} aggregated-ether-options mc-ae mode active-active\")";
         junos:must-message "multi-chassis-protection is only supported for MC-AE active-active mode";
         uses multi-chassis-protection-group-ifl;
       }
       leaf statistics {
         description "Enable statistics collection in PFE";
         type empty;
       }
       choice virtual-gateway {
         case case_1 {
           leaf no-auto-virtual-gateway-esi {
             description "Disable auto ESI generation for virtual gateway address";
             junos:must "((any \".. family inet address <*> virtual-gateway-address\" || any \".. family inet6 address <*> virtual-gateway-address\"))";
             junos:must-message "Only when virtual gateway address is configured";
             type empty;
           }
         }
         case case_2 {
           container virtual-gateway-esi {
             description "ESI configuration of virtual gateway";
             uses apply-advanced;
             leaf identifier {
               description "ESI value for the interface";
               junos:cli-feature "nokeyword";
               junos:must "(unique \"interfaces <*> unit <*> virtual-gateway-esi $$\")";
               junos:must-message "virtual-gateway-esi value must be unique under all IFDs and IFLs";
               junos:must "(unique \"interfaces <*> esi $$\")";
               junos:must-message "ESI value must be unique under all IFDs and IFLs";
               type jt:esi;
             }
             choice mode {
               case case_1 {
                 leaf single-active {
                   description "Single-active mode";
                   type empty;
                 }
               }
               case case_2 {
                 leaf all-active {
                   description "All-active mode";
                   type empty;
                 }
               }
             }
           }
         }
       }
       container service {
         description "Service operations";
         uses apply-advanced;
         list pcef {
           key name;
           ordered-by user;
           description "PCEF configuration";
           leaf name {
             description "PCEF Profile name";
             junos:cli-feature "nokeyword";
             junos:must "((\".. family inet service\" || \".. family inet6 service\"))";
             junos:must-message "Must be configured along with a family inet/inet6 service.";
             type string;
           }
           uses apply-advanced;
           leaf activate-all {
             description "Activate all rules and rulebases in the pcef profile";
             junos:must "(!(\"activate\"))";
             junos:must-message "Can't be configured with activate-rule or activate- rulebase.";
             type empty;
           }
           list activate {
             key name;
             ordered-by user;
             description "Name of pcef profile rule or rulebase to activate";
             leaf name {
               description "Name of pcef profile rule or rulebase to activate";
               junos:cli-feature "nokeyword";
               type string;
             }
             uses apply-advanced;
           }
         }
       }
       choice generate-eui64-choice {
         leaf generate-eui64 {
           description "To generate Link Local EUI-64 addresses";
           junos:must "(\".. family inet6 unnumbered-address\")";
           junos:must-message "generate-eui64 attribute must be set when unnumbered-address is configured under family inet6";
           type empty;
         }
         leaf no-generate-eui64 {
           description "Don't to generate Link Local EUI-64 addresses";
           junos:must "(\".. family inet6 unnumbered-address\")";
           junos:must-message "generate-eui64 attribute must be set when unnumbered-address is configured under family inet6";
           type empty;
         }
       }
       container mode {
         description "Add an interface to a tap or tool group";
         uses apply-advanced;
         list tap {
           key name;
           ordered-by user;
           description "Add an interface to a tap group";
           leaf name {
             description "Tap group name";
             junos:cli-feature "nokeyword";
             type string;
           }
           uses apply-advanced;
         }
         list tool {
           key name;
           ordered-by user;
           description "Add an interface to a tool group";
           leaf name {
             description "Tool group name";
             junos:cli-feature "nokeyword";
             type string;
           }
           uses apply-advanced;
         }
       }
       container family {
         junos:must "(!(\".. encapsulation ppp-over-ether\"))";
         junos:must-message "Can't configure protocol family with encapsulation ppp-over-ether";
         junos:cli-feature "homogeneous";
         description "Protocol family";
         container inet {
           presence "enable inet";
           junos:must "(!(\".. .. .. encapsulation vlan-vpls\"))";
           junos:must-message "Can't configure protocol family inet with encapsulation vpls";
           description "IPv4 parameters";
           uses apply-advanced;
           leaf source-lookup {
             description "Set source lookup flag";
             junos:must "(!(\".. accouting source-class-usage\"))";
             junos:must-message " Source lookup is not allowed with source-class-usage";
             type empty;
           }
           container class-based-filtering {
             description "Enable class based filter on interface";
             uses apply-advanced;
           }
           container dhcp {
             presence "enable dhcp";
             junos:must "(!(any \"forwarding-options dhcp-relay group <*> interface ${interface}.${unit}\"))";
             junos:must-message "Incompatible with the interface configured under 'forwarding-options dhcp-relay group'";
             junos:must "(!(\"system services dhcp\"))";
             junos:must-message "Incompatible with the dhcp server configured under 'system services dhcp'";
             junos:must "(!(\"system autoinstallation interfaces\"))";
             junos:must-message "Incompatible with 'system autoinstallation interfaces'";
             junos:must "(!(\".. address\"))";
             junos:must-message "Incompatible with interface assigned with address";
             junos:must "(!(\"system autoinstallation\"))";
             junos:must-message "Incompatible with 'system autoinstallation'";
             description "Configure DHCP Client";
             uses apply-advanced;
             container client-identifier {
               junos:cli-feature "oneliner";
               description "DHCP Server identifies a client by client-identifier value ";
               choice client-identifier-choice {
                 case case_1 {
                   leaf ascii {
                     description "Client identifier as an ASCII string";
                     type string;
                   }
                 }
                 case case_2 {
                   leaf hexadecimal {
                     description "Client identifier as a hexadecimal string";
                     type string {
                       junos:posix-pattern "^[[:xdigit:]]+$";
                       junos:pattern-message "Must be hexadecimal digits (0-9, a-f, A-F)";
                     }
                   }
                 }
               }
             }
             leaf lease-time {
               description "Default lease time requested in ";
               units "seconds";
               type string;
             }
             leaf retransmission-attempt {
               description "Number of attempts to retransmit the DHCP client protocol packet";
               default "4";
               type union {
                 type string {
                   pattern "<.*>|$.*";
                 }
                 type uint32 {
                   range "0 .. 6";
                 }
               }
             }
             leaf retransmission-interval {
               description "Number of seconds between successive retransmission";
               default "4";
               units "seconds";
               type union {
                 type string {
                   pattern "<.*>|$.*";
                 }
                 type uint32 {
                   range "4 .. 64";
                 }
               }
             }
             leaf server-address {
               description "DHCP Server-address";
               type jt:ipv4addr;
             }
             leaf update-server {
               description "Propagate TCP/IP settings to DHCP server ";
               type empty;
             }
             leaf vendor-id {
               description "Vendor class id for the DHCP Client";
               type string;
             }
           }
           container targeted-broadcast {
             presence "enable targeted-broadcast";
             description "Directed broadcast";
             uses apply-advanced;
             choice targeted-bcast-choice {
               case case_1 {
                 leaf forward-and-send-to-re {
                   description "Allow packets to be forwarded and sent to re";
                   type empty;
                 }
               }
               case case_2 {
                 leaf forward-only {
                   description "Allow packets only to be forwarded";
                   type empty;
                 }
               }
             }
           }
           leaf destination-class-usage {
             description "Enable destination class usage on this interface";
             status deprecated;
             type empty;
           }
           leaf transit-options-packets {
             description "Transit IP options packets (don't send to Routing Engine)";
             status deprecated;
             type empty;
           }
           leaf transit-ttl-exceeded {
             description "Transit IP TTL-exceeded packets (don't send to Routing Engine)";
             status deprecated;
             type empty;
           }
           leaf receive-options-packets {
             description "Receive IP options packets (don't send to Routing Engine)";
             type empty;
           }
           leaf receive-ttl-exceeded {
             description "Receive IP TTL-exceeded packets (don't send to Routing Engine)";
             type empty;
           }
           container accounting {
             description "Configure interface-based accounting options";
             uses apply-advanced;
             container source-class-usage {
               junos:must "(!(\".. .. class-based-filtering source-class-usage\"))";
               junos:must-message "source-class-usage is not allowed with class-based-filtering source-class-usage";
               junos:must "(!(\".. .. source-lookup\"))";
               junos:must-message " source-class-usage is not allowed with source-lookup";
               description "Enable source class usage on this interface";
               uses apply-advanced;
               leaf input {
                 description "Specify this interface for source-class-usage input";
                 type empty;
               }
               leaf output {
                 description "Specify this interface for source-class-usage output";
                 type empty;
               }
             }
             leaf destination-class-usage {
               description "Enable destination class usage on this interface";
               junos:must "(!(\".. .. class-based-filtering destination-class-usage\"))";
               junos:must-message "destination-class-usage is not allowed with class-based-filtering destination-class-usage";
               type empty;
             }
           }
           leaf mac-validate {
             description "Validate source MAC address";
             type enumeration {
               enum "strict" {
                 description "Strict mac-validation";
               }
               enum "loose" {
                 description "Loose mac-validation";
               }
             }
           }
           container rpf-check {
             presence "enable rpf-check";
             junos:cli-feature "oneliner-plus";
             description "Enable reverse-path-forwarding checks on this interface";
             uses apply-advanced;
             leaf fail-filter {
               description "Name of filter applied to packets failing RPF check";
               type string;
             }
             container mode {
               junos:cli-feature "oneliner";
               description "Mode for reverse path forwarding";
               leaf loose {
                 description "Reverse-path-forwarding loose mode";
                 type empty;
               }
             }
           }
           leaf mtu {
             description "Protocol family maximum transmission unit";
             type union {
               type uint32;
               type string {
                 pattern "<.*>|$.*";
               }
             }
           }
           leaf arp-max-cache {
             description "Max interface ARP nexthop cache size";
             type union {
               type string {
                 pattern "<.*>|$.*";
               }
               type uint32 {
                 range "1 .. 2000000";
               }
             }
           }
           leaf arp-new-hold-limit {
             description "Max no. of new unresolved nexthops";
             junos:must "(\".. arp-max-cache\")";
             junos:must-message "Interface max ARP cache size must be configured";
             type union {
               type string {
                 pattern "<.*>|$.*";
               }
               type uint32 {
                 range "1 .. 2000000";
               }
             }
           }
           leaf no-redirects {
             description "Do not redirect traffic";
             type empty;
           }
           leaf nat-outside-interface {
             description "Public interface used for NAT";
             junos:must "(!(\"interfaces ${interface} unit ${unit} family inet6\"))";
             junos:must-message "family inet6 is not supported with nat-outside-interface";
             type empty;
           }
           leaf no-neighbor-learn {
             description "Disable neighbor address learning on interface";
             type empty;
           }
           leaf unconditional-src-learn {
             description "Glean from arp packets even when source cannot be validated";
             type empty;
           }
           leaf multicast-only {
             description "Allow only multicast traffic (tunnels only)";
             type empty;
           }
           leaf primary {
             description "Candidate for primary interface in system";
             type empty;
           }
           leaf ipsec-sa {
             description "Name of security association";
             type string {
               length "1 .. 32";
             }
           }
           container filter {
             description "Packet filtering";
             uses apply-advanced;
             choice input_choice {
               case case_1 {
                 container input {
                   junos:cli-feature "oneliner";
                   description "Filter to be applied to received packets";
                   leaf filter-name {
                     description "Name of the filter";
                     junos:cli-feature "nokeyword";
                     junos:must "((!(\".. .. .. rpf-check\") || (!(any \"firewall family inet filter $$ term <*> from first-byte-of-payload\") && !(any \"firewall family inet filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             leaf-list input-chain {
               ordered-by user;
               description "List of filter modules applied to received packets ";
               type string;
             }
             leaf-list output-chain {
               ordered-by user;
               description "List of filter modules applied to transmitted packets ";
               type string;
             }
             choice output_choice {
               case case_1 {
                 container output {
                   junos:cli-feature "oneliner";
                   description "Filter to be applied to transmitted packets";
                   leaf filter-name {
                     description "Name of the filter";
                     junos:cli-feature "nokeyword";
                     junos:must "((!(\".. .. .. rpf-check\") || (!(any \"firewall family inet filter $$ term <*> from first-byte-of-payload\") && !(any \"firewall family inet filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   junos:cli-feature "nokeyword";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32;
               }
             }
           }
           container simple-filter {
             description "Filter for doing multifield classification";
             uses apply-advanced;
             leaf input {
               description "Name of simple filter applied to received packets";
               type string;
             }
           }
           container policer {
             description "Interface policing";
             uses apply-advanced;
             leaf arp {
               description "Name of policer applied to received ARP packets";
               junos:must "(!(\".. disable-arp-policer\"))";
               junos:must-message "Interface configuration can have either disable-arp-policer or arp policer configured";
               junos:must "((!(\".. .. .. .. peer-unit\") || (\".. .. .. .. encapsulation ethernet\" || \".. .. .. .. encapsulation vlan\")))";
               junos:must-message "Interface encapsulation must be ethernet or vlan";
               type string;
             }
             leaf input {
               description "Name of policer applied to received packets";
               junos:must "(!(\".. .. input-hierarchical-policer\"))";
               junos:must-message "Both input policer and input hierarchical policer can not be applied on the same family";
               type string;
             }
             leaf output {
               description "Name of policer applied to transmitted packets";
               type string;
             }
           }
           container sampling {
             junos:must "((\"forwarding-options sampling family inet\" || (\"forwarding-options packet-capture\" || any \"forwarding-options sampling instance <*> family inet\")))";
             junos:must-message "Requires forwarding-options sampling or packet-capture config";
             description "Interface sampling";
             uses apply-advanced;
             leaf input {
               description "Sample all packets input on this interface";
               type empty;
             }
             leaf output {
               description "Sample all packets output on this interface";
               type empty;
             }
           }
           list next-hop-tunnel {
             key name;
             ordered-by user;
             junos:cli-feature "oneliner-plus";
             description "One or more next-hop tunnel tables";
             leaf name {
               description "Next-hop tunnel gateway address";
               junos:cli-feature "nokeyword";
               type string;
             }
             uses apply-advanced;
             leaf ipsec-vpn {
               description "Name of IPSec VPN";
               junos:must "(\"security ipsec vpn $$\")";
               junos:must-message "Referenced IPSec vpn must be defined under [edit security ipsec vpn] hierarchy level";
               junos:must "(unique \"interfaces st0 unit <*> family inet next-hop-tunnel <*> ipsec-vpn $$\")";
               junos:must-message "Referenced IPSec vpn must be unique";
               type string;
             }
           }
           choice tunnel-termination-status {
             case case_1 {
               leaf tunnel-termination {
                 description "Tunnel termination";
                 type empty;
               }
             }
             case case_2 {
               leaf no-tunnel-termination {
                 description "No Tunnel termination";
                 type empty;
               }
             }
           }
           leaf tunnel-loopback {
             description "Allows tunnel packet processing on IRB underlay using the loopback path";
             type empty;
           }
           list address {
             key name;
             ordered-by user;
             description "Interface address/destination prefix";
             junos:must "((!(\".. unnumbered-address\") && !(\".. location-pool-address\")))";
             junos:must-message "address cannot be defined with unnumbered-address or location-pool-address simultaneously";
             leaf name {
               description "Interface address/destination prefix";
               junos:cli-feature "nokeyword";
               type jt:ipv4prefix;
             }
             uses apply-advanced;
             leaf destination {
               description "Destination address";
               type jt:ipv4addr;
             }
             leaf destination-profile {
               description "Profile to use for destination address";
               junos:must "(\"access group-profile $$ ppp\")";
               junos:must-message "referenced group-profile must be defined and must contain ppp statement";
               type string;
             }
             leaf broadcast {
               description "Broadcast address";
               type jt:ipv4addr;
             }
             leaf primary {
               description "Candidate for primary address in system";
               type empty;
             }
             leaf preferred {
               description "Preferred address on interface";
               type empty;
             }
             leaf master-only {
               description "Master management IP address for router";
               type empty;
             }
             container tag {
               description "Tag used for route/local";
               uses apply-advanced;
               leaf tag-value {
                 description "The tag value on the address";
                 junos:cli-feature "nokeyword";
                 type union {
                   type string {
                     pattern "<.*>|$.*";
                   }
                   type uint32 {
                     range "1 .. 4294967295";
                   }
                 }
               }
               leaf type {
                 description "Tag type must be [1-16]";
                 type union {
                   type string {
                     pattern "<.*>|$.*";
                   }
                   type uint32 {
                     range "1 .. 16";
                   }
                 }
               }
             }
             container tag2 {
               description "Tag2 used for route/local";
               uses apply-advanced;
               leaf tag2-value {
                 description "The tag value on the address";
                 junos:cli-feature "nokeyword";
                 type union {
                   type string {
                     pattern "<.*>|$.*";
                   }
                   type uint32 {
                     range "1 .. 4294967295";
                   }
                 }
               }
               leaf type {
                 description "Tag type must be [1-16]";
                 type union {
                   type string {
                     pattern "<.*>|$.*";
                   }
                   type uint32 {
                     range "1 .. 16";
                   }
                 }
               }
             }
             list multipoint-destination {
               key name;
               ordered-by user;
               junos:cli-feature "oneliner-plus";
               description "Multipoint NBMA destination";
               leaf name {
                 description "Destination address";
                 junos:cli-feature "nokeyword";
                 type jt:ipv4addr;
               }
               uses apply-advanced;
               choice link-address {
                 case case_1 {
                   leaf dlci {
                     description "Frame Relay data-link control identifier";
                     type union {
                       type string {
                         pattern "<.*>|$.*";
                       }
                       type uint32 {
                         range "1 .. 1022";
                       }
                     }
                   }
                 }
                 case case_2 {
                   leaf vci {
                     description "ATM virtual circuit identifier ([vpi.]vci)";
                     type jt:atm-vci;
                   }
                 }
               }
               container shaping {
                 description "Virtual circuit traffic-shaping options";
                 uses dcd_shaping_config;
               }
               container oam-period {
                 junos:cli-feature "oneliner";
                 description "OAM cell period";
                 choice oam_period_choices {
                   case case_1 {
                     leaf oam_period {
                       description "OAM cell period";
                       junos:cli-feature "nokeyword";
                       units "seconds";
                       type union {
                         type string {
                           pattern "<.*>|$.*";
                         }
                         type uint32 {
                           range "1 .. 900";
                         }
                       }
                     }
                   }
                   case case_2 {
                     container disable {
                       presence "enable disable";
                       junos:cli-feature "oneliner";
                       description "Disable OAM loopback";
                     }
                   }
                 }
               }
               container oam-liveness {
                 description "OAM virtual circuit liveness parameters";
                 uses apply-advanced;
                 leaf up-count {
                   description "Number of OAM cells to consider VC up";
                   type union {
                     type string {
                       pattern "<.*>|$.*";
                     }
                     type uint32 {
                       range "1 .. 255";
                     }
                   }
                 }
                 leaf down-count {
                   description "Number of OAM cells to consider VC down";
                   type union {
                     type string {
                       pattern "<.*>|$.*";
                     }
                     type uint32 {
                       range "1 .. 255";
                     }
                   }
                 }
               }
               leaf inverse-arp {
                 description "Enable inverse ARP reply messages";
                 type empty;
               }
               leaf transmit-weight {
                 description "ATM2 transmit weight for VC under VP tunnel";
                 type union {
                   type string {
                     pattern "<.*>|$.*";
                   }
                   type uint16 {
                     range "1 .. 32767";
                   }
                 }
               }
               container epd-threshold {
                 description "Early packet discard threshold for ATM2";
                 junos:cli-feature "oneliner";
                 uses epd_threshold_config;
               }
             }
             list arp {
               key name;
               ordered-by user;
               junos:cli-feature "oneliner";
               description "Static Address Resolution Protocol entries";
               leaf name {
                 description "Destination IP address";
                 junos:cli-feature "nokeyword";
                 type jt:ipv4addr;
               }
               leaf l2-interface {
                 description "Layer 2 interface name for ARP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to ARP requests for this entry";
                 junos:must "((\".. mac\" || \".. multicast-mac\"))";
                 junos:must-message "mac or multicast-mac must be configured to publish";
                 type empty;
               }
               leaf flood-as-unknown-unicast {
                 description "Broadcast the packet with unicast MAC";
                 junos:must "(!(\".. l2-interface\"))";
                 junos:must-message "l2-interface cannot be configured with flood-as-unknown-unicast";
                 junos:must "(\".. mac\")";
                 junos:must-message "mac must be configured to flood-as-unknown-unicast";
                 type empty;
               }
             }
             list host-discovery {
               key name;
               ordered-by user;
               junos:cli-feature "oneliner";
               description "Discover servers IP based on subnet range";
               junos:must "(\"system arp proactive-arp-detection \")";
               junos:must-message "Proactive ARP Detection feature should be enabled";
               max-elements 8;
               leaf name {
                 description "IP address subnet range";
                 junos:cli-feature "nokeyword";
                 type jt:ipv4prefix;
               }
               leaf aging-timer {
                 description "ARP aging timer";
                 type union {
                   type string {
                     pattern "<.*>|$.*";
                   }
                   type uint32 {
                     range "10 .. 1200";
                   }
                 }
               }
               leaf discovery-interval {
                 description "ARP proactive discovery time";
                 type union {
                   type string {
                     pattern "<.*>|$.*";
                   }
                   type uint32 {
                     range "3 .. 300";
                   }
                 }
               }
             }
             list vrrp-group {
               key name;
               ordered-by user;
               description "VRRP group";
               uses vrrp-group;
             }
             leaf virtual-gateway-address {
               description "Virtual Gateway IP address";
               junos:must "(!(\".. vrrp-group\"))";
               junos:must-message "vrrp configuration incompatible with virtual gateway address";
               type jt:ipv4addr;
             }
           }
           container unnumbered-address {
             junos:cli-feature "oneliner";
             description "Unnumbered interface address/destination prefix";
             leaf source {
               description "Interface from which to take local address";
               junos:cli-feature "nokeyword";
               junos:must "(\"interfaces $$-IFL family inet address\")";
               junos:must-message "referred interface must have address configured under family inet";
               type union {
                 type jt:interface-unit;
                 type string {
                   pattern "<.*>|$.*";
                 }
               }
             }
             leaf preferred-source-address {
               description "Preferred address on the donor interface";
               type string;
             }
             leaf destination {
               description "Destination address";
               type jt:ipv4addr;
             }
             leaf destination-profile {
               description "Profile to use for destination address";
               junos:must "(\"access group-profile $$ ppp\")";
               junos:must-message "referenced group-profile must be defined and must contain ppp statement";
               type string;
             }
           }
           leaf negotiate-address {
             description "Negotiate address with remote";
             junos:must "(!(\".. .. .. .. encapsulation multilink-frame-relay-uni-nni\"))";
             junos:must-message "negotiate-address is not supported with family mlfr-uni-nni ";
             junos:must "(!(\".. .. .. encapsulation multilink-frame-relay-end-to-end\"))";
             junos:must-message "negotiate-address is not supported with family mlfr-end-to-end ";
             junos:must "(!(\".. location-pool-address\"))";
             junos:must-message "negotiate-address and location-pool-address must not be defined simultaneously";
             junos:must "(!(\".. unnumbered-address\"))";
             junos:must-message "negotiate-address and unnumbered-address must not be defined simultaneously";
             junos:must "(!(\".. address\"))";
             junos:must-message "negotiate-address and address must not be defined simultaneously";
             type empty;
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10000 .. 10009";
               }
             }
           }
           container auto-configure {
             description "Auto configuration";
             uses dynamic_ipv4_type;
           }
         }
         container iso {
           presence "enable iso";
           junos:must "(!(\".. .. encapsulation frame-relay-ppp\"))";
           junos:must-message "family iso is not supported on encapsulation frame-relay-ppp";
           description "OSI ISO protocol parameters";
           uses apply-advanced;
           list address {
             key name;
             ordered-by user;
             description "Interface address";
             leaf name {
               description "Interface address";
               junos:cli-feature "nokeyword";
               type jt:isoaddr;
             }
             uses apply-advanced;
           }
           leaf mtu {
             description "Protocol family maximum transmission unit";
             type union {
               type uint32;
               type string {
                 pattern "<.*>|$.*";
               }
             }
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10030 .. 10039";
               }
             }
           }
         }
         container inet6 {
           presence "enable inet6";
           description "IPv6 protocol parameters";
           uses apply-advanced;
           leaf source-lookup {
             description "Set source lookup flag";
             junos:must "(!(\".. accouting source-class-usage\"))";
             junos:must-message " Source lookup is not allowed with source-class-usage";
             type empty;
           }
           container class-based-filtering {
             description "Enable class based filter on interface";
             uses apply-advanced;
           }
           container dhcpv6-client {
             junos:must "(!(\"system services dhcp\"))";
             junos:must-message "Incompatible with the dhcp server configured under 'system services dhcp'";
             junos:must "(!(\"system autoinstallation\"))";
             junos:must-message "Incompatible with 'system autoinstallation'";
             junos:must "(!(\".. address\"))";
             junos:must-message "Incompatible with interface assigned with address";
             junos:must "(!(any \"forwarding-options dhcp-relay dhcpv6  group <*> interface ${interface}.${unit}\"))";
             junos:must-message "DHCPv6 client and relay cannot be configured on the same interface ";
             junos:must "(!(any \"system services dhcp-local-server dhcpv6 group <*> interface ${interface}.${unit}\"))";
             junos:must-message "DHCPv6 client and server cannot be configured on the same interface ";
             description "Dynamic Host Configuration Protocol DHCPv6 client configuration";
             uses apply-advanced;
             leaf client-type {
               description "DHCPv6 client type";
               type enumeration {
                 enum "stateful" {
                   description "Stateful client type for address assignment.";
                 }
                 enum "autoconfig" {
                   description "Autoconfig  client type for router-advertisement";
                   junos:must "(\"protocols router-advertisement interface ${interface}.${unit}\")";
                   junos:must-message "Interface for ra messages is must for auto mode";
                   junos:must "(!(\"interfaces ${interface} unit ${unit} family inet6 dhcpv6-client update-router-advertisement\"))";
                   junos:must-message "Incompatible with 'dhcpv6-client update-router-advertisement'";
                   junos:must "(!(\"interfaces ${interface} unit ${unit} family inet6 dhcpv6-client client-ia-type ia-pd\"))";
                   junos:must-message "Incompatible with 'client-ia-type ia-pd'";
                 }
               }
             }
             list client-ia-type {
               key name;
               ordered-by user;
               description "DHCPv6 client identity association type";
               leaf name {
                 junos:cli-feature "nokeyword";
                 type enumeration {
                   enum "ia-na" {
                     description "Identity Association-Non-temporary Address";
                   }
                   enum "ia-pd" {
                     description "Identity Association-Prefix Address";
                   }
                 }
               }
               uses apply-advanced;
             }
             container rapid-commit {
               presence "enable rapid-commit";
               description "Option is used to signal the use of the two message exchange for address assignment";
             }
             leaf interface-identifier {
               description "Identifier for this interface";
               type jt:ipv6addr;
             }
             leaf use-ra-prefix {
               description "Assign interface IP from RA prefix when ia-na address not received";
               junos:must "(\"interfaces ${interface} unit ${unit} family inet6 dhcpv6-client client-ia-type ia-na\")";
               junos:must-message "Incompatible with out 'client-ia-type ia-na'";
               junos:must "(\"interfaces ${interface} unit ${unit} family inet6 dhcpv6-client client-type stateful\")";
               junos:must-message "Incompatible with out 'client-type stateful'";
               type empty;
             }
             container prefix-delegating {
               junos:must "(\"interfaces ${interface} unit ${unit} family inet6 dhcpv6-client client-ia-type ia-pd\")";
               junos:must-message "Incompatible with out 'client-ia-type ia-pd'";
               description "Prefix delegating parameters";
               uses apply-advanced;
               leaf preferred-prefix-length {
                 description "Client preferred prefix length";
                 type union {
                   type string {
                     pattern "<.*>|$.*";
                   }
                   type uint32 {
                     range "0 .. 64";
                   }
                 }
               }
               leaf sub-prefix-length {
                 description "The sub prefix length for LAN interfaces";
                 type union {
                   type string {
                     pattern "<.*>|$.*";
                   }
                   type uint32 {
                     range "1 .. 127";
                   }
                 }
               }
             }
             container client-identifier {
               junos:cli-feature "oneliner";
               description "DHCP Server identifies a client by client-identifier value ";
               leaf duid-type {
                 description "DUID identifying a client";
                 type enumeration {
                   enum "duid-llt" {
                     description "Link-layer address plus time";
                   }
                   enum "vendor" {
                     description "Vendor-assigned unique ID based on Enterprise Number";
                   }
                   enum "duid-ll" {
                     description "Link-layer address";
                   }
                 }
               }
             }
             leaf vendor-id {
               description "Vendor class id for the dhcpv6 client";
               type string {
                 length "1 .. 60";
               }
             }
             list req-option {
               key name;
               ordered-by user;
               description "DHCPV6 client requested option configuration";
               leaf name {
                 junos:cli-feature "nokeyword";
                 type enumeration {
                   enum "dns-server" {
                     description "Dns-server option";
                   }
                   enum "domain" {
                     description "Dns-server option";
                   }
                   enum "ntp-server" {
                     description "Ntp-server option";
                   }
                   enum "time-zone" {
                     description "Time-zone option";
                   }
                   enum "sip-server" {
                     description "Sip-server option";
                   }
                   enum "sip-domain" {
                     description "Sip-domain option";
                   }
                   enum "nis-server" {
                     description "Nis-server option";
                   }
                   enum "nis-domain" {
                     description "Nis-domain option";
                   }
                   enum "fqdn" {
                     description "Fully-qualified-domain option";
                   }
                   enum "vendor-spec" {
                     description "Vendor-spec option";
                   }
                   enum "zero-touch-redirect" {
                     description "Zero-touch-redirect";
                   }
                   enum "bootfile-url" {
                     description "Bootfile url";
                   }
                   enum "bootfile-param" {
                     description "Bootfile param";
                   }
                 }
               }
               uses apply-advanced;
             }
             container options {
               description "DHCP options";
               uses apply-advanced;
               list number {
                 key name;
                 junos:cli-feature "oneliner";
                 description "DHCP option code";
                 leaf name {
                   description "DHCP option identifier code";
                   junos:cli-feature "nokeyword";
                   type union {
                     type string {
                       pattern "<.*>|$.*";
                     }
                     type uint32 {
                       range "1 .. 254";
                     }
                   }
                 }
                 choice option-type-choice {
                   case case_1 {
                     leaf hex-string {
                       description "Hexadecimal string";
                       type string {
                         length "1 .. 510";
                         junos:posix-pattern "^[[:xdigit:]]+$";
                         junos:pattern-message "Must be hexadecimal digits (0-9, a-f, A-F)";
                       }
                     }
                   }
                 }
               }
             }
             leaf retransmission-attempt {
               description "Number of attempts to retransmit the DHCPV6 client protocol packet";
               default "9";
               type union {
                 type string {
                   pattern "<.*>|$.*";
                 }
                 type uint32 {
                   range "0 .. 50000";
                 }
               }
             }
             container update-router-advertisement {
               junos:must "(\"interfaces ${interface} unit ${unit} family inet6 dhcpv6-client client-ia-type $$={2}\")";
               junos:must-message "Incompatible without 'client-ia-type ia-pd'";
               description "Dhcpv6 client update rpd for prefix delegation";
               uses apply-advanced;
               list interface {
                 key name;
                 ordered-by user;
                 description "Interfaces on which to delegate prefix";
                 max-elements 3;
                 leaf name {
                   description "Interfaces-name on which to delegate prefix";
                   junos:cli-feature "nokeyword";
                   junos:must "(unique \"interfaces <*> unit 0 family inet6 dhcpv6-client update-router-advertisement interface $$\")";
                   junos:must-message "This interface is already updated by a dhcpv6-client";
                   junos:must "(!(\"protocols router-advertisement interface $$\"))";
                   junos:must-message "Incompatible with the interface configured under 'protocols router-advertisement interface'";
                   type union {
                     type jt:interface-name;
                     type string {
                       pattern "<.*>|$.*";
                     }
                   }
                 }
                 uses apply-advanced;
                 leaf interface-identifier {
                   description "Identifier for this interface";
                   type jt:ipv6addr;
                 }
                 leaf prefix-identifier {
                   description "Prefix identifier for prefix used in this interface";
                   type jt:ipv6addr;
                 }
                 choice managed-configuration-choice {
                   leaf managed-configuration {
                     description "Set managed address configuration";
                     type empty;
                   }
                   leaf no-managed-configuration {
                     description "Don't set managed address configuration";
                     type empty;
                   }
                 }
                 choice other-stateful-configuration-choice {
                   leaf other-stateful-configuration {
                     description "Set other stateful configuration";
                     type empty;
                   }
                   leaf no-other-stateful-configuration {
                     description "Don't set other stateful configuration";
                     type empty;
                   }
                 }
                 leaf max-advertisement-interval {
                   description "Maximum advertisement interval";
                   units "seconds";
                   type union {
                     type string {
                       pattern "<.*>|$.*";
                     }
                     type uint32 {
                       range "4 .. 1800";
                     }
                   }
                 }
                 leaf min-advertisement-interval {
                   description "Minimum advertisement interval";
                   units "seconds";
                   type union {
                     type string {
                       pattern "<.*>|$.*";
                     }
                     type uint32 {
                       range "3 .. 1350";
                     }
                   }
                 }
                 choice enable-recursive-dns-server-option-choice {
                   leaf enable-recursive-dns-server-option {
                     description "Enables the recursive DNS server option";
                     type empty;
                   }
                   leaf no-enable-recursive-dns-server-option {
                     description "Don't enables the recursive DNS server option";
                     type empty;
                   }
                 }
               }
             }
           }
           leaf mac-validate {
             description "Validate source MAC address";
             type enumeration {
               enum "strict" {
                 description "Strict mac-validation";
               }
               enum "loose" {
                 description "Loose mac-validation";
               }
             }
           }
           container rpf-check {
             presence "enable rpf-check";
             junos:cli-feature "oneliner-plus";
             description "Enable reverse-path-forwarding checks on this interface";
             uses apply-advanced;
             leaf fail-filter {
               description "Name of filter applied to packets failing RPF check";
               type string;
             }
             container mode {
               junos:cli-feature "oneliner";
               description "Mode for reverse path forwarding";
               leaf loose {
                 description "Reverse-path-forwarding loose mode";
                 type empty;
               }
             }
           }
           container accounting {
             description "Interface-based accounting options";
             uses apply-advanced;
             container source-class-usage {
               junos:must "(!(\".. .. class-based-filtering source-class-usage\"))";
               junos:must-message "source-class-usage is not allowed with class-based-filtering source-class-usage";
               junos:must "(!(\".. .. source-lookup\"))";
               junos:must-message " source-class-usage is not allowed with source-lookup";
               uses apply-advanced;
               leaf input {
                 description "Interface for source-class-usage input";
                 type empty;
               }
               leaf output {
                 description "Interface for source-class-usage output";
                 type empty;
               }
             }
             leaf destination-class-usage {
               description "Enable destination class usage on this interface";
               junos:must "(!(\".. .. class-based-filtering destination-class-usage\"))";
               junos:must-message "destination-class-usage is not allowed with class-based-filtering destination-class-usage";
               type empty;
             }
           }
           leaf mtu {
             description "Protocol family maximum transmission unit";
             type union {
               type uint32;
               type string {
                 pattern "<.*>|$.*";
               }
             }
           }
           leaf nd6-stale-time {
             description "Stale time to reconfirm reachability with inet6 neighbour";
             units "seconds";
             type union {
               type string {
                 pattern "<.*>|$.*";
               }
               type uint32 {
                 range "1 .. 18000";
               }
             }
           }
           leaf no-neighbor-learn {
             description "Disable neighbor address learning on interface";
             type empty;
           }
           container ndp-proxy {
             description "Enable ndp proxy on interface";
             uses apply-advanced;
             leaf interface-restricted {
               description "Enable ndp interface proxy restricted to interface";
               junos:must "(!(\".. interface-unrestricted\"))";
               junos:must-message "interface-restricted and interface-unrestricted are not allowed together";
               type empty;
             }
             leaf interface-unrestricted {
               description "Enable ndp interface proxy unrestricted to interface";
               junos:must "(!(\".. interface-restricted\"))";
               junos:must-message "interface-restricted and interface-unrestricted are not allowed together";
               type empty;
             }
           }
           container dad-proxy {
             junos:must "(\".. ndp-proxy\")";
             junos:must-message "ndp-proxy must be configured";
             description "DAD proxy on interface";
             uses apply-advanced;
             leaf interface-restricted {
               description "Enable DAD interface proxy restricted to interface";
               junos:must "(!(\".. interface-unrestricted\"))";
               junos:must-message "interface-restricted and interface-unrestricted are not allowed together";
               junos:must "(\".. .. ndp-proxy interface-restricted\")";
               junos:must-message "ndp-proxy interface-restricted must be configured to set this";
               type empty;
             }
             leaf interface-unrestricted {
               description "Enable DAD interface proxy unrestricted to interface";
               junos:must "(!(\".. interface-restricted\"))";
               junos:must-message "interface-restricted and interface-unrestricted are not allowed together";
               junos:must "(\".. .. ndp-proxy interface-unrestricted\")";
               junos:must-message "ndp-proxy interface-unrestricted must be configured to set this";
               type empty;
             }
           }
           leaf nd6-max-cache {
             description "Max interface ND nexthop cache size";
             type union {
               type string {
                 pattern "<.*>|$.*";
               }
               type uint32 {
                 range "1 .. 2000000";
               }
             }
           }
           leaf nd6-new-hold-limit {
             description "Max no. of new unresolved nexthops";
             junos:must "(\".. nd6-max-cache\")";
             junos:must-message "Interface max ND cache size must be configured";
             type union {
               type string {
                 pattern "<.*>|$.*";
               }
               type uint32 {
                 range "1 .. 2000000";
               }
             }
           }
           leaf no-redirects {
             description "Do not redirect traffic";
             type empty;
           }
           container filter {
             description "Packet filtering";
             uses apply-advanced;
             choice input_choice {
               case case_1 {
                 container input {
                   junos:cli-feature "oneliner";
                   description "Filter to be applied to received packets";
                   leaf filter-name {
                     description "Name of the filter";
                     junos:cli-feature "nokeyword";
                     junos:must "((!(\".. .. .. rpf-check\") || (!(any \"firewall family inet6 filter $$ term <*> from first-byte-of-payload\") && !(any \"firewall family inet6 filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   junos:cli-feature "oneliner";
                   description "Filter to be applied to transmitted packets";
                   leaf filter-name {
                     description "Name of the filter";
                     junos:cli-feature "nokeyword";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             leaf-list input-chain {
               ordered-by user;
               description "List of filter modules applied to received packets ";
               type string;
             }
             leaf-list output-chain {
               ordered-by user;
               description "List of filter modules applied to transmitted packets ";
               type string;
             }
             container adf {
               description "Ascend Data Filter definition";
               uses apply-advanced;
               list rule {
                 key name;
                 ordered-by user;
                 description "Set of ADF rules";
                 leaf name {
                   description "Value for a single rule";
                   junos:cli-feature "nokeyword";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32;
               }
             }
           }
           container policer {
             description "Interface policing";
             uses apply-advanced;
             leaf input {
               description "Name of policer applied to received packets";
               type string;
             }
             leaf output {
               description "Name of policer applied to transmitted packets";
               type string;
             }
           }
           container sampling {
             junos:must "((\"forwarding-options sampling family inet6\" || (\"forwarding-options packet-capture\" || any \"forwarding-options sampling instance <*> family inet6\")))";
             junos:must-message "Requires forwarding-options sampling or packet-capture config";
             description "Interface sampling";
             uses apply-advanced;
             leaf input {
               description "Sample all packets input on this interface";
               type empty;
             }
             leaf output {
               description "Sample all packets output on this interface";
               type empty;
             }
           }
           choice tunnel-termination-status {
             case case_1 {
               leaf tunnel-termination {
                 description "Tunnel termination";
                 type empty;
               }
             }
             case case_2 {
               leaf no-tunnel-termination {
                 description "No Tunnel termination";
                 type empty;
               }
             }
           }
           list address {
             key name;
             ordered-by user;
             description "Interface address or destination prefix";
             junos:must "(!(\".. unnumbered-address\"))";
             junos:must-message "ipv6 unnumbered-address and ipv6 address must not be defined simultaneously";
             leaf name {
               description "Interface address or destination prefix";
               junos:cli-feature "nokeyword";
               type jt:ipv6prefix;
             }
             uses apply-advanced;
             leaf destination {
               description "Destination address";
               type jt:ipv6addr;
             }
             leaf eui-64 {
               description "Generate EUI-64 interface ID";
               type empty;
             }
             leaf primary {
               description "Candidate for primary address in system";
               type empty;
             }
             leaf preferred {
               description "Preferred address on interface";
               type empty;
             }
             leaf master-only {
               description "Master management IP address for router";
               type empty;
             }
             container tag {
               description "Tag used for route/local";
               uses apply-advanced;
               leaf tag-value {
                 description "The tag value on the address";
                 junos:cli-feature "nokeyword";
                 type union {
                   type string {
                     pattern "<.*>|$.*";
                   }
                   type uint32 {
                     range "1 .. 4294967295";
                   }
                 }
               }
               leaf type {
                 description "Tag type must be [1-16]";
                 type union {
                   type string {
                     pattern "<.*>|$.*";
                   }
                   type uint32 {
                     range "1 .. 16";
                   }
                 }
               }
             }
             container tag2 {
               description "Tag2 used for route/local";
               uses apply-advanced;
               leaf tag2-value {
                 description "The tag value on the address";
                 junos:cli-feature "nokeyword";
                 type union {
                   type string {
                     pattern "<.*>|$.*";
                   }
                   type uint32 {
                     range "1 .. 4294967295";
                   }
                 }
               }
               leaf type {
                 description "Tag type must be [1-16]";
                 type union {
                   type string {
                     pattern "<.*>|$.*";
                   }
                   type uint32 {
                     range "1 .. 16";
                   }
                 }
               }
             }
             list ndp {
               key name;
               ordered-by user;
               junos:cli-feature "oneliner";
               description "Static Neighbor Discovery Protocol  entries";
               leaf name {
                 description "Destination IP address";
                 junos:cli-feature "nokeyword";
                 type jt:ipv6addr;
               }
               leaf l2-interface {
                 description "Layer 2 interface name for NDP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to NDP requests for this entry";
                 junos:must "((\".. mac\" || \".. multicast-mac\"))";
                 junos:must-message "either 'mac' or 'multicast-mac' must be configured along with 'publish' statment";
                 type empty;
               }
             }
             list host-discovery {
               key name;
               ordered-by user;
               junos:cli-feature "oneliner";
               description "Discover servers IP based on subnet range";
               junos:must "(\"system arp proactive-arp-detection\")";
               junos:must-message "Proactive ARP detection feature should be enabled";
               max-elements 8;
               leaf name {
                 description "IPv6 address subnet range";
                 junos:cli-feature "nokeyword";
                 type jt:ipv6prefix;
               }
               leaf aging-timer {
                 description "Neighbor solicitation stale timer";
                 type union {
                   type string {
                     pattern "<.*>|$.*";
                   }
                   type uint32 {
                     range "100 .. 1200";
                   }
                 }
               }
               leaf discovery-interval {
                 description "Neighbor proactive discovery time";
                 type union {
                   type string {
                     pattern "<.*>|$.*";
                   }
                   type uint32 {
                     range "3 .. 300";
                   }
                 }
               }
             }
             list vrrp-inet6-group {
               key name;
               ordered-by user;
               description "VRRP group";
               junos:must "(!(\".. eui-64\"))";
               junos:must-message "'vrrp-inet6-group' is not supported when 'eui-64' is configured";
               uses vrrp-group;
             }
             leaf virtual-gateway-address {
               description "Virtual Gateway IP address";
               junos:must "(!(\".. vrrp-inet6-group\"))";
               junos:must-message "vrrp configuration incompatible with virtual gateway address";
               type jt:ipv6addr;
             }
             leaf subnet-router-anycast {
               description "Create a subnet roter anycast address for this address.";
               type empty;
             }
           }
           container unnumbered-address {
             junos:cli-feature "oneliner";
             description "Unnumbered interface address/destination prefix";
             leaf source {
               description "Interface from which to take local address";
               junos:cli-feature "nokeyword";
               junos:must "(\"interfaces $$-IFL family inet6 address\")";
               junos:must-message "referred interface must have address configured under family inet6";
               type union {
                 type jt:interface-unit;
                 type string {
                   pattern "<.*>|$.*";
                 }
               }
             }
             leaf preferred-source-address {
               description "Preferred address on the donor interface";
               type string;
             }
           }
           choice dad-disable-choice {
             leaf dad-disable {
               description "Disable duplicate-address-detection";
               type empty;
             }
             leaf no-dad-disable {
               description "Don't disable duplicate-address-detection";
               type empty;
             }
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10010 .. 10019";
               }
             }
           }
           leaf enhanced-dad-disable {
             description "Disable Enhanced DAD while send NS with Nonce option";
             type empty;
           }
           container auto-configure {
             description "Auto configuration";
             uses dynamic_ipv6_type;
           }
         }
         container mpls {
           presence "enable mpls";
           junos:must "(!(\".. .. encapsulation frame-relay-ppp\"))";
           junos:must-message "family mpls is not supported on encapsulation frame-relay-ppp";
           description "MPLS protocol parameters";
           uses apply-advanced;
           leaf mtu {
             description "Protocol family maximum transmission unit";
             type union {
               type uint32;
               type string {
                 pattern "<.*>|$.*";
               }
             }
           }
           leaf maximum-labels {
             description "Protocol family maximum number of labels";
             type union {
               type string {
                 pattern "<.*>|$.*";
               }
               type uint32;
             }
           }
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
           }
           container ingress-queuing-filter {
             junos:cli-feature "oneliner";
             description "Protocol family ingress-queuing-filter";
             leaf filter-name {
               description "Name of the ingress-queuing-filter";
               junos:cli-feature "nokeyword";
               type string;
             }
           }
           container policer {
             description "Interface policing";
             uses apply-advanced;
             leaf input {
               description "Name of policer applied to received packets";
               type string;
             }
             leaf output {
               description "Name of policer applied to transmitted packets";
               type string;
             }
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10020 .. 10029";
               }
             }
           }
         }
         container mlppp {
           junos:must "(!(\"interfaces ${interface} container-options\"))";
           junos:must-message "mlppp is not supported for container interfaces";
           description "Multilink PPP protocol parameters";
           uses apply-advanced;
           leaf bundle {
             description "Logical interface name this link will join";
             junos:must "((!(\".. .. .. dial-options\") || \"interfaces $$-IFL encapsulation multilink-ppp\"))";
             junos:must-message "Bundle interface must be configured";
             junos:must "((!(\".. .. .. pppoe-options\") || \"interfaces $$-IFL encapsulation multilink-ppp\"))";
             junos:must-message "Bundle interface must be configured";
             type string;
           }
           choice anchor-points {
             case case_1 {
             }
             case case_2 {
             }
           }
           leaf dynamic-profile {
             description " dynamic profile for interface to use";
             junos:must "(\"dynamic-profiles $$\")";
             junos:must-message "referenced dynamic-profile must be defined";
             type string {
               length "1 .. 80";
             }
           }
         }
         container mlfr-end-to-end {
           presence "enable mlfr-end-to-end";
           junos:must "(!(\".. .. encapsulation frame-relay-ppp\"))";
           junos:must-message "family mlfr-end-to-end is not supported on encapsulation frame-relay-ppp";
           description "Multilink Frame Relay end-to-end protocol parameters";
           uses apply-advanced;
           leaf bundle {
             description "Logical interface name this link will join";
             type union {
               type jt:interface-unit;
               type string {
                 pattern "<.*>|$.*";
               }
             }
           }
         }
         container mlfr-uni-nni {
           presence "enable mlfr-uni-nni";
           junos:must "(!(\".. .. encapsulation frame-relay-ppp\"))";
           junos:must-message "family mlfr-uni-uni is not supported on encapsulation frame-relay-ppp";
           description "Multilink Frame Relay UNI NNI protocol parameters";
           uses apply-advanced;
           leaf bundle {
             description "Logical interface name this link will join";
             type union {
               type jt:interface-unit;
               type string {
                 pattern "<.*>|$.*";
               }
             }
           }
         }
         container ccc {
           presence "enable ccc";
           junos:must "(!(\".. .. encapsulation frame-relay-ppp\"))";
           junos:must-message "family ccc is not supported on encapsulation frame-relay-ppp";
           description "Circuit cross-connect parameters";
           uses apply-advanced;
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
           leaf translate-fecn-and-becn {
             description "Translate FECN and BECN bits";
             type empty;
           }
           choice de-or-plp {
             case case_1 {
               leaf translate-discard-eligible {
                 description "Translate DE bit";
                 type empty;
               }
             }
             case case_2 {
             }
           }
           leaf keep-address-and-control {
             description "Don't strip PPP address and control bytes";
             type empty;
           }
         }
         container tcc {
           presence "enable tcc";
           junos:must "(!(\".. .. encapsulation frame-relay-ppp\"))";
           junos:must-message "family tcc is not supported on encapsulation frame-relay-ppp";
           description "Translational cross-connect parameters";
           uses apply-advanced;
           container policer {
             description "Interface policing";
             uses apply-advanced;
             leaf input {
               description "Name of policer applied to received packets";
               type string;
             }
             leaf output {
               description "Name of policer applied to transmitted packets";
               type string;
             }
           }
           container proxy {
             presence "enable proxy";
             uses apply-advanced;
             leaf inet-address {
               description "Remote host address on non-Ethernet side of Ethernet TCC";
               type jt:ipv4addr;
             }
           }
           container remote {
             presence "enable remote";
             uses apply-advanced;
             leaf inet-address {
               description "Remote host address on Ethernet side of Ethernet TCC";
               type jt:ipv4addr;
             }
             leaf mac-address {
               description "Remote host MAC address on Ethernet side of Ethernet TCC";
               type jt:mac-addr;
             }
           }
           leaf-list protocols {
             ordered-by user;
             description "Protocols supported on TCC interface";
             type enumeration {
               enum "mpls" {
                 description "Multiprotocol Label Switching";
               }
               enum "inet" {
                 description "IP version 4";
               }
               enum "iso" {
                 description "International Organization for Standardization";
               }
               enum "inet6" {
                 description "IP version 6";
               }
             }
           }
         }
         container vpls {
           presence "enable vpls";
           description "Virtual private LAN service parameters";
           uses apply-advanced;
           leaf core-facing {
             description "Interface is core facing";
             type empty;
           }
           container filter {
             description "Packet filtering";
             uses apply-advanced;
             choice input_choice {
               case case_1 {
                 container input {
                   junos:cli-feature "oneliner";
                   description "Filter to be applied to received packets";
                   leaf filter-name {
                     description "Name of the filter";
                     junos:cli-feature "nokeyword";
                     junos:must "((!(\".. .. .. rpf-check\") || (!(any \"firewall family inet filter $$ term <*> from first-byte-of-payload\") && !(any \"firewall family inet filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             leaf-list input-chain {
               ordered-by user;
               description "List of filter modules applied to received packets ";
               type string;
             }
             leaf-list output-chain {
               ordered-by user;
               description "List of filter modules applied to transmitted packets ";
               type string;
             }
             choice output_choice {
               case case_1 {
                 container output {
                   junos:cli-feature "oneliner";
                   description "Filter to be applied to transmitted packets";
                   leaf filter-name {
                     description "Name of the filter";
                     junos:cli-feature "nokeyword";
                     junos:must "((!(\".. .. .. rpf-check\") || (!(any \"firewall family inet filter $$ term <*> from first-byte-of-payload\") && !(any \"firewall family inet filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   junos:cli-feature "nokeyword";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
         }
         container ethernet-switching {
           description "Ethernet switching parameters";
           presence "enable ethernet-switching";
           junos:must "((!(\".. vpls\") && (!(\".. inet\") && (!(\".. inet6\") && (!(\".. bridge\") && (!(\".. ccc\") && (!(\".. iso\") && (!(\".. llc2\") && (!(\".. mpls\") && (!(\".. tcc\") && (!(\".. pppoe\") && !(\".. gre\"))))))))))))";
           junos:must-message "Family ethernet-switching and rest of the families are mutually exclusive";
           uses ethernet-switching-type;
         }
         container fibre-channel {
           description "Fibre channel switching parameters";
           presence "enable fibre-channel";
           uses fibre-channel-type;
         }
         container any {
           presence "enable any";
           description "Parameters for 'any' family";
           uses apply-advanced;
           container filter {
             description "Layer 2 packet filtering";
             uses apply-advanced;
             leaf input {
               description "Name of filter applied to received packets";
               junos:must "((\"firewall family any filter $$\" || (!(\"firewall\") && \".. .. .. .. .. .. firewall family any filter $$\")))";
               junos:must-message "referenced filter must be defined under firewall family any";
               type string {
                 junos:posix-pattern "!^((__.*)|(.{65,}))$";
                 junos:pattern-message "Must be a non-reserved string of 64 characters or less";
               }
             }
             leaf group {
               description "Group to which interface belongs";
               type union {
                 type string {
                   pattern "<.*>|$.*";
                 }
                 type uint32 {
                   range "1 .. 255";
                 }
               }
             }
           }
         }
         uses apply-advanced;
       }
       leaf service-domain {
         description "Service domain to which interface belongs";
         type enumeration {
           enum "inside" {
             description "Inside network";
           }
           enum "outside" {
             description "Outside network";
           }
         }
       }
       leaf copy-tos-to-outer-ip-header {
         description "Copy IP payload header's ToS field to GRE delivery header";
         type empty;
       }
       container load-balancing-options {
         junos:must "(!(\".. .. load-balancing-options high-availability-options one-to-one\"))";
         junos:must-message "load-balancing-options are used when number of active members is more than one";
         description "AMS subunit load balancing options";
         uses apply-advanced;
         leaf preferred-active {
           description "Preferred active Interface name";
           junos:must "((\".. .. .. load-balancing-options member-interface $$\" && !(\".. .. .. load-balancing-options high-availability-options many-to-one preferred-backup $$\")))";
           junos:must-message "Active should be one of member-interfaces excluding preferred-backup";
           type union {
             type jt:interface-device;
             type string {
               pattern "<.*>|$.*";
             }
           }
         }
         leaf disable-hash {
           description "Hash based distribution is not needed for this subunit";
           junos:must "(\".. .. service-domain\")";
           junos:must-message "service-domain must be configured if disable-hash is enabled";
           junos:must "(!(\".. hash-keys\"))";
           junos:must-message "hash-keys must not be configured if disable-hash is enabled";
           type empty;
         }
         leaf modulo-key {
           description "Modulo based distribution";
           junos:must "(!(\".. .. .. load-balancing-options member-failure-options redistribute-all-traffic\"))";
           junos:must-message "redistribute-all-traffic can not be configured with modulo-key";
           junos:must "(!(\".. disable-hash\"))";
           junos:must-message "disable-hash can not be configured with modulo-key";
           junos:must "(\".. .. service-domain\")";
           junos:must-message "service-domain must be configured with modulo-key";
           junos:must "(!(\".. hash-keys\"))";
           junos:must-message "hash-keys can not be configured with modulo-key";
           type enumeration {
             enum "source-ip" {
               description "Source Ip Address";
             }
             enum "destination-ip" {
               description "Destination Ip Address";
             }
           }
         }
         container hash-keys {
           uses apply-advanced;
           leaf-list ingress-key {
             ordered-by user;
             description "Hash Key for the ingress direction";
             type enumeration {
               enum "source-ip" {
                 description "Source Ip Address";
               }
               enum "destination-ip" {
                 description "Destination Ip Address";
               }
               enum "protocol" {
                 description "Protocol";
               }
               enum "iif" {
                 description "Incoming Interface";
               }
             }
           }
           leaf-list egress-key {
             ordered-by user;
             description "Hash Key for the egress direction";
             status deprecated;
             type enumeration {
               enum "source-ip" {
                 description "Source Ip Address";
                 status deprecated;
               }
               enum "destination-ip" {
                 description "Destination Ip Address";
                 status deprecated;
               }
               enum "protocol" {
                 description "Protocol";
                 status deprecated;
               }
               enum "oif" {
                 description "Outgoing Interface";
                 status deprecated;
               }
             }
           }
           leaf ipv6-source-prefix-length {
             description "IPv6 source prefix length for hash computation";
             type enumeration {
               enum "56" {
                 description "56 bit IPv6 address prefix";
               }
               enum "64" {
                 description "64 bit IPv6 address prefix";
               }
               enum "96" {
                 description "96 bit IPv6 address prefix";
               }
               enum "128" {
                 description "Complete 128 bit IPv6 address";
               }
             }
           }
         }
       }
       container interface-state {
         description "IRB interface state computation";
         uses apply-advanced;
         choice state {
           case case_1 {
             leaf local {
               description "IRB State computation based on local interface state";
               type empty;
             }
           }
           case case_2 {
             leaf remote {
               description "IRB State computation based on remote reachability";
               type empty;
             }
           }
           case case_3 {
             leaf local-remote {
               description "IRB State computation based on local or remote reachability";
               type empty;
             }
           }
           case case_4 {
             leaf local-interface {
               description "IRB State computation based on loopback AE port state";
               type union {
                 type jt:interface-name;
                 type string {
                   pattern "<.*>|$.*";
                 }
               }
             }
           }
         }
         leaf local-count {
           description "Minimum number of local layer2 link in up state to consider IRB up";
           junos:must "(!(\".. remote\"))";
           junos:must-message "Must configure local, local-remote or keep default";
           type union {
             type uint16;
             type string {
               pattern "<.*>|$.*";
             }
           }
         }
         leaf vtep-count {
           description "Minimum number of VTEP link in up state to consider IRB up";
           junos:must "(!(\".. local\"))";
           junos:must-message "Must configure remote,local-remote or keep default";
           type union {
             type uint16;
             type string {
               pattern "<.*>|$.*";
             }
           }
         }
         container hold-time {
           description "Delay before marking interface up or down for defect";
           uses apply-advanced;
           leaf up {
             description "Delay in seconds before marking IRB interface up";
             units "seconds";
             type union {
               type uint32;
               type string {
                 pattern "<.*>|$.*";
               }
             }
           }
           leaf down {
             description "Delay in seconds before marking IRB interface down";
             units "seconds";
             type union {
               type uint32;
               type string {
                 pattern "<.*>|$.*";
               }
             }
           }
         }
       }
       leaf mac {
         description "Configure logical interface MAC address";
         type jt:mac-unicast;
       }
       leaf virtual-gateway-v4-mac {
         description "Configure virtual gateway IPV4 virtual MAC address";
         type jt:mac-unicast;
       }
       leaf virtual-gateway-v6-mac {
         description "Configure virtual gateway IPV6 virtual MAC address";
         type jt:mac-unicast;
       }
       leaf no-dhcp-flood {
         description "Disable dhcp flooding";
         type empty;
       }
       leaf etree-ac-role {
         description "ETREE attachment circuit role";
         type enumeration {
           enum "root" {
             description "ETREE root interface";
           }
           enum "leaf" {
             description "ETREE leaf interface";
           }
         }
       }
     }
     container no-partition {
       junos:cli-feature "oneliner";
       description "Use channelizable interface as clear channel";
       leaf interface-type {
         description "Interface type";
         type enumeration {
           enum "e1" {
             description "E1 interface";
           }
           enum "t1" {
             description "T1 interface";
           }
           enum "at" {
             description "ATM interface";
           }
           enum "t3" {
             description "T3 interface";
           }
           enum "e3" {
             description "E3 interface";
           }
           enum "ct3" {
             description "Channelized T3 interface";
           }
           enum "so" {
             description "SONET interface";
           }
           enum "cau4" {
             description "CAU4 interface";
           }
         }
       }
     }
     list partition {
       key name;
       ordered-by user;
       junos:cli-feature "oneliner";
       description "Channelized interface partition";
       junos:must "(!(\".. no-partition\"))";
       junos:must-message "cannot set partitions with no-partition attribute turned on";
       leaf name {
         description "Sublevel interface partition index (for example, 1, 3-4)";
         junos:cli-feature "nokeyword";
         type string;
       }
       leaf oc-slice {
         description "Range of SONET/SDH slices (for example, 1, 7-9)";
         type string;
       }
       leaf timeslots {
         description "Timeslots [(1..24) for T1, (1..31) for E1]; for example, 1-3,4,9,22-24 (no spaces)";
         type string;
       }
       leaf interface-type {
         description "Sublevel interface type";
         type enumeration {
           enum "ds" {
             description "DS0 interface";
           }
           enum "e1" {
             description "E1 interface";
           }
           enum "t1" {
             description "T1 interface";
           }
           enum "at" {
             description "ATM interface";
           }
           enum "ct1" {
             description "Channelized T1 interface";
           }
           enum "ce1" {
             description "Channelized E1 interface";
           }
           enum "t3" {
             description "T3 interface";
           }
           enum "ct3" {
             description "Channelized T3 interface";
           }
           enum "e3" {
             description "E3 interface";
           }
           enum "so" {
             description "SONET interface";
           }
           enum "coc1" {
             description "Channelized OC1 interface";
           }
           enum "cau4" {
             description "Channelized AU4 interface";
           }
           enum "dc" {
             description "D channel interface";
             junos:must "(any \".. .. partition <*> interface-type bc\")";
             junos:must-message "BC partition must be defined for PRI";
           }
           enum "bc" {
             description "B channel interface";
             junos:must "(any \".. .. partition <*> interface-type dc\")";
             junos:must-message "DC partition must be defined for PRI";
           }
         }
       }
     }
   }
   grouping juniper-class-of-service-options {
     uses apply-advanced;
     container classifiers {
       description "Classify incoming packets based on code point value";
       uses apply-advanced;
       list dscp {
         key name;
         ordered-by user;
         description "Differentiated Services code point classifier";
         leaf name {
           description "Classifier name";
           junos:cli-feature "nokeyword";
           junos:must "((\".. forwarding-class\" || (\".. import\" || \".. term-id\")))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             junos:cli-feature "nokeyword";
             type string {
               length "1 .. 64";
             }
           }
           uses apply-advanced;
           list loss-priority {
             key name;
             junos:cli-feature "oneliner";
             description "Classify code points to a loss priority";
             leaf name {
               junos:cli-feature "nokeyword";
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list dscp-ipv6 {
         key name;
         ordered-by user;
         description "Differentiated Services code point classifier IPv6";
         leaf name {
           description "Classifier name";
           junos:cli-feature "nokeyword";
           junos:must "((\".. forwarding-class\" || (\".. import\" || \".. term-id\")))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             junos:cli-feature "nokeyword";
             type string {
               length "1 .. 64";
             }
           }
           uses apply-advanced;
           list loss-priority {
             key name;
             junos:cli-feature "oneliner";
             description "Classify code points to a loss priority";
             leaf name {
               junos:cli-feature "nokeyword";
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list exp {
         key name;
         ordered-by user;
         description "MPLS EXP classifier";
         leaf name {
           description "Classifier name";
           junos:cli-feature "nokeyword";
           junos:must "((\".. forwarding-class\" || (\".. import\" || \".. term-id\")))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             junos:cli-feature "nokeyword";
             type string {
               length "1 .. 64";
             }
           }
           uses apply-advanced;
           list loss-priority {
             key name;
             junos:cli-feature "oneliner";
             description "Classify code points to a loss priority";
             leaf name {
               junos:cli-feature "nokeyword";
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list ieee-802.1 {
         key name;
         ordered-by user;
         description "IEEE-802.1 classifier";
         leaf name {
           description "Classifier name";
           junos:cli-feature "nokeyword";
           junos:must "((\".. forwarding-class\" || (\".. import\" || \".. term-id\")))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             junos:cli-feature "nokeyword";
             type string {
               length "1 .. 64";
             }
           }
           uses apply-advanced;
           list loss-priority {
             key name;
             junos:cli-feature "oneliner";
             description "Classify code points to a loss priority";
             leaf name {
               junos:cli-feature "nokeyword";
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list inet-precedence {
         key name;
         ordered-by user;
         description "IPv4 precedence classifier";
         leaf name {
           description "Classifier name";
           junos:cli-feature "nokeyword";
           junos:must "((\".. forwarding-class\" || (\".. import\" || \".. term-id\")))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             junos:cli-feature "nokeyword";
             type string {
               length "1 .. 64";
             }
           }
           uses apply-advanced;
           list loss-priority {
             key name;
             junos:cli-feature "oneliner";
             description "Classify code points to a loss priority";
             leaf name {
               junos:cli-feature "nokeyword";
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list ieee-802.1ad {
         key name;
         ordered-by user;
         description "IEEE-802.1ad (DEI) classifier";
         leaf name {
           description "Classifier name";
           junos:cli-feature "nokeyword";
           junos:must "((\".. forwarding-class\" || (\".. import\" || \".. term-id\")))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             junos:cli-feature "nokeyword";
             type string {
               length "1 .. 64";
             }
           }
           uses apply-advanced;
           list loss-priority {
             key name;
             junos:cli-feature "oneliner";
             description "Classify code points to a loss priority";
             leaf name {
               junos:cli-feature "nokeyword";
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
     }
     container code-point-aliases {
       description "Mapping of code point aliases to bit strings";
       uses apply-advanced;
       list dscp {
         key name;
         junos:cli-feature "homogeneous";
         junos:cli-feature "oneliner";
         description "Differentiated Services code point aliases";
         leaf name {
           description "DSCP alias name";
           junos:cli-feature "nokeyword";
           type string {
             junos:posix-pattern "^([a-zA-Z].{0,63})$";
             junos:pattern-message "Must be string of 64 characters or less beginning with letter";
           }
         }
         leaf bits {
           description "DSCP 6-bit pattern";
           junos:cli-feature "nokeyword";
           type string {
             junos:posix-pattern "^([01]{6})$";
             junos:pattern-message "Must be of form xxxxxx, where x is 1 or 0";
           }
         }
       }
       list dscp-ipv6 {
         key name;
         junos:cli-feature "homogeneous";
         junos:cli-feature "oneliner";
         description "Differentiated Services code point aliases IPv6";
         leaf name {
           description "DSCP IPv6 alias name";
           junos:cli-feature "nokeyword";
           type string {
             junos:posix-pattern "^([a-zA-Z].{0,63})$";
             junos:pattern-message "Must be string of 64 characters or less beginning with letter";
           }
         }
         leaf bits {
           description "DSCP 6-bit pattern";
           junos:cli-feature "nokeyword";
           type string {
             junos:posix-pattern "^([01]{6})$";
             junos:pattern-message "Must be of form xxxxxx, where x is 1 or 0";
           }
         }
       }
       list exp {
         key name;
         junos:cli-feature "homogeneous";
         junos:cli-feature "oneliner";
         description "MPLS EXP code point aliases";
         leaf name {
           description "EXP alias name";
           junos:cli-feature "nokeyword";
           type string {
             junos:posix-pattern "^([a-zA-Z].{0,63})$";
             junos:pattern-message "Must be string of 64 characters or less beginning with letter";
           }
         }
         leaf bits {
           description "EXP 3-bit pattern";
           junos:cli-feature "nokeyword";
           type string {
             junos:posix-pattern "^([01]{3})$";
             junos:pattern-message "Must be of form xxx, where x is 0 or 1";
           }
         }
       }
       list ieee-802.1 {
         key name;
         junos:cli-feature "homogeneous";
         junos:cli-feature "oneliner";
         description "IEEE-802.1 code point aliases";
         leaf name {
           description "IEEE-802.1 alias name";
           junos:cli-feature "nokeyword";
           type string {
             junos:posix-pattern "^([a-zA-Z].{0,63})$";
             junos:pattern-message "Must be string of 64 characters or less beginning with letter";
           }
         }
         leaf bits {
           description "IEEE-802.1 3-bit pattern";
           junos:cli-feature "nokeyword";
           type string {
             junos:posix-pattern "^([01]{3})$";
             junos:pattern-message "Must be of form xxx, where x is 0 or 1";
           }
         }
       }
       list inet-precedence {
         key name;
         junos:cli-feature "homogeneous";
         junos:cli-feature "oneliner";
         description "IPv4 precedence code point aliases";
         leaf name {
           description "IPv4 precedence alias name";
           junos:cli-feature "nokeyword";
           type string {
             junos:posix-pattern "^([a-zA-Z].{0,63})$";
             junos:pattern-message "Must be string of 64 characters or less beginning with letter";
           }
         }
         leaf bits {
           description "IPv4 precedence 3-bit pattern";
           junos:cli-feature "nokeyword";
           type string {
             junos:posix-pattern "^([01]{3})$";
             junos:pattern-message "Must be of form xxx, where x is 0 or 1";
           }
         }
       }
       list ieee-802.1ad {
         key name;
         junos:cli-feature "homogeneous";
         junos:cli-feature "oneliner";
         description "IEEE-802.1ad (DEI) code point aliases";
         leaf name {
           description "IEEE-802.1ad (DEI) alias name";
           junos:cli-feature "nokeyword";
           type string {
             junos:posix-pattern "^([a-zA-Z].{0,63})$";
             junos:pattern-message "Must be string of 64 characters or less beginning with letter";
           }
         }
         leaf bits {
           description "IEEE-802.1ad (DEI) 4-bit pattern";
           junos:cli-feature "nokeyword";
           type string {
             junos:posix-pattern "^([01]{4})$";
             junos:pattern-message "Must be of form xxxx, where x is 0 or 1";
           }
         }
       }
     }
     container host-outbound-traffic {
       description "Classify and mark host traffic to forwarding engine";
       uses apply-advanced;
       leaf forwarding-class {
         description "Classification of host traffic to forwarding engine";
         type string {
           length "1 .. 64";
         }
       }
       leaf dscp-code-point {
         description "Static DSCP code point of egress host traffic";
         type string {
           junos:posix-pattern "^(([01]{6})|([a-zA-Z].{0,63}))$";
           junos:pattern-message "Not 6-bit pattern or code point alias";
         }
       }
       leaf override-firewall {
         description "Override firewall filter actions for RE generated traffic";
         type empty;
       }
       container tcp {
         presence "enable tcp";
         description "Settings for host outbound TCP packets";
         uses apply-advanced;
         leaf raise-internet-control-priority {
           description "Place packets with IP Precedence set to Internet control into Q3 (network-control)";
           type empty;
         }
       }
       container ieee-802.1 {
         presence "enable ieee-802.1";
         description "Mark IEEE 802.1p for host output traffic";
         uses apply-advanced;
         leaf rewrite-rules {
           description "Mark IEEE 802.1p for host outbound traffic using rewrite-rules";
           type empty;
         }
         leaf default {
           description "Mark IEEE 802.1p for host outbound traffic default value";
           type string {
             junos:posix-pattern "^(([01]{3})|([a-zA-Z].{0,63}))$";
             junos:pattern-message "Not 3-bit pattern or code point alias";
           }
         }
       }
       container protocol {
         description "Settings for specific host outbound protocol packets";
         uses apply-advanced;
         container isis-over-gre {
           description "Settings for ISIS over GRE packets";
           uses apply-advanced;
           leaf dscp-code-point {
             description "Static DSCP code point of egress host traffic";
             type string {
               junos:posix-pattern "^(([01]{6})|([a-zA-Z].{0,63}))$";
               junos:pattern-message "Not 6-bit pattern or code point alias";
             }
           }
         }
       }
     }
     list drop-profiles {
       key name;
       junos:cli-feature "homogeneous";
       description "Random Early Drop (RED) data point map";
       leaf name {
         description "Drop profile name";
         junos:cli-feature "nokeyword";
         type string {
           length "1 .. 64";
         }
       }
       uses apply-advanced;
       list fill-level {
         key name;
         junos:cli-feature "oneliner";
         description "Fill-level value of data point";
         leaf name {
           description "Percentage the queue is full";
           junos:cli-feature "nokeyword";
           type union {
             type string {
               pattern "<.*>|$.*";
             }
             type uint32 {
               range "0 .. 100";
             }
           }
         }
         leaf drop-probability {
           description "Probability packet will be dropped";
           type union {
             type string {
               pattern "<.*>|$.*";
             }
             type uint32 {
               range "0 .. 100";
             }
           }
         }
       }
       container interpolate {
         description "Data points interpolated";
         uses apply-advanced;
         leaf-list fill-level {
           ordered-by user;
           description "Data points for queue full percentage";
           type union {
             type string {
               pattern "<.*>|$.*";
             }
             type uint32 {
               range "0 .. 100";
             }
           }
         }
         leaf-list drop-probability {
           ordered-by user;
           description "Data points for packet drop probability";
           type union {
             type string {
               pattern "<.*>|$.*";
             }
             type uint32 {
               range "0 .. 100";
             }
           }
         }
       }
     }
     leaf tri-color {
       description "Enable tricolor marking";
       type empty;
     }
     container shared-buffer {
       description "Shared buffer configuration";
       uses apply-advanced;
       leaf percent {
         description "Percentage of shared buffer to be used";
         type union {
           type string {
             pattern "<.*>|$.*";
           }
           type uint32 {
             range "5 .. 100";
           }
         }
       }
       container ingress {
         description "Shared buffer configuration at ingress";
         uses apply-advanced;
         leaf percent {
           description "Percentage of shared buffer to be used at ingress";
           type union {
             type string {
               pattern "<.*>|$.*";
             }
             type uint32 {
               range "0 .. 100";
             }
           }
         }
         list buffer-partition {
           key name;
           description "Buffer-partition";
           leaf name {
             description "Buffer-partition name";
             junos:cli-feature "nokeyword";
             type string {
               junos:posix-pattern "^.{1,64}$";
               junos:pattern-message "Must be string of 64 characters or less";
             }
           }
           uses apply-advanced;
           leaf percent {
             description "Percentage of ingress shared buffer to be used";
             type union {
               type string {
                 pattern "<.*>|$.*";
               }
               type uint32 {
                 range "0 .. 100";
               }
             }
           }
           leaf dynamic-threshold {
             description "Threshold for maximum buffer share for a queue at ingress buffer-partition";
             type union {
               type string {
                 pattern "<.*>|$.*";
               }
               type uint32 {
                 range "0 .. 10";
               }
             }
           }
         }
       }
       container egress {
         description "Shared buffer configuration at egress";
         uses apply-advanced;
         leaf percent {
           description "Percentage of shared buffer to be used at egress";
           type union {
             type string {
               pattern "<.*>|$.*";
             }
             type uint32 {
               range "0 .. 100";
             }
           }
         }
         list buffer-partition {
           key name;
           description "Buffer-partition";
           leaf name {
             description "Buffer-partition name";
             junos:cli-feature "nokeyword";
             type string {
               junos:posix-pattern "^.{1,64}$";
               junos:pattern-message "Must be string of 64 characters or less";
             }
           }
           uses apply-advanced;
           leaf percent {
             description "Percentage of egress shared buffer to be used";
             type union {
               type string {
                 pattern "<.*>|$.*";
               }
               type uint32 {
                 range "0 .. 100";
               }
             }
           }
           leaf dynamic-threshold {
             description "Threshold for maximum buffer share for a queue at egress buffer-partition";
             type union {
               type string {
                 pattern "<.*>|$.*";
               }
               type uint32 {
                 range "0 .. 10";
               }
             }
           }
         }
       }
     }
     container dedicated-buffer {
       description "Dedicated buffer configuration";
       uses apply-advanced;
       container ingress {
         description "Dedicated buffer configuration at ingress";
         uses apply-advanced;
         leaf percent {
           description "Percentage of dedicated buffer to be used at ingress";
           type union {
             type string {
               pattern "<.*>|$.*";
             }
             type uint32 {
               range "15 .. 100";
             }
           }
         }
       }
       container egress {
         description "Dedicated buffer configuration at egress";
         uses apply-advanced;
         leaf percent {
           description "Percentage of dedicated buffer to be used at egress";
           type union {
             type string {
               pattern "<.*>|$.*";
             }
             type uint32 {
               range "15 .. 100";
             }
           }
         }
       }
     }
     list dedicated-buffer-profile {
       key name;
       description "Dedicated buffer profile configuration";
       leaf name {
         description "Dedicated buffer profile name";
         junos:cli-feature "nokeyword";
         type string {
           length "1 .. 64";
         }
       }
       uses apply-advanced;
       container ingress {
         presence "enable ingress";
         uses apply-advanced;
         container buffer-size {
           presence "enable buffer-size";
           description "Dedicated buffer size";
           uses apply-advanced;
           choice buffer_size_choice {
             case case_1 {
               leaf none {
                 description "No dedicated buffer";
                 type empty;
               }
             }
             case case_2 {
               leaf cells {
                 description "Dedicated buffer size in terms of cells";
                 junos:cli-feature "nokeyword";
                 type union {
                   type string {
                     pattern "<.*>|$.*";
                   }
                   type uint32 {
                     range "20 .. 50000";
                   }
                 }
               }
             }
           }
         }
       }
       container egress {
         presence "enable egress";
         uses apply-advanced;
         container buffer-size {
           presence "enable buffer-size";
           description "Dedicated buffer size";
           uses apply-advanced;
           choice buffer_size_choice {
             case case_1 {
               leaf none {
                 description "No dedicated buffer";
                 type empty;
               }
             }
             case case_2 {
               leaf cells {
                 description "Dedicated buffer size in terms of cells";
                 junos:cli-feature "nokeyword";
                 type union {
                   type string {
                     pattern "<.*>|$.*";
                   }
                   type uint32 {
                     range "20 .. 100000";
                   }
                 }
               }
             }
           }
         }
       }
     }
     list decn-profile {
       key name;
       junos:cli-feature "homogeneous";
       description "Dynamic Explicit Congestion Notification Profile";
       leaf name {
         description "DECN profile name";
         junos:cli-feature "nokeyword";
         type string {
           length "1 .. 64";
         }
       }
       uses apply-advanced;
       list queue {
         key name;
         junos:cli-feature "oneliner";
         description "Queue number to map to flag and offset values";
         leaf name {
           description "Queue number";
           junos:cli-feature "nokeyword";
           type union {
             type string {
               pattern "<.*>|$.*";
             }
             type uint32;
           }
         }
         leaf floor {
           description "Configure dynamic explicit congestion notification's floor";
           default "524287";
           type union {
             type string {
               pattern "<.*>|$.*";
             }
             type uint64 {
               range "0 .. 524287";
             }
           }
         }
         leaf offset {
           description "Configure dynamic explicit congestion notification's offset";
           default "524287";
           type union {
             type string {
               pattern "<.*>|$.*";
             }
             type uint64 {
               range "0 .. 524287";
             }
           }
         }
       }
     }
     list lecn-profile {
       key name;
       junos:cli-feature "homogeneous";
       description "Latency Explicit Congestion Notification Profile";
       leaf name {
         description "LECN profile name";
         junos:cli-feature "nokeyword";
         type string {
           length "1 .. 64";
         }
       }
       uses apply-advanced;
       list queue {
         key name;
         junos:cli-feature "oneliner";
         description "Queue number to map to lecn values";
         leaf name {
           description "Queue number";
           junos:cli-feature "nokeyword";
           type union {
             type string {
               pattern "<.*>|$.*";
             }
             type uint32;
           }
         }
         leaf latency {
           description "Configure latency explicit congestion notification's latency";
           type union {
             type uint64;
             type string {
               pattern "<.*>|$.*";
             }
           }
         }
       }
     }
     container drop-congestion-notification {
       description "Drop Congestion Notification";
       uses apply-advanced;
       leaf udp-port {
         description "Drop Congestion Notification protocol number";
         junos:must "(!(\".. dscp-map\"))";
         junos:must-message "udp-port and dscp-map are mutually exclusive";
         type union {
           type string {
             pattern "<.*>|$.*";
           }
           type uint32 {
             range "1 .. 65535";
           }
         }
       }
       leaf forwarding-class {
         description "Forwarding class for Drop Congestion Notification packets";
         junos:must "((\".. udp-port\" || \".. dscp-map\"))";
         junos:must-message "forwarding-class must be configured with either udp-port or dscp-map";
         type string {
           length "1 .. 64";
         }
       }
       container dscp-map {
         junos:must "(!(\".. udp-port\"))";
         junos:must-message "dscp-map and udp-port are mutually exclusive";
         description "DSCP code point mapping for trimming decisions";
         uses apply-advanced;
         list trimmable {
           key name;
           junos:cli-feature "oneliner";
           description "Map trimmable DSCP code point to trimmed code point";
           leaf name {
             description "Trimmable DSCP code point (0-63)";
             junos:cli-feature "nokeyword";
             type union {
               type string {
                 pattern "<.*>|$.*";
               }
               type uint32 {
                 range "0 .. 63";
               }
             }
           }
           leaf trimmed {
             description "Trimmed DSCP code point (0-63)";
             type union {
               type string {
                 pattern "<.*>|$.*";
               }
               type uint32 {
                 range "0 .. 63";
               }
             }
           }
         }
       }
     }
     list dynamic-threshold-profile {
       key name;
       junos:cli-feature "homogeneous";
       description "Dynamic threshold profile configuration";
       leaf name {
         description "Dynamic threshold profile name";
         junos:cli-feature "nokeyword";
         type string {
           length "1 .. 128";
         }
       }
       uses apply-advanced;
       container ingress {
         description "Dynamic threshold profile at ingress";
         uses apply-advanced;
         choice pg_selection_choice {
           case case_1 {
             list priority-group {
               key name;
               junos:cli-feature "oneliner";
               description "Priority Group";
               leaf name {
                 description "Priority Group";
                 junos:cli-feature "nokeyword";
                 type union {
                   type string {
                     pattern "<.*>|$.*";
                   }
                   type uint32 {
                     range "0 .. 7";
                   }
                 }
               }
               leaf dynamic-threshold {
                 description "Dynamic threshold value for the PG";
                 type union {
                   type string {
                     pattern "<.*>|$.*";
                   }
                   type uint32 {
                     range "0 .. 10";
                   }
                 }
               }
             }
           }
           case case_2 {
             container priority-group-all {
               junos:cli-feature "oneliner-plus";
               description "Priority Group All";
               uses apply-advanced;
               leaf dynamic-threshold {
                 description "Dynamic threshold value for the PG";
                 type union {
                   type string {
                     pattern "<.*>|$.*";
                   }
                   type uint32 {
                     range "0 .. 10";
                   }
                 }
               }
             }
           }
         }
       }
     }
     container forwarding-classes {
       description "One or more mappings of forwarding class to queue number";
       uses apply-advanced;
       list class {
         key name;
         ordered-by user;
         junos:cli-feature "oneliner";
         description "Forwarding class to map to queue number";
         junos:must "(!(\".. queue\"))";
         junos:must-message "'queue' and 'class' cannot coexist";
         max-elements 16;
         leaf name {
           description "Name of forwarding class";
           junos:cli-feature "nokeyword";
           type string {
             length "1 .. 64";
           }
         }
         leaf queue-num {
           description "Queue number";
           type union {
             type string {
               pattern "<.*>|$.*";
             }
             type uint32;
           }
         }
         leaf priority {
           description "Fabric priority";
           type enumeration {
             enum "low" {
               description "Low fabric priority";
             }
             enum "high" {
               description "High fabric priority";
             }
           }
         }
         leaf no-loss {
           description "This is no traffic loss class";
           type empty;
         }
         leaf pfc-priority {
           description "PFC priority (FC id's)";
           type union {
             type string {
               pattern "<.*>|$.*";
             }
             type uint32 {
               range "0 .. 7";
             }
           }
         }
         leaf restricted-queue {
           description "Queue number for 4Q mode";
           type union {
             type string {
               pattern "<.*>|$.*";
             }
             type uint32 {
               range "0 .. 3";
             }
           }
         }
       }
       list queue {
         key name;
         ordered-by user;
         junos:cli-feature "oneliner";
         description "Queue number to map to forwarding class";
         leaf name {
           description "Queue number";
           junos:cli-feature "nokeyword";
           type union {
             type string {
               pattern "<.*>|$.*";
             }
             type uint32;
           }
         }
         leaf class-name {
           description "Forwarding class name";
           junos:cli-feature "nokeyword";
           type string {
             length "1 .. 64";
           }
         }
         leaf priority {
           description "Fabric priority";
           type enumeration {
             enum "low" {
               description "Fabric priority low";
             }
             enum "high" {
               description "Fabric priority high";
             }
           }
         }
       }
     }
     list traffic-control-profiles {
       key name;
       junos:cli-feature "homogeneous";
       description "Traffic shaping and scheduling profiles";
       leaf name {
         description "Traffic control profile name";
         junos:cli-feature "nokeyword";
         type string {
           length "1 .. 64";
         }
       }
       uses apply-advanced;
       leaf scheduler-map {
         description "Mapping of forwarding classes to packet schedulers";
         type string {
           length "1 .. 64";
         }
       }
       leaf strict-priority-scheduler {
         description "Enable strict priority scheduler.";
         type empty;
       }
       leaf atm-service {
         description "ATM service category";
         type enumeration {
           enum "cbr" {
             description "Constant bit rate";
           }
           enum "rtvbr" {
             description "Real-time variable bit rate";
           }
           enum "nrtvbr" {
             description "Non-real-time variable bit rate";
           }
         }
       }
       leaf peak-rate {
         description "ATM Peak Cell Rate (PCR)";
         units "cps";
         type string;
       }
       leaf sustained-rate {
         description "ATM Sustained Cell Rate (SCR)";
         units "cps";
         type string;
       }
       leaf max-burst-size {
         description "ATM Maximum Burst Size (MBS)";
         units "cells";
         type union {
           type string {
             pattern "<.*>|$.*";
           }
           type uint64 {
             range "1 .. 4000";
           }
         }
       }
       container shaping-rate {
         junos:cli-feature "oneliner";
         description "Shaping rate";
         choice shaping_rate_choice {
           case case_1 {
             leaf rate {
               description "Shaping rate as an absolute rate";
               junos:cli-feature "nokeyword";
               units "bits per second";
               junos:must "(!(\"interfaces ${interface} aggregated-ether-options link-speed mixed\"))";
               junos:must-message "Scheduler shaping-rate in bits per second is incompatible with link-speed mixed";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       leaf queue-mode-4q {
         description "4Q/8Q voq mode support";
         type empty;
       }
       leaf granularity-mode-low {
         description "Low granularity mode";
         type empty;
       }
       container overhead-accounting {
         junos:cli-feature "oneliner";
         description "Overhead accounting";
         leaf mode {
           junos:cli-feature "nokeyword";
           type string {
             length "1 .. 64";
           }
         }
         leaf bytes {
           description "Byte adjust value";
           type union {
             type string {
               pattern "<.*>|$.*";
             }
             type int32;
           }
         }
         leaf frame-mode-bytes {
           description "Overhead bytes when in frame-mode";
           junos:must "(!(\".. bytes\"))";
           junos:must-message "cannot specify both bytes and frame-mode-bytes";
           type union {
             type string {
               pattern "<.*>|$.*";
             }
             type int32 {
               range "-120 .. 124";
             }
           }
         }
         leaf cell-mode-bytes {
           description "Overhead bytes when in cell-mode";
           junos:must "(!(\".. bytes\"))";
           junos:must-message "cannot specify both bytes and cell-mode-bytes";
           type union {
             type string {
               pattern "<.*>|$.*";
             }
             type int32 {
               range "-120 .. 124";
             }
           }
         }
       }
       container guaranteed-rate {
         junos:cli-feature "oneliner";
         description "Guaranteed rate";
         choice guaranteed_rate_choice {
           case case_1 {
             leaf rate {
               description "Guaranteed rate as an absolute rate";
               junos:cli-feature "nokeyword";
               units "bits per second";
               type string;
             }
           }
           case case_2 {
             leaf percent {
               description "Guaranteed rate as a percentage";
               type union {
                 type string {
                   pattern "<.*>|$.*";
                 }
                 type uint32 {
                   range "1 .. 100";
                 }
               }
             }
           }
         }
         leaf burst-size {
           description "Guaranteed rate burst size";
           units "bytes";
           type string;
         }
       }
       container excess-rate {
         junos:must "(!((\".. excess-rate-high\" || (\".. excess-rate-low\" || (\".. excess-rate-medium-high\" || \".. excess-rate-medium-low\")))))";
         junos:must-message "cannot specify both excess-rate and excess-rate-high or excess-rate-low or excess-rate-medium-high or excess-rate-medium-low";
         junos:cli-feature "oneliner";
         description "Excess bandwidth sharing proportion";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-high {
         junos:must "(!(\".. excess-rate\"))";
         junos:must-message "cannot specify both excess-rate and excess-rate-high";
         junos:cli-feature "oneliner";
         description "Excess bandwidth sharing for excess-high priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-medium-high {
         junos:must "(!(\".. excess-rate\"))";
         junos:must-message "cannot specify both excess-rate and excess-rate-medium-high";
         junos:cli-feature "oneliner";
         description "Excess bandwidth sharing for excess-medium-high priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-low {
         junos:must "(!(\".. excess-rate\"))";
         junos:must-message "cannot specify both excess-rate and excess-rate-low";
         junos:cli-feature "oneliner";
         description "Excess bandwidth sharing for excess-low priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-medium-low {
         junos:must "(!(\".. excess-rate\"))";
         junos:must-message "cannot specify both excess-rate and excess-rate-medium-low";
         junos:cli-feature "oneliner";
         description "Excess bandwidth sharing for excess-medium-low priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       choice delay_buffer_sizing {
         case case_1 {
           container delay-buffer-rate {
             junos:cli-feature "oneliner";
             description "Delay buffer rate";
             choice delay_buffer_rate_choice {
               case case_1 {
                 leaf rate {
                   description "Delay buffer rate as an absolute rate";
                   junos:cli-feature "nokeyword";
                   units "bits per second";
                   type string;
                 }
               }
               case case_2 {
                 leaf percent {
                   description "Delay buffer rate as a percentage";
                   type union {
                     type string {
                       pattern "<.*>|$.*";
                     }
                     type uint32 {
                       range "1 .. 100";
                     }
                   }
                 }
               }
               case case_3 {
                 leaf cps {
                   description "Delay buffer rate as an absolute cells per second rate";
                   units "cells per second";
                   type string;
                 }
               }
             }
           }
         }
       }
       leaf shaping-rate-granularity {
         description "Shaping rate granularity";
         type enumeration {
           enum "2600k" {
             description "2600 Kbps";
           }
           enum "128k" {
             description "128 Kbps";
           }
         }
       }
       leaf number-of-queues {
         description "Number of queues";
         type enumeration {
           enum "4" {
             description "4 Queues";
           }
           enum "8" {
             description "8 Queues";
           }
         }
       }
     }
     list forwarding-class-sets {
       key name;
       junos:cli-feature "homogeneous";
       description "Forwarding class sets";
       leaf name {
         description "Forwarding class set";
         junos:cli-feature "nokeyword";
         type string {
           length "1 .. 64";
         }
       }
       uses apply-advanced;
       list class {
         key name;
         description "Forwarding class";
         leaf name {
           description "Class name";
           junos:cli-feature "nokeyword";
           type string {
             length "1 .. 64";
           }
         }
         uses apply-advanced;
       }
     }
     list congestion-notification-profile {
       key name;
       junos:cli-feature "homogeneous";
       description "Congestion notification profile";
       leaf name {
         description "Congestion notification name";
         junos:cli-feature "nokeyword";
         type string {
           length "1 .. 64";
         }
       }
       uses apply-advanced;
       container pfc-watchdog {
         presence "enable pfc-watchdog";
         junos:must "(\".. output\")";
         junos:must-message "pfc-watchdog configurations mandate output config";
         description "Configure pfc-watchdog parameters";
         uses apply-advanced;
         leaf poll-interval {
           description "Pfc watchdog poll interval timings";
           units "milliseconds";
           type union {
             type string {
               pattern "<.*>|$.*";
             }
             type uint16;
           }
         }
         leaf detection {
           description "Pfc Number of poll periods";
           type union {
             type string {
               pattern "<.*>|$.*";
             }
             type uint32;
           }
         }
         leaf recovery {
           description "Pfc watchdog recovery time interval";
           units "milliseconds";
           type union {
             type string {
               pattern "<.*>|$.*";
             }
             type uint16;
           }
         }
         leaf watchdog-action {
           description "Configure pfc-wathdog action";
           type enumeration {
             enum "drop" {
               description "Pfc watchdog action drop";
             }
             enum "forward" {
               description "Pfc watchdog action forward";
             }
           }
         }
       }
       container input {
         description "Input congestion notification components";
         uses apply-advanced;
         leaf cable-length {
           description "Length of cable in metre";
           units "metre";
           type string;
         }
         container ieee-802.1 {
           description "IEEE 802.1 code point";
           uses apply-advanced;
           list code-point {
             key name;
             description "IEEE 802.1 code point";
             max-elements 8;
             leaf name {
               description "IEEE 802.1 code point";
               junos:cli-feature "nokeyword";
               type string {
                 junos:posix-pattern "^([01]{3})$";
                 junos:pattern-message "Must be of form xxx, where x is 0 or 1";
               }
             }
             uses apply-advanced;
             leaf pfc {
               description "PFC";
               type empty;
             }
             leaf mru {
               description "Max Receive Size of packet for this code point";
               units "bytes";
               junos:must "(\".. pfc\")";
               junos:must-message "MRU not allowed without PFC";
               type string;
             }
             leaf xon {
               description "Specifies XON threshold offset cells for Tx resume from dynamic shared buffer";
               junos:must "(\".. pfc\")";
               junos:must-message "XON not allowed without PFC";
               type union {
                 type string {
                   pattern "<.*>|$.*";
                 }
                 type uint32 {
                   range "1 .. 100000";
                 }
               }
             }
             choice qfc-control {
               case case_1 {
                 leaf qfc {
                   description "QFC";
                   type empty;
                 }
               }
               case case_2 {
                 container qcn {
                   presence "enable qcn";
                   description "QCN";
                   uses apply-advanced;
                   container defense-mode-edge {
                     description "Choose the defense mode edge";
                     uses apply-advanced;
                     container alternate-priority {
                       description "Choose the alternate priority for defense mode edge";
                       uses apply-advanced;
                       leaf bits {
                         description "IEEE 802.1 code point";
                         junos:cli-feature "nokeyword";
                         type string {
                           junos:posix-pattern "^([01]{3})$";
                           junos:pattern-message "Must be of form xxx, where x is 0 or 1";
                         }
                       }
                     }
                   }
                 }
               }
             }
           }
         }
         container dscp {
           description "DSCP code point";
           uses apply-advanced;
           list code-point {
             key name;
             description "DSCP code point";
             max-elements 64;
             leaf name {
               description "DSCP code point";
               junos:cli-feature "nokeyword";
               type string {
                 junos:posix-pattern "^([01]{6})$";
                 junos:pattern-message "Must be of form xxxxxx, where x is 0 or 1";
               }
             }
             uses apply-advanced;
             leaf pfc {
               description "PFC";
               type empty;
             }
             leaf mru {
               description "Max Receive Size of packet for this code point";
               units "bytes";
               junos:must "(\".. pfc\")";
               junos:must-message "MRU not allowed without PFC";
               type string;
             }
             leaf xon {
               description "Specifies XON threshold offset cells for TX resume from dynamic shared buffer";
               junos:must "(\".. pfc\")";
               junos:must-message "XON not allowed without PFC";
               type union {
                 type string {
                   pattern "<.*>|$.*";
                 }
                 type uint32 {
                   range "1 .. 100000";
                 }
               }
             }
           }
         }
       }
       container output {
         description "Output congestion notification components";
         uses apply-advanced;
         list class {
           key name;
           description "Forwarding class";
           max-elements 16;
           leaf name {
             description "Class name";
             junos:cli-feature "nokeyword";
             type string {
               length "1 .. 64";
             }
           }
           uses apply-advanced;
           leaf remove-cntag {
             description "Remove cntag for this forwarding class";
             type empty;
           }
           leaf qcn {
             description "Enabling Quantized Congestion Notification for this forwarding class";
             type empty;
           }
         }
         container ieee-802.1 {
           description "IEEE 802.1 code point";
           uses apply-advanced;
           list code-point {
             key name;
             description "IEEE 802.1 code point";
             max-elements 8;
             leaf name {
               description "IEEE 802.1 code point";
               junos:cli-feature "nokeyword";
               type string {
                 junos:posix-pattern "^([01]{3})$";
                 junos:pattern-message "Must be of form xxx, where x is 0 or 1";
               }
             }
             uses apply-advanced;
             leaf-list flow-control-queue {
               ordered-by user;
               description "Flow control queue( set of queues)";
               type union {
                 type string {
                   pattern "<.*>|$.*";
                 }
                 type uint32 {
                   range "0 .. 7";
                 }
               }
             }
           }
         }
       }
     }
     list scheduler-map-forwarding-class-sets {
       key name;
       junos:cli-feature "homogeneous";
       description "Mapping of forwarding class sets to packet schedulers";
       leaf name {
         description "Scheduler map forwarding class set name";
         junos:cli-feature "nokeyword";
         type string {
           length "1 .. 64";
         }
       }
       uses apply-advanced;
       list forwarding-class-set {
         key name;
         junos:cli-feature "oneliner";
         description "Forwarding class set name to map to scheduler";
         leaf name {
           description "Forwarding class set name";
           junos:cli-feature "nokeyword";
           type string {
             length "1 .. 64";
           }
         }
         leaf scheduler {
           description "Scheduler name";
           type string {
             length "1 .. 64";
           }
         }
       }
     }
     container system-defaults {
       description "System defaults";
       uses apply-advanced;
       container classifiers {
         description "System wide Classifiers applied to incoming packets";
         uses apply-advanced;
         container exp {
           junos:cli-feature "oneliner";
           description "EXP classifier";
           leaf classifier-name {
             description "Name of classifier to be applied";
             junos:cli-feature "nokeyword";
             type union {
               type string {
                 pattern "default";
               }
               type string {
                 length "1 .. 64";
               }
             }
           }
         }
       }
       container traffic-control-profiles {
         description "Default traffic control profiles";
         uses apply-advanced;
         container interface-set-input {
           junos:cli-feature "oneliner";
           description "Default input traffic control profile for dynamic interface-set";
           leaf profile-name {
             description "Name of traffic control profile";
             junos:cli-feature "nokeyword";
             type string {
               length "1 .. 64";
             }
           }
         }
         container interface-set-output {
           junos:cli-feature "oneliner";
           description "Default output traffic control profile for dynamic interface-set";
           leaf profile-name {
             description "Name of traffic control profile";
             junos:cli-feature "nokeyword";
             type string {
               length "1 .. 64";
             }
           }
         }
       }
     }
     container interfaces {
       description "Apply class-of-service options to interfaces";
       uses apply-advanced;
       list interface-set {
         key name;
         description "Interface set traffic-control-profile attachment";
         leaf name {
           description "Name of the interface set";
           junos:cli-feature "nokeyword";
           type string {
             length "1 .. 64";
           }
         }
         uses apply-advanced;
         leaf internal-node {
           description "Internal node";
           type empty;
         }
         container input-traffic-control-profile {
           junos:cli-feature "oneliner";
           description "Input traffic control profile for the interface set";
           leaf profile-name {
             description "Name of the input traffic control profile associated with the interface set";
             junos:cli-feature "nokeyword";
             type string {
               length "1 .. 64";
             }
           }
         }
         container input-traffic-control-profile-remaining {
           junos:cli-feature "oneliner";
           description "Input traffic control profile for the remaining traffic on an interface set";
           leaf profile-name {
             description "Name of the input traffic control profile associated with the remaining traffic for the interface set";
             junos:cli-feature "nokeyword";
             type string {
               length "1 .. 64";
             }
           }
         }
         container output-traffic-control-profile {
           junos:cli-feature "oneliner";
           description "Output traffic control profile for the interface set";
           leaf profile-name {
             description "Name of the output traffic control profile associated with the interface set";
             junos:cli-feature "nokeyword";
             type string {
               length "1 .. 64";
             }
           }
         }
         container output-traffic-control-profile-remaining {
           junos:cli-feature "oneliner";
           description "Output traffic control profile for the remaining traffic on an interface set";
           leaf profile-name {
             description "Name of the output traffic control profile associated with the remaining traffic for the interface set";
             junos:cli-feature "nokeyword";
             type string {
               length "1 .. 64";
             }
           }
         }
       }
       list interface {
         key name;
         uses cos_interfaces_type;
         junos:cli-feature "nokeyword";
         junos:cli-feature "homogeneous";
       }
     }
     list routing-instances {
       key name;
       junos:cli-feature "homogeneous";
       description "Apply CoS options to routing instances with VRF table label";
       leaf name {
         description "Routing instance name (or wildcard)";
         junos:cli-feature "nokeyword";
         junos:must "((!(\".. classifiers\") || (!(\"routing-instances $$\") || (\"routing-instances $$ vrf-table-label\" || (\"routing-instances $$ protocols vpls no-tunnel-services\" || \"routing-instances $$ routing-options localize\")))))";
         junos:must-message "'vrf-table-label' or 'no-tunnel-services' or 'routing-options localize' for this routing instance is required for classifier configuration";
         type string {
           junos:posix-pattern "!^(([*]{1,})|(__.*__)|(.{129,}))$";
           junos:pattern-message "Must be a non-reserved string of 128 characters or less";
         }
       }
       uses apply-advanced;
       container classifiers {
         description "Classifiers applied to incoming packets";
         uses apply-advanced;
         leaf no-default {
           description "Do not apply default classifiers to this interface";
           type empty;
         }
         container exp {
           junos:cli-feature "oneliner";
           description "EXP classifier";
           leaf classifier-name {
             description "Name of classifier to be applied";
             junos:cli-feature "nokeyword";
             type union {
               type string {
                 pattern "default";
               }
               type string {
                 length "1 .. 64";
               }
             }
           }
         }
         container dscp {
           junos:cli-feature "oneliner";
           description "Differentiated Services code point classifier";
           leaf classifier-name {
             description "Name of classifier to be applied";
             junos:cli-feature "nokeyword";
             type union {
               type string {
                 pattern "default";
               }
               type string {
                 length "1 .. 64";
               }
             }
           }
         }
         container dscp-ipv6 {
           junos:cli-feature "oneliner";
           description "Differentiated Services code point classifier IPv6";
           leaf classifier-name {
             description "Name of classifier to be applied";
             junos:cli-feature "nokeyword";
             type union {
               type string {
                 pattern "default";
               }
               type string {
                 length "1 .. 64";
               }
             }
           }
         }
       }
     }
     container rewrite-rules {
       description "Write code point value of outgoing packets";
       uses apply-advanced;
       list dscp {
         key name;
         ordered-by user;
         description "Differentiated Services code point rewrite rule";
         leaf name {
           description "Rewrite rule name";
           junos:cli-feature "nokeyword";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             junos:cli-feature "nokeyword";
             type string {
               length "1 .. 64";
             }
           }
           uses apply-advanced;
           list loss-priority {
             key name;
             junos:cli-feature "oneliner";
             description "Code point marking based on loss priority";
             leaf name {
               junos:cli-feature "nokeyword";
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{6})|([a-zA-Z].{0,63}))$";
                 junos:pattern-message "Not 6-bit pattern or code point alias";
               }
             }
           }
         }
       }
       list dscp-ipv6 {
         key name;
         ordered-by user;
         description "Differentiated Services code point rewrite rule IPv6";
         leaf name {
           description "Rewrite rule name";
           junos:cli-feature "nokeyword";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             junos:cli-feature "nokeyword";
             type string {
               length "1 .. 64";
             }
           }
           uses apply-advanced;
           list loss-priority {
             key name;
             junos:cli-feature "oneliner";
             description "Code point marking based on loss priority";
             leaf name {
               junos:cli-feature "nokeyword";
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{6})|([a-zA-Z].{0,63}))$";
                 junos:pattern-message "Not 6-bit pattern or code point alias";
               }
             }
           }
         }
       }
       list exp {
         key name;
         ordered-by user;
         description "MPLS EXP rewrite rule";
         leaf name {
           description "Rewrite rule name";
           junos:cli-feature "nokeyword";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             junos:cli-feature "nokeyword";
             type string {
               length "1 .. 64";
             }
           }
           uses apply-advanced;
           list loss-priority {
             key name;
             junos:cli-feature "oneliner";
             description "Code point marking based on loss priority";
             leaf name {
               junos:cli-feature "nokeyword";
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{3})|([a-zA-Z].{0,63}))$";
                 junos:pattern-message "Not 3-bit pattern or code point alias";
               }
             }
           }
         }
       }
       list ieee-802.1 {
         key name;
         ordered-by user;
         description "IEEE-802.1 rewrite rule";
         leaf name {
           description "Rewrite rule name";
           junos:cli-feature "nokeyword";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             junos:cli-feature "nokeyword";
             type string {
               length "1 .. 64";
             }
           }
           uses apply-advanced;
           list loss-priority {
             key name;
             junos:cli-feature "oneliner";
             description "Code point marking based on loss priority";
             leaf name {
               junos:cli-feature "nokeyword";
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{3})|([a-zA-Z].{0,63}))$";
                 junos:pattern-message "Not 3-bit pattern or code point alias";
               }
             }
           }
         }
       }
       list inet-precedence {
         key name;
         ordered-by user;
         description "IPv4 precedence rewrite rule";
         leaf name {
           description "Rewrite rule name";
           junos:cli-feature "nokeyword";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             junos:cli-feature "nokeyword";
             type string {
               length "1 .. 64";
             }
           }
           uses apply-advanced;
           list loss-priority {
             key name;
             junos:cli-feature "oneliner";
             description "Code point marking based on loss priority";
             leaf name {
               junos:cli-feature "nokeyword";
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{3})|([a-zA-Z].{0,63}))$";
                 junos:pattern-message "Not 3-bit pattern or code point alias";
               }
             }
           }
         }
       }
       list ieee-802.1ad {
         key name;
         ordered-by user;
         description "IEEE-802.1ad (DEI) rewrite rule";
         leaf name {
           description "Rewrite rule name";
           junos:cli-feature "nokeyword";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             junos:cli-feature "nokeyword";
             type string {
               length "1 .. 64";
             }
           }
           uses apply-advanced;
           list loss-priority {
             key name;
             junos:cli-feature "oneliner";
             description "Code point marking based on loss priority";
             leaf name {
               junos:cli-feature "nokeyword";
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{4})|([a-zA-Z].{0,63}))$";
                 junos:pattern-message "Not 4-bit pattern or code point alias";
               }
             }
           }
         }
       }
     }
     container mpls-ecn-map {
       description "Mapping of MPLS ECN capable and congestion experienced exp";
       uses apply-advanced;
       list ecn-capable-exp {
         key name;
         junos:cli-feature "oneliner";
         description "MPLS ECN capability";
         leaf name {
           description "MPLS ECN capable exp";
           junos:cli-feature "nokeyword";
           type union {
             type string {
               pattern "<.*>|$.*";
             }
             type uint32 {
               range "0 .. 7";
             }
           }
         }
         leaf congestion-experienced-exp-value {
           description "MPLS ECN experienced mark value";
           type union {
             type string {
               pattern "<.*>|$.*";
             }
             type uint32 {
               range "0 .. 7";
             }
           }
         }
       }
     }
     list scheduler-maps {
       key name;
       junos:cli-feature "homogeneous";
       description "Mapping of forwarding classes to packet schedulers";
       leaf name {
         description "Scheduler map name";
         junos:cli-feature "nokeyword";
         type string {
           length "1 .. 64";
         }
       }
       uses apply-advanced;
       list forwarding-class {
         key name;
         junos:cli-feature "oneliner";
         description "Forwarding class name to map to scheduler";
         leaf name {
           description "Forwarding class name";
           junos:cli-feature "nokeyword";
           type string {
             length "1 .. 64";
           }
         }
         leaf scheduler {
           description "Scheduler name";
           type string {
             length "1 .. 64";
           }
         }
       }
     }
     list fragmentation-maps {
       key name;
       junos:cli-feature "homogeneous";
       description "Mapping of forwarding class to fragmentation options";
       leaf name {
         description "Fragmentation map name";
         junos:cli-feature "nokeyword";
         type string {
           length "1 .. 64";
         }
       }
       uses apply-advanced;
       list forwarding-class {
         key name;
         junos:cli-feature "homogeneous";
         description "Forwarding class name to map to fragmentation options";
         leaf name {
           description "Forwarding class name";
           junos:cli-feature "nokeyword";
           type string {
             length "1 .. 64";
           }
         }
         uses apply-advanced;
         choice fragmentation-control {
           case case_1 {
             leaf fragment-threshold {
               description "Fragmentation threshold";
               units "bytes";
               type union {
                 type string {
                   pattern "<.*>|$.*";
                 }
                 type uint16 {
                   range "64 .. 9192";
                 }
               }
             }
           }
           case case_2 {
             leaf no-fragmentation {
               description "Don't allow fragmentation";
               type empty;
             }
           }
         }
         leaf multilink-class {
           description "Multilink-Class assigned to the forwarding class";
           type union {
             type string {
               pattern "<.*>|$.*";
             }
             type uint16 {
               range "0 .. 7";
             }
           }
         }
         leaf drop-timeout {
           description "Drop timeout";
           units "milliseconds";
           type union {
             type string {
               pattern "<.*>|$.*";
             }
             type uint16 {
               range "0 .. 2000";
             }
           }
         }
       }
     }
     container options {
       description "Configure class-of-service optional parameters";
       uses apply-advanced;
       leaf hierarchical-scheduler-disable {
         description "Enable or disable HQoS scheduler mode";
         type empty;
       }
       leaf latency-tracking {
         description "Enable latency-tracking";
         type empty;
       }
       container latency-ecn {
         description "Latency ECN configuration";
         uses apply-advanced;
         leaf threshold {
           description "Latency ECN threshold value";
           units "microseconds";
           type union {
             type string {
               pattern "<.*>|$.*";
             }
             type uint32 {
               range "1 .. 100000";
             }
           }
         }
       }
       leaf dscp-pfc-for-tagged-traffic {
         description "Enable DSCP-based PFC for VLAN tagged traffic";
         type empty;
       }
     }
     list schedulers {
       key name;
       junos:cli-feature "homogeneous";
       description "Packet schedulers";
       leaf name {
         description "Scheduler name";
         junos:cli-feature "nokeyword";
         type string {
           length "1 .. 64";
         }
       }
       uses apply-advanced;
       container transmit-rate {
         junos:cli-feature "oneliner-plus";
         description "Transmit rate";
         uses apply-advanced;
         choice transmit_rate_choice {
           case case_1 {
             leaf rate {
               description "Transmit rate as rate";
               junos:cli-feature "nokeyword";
               units "bits per second";
               junos:must "(!(\"interfaces ${interface} aggregated-ether-options link-speed mixed\"))";
               junos:must-message "Scheduler transmit-rate in bits per second is incompatible with link-speed mixed";
               type string;
             }
           }
           case case_2 {
             leaf percent {
               description "Transmit rate as percentage";
               type union {
                 type string {
                   pattern "<.*>|$.*";
                 }
                 type uint32 {
                   range "0 .. 100";
                 }
               }
             }
           }
           case case_3 {
             container remainder {
               presence "enable remainder";
               description "Remainder available";
               uses apply-advanced;
               leaf percent {
                 junos:cli-feature "nokeyword";
                 default "0";
                 type union {
                   type string {
                     pattern "<.*>|$.*";
                   }
                   type uint32 {
                     range "0 .. 100";
                   }
                 }
               }
             }
           }
         }
         choice rate_limit_choice {
           case case_1 {
             leaf exact {
               description "Enforce exact transmit rate";
               type empty;
             }
           }
           case case_2 {
             leaf rate-limit {
               description "Enforce rate limit that uses policer";
               type empty;
             }
           }
         }
       }
       container excess-rate {
         junos:must "((!((\".. transmit-rate exact\" && \".. excess-rate\")) && (!((\".. transmit-rate rate-limit\" && \".. excess-rate\")) && !((\".. priority $$={strict-high}\" && \".. excess-rate\")))))";
         junos:must-message "Cannot specify excess-rate with transmit-rate exact/rate-limit or strict-high priority";
         junos:cli-feature "oneliner";
         description "Excess bandwidth sharing proportion";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container shaping-rate {
         junos:must "(!((\".. transmit-rate rate-limit\" && \".. shaping-rate\")))";
         junos:must-message "only one option (shaping-rate or transmit-rate rate-limit) can be configured at a time";
         junos:must "(!((\".. transmit-rate exact\" && \".. shaping-rate\")))";
         junos:must-message "only one option (shaping-rate or transmit-rate exact) can be configured at a time";
         junos:cli-feature "oneliner";
         description "Shaping rate";
         choice shaping_rate_choice {
           case case_1 {
             leaf rate {
               description "Shaping rate as an absolute rate";
               junos:cli-feature "nokeyword";
               units "bits per second";
               junos:must "(!(\"interfaces ${interface} aggregated-ether-options link-speed mixed\"))";
               junos:must-message "Scheduler shaping-rate in bits per second is incompatible with link-speed mixed";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container buffer-size {
         junos:cli-feature "oneliner-plus";
         description "Queue transmission buffer size";
         uses apply-advanced;
         choice buffer_size_choice {
           case case_1 {
             leaf percent {
               description "Buffer size as a percentage";
               type union {
                 type string {
                   pattern "<.*>|$.*";
                 }
                 type uint32 {
                   range "0 .. 100";
                 }
               }
             }
           }
           case case_2 {
             container remainder {
               presence "enable remainder";
               description "Remainder of buffer size available";
               uses apply-advanced;
               leaf percent {
                 junos:cli-feature "nokeyword";
                 default "0";
                 type union {
                   type string {
                     pattern "<.*>|$.*";
                   }
                   type uint32 {
                     range "0 .. 100";
                   }
                 }
               }
             }
           }
           case case_3 {
             leaf shared {
               description "Shared buffer allocation";
               type empty;
             }
           }
           case case_4 {
             leaf temporal {
               description "Buffer size as temporal value";
               units "microseconds";
               type string;
             }
           }
           case case_5 {
             leaf temporal-absolute {
               description "Absolute temporal value";
               default "2048";
               units "bytes";
               type string;
             }
           }
         }
         choice buffer_limit {
           case case_1 {
           }
         }
         container buffer-partition {
           presence "enable buffer-partition";
           description "Partition buffer size among multicast and unicast";
           uses apply-advanced;
           container multicast {
             presence "enable multicast";
             description "Specify multicast fraction of reserved buffer";
             uses apply-advanced;
             leaf percent {
               default "50";
               type union {
                 type string {
                   pattern "<.*>|$.*";
                 }
                 type uint32 {
                   range "0 .. 100";
                 }
               }
             }
           }
         }
       }
       container shared-buffer {
         junos:cli-feature "oneliner-plus";
         description "Queue transmission shared-buffer";
         uses apply-advanced;
         container maximum {
           presence "enable maximum";
           description "Control the amount of shared buffer a given queue can consume";
           uses apply-advanced;
           leaf percent {
             description "Maximum shared buffer size as a percentage";
             junos:cli-feature "nokeyword";
             default "0";
             type union {
               type string {
                 pattern "<.*>|$.*";
               }
               type uint32 {
                 range "0 .. 100";
               }
             }
           }
           container multicast {
             presence "enable multicast";
             description "Control the amount of shared buffer mcast pkts consume";
             uses apply-advanced;
             leaf percent {
               description "Maximum shared buffer size as a percentage";
               junos:cli-feature "nokeyword";
               default "0";
               type union {
                 type string {
                   pattern "<.*>|$.*";
                 }
                 type uint32 {
                   range "0 .. 100";
                 }
               }
             }
           }
         }
       }
       leaf priority {
         description "Scheduling priority";
         type string {
           length "1 .. 64";
         }
       }
       leaf excess-priority {
         description "Priority in the excess region";
         junos:must "((!((\".. transmit-rate exact\" && (\".. excess-priority $$={high}\" || (\".. excess-priority $$={low}\" || (\".. excess-priority $$={medium-high}\" || \".. excess-priority $$={medium-low}\"))))) && (!((\".. transmit-rate rate-limit\" && (\".. excess-priority $$={high}\" || (\".. excess-priority $$={low}\" || (\".. excess-priority $$={medium-high}\" || \".. excess-priority $$={medium-low}\"))))) && !((\".. priority $$={strict-high}\" && (\".. excess-priority $$={high}\" || (\".. excess-priority $$={low}\" || (\".. excess-priority $$={medium-high}\" || \".. excess-priority $$={medium-low}\"))))))))";
         junos:must-message "Cannot specify excess-priority with transmit-rate exact/rate-limit or strict-high priority";
         type string {
           length "1 .. 64";
         }
       }
       list drop-profile-map {
         key "loss-priority protocol";
         junos:cli-feature "oneliner";
         description "Assign drop profile to a loss priority and protocol";
         leaf loss-priority {
           description "Loss priority value";
           type enumeration {
             enum "low" {
               description "Loss priority low";
             }
             enum "high" {
               description "Loss priority high";
             }
             enum "medium-low" {
               description "Loss priority medium-low";
             }
             enum "medium-high" {
               description "Loss priority medium-high";
             }
             enum "any" {
               description "Ignore loss priority when assigning drop profile";
             }
           }
         }
         leaf protocol {
           description "Protocol type";
           type enumeration {
             enum "tcp" {
               description "TCP protocol only";
             }
             enum "non-tcp" {
               description "Non-TCP protocols only";
             }
             enum "any" {
               description "Ignore protocol type when assigning drop profile";
             }
           }
         }
         leaf drop-profile {
           description "Name of drop profile to apply";
           type string {
             length "1 .. 64";
           }
         }
       }
       leaf explicit-congestion-notification {
         description "Enable static explicit congestion notification";
         type empty;
       }
       container latency-ecn {
         presence "enable latency-ecn";
         description "Latency ECN configuration";
         uses apply-advanced;
         leaf threshold {
           description "Latency ECN threshold value";
           type union {
             type string {
               pattern "<.*>|$.*";
             }
             type uint32 {
               range "1 .. 1000000000";
             }
           }
         }
       }
       leaf ecn-rtlog-rate-limit {
         description "Rate-limit for ECN security logs";
         units "logs per second";
         type union {
           type string {
             pattern "<.*>|$.*";
           }
           type uint32 {
             range "1 .. 65535";
           }
         }
       }
       container drop-profile-map-set {
         presence "enable drop-profile-map-set";
         description "System drop profile";
         uses apply-advanced;
         leaf profile-name {
           description "Drop Profile Name";
           junos:cli-feature "nokeyword";
           type string {
             length "1 .. 64";
             junos:posix-pattern "default";
             junos:pattern-message "Only default is supported";
           }
         }
         leaf profile-type {
           type enumeration {
             enum "drop" {
               description "Set drop type";
             }
             enum "mark" {
               description "Set ECN marking";
             }
           }
         }
       }
       leaf queue-monitoring {
         description "Enable queue depth monitoring";
         type empty;
       }
       leaf buffer-dynamic-threshold {
         description "Threshold for maximum buffer share for a queue at egress buffer-partition";
         type union {
           type string {
             pattern "<.*>|$.*";
           }
           type uint32 {
             range "0 .. 10";
           }
         }
       }
     }
     container traceoptions {
       description "Trace options for class-of-service process";
       uses apply-advanced;
       leaf no-remote-trace {
         description "Disable remote tracing";
         junos:must "(\"system tracing\")";
         junos:must-message "'no-remote-trace' is valid only when [system tracing] is configured";
         type empty;
       }
       container file {
         junos:cli-feature "oneliner";
         description "Trace file information";
         leaf filename {
           description "Name of file in which to write trace information";
           junos:cli-feature "nokeyword";
           type string {
             length "1 .. 1024";
             junos:posix-pattern "![/ %]";
             junos:pattern-message "Must not contain \'/\', % or a space";
           }
         }
         leaf size {
           description "Maximum trace file size";
           units "bytes";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         junos:cli-feature "oneliner";
         description "Tracing parameters";
         leaf name {
           junos:cli-feature "nokeyword";
           type enumeration {
             enum "init" {
               description "Trace initialization events";
             }
             enum "show" {
               description "Trace show command servicing";
             }
             enum "route-socket" {
               description "Trace route-socket events";
             }
             enum "parse" {
               description "Trace parser processing";
             }
             enum "process" {
               description "Trace configuration processing";
             }
             enum "util" {
               description "Trace utilities";
             }
             enum "restart" {
               description "Trace restart processing";
             }
             enum "snmp" {
               description "Trace SNMP-related processing";
             }
             enum "hardware-database" {
               description "Trace chassis hardware database related processing";
             }
             enum "asynch" {
               description "Trace asynchronous configuration processing";
             }
             enum "dynamic" {
               description "Trace dynamic CoS functions";
             }
             enum "cos-adjustment" {
               description "Trace CoS rate adjustments";
             }
             enum "performance-monitor" {
               description "Trace performance monitor counters";
             }
             enum "chassis-scheduler" {
               description "Trace chassis stream scheduler processing";
             }
             enum "cn-util" {
               description "Trace utilities for congestion-notification";
             }
             enum "snmp-timeouts" {
               description "Trace SNMP COSD kernel timeouts";
             }
             enum "all" {
               description "Trace everything";
             }
             enum "feature-capability" {
               description "Trace feature capability";
             }
             enum "application" {
               description "Trace Junos application programming";
             }
             enum "jvision" {
               description "Cos Junos Jvision traces";
             }
             enum "uidebug" {
               description "Cos Junos UIDebug messages";
             }
           }
         }
       }
     }
     container multi-destination {
       description "Multicast class of service";
       uses apply-advanced;
       leaf scheduler-map {
         description "Scheduler map for multi destination";
         type string {
           length "1 .. 64";
         }
       }
       container family {
         description "Family Inet/Inet6/Ethernet";
         uses apply-advanced;
         container ethernet {
           description "Ethernet switching options";
           uses apply-advanced;
           leaf broadcast {
             description "Forwarding class to be applied to broadcast";
             type string {
               length "1 .. 64";
             }
           }
         }
         container inet {
           description "IP Multicast";
           uses apply-advanced;
           container classifier {
             description "Classifier applied to ip-multicast";
             uses apply-advanced;
             container dscp {
               junos:cli-feature "oneliner";
               description "Differentiated Services code point classifier";
               leaf classifier-name {
                 description "Name of classifier to be applied";
                 junos:cli-feature "nokeyword";
                 type string {
                   length "1 .. 64";
                 }
               }
             }
             container inet-precedence {
               junos:cli-feature "oneliner";
               description "IPv4 precedence classifier";
               leaf classifier-name {
                 description "Name of classifier to be applied";
                 junos:cli-feature "nokeyword";
                 type string {
                   length "1 .. 64";
                 }
               }
             }
           }
         }
         container inet6 {
           description "IPv6 Multicast";
           uses apply-advanced;
           container classifier {
             description "Classifier applied to ipv6-multicast";
             uses apply-advanced;
             container dscp-ipv6 {
               junos:cli-feature "oneliner";
               description "Differentiated Services code point classifier";
               leaf classifier-name {
                 description "Name of classifier to be applied";
                 junos:cli-feature "nokeyword";
                 type string {
                   length "1 .. 64";
                 }
               }
             }
           }
         }
       }
       container classifiers {
         junos:must "(!(\".. forwarding-class\"))";
         junos:must-message "Either Forwarding-class or Classifiers can be configured";
         description "Classifier applied to multicast traffic";
         uses apply-advanced;
         container ieee-802.1 {
           junos:cli-feature "oneliner";
           description "IEEE-802.1 classifier";
           leaf classifier-name {
             description "Name of classifier to be applied";
             junos:cli-feature "nokeyword";
             type string {
               length "1 .. 64";
             }
           }
         }
         container dscp {
           junos:must "(!(\".. inet-precedence\"))";
           junos:must-message "Either DSCP or Inet-Precedence can be configured";
           junos:cli-feature "oneliner";
           description "Differentiated services code point classifier";
           leaf classifier-name {
             description "Name of classifier to be applied";
             junos:cli-feature "nokeyword";
             type string {
               length "1 .. 64";
             }
           }
         }
         container dscp-ipv6 {
           junos:cli-feature "oneliner";
           description "Differentiated services code point classifier IPv6";
           leaf classifier-name {
             description "Name of classifier to be applied";
             junos:cli-feature "nokeyword";
             type string {
               length "1 .. 64";
             }
           }
         }
         container inet-precedence {
           junos:cli-feature "oneliner";
           description "IPv4 precedence classifier";
           leaf classifier-name {
             description "Name of classifier to be applied";
             junos:cli-feature "nokeyword";
             type string {
               length "1 .. 64";
             }
           }
         }
       }
       leaf forwarding-class {
         description "Forwarding class assigned to incoming Multi-destination packets";
         type string {
           junos:posix-pattern "^.{1,64}$";
           junos:pattern-message "Must be string of 64 characters or less";
         }
       }
     }
     container application-traffic-control {
       presence "enable application-traffic-control";
       description "Application classifier configuration";
       uses apply-advanced;
       container traceoptions {
         description "Trace options for application classifier";
         uses appqos-traceoptions-type;
       }
       list rate-limiters {
         key name;
         ordered-by user;
         description "Configure application-traffic-control rate limiters";
         leaf name {
           description "Application classifier rate-limiter name";
           junos:cli-feature "nokeyword";
           type string {
             length "1 .. 63";
           }
         }
         uses apply-advanced;
         leaf bandwidth-limit {
           description "Bandwidth limit";
           units "kbps";
           type union {
             type string {
               pattern "<.*>|$.*";
             }
             type uint32 {
               range "64 .. 10485760";
             }
           }
         }
         leaf burst-size-limit {
           description "Burst size limit (default with bandwidth-limit and no larger than 6400 * bandwidth)";
           units "bytes";
           type union {
             type string {
               pattern "<.*>|$.*";
             }
             type uint32 {
               range "1 .. 1342177280";
             }
           }
         }
       }
       list rule-sets {
         key name;
         ordered-by user;
         description "Configure application-traffic-control rule-sets";
         leaf name {
           description "Application classifier rule-set name";
           junos:cli-feature "nokeyword";
           type string {
             length "1 .. 63";
           }
         }
         uses apply-advanced;
         list rule {
           key name;
           ordered-by user;
           description "Rule";
           uses appqos_rule_type;
         }
       }
     }
     container forwarding-policy {
       description "Class-of-service forwarding policy";
       uses apply-advanced;
       list next-hop-map {
         key name;
         ordered-by user;
         description "Class-of-service next-hop map";
         leaf name {
           description "Name to identify next-hop map";
           junos:cli-feature "nokeyword";
           type string {
             junos:posix-pattern "^.{1,64}$";
             junos:pattern-message "Must be string of 64 characters or less";
           }
         }
         uses apply-advanced;
         list forwarding-class {
           key name;
           ordered-by user;
           description "Forwarding class from which to map";
           leaf name {
             description "Forwarding class";
             junos:cli-feature "nokeyword";
             type string {
               junos:posix-pattern "^.{1,64}$";
               junos:pattern-message "Must be string of 64 characters or less";
             }
           }
           uses apply-advanced;
           leaf-list next-hop {
             ordered-by user;
             description "Next-hop identifier to which to map";
             type union {
               type jt:ipaddr-or-interface;
               type string {
                 pattern "<.*>|$.*";
               }
             }
           }
           leaf-list lsp-next-hop {
             ordered-by user;
             description "Regular expression for LSP next hop";
             type string;
           }
           leaf non-lsp-next-hop {
             description "Any non-RSVP LSP next hop";
             type empty;
           }
           leaf non-labelled-next-hop {
             description "Any non-labelled next hop";
             type empty;
           }
           leaf discard {
             description "Discard next hop";
             type empty;
           }
           container transport-class {
             description "Transport class to be mapped with forwarding class";
             uses apply-advanced;
             list color {
               key name;
               ordered-by user;
               description "Transport class color";
               leaf name {
                 description "Transport class color";
                 junos:cli-feature "nokeyword";
                 junos:must "(\"routing-options transport-class any-class\")";
                 junos:must-message "TC any-class is not configured";
                 type union {
                   type uint32;
                   type string {
                     pattern "<.*>|$.*";
                   }
                 }
               }
               uses apply-advanced;
             }
           }
         }
         container forwarding-class-default {
           description "Next Hop For traffic which does not meet any FC in the next-hop-map";
           uses apply-advanced;
           leaf-list next-hop {
             ordered-by user;
             description "Next-hop identifier to which to map";
             type union {
               type jt:ipaddr-or-interface;
               type string {
                 pattern "<.*>|$.*";
               }
             }
           }
           leaf-list lsp-next-hop {
             ordered-by user;
             description "Regular expression for LSP next hop";
             type string;
           }
           leaf non-lsp-next-hop {
             description "Any non-RSVP LSP next hop";
             type empty;
           }
           leaf non-labelled-next-hop {
             description "Any non-labelled next hop";
             type empty;
           }
           leaf discard {
             description "Discard next hop";
             type empty;
           }
           container transport-class {
             description "Transport class to be mapped with forwarding class";
             uses apply-advanced;
             list name {
               key name;
               ordered-by user;
               description "Transport class name";
               leaf name {
                 description "Transport class name";
                 junos:cli-feature "nokeyword";
                 junos:must "(\"routing-options transport-class any-class\")";
                 junos:must-message "TC any-class is not configured";
                 type string;
               }
               uses apply-advanced;
             }
             list color {
               key name;
               ordered-by user;
               description "Transport class color";
               leaf name {
                 description "Transport class color";
                 junos:cli-feature "nokeyword";
                 junos:must "(\"routing-options transport-class any-class\")";
                 junos:must-message "TC any-class is not configured";
                 type union {
                   type uint32;
                   type string {
                     pattern "<.*>|$.*";
                   }
                 }
               }
               uses apply-advanced;
             }
           }
         }
       }
       list class {
         key name;
         ordered-by user;
         description "Class-of-service description";
         leaf name {
           description "Name to identify class of service";
           junos:cli-feature "nokeyword";
           type string {
             junos:posix-pattern "^.{1,64}$";
             junos:pattern-message "Must be string of 64 characters or less";
           }
         }
         uses apply-advanced;
         container classification-override {
           description "Define classification overrides";
           uses apply-advanced;
           leaf forwarding-class {
             description "Forwarding class name";
             type string {
               junos:posix-pattern "^.{1,64}$";
               junos:pattern-message "Must be string of 64 characters or less";
             }
           }
         }
       }
     }
   }
   grouping appqos-traceoptions-type {
     description "Trace options for application classifier";
     uses apply-advanced;
     leaf no-remote-trace {
       description "Disable remote tracing";
       junos:must "(\"system tracing\")";
       junos:must-message "'no-remote-trace' is valid only when [system tracing] is configured";
       type empty;
     }
     container file {
       junos:cli-feature "oneliner";
       description "Trace file information";
       leaf filename {
         description "Name of file in which to write trace information";
         junos:cli-feature "nokeyword";
         type string {
           length "1 .. 1024";
           junos:posix-pattern "![/ %]";
           junos:pattern-message "Must not contain \'/\', % or a space";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       junos:cli-feature "oneliner";
       description "Events and other information to include in trace output";
       leaf name {
         description "Flag name to include in trace output";
         junos:cli-feature "nokeyword";
         type enumeration {
           enum "all" {
             description "All events";
           }
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
   }
   grouping appqos_rule_type {
     leaf name {
       description "Rule name";
       junos:cli-feature "nokeyword";
       type string {
         length "1 .. 63";
       }
     }
     uses apply-advanced;
     container match {
       description "Specify application traffic control rule match-criteria";
       uses apply-advanced;
       leaf application-any {
         description "Any applications";
         type empty;
       }
       leaf application-unknown {
         description "Uknown applcations";
         status deprecated;
         type empty;
       }
       leaf application-known {
         description "Identifiable applications";
         type empty;
       }
       leaf-list application {
         ordered-by user;
         description "Specify application name to match";
         type string {
           length "1 .. 63";
         }
       }
       leaf-list application-group {
         ordered-by user;
         description "Specify application group name to match";
         type string {
           length "1 .. 63";
         }
       }
     }
     container then {
       description "Specify rule action to take when packet match criteria";
       uses apply-advanced;
       leaf forwarding-class {
         description "Forwarding class for outgoing packets";
         type string {
           junos:posix-pattern "^.{1,64}$";
           junos:pattern-message "Must be string of 64 characters or less";
         }
       }
       leaf dscp-code-point {
         description "DSCP code point bitmap or alias";
         type string {
           junos:posix-pattern "^(([01]{6})|([a-zA-Z].{0,63}))$";
           junos:pattern-message "Not 6-bit pattern or code point alias";
         }
       }
       leaf loss-priority {
         description "Packet loss priority";
         type enumeration {
           enum "low" {
             description "Low loss priority";
           }
           enum "medium-low" {
             description "Medium-low loss priority";
           }
           enum "medium-high" {
             description "Medium-high loss priority";
           }
           enum "high" {
             description "High loss priority";
           }
         }
       }
       container rate-limit {
         description "Apply rate limiters";
         uses apply-advanced;
         leaf client-to-server {
           description "Client-to-server rate limiter";
           junos:must "(\"class-of-service application-traffic-control rate-limiters $$\")";
           junos:must-message "Rate limiter must be defined";
           type string;
         }
         leaf server-to-client {
           description "Server-to-client rate limiter";
           junos:must "(\"class-of-service application-traffic-control rate-limiters $$\")";
           junos:must-message "Rate limiter must be defined";
           type string;
         }
         leaf loss-priority-high {
           description "Set Rate limiter's action Loss-Priority to high";
           type empty;
         }
       }
       leaf log {
         description "Log the action";
         type empty;
       }
     }
   }
   grouping cos_interfaces_type {
     junos:cli-feature "nokeyword";
     junos:cli-feature "homogeneous";
     description "Physical interface";
     leaf name {
       description "Interface name (or wildcard)";
       junos:cli-feature "nokeyword";
       junos:must "((!(\".. classifiers\") || !(\".. forwarding-class\")))";
       junos:must-message "Forwarding-class and BA Classifiers not allowed on the same physical interface together";
       junos:must "((!((any \".. unit <*> rewrite-rules dscp-ipv6\" || any \".. unit <*> rewrite-rules inet6-precedence <*> protocol $$={mpls}\")) || !(\".. output-forwarding-class-map\")))";
       junos:must-message "DSCP-IPv6 rewrite or IPv6 Precedence for MPLS traffic and forwarding class map not allowed on same interface";
       junos:must "((!((any \".. unit <*> rewrite-rules dscp\" || any \".. unit <*> rewrite-rules inet-precedence <*> protocol $$={mpls}\")) || !(\".. output-forwarding-class-map\")))";
       junos:must-message "DSCP rewrite or IP Precedence rewrite for MPLS traffic and forwarding class map not allowed on same interface";
       junos:must "((!(any \".. unit <*> output-forwarding-class-map\") || !(\".. output-forwarding-class-map\")))";
       junos:must-message "Cannot configure forwarding-class-map statement on both physical and logical interface";
       junos:must "((!((any \".. unit <*> scheduler-map\" || (any \".. unit <*> input-scheduler-map\" || (any \".. unit <*> output-traffic-control-profile\" || any \".. unit <*> input-traffic-control-profile\")))) || !((\".. scheduler-map\" || \".. input-scheduler-map\"))))";
       junos:must-message "Cannot configure scheduler-map or traffic-control-profile statement on both physical and logical interface";
       junos:must "((!((\".. scheduler-map\" || \".. input-scheduler-map\")) || (!(\"interfaces $$\") || !((\"interfaces $$ per-unit-scheduler\" || (\"interfaces $$ shared-scheduler\" || \"interfaces $$ hierarchical-scheduler\"))))))";
       junos:must-message "'per-unit-scheduler', 'hierarchical-scheduler', or 'shared scheduler' is not compatible with scheduler map/input scheduler map on an interface";
       junos:must "((!(any \".. unit <*> input-traffic-control-profile\") || (!(\"interfaces $$\") || (\"interfaces $$ per-unit-scheduler\" || (\"interfaces $$ shared-scheduler\" || (\"interfaces $$ hierarchical-scheduler\" || any \"interfaces $$ unit <*> pppoe-options\"))))))";
       junos:must-message "'per-unit-scheduler', 'hierarchical-scheduler',or 'shared scheduler' for this interface is required for input-traffic-control-profile configuration on interface unit";
       junos:must "((!(any \".. unit <*> output-traffic-control-profile\") || (!(\"interfaces $$\") || (\"interfaces $$ per-unit-scheduler\" || (\"interfaces $$ shared-scheduler\" || (\"interfaces $$ hierarchical-scheduler\" || (\"interfaces $$ cascade-port\" || (\"interfaces $$ anchor-point\" || (any \"interfaces $$ unit <*> pppoe-options\" || any \"interfaces $$ unit <*> demux-options\")))))))))";
       junos:must-message "'per-unit-scheduler', 'hierarchical-scheduler', or 'shared scheduler' for this interface is required for output-traffic-control-profile configuration on interface unit";
       junos:must "((!(any \".. unit <*> shaping-rate\") || (!(\"interfaces $$\") || (\"interfaces $$ per-unit-scheduler\" || (\"interfaces $$ shared-scheduler\" || (\"interfaces $$ hierarchical-scheduler\" || (any \"interfaces $$ unit <*> pppoe-options\" || any \"interfaces $$ unit <*> demux-options\")))))))";
       junos:must-message "'per-unit-scheduler', 'hierarchical-scheduler', or 'shared scheduler' for this interface is required for bandwidth configuration on interface unit";
       junos:must "((!(\".. output-traffic-control-profile-remaining\") || (!(\"interfaces $$\") || \"interfaces $$ hierarchical-scheduler\")))";
       junos:must-message "'hierarchical-scheduler' for this interface is required for output-traffic-control-profile-remaining on ifd ";
       junos:must "((!(any \".. slice <*> output-traffic-control-profile\") || (!(\"interfaces $$\") || \"interfaces $$ hierarchical-scheduler\")))";
       junos:must-message "'hierarchical-scheduler' for this interface is required for output-traffic-control-profile on slice ";
       junos:must "((!(any \".. unit <*> virtual-channel-group\") || (!(\"interfaces $$\") || \"interfaces $$ per-unit-scheduler\")))";
       junos:must-message "'per-unit-scheduler' for this interface is required for virtual-channel-group on interface unit";
       junos:must "((!((any \".. unit <*> scheduler-map\" || any \".. unit <*> input-scheduler-map\")) || (!(\"interfaces $$\") || (\"interfaces $$ per-unit-scheduler\" || (\"interfaces $$ shared-scheduler\" || (\"interfaces $$ hierarchical-scheduler\" || (\"interfaces $$ cascade-port\" || (any \"interfaces $$ unit <*> pppoe-options\" || any \"interfaces $$ unit <*> demux-options\"))))))))";
       junos:must-message "'per-unit-scheduler', 'hierarchical-scheduler', or 'shared-scheduler' for this interface is required for scheduler map on interface unit";
       type union {
         type jt:interface-device-wildcard;
         type string {
           pattern "<.*>|$.*";
         }
       }
     }
     uses apply-advanced;
     list forwarding-class-set {
       key name;
       junos:cli-feature "homogeneous";
       description "Map forwarding class sets to output traffic control profile";
       junos:must "(!(\".. scheduler-map\"))";
       junos:must-message "Scheduler-map and forwarding-class-set not allowed on same interface together ";
       max-elements 4;
       leaf name {
         description "Forwarding class sets name";
         junos:cli-feature "nokeyword";
         type string {
           length "1 .. 64";
         }
       }
       uses apply-advanced;
       container output-traffic-control-profile {
         junos:cli-feature "oneliner";
         description "Output traffic control profile for the interface";
         leaf profile-name {
           description "Name of the output traffic control profile associated with the interface";
           junos:cli-feature "nokeyword";
           type string {
             length "1 .. 64";
           }
         }
       }
     }
     leaf drop-congestion-notification {
       description "Drop congestion notification for the interface";
       junos:must "(\"class-of-service drop-congestion-notification\")";
       junos:must-message "drop-congestion-notification udp-port and forwarding-class configuration needed";
       type empty;
     }
     leaf congestion-notification-profile {
       description "Congestion notification profile for the interface";
       type string {
         length "1 .. 64";
       }
     }
     leaf decn-profile {
       description "DECN profile for the interface";
       type string {
         length "1 .. 64";
       }
     }
     leaf lecn-profile {
       description "LECN profile for the interface";
       type string {
         length "1 .. 64";
       }
     }
     leaf dedicated-buffer-profile {
       description "Dedicated buffer profile on the ifd";
       type string {
         length "1 .. 64";
       }
     }
     leaf dynamic-threshold-profile {
       description "Dynamic threshold profile on the ifd";
       type string {
         length "1 .. 64";
       }
     }
     container rewrite-value {
       description "FC interface rewrite value";
       uses apply-advanced;
       container input {
         description "Input direction";
         uses apply-advanced;
         container ieee-802.1 {
           description "IEEE 802.1 code point";
           uses apply-advanced;
           container code-point {
             description "IEEE 802.1 code point";
             uses apply-advanced;
             leaf bits {
               description "IEEE 802.1 code point";
               junos:cli-feature "nokeyword";
               type string {
                 junos:posix-pattern "^([01]{3})$";
                 junos:pattern-message "Must be of form xxx, where x is 0 or 1";
               }
             }
           }
         }
       }
     }
     leaf scheduler-map-forwarding-class-set {
       description "Output scheduler map forwarding-class-set  ";
       type string {
         junos:posix-pattern "^.{1,64}$";
         junos:pattern-message "Must be string of 64 characters or less";
       }
     }
     leaf scheduler-map {
       description "Output scheduler map";
       type string {
         length "1 .. 64";
       }
     }
     leaf input-scheduler-map {
       description "Input scheduler map";
       type string {
         length "1 .. 64";
       }
     }
     leaf scheduler-map-chassis {
       description "Scheduler map applied to chassis queues (not PIC queues)";
       type union {
         type string {
           pattern "derived";
         }
         type string {
           length "1 .. 64";
         }
       }
     }
     container shaping-rate {
       junos:must "(!(\"interfaces ${interface} aggregated-ether-options link-speed mixed\"))";
       junos:must-message "CoS features are incompatible with link-speed mixed";
       junos:cli-feature "oneliner";
       description "Output shaping rate";
       leaf rate {
         description "Shaping rate as an absolute rate";
         junos:cli-feature "nokeyword";
         units "bits per second";
         type string;
       }
     }
     container input-shaping-rate {
       junos:must "(!(\"interfaces ${interface} aggregated-ether-options link-speed mixed\"))";
       junos:must-message "CoS features are incompatible with link-speed mixed";
       junos:cli-feature "oneliner";
       description "Input shaping rate";
       leaf rate {
         description "Input shaping rate as an absolute rate";
         junos:cli-feature "nokeyword";
         units "bits per second";
         type string;
       }
     }
     container input-traffic-control-profile {
       junos:must "(!((\"..  input-scheduler-map\" || \".. input-shaping-rate\")))";
       junos:must-message "input-traffic-control-profile cannot be configured if any of the following are configured: input-scheduler-map, input-shaping-rate";
       junos:cli-feature "oneliner";
       description "Input traffic control profile";
       leaf profile-name {
         description "Name of the traffic control profile";
         junos:cli-feature "nokeyword";
         type string {
           length "1 .. 64";
         }
       }
     }
     container input-traffic-control-profile-remaining {
       junos:must "(!((\"..  scheduler-map\" || \".. shaping-rate\")))";
       junos:must-message "input-traffic-control-profile cannot be configured if any of the following are configured: scheduler-map, shaping-rate";
       junos:cli-feature "oneliner";
       description "Input traffic control profile for remaining traffic on the ifd";
       leaf profile-name {
         description "Name of the traffic control profile";
         junos:cli-feature "nokeyword";
         type string {
           length "1 .. 64";
         }
       }
     }
     container output-traffic-control-profile {
       junos:must "(!((\"..  scheduler-map\" || \".. shaping-rate\")))";
       junos:must-message "output-traffic-control-profile cannot be configured if any of the following are configured: scheduler-map, shaping-rate";
       junos:cli-feature "oneliner";
       description "Output traffic control profile";
       leaf profile-name {
         description "Name of the traffic control profile";
         junos:cli-feature "nokeyword";
         type string {
           length "1 .. 64";
         }
       }
     }
     container monitoring-profile {
       junos:cli-feature "oneliner";
       description "Monitoring profile";
       leaf profile-name {
         description "Name of the monitoring profile";
         junos:cli-feature "nokeyword";
         type string {
           length "1 .. 64";
         }
       }
     }
     container output-traffic-control-profile-remaining {
       junos:must "(!((\"..  scheduler-map\" || \".. shaping-rate\")))";
       junos:must-message "output-traffic-control-profile cannot be configured if any of the following are configured: scheduler-map, shaping-rate";
       junos:cli-feature "oneliner";
       description "Output traffic control profile for remaining traffic on the ifd";
       leaf profile-name {
         description "Name of the traffic control profile";
         junos:cli-feature "nokeyword";
         type string {
           length "1 .. 64";
         }
       }
     }
     container member-link-scheduler {
       junos:must "(!(\"interfaces ${interface} aggregated-ether-options link-speed mixed\"))";
       junos:must-message "CoS features are incompatible with link-speed mixed";
       junos:cli-feature "oneliner";
       description "Scheduler parameter model for member link";
       choice model {
         case case_1 {
           leaf scale {
             description "Scale scheduler parameters on aggregate interface";
             type empty;
           }
         }
         case case_2 {
           leaf replicate {
             description "Copy scheduler parameters from aggregate interface";
             type empty;
           }
         }
       }
     }
     container exclude-queue-overhead-bytes {
       presence "enable exclude-queue-overhead-bytes";
       description "Exclude the overhead bytes from the queue statistics";
       uses apply-advanced;
       leaf include-hierarchy {
         description "Perform overhead adjustment on IFD and all children";
         type empty;
       }
     }
     container logical-interface-aggregate-statistics {
       presence "enable logical-interface-aggregate-statistics";
       description "Logical interface aggregate queue statistics";
     }
     list unit {
       key name;
       description "Logical interface unit (or wildcard)";
       leaf name {
         description "Logical unit number";
         junos:cli-feature "nokeyword";
         type union {
           type string {
             pattern "\*";
           }
           type union {
             type string {
               pattern "<.*>|$.*";
             }
             type uint32 {
               range "0 .. 1073741823";
             }
           }
         }
       }
       uses apply-advanced;
       leaf service-accounting {
         description "Cos service accounting";
         type empty;
       }
       leaf forwarding-class {
         description "Forwarding class assigned to incoming packets";
         type string {
           length "1 .. 64";
         }
       }
       leaf scheduler-map {
         description "Output scheduler map";
         junos:must "(!(\"interfaces ${interface} hierarchical-scheduler\"))";
         junos:must-message "scheduler-map cannot be configured on a logical interface when the hierarchical-scheduler is configured: use a traffic-control-profile which references the scheduler-map";
         type string {
           length "1 .. 64";
         }
       }
       leaf input-scheduler-map {
         description "Input scheduler map";
         junos:must "(!(\"interfaces ${interface} hierarchical-scheduler\"))";
         junos:must-message "input-scheduler-map cannot be configured on a logical interface when the hierarchical-scheduler is configured";
         type string {
           length "1 .. 64";
         }
       }
       leaf fragmentation-map {
         description "Fragmentation map applied to this logical interface";
         type string {
           length "1 .. 64";
         }
       }
       container shaping-rate {
         presence "enable shaping-rate";
         junos:must "(!(\"interfaces ${interface} hierarchical-scheduler\"))";
         junos:must-message "shaping-rate cannot be configured on a logical interface when the hierarchical-scheduler is configured: use a traffic-control-profile which specifies the shaping-rate";
         junos:cli-feature "oneliner";
         description "Output shaping rate";
         choice shaping_rate_choice {
           case case_1 {
             leaf rate {
               description "Shaping rate as an absolute rate";
               junos:cli-feature "nokeyword";
               units "bits per second";
               junos:must "(!(\"interfaces ${interface} aggregated-ether-options link-speed mixed\"))";
               junos:must-message "Scheduler shaping-rate in bits per second is incompatible with link-speed mixed";
               type string;
             }
           }
           case case_2 {
             leaf percent {
               description "Shaping rate as a percentage";
               type union {
                 type string {
                   pattern "<.*>|$.*";
                 }
                 type uint32 {
                   range "0 .. 100";
                 }
               }
             }
           }
         }
       }
       container input-shaping-rate {
         junos:must "(!(\"interfaces ${interface} hierarchical-scheduler\"))";
         junos:must-message "input-shaping-rate cannot be configured on a logical interface when the hierarchical-scheduler is configured";
         junos:cli-feature "oneliner";
         description "Input shaping rate";
         choice shaping_rate_choice {
           case case_1 {
             leaf rate {
               description "Shaping rate as an absolute rate";
               junos:cli-feature "nokeyword";
               units "bits per second";
               type string;
             }
           }
           case case_2 {
             leaf percent {
               description "Shaping rate as a percentage";
               type union {
                 type string {
                   pattern "<.*>|$.*";
                 }
                 type uint32 {
                   range "0 .. 100";
                 }
               }
             }
           }
         }
       }
       container input-traffic-control-profile {
         junos:must "(!((\"..  input-scheduler-map\" || (\".. input-shaping-rate\" || (\".. adaptive-shaper\" || \".. virtual-channel-group\")))))";
         junos:must-message "input-traffic-control-profile cannot be configured if any of the following are configured under logical interface: input-scheduler-map, input-shaping-rate, adaptive-shaper, virtual-channel-group";
         junos:cli-feature "oneliner";
         description "Input traffic control profile";
         leaf profile-name {
           description "Name of traffic control profile";
           junos:cli-feature "nokeyword";
           type string {
             length "1 .. 64";
           }
         }
         leaf shared-instance {
           description "Name of the shared instance";
           junos:must "(\"interfaces ${interface} shared-scheduler\")";
           junos:must-message "Requires [edit interface <interface name> shared-scheduler]";
           type string {
             length "1 .. 64";
           }
         }
       }
       container output-traffic-control-profile {
         junos:must "(!((\"..  scheduler-map\" || (\".. shaping-rate\" || (\".. adaptive-shaper\" || \"..  virtual-channel-group\")))))";
         junos:must-message "output-traffic-control-profile cannot be configured if any of the following are configured under logical interface: scheduler-map, shaping-rate, adaptive-shaper, virtual-channel-group";
         junos:cli-feature "oneliner";
         description "Output traffic control profile";
         leaf profile-name {
           description "Name of the traffic control profile";
           junos:cli-feature "nokeyword";
           type string {
             length "1 .. 64";
           }
         }
         leaf shared-instance {
           description "Name of the shared instance";
           junos:must "(\"interfaces ${interface} shared-scheduler\")";
           junos:must-message "Requires [edit interface <interface name> shared-scheduler]";
           type string {
             length "1 .. 64";
           }
         }
       }
       container report-ingress-shaping-rate {
         junos:cli-feature "oneliner";
         description "Report ingress shaping rate";
         choice report_ingress_shaping_rate_choice {
           case case_1 {
             leaf rate {
               description "Ingress shaping rate as an absolute value";
               junos:cli-feature "nokeyword";
               units "bits per second";
               type string;
             }
           }
         }
       }
       container classifiers {
         description "Classifiers applied to incoming packets";
         uses apply-advanced;
         list dscp {
           key name;
           description "Differentiated Services code point classifier";
           leaf name {
             description "Name of classifier to be applied";
             junos:cli-feature "nokeyword";
             type union {
               type string {
                 pattern "default";
               }
               type string {
                 length "1 .. 64";
               }
             }
           }
           uses apply-advanced;
           leaf-list family {
             ordered-by user;
             description "Family for DSCP classifier";
             type string;
           }
         }
         list dscp-ipv6 {
           key name;
           description "Differentiated Services code point classifier IPv6";
           leaf name {
             description "Name of classifier to be applied";
             junos:cli-feature "nokeyword";
             type union {
               type string {
                 pattern "default";
               }
               type string {
                 length "1 .. 64";
               }
             }
           }
           uses apply-advanced;
           leaf-list family {
             ordered-by user;
             description "Family for DSCP Ipv6 classifier";
             type string;
           }
         }
         container exp {
           junos:cli-feature "oneliner";
           description "EXP classifier";
           leaf classifier-name {
             description "Name of classifier to be applied";
             junos:cli-feature "nokeyword";
             type union {
               type string {
                 pattern "default";
               }
               type string {
                 length "1 .. 64";
               }
             }
           }
         }
         container ieee-802.1 {
           junos:cli-feature "oneliner";
           description "IEEE-802.1 classifier";
           leaf classifier-name {
             description "Name of classifier to be applied";
             junos:cli-feature "nokeyword";
             type union {
               type string {
                 pattern "default";
               }
               type string {
                 length "1 .. 64";
               }
             }
           }
           leaf vlan-tag {
             description "VLAN tag used for classification";
             type enumeration {
               enum "outer" {
                 description "Classification based on outer VLAN tag";
               }
               enum "inner" {
                 description "Classification based on inner VLAN tag";
               }
               enum "transparent" {
                 description "Classification based on hidden VLAN tag";
               }
             }
           }
         }
         container inet-precedence {
           junos:cli-feature "oneliner";
           description "IPv4 precedence classifier";
           leaf classifier-name {
             description "Name of classifier to be applied";
             junos:cli-feature "nokeyword";
             type union {
               type string {
                 pattern "default";
               }
               type string {
                 length "1 .. 64";
               }
             }
           }
         }
         container ieee-802.1ad {
           junos:must "(!(\".. ieee-802.1\"))";
           junos:must-message "ieee-802.1ad and ieee-802.1 not allowed on same unit";
           junos:cli-feature "oneliner";
           junos:cli-feature "oneliner-plus";
           description "IEEE-802.1ad (DEI) classifier";
           leaf classifier-name {
             description "Name of classifier to be applied";
             junos:cli-feature "nokeyword";
             type union {
               type string {
                 pattern "default";
               }
               type string {
                 length "1 .. 64";
               }
             }
           }
           leaf vlan-tag {
             description "VLAN tag used for classification";
             type enumeration {
               enum "outer" {
                 description "Classification based on outer VLAN tag";
               }
               enum "inner" {
                 description "Classification based on inner VLAN tag";
               }
             }
           }
         }
       }
       container rewrite-rules {
         description "Rewrite rules applied to outgoing packets";
         uses apply-advanced;
         list dscp {
           key name;
           junos:cli-feature "oneliner";
           description "Differentiated Services code point rewrite rule";
           junos:must "(!(\".. inet-precedence\"))";
           junos:must-message "DSCP and inet-precedence not allowed on same unit";
           leaf name {
             description "Name of rewrite rule to be applied";
             junos:cli-feature "nokeyword";
             type union {
               type string {
                 pattern "default";
               }
               type string {
                 length "1 .. 64";
               }
             }
           }
           leaf-list protocol {
             ordered-by user;
             description "Specify protocol matching criteria";
             type enumeration {
               enum "mpls" {
                 description "Apply to IPv4 packets entering MPLS tunnel";
               }
               enum "gtp-inet-outer" {
                 description "Apply to outer IP header";
               }
               enum "gtp-inet-both" {
                 description "Apply to both IP header";
               }
               enum "inet-outer" {
                 description "Apply to outer IP header";
               }
               enum "inet-both" {
                 description "Apply to both IP header";
               }
             }
           }
         }
         list dscp-ipv6 {
           key name;
           junos:cli-feature "oneliner";
           description "Differentiated Services code point rewrite rule IPv6";
           junos:must "(!(\".. inet6-precedence\"))";
           junos:must-message "IPv6 DSCP and inet6-precedence not allowed on same unit";
           leaf name {
             description "Name of rewrite rule to be applied";
             junos:cli-feature "nokeyword";
             type union {
               type string {
                 pattern "default";
               }
               type string {
                 length "1 .. 64";
               }
             }
           }
           leaf-list protocol {
             ordered-by user;
             description "Specify protocol matching criteria";
             type enumeration {
               enum "mpls" {
                 description "Apply to IPv6 packets entering MPLS tunnel";
               }
               enum "gtp-inet-outer" {
                 description "Apply to outer IP header";
               }
               enum "gtp-inet-both" {
                 description "Apply to both IP header";
               }
             }
           }
         }
         list exp {
           key name;
           junos:cli-feature "oneliner";
           description "EXP rewrite rule";
           leaf name {
             description "Name of rewrite rule to be applied";
             junos:cli-feature "nokeyword";
             type union {
               type string {
                 pattern "default";
               }
               type string {
                 length "1 .. 64";
               }
             }
           }
           leaf-list protocol {
             ordered-by user;
             description "Specify protocol matching criteria";
             type enumeration {
               enum "mpls-any" {
                 description "Apply to MPLS packets, write MPLS header only";
               }
               enum "mpls-inet-both" {
                 description "Apply to IPv4 MPLS packets, write MPLS and IPv4 header";
               }
               enum "mpls-inet-both-non-vpn" {
                 description "Apply to IPv4 MPLS packets, write MPLS and IPv4 header for only non VPN traffic";
               }
             }
           }
         }
         container ieee-802.1 {
           junos:cli-feature "oneliner";
           description "IEEE-802.1 rewrite rule";
           leaf rewrite-rule-name {
             description "Name of rewrite rule to be applied";
             junos:cli-feature "nokeyword";
             type union {
               type string {
                 pattern "default";
               }
               type string {
                 length "1 .. 64";
               }
             }
           }
           leaf vlan-tag {
             description "One or more VLAN tags to which rewrite rule applies";
             type enumeration {
               enum "outer" {
                 description "Rewrite rule applies to outer VLAN tag";
               }
               enum "outer-and-inner" {
                 description "Rewrite rule applies to both outer and inner VLAN tags";
               }
             }
           }
         }
         list inet-precedence {
           key name;
           junos:cli-feature "oneliner";
           description "IPv4 precedence rewrite rule";
           leaf name {
             description "Name of rewrite rule to be applied";
             junos:cli-feature "nokeyword";
             type union {
               type string {
                 pattern "default";
               }
               type string {
                 length "1 .. 64";
               }
             }
           }
           leaf-list protocol {
             ordered-by user;
             description "Specify protocol matching criteria";
             type enumeration {
               enum "mpls" {
                 description "Apply to IPv4 packets entering MPLS tunnel";
               }
               enum "gtp-inet-outer" {
                 description "Apply to outer IP header";
               }
               enum "gtp-inet-both" {
                 description "Apply to both IP header";
               }
               enum "inet-outer" {
                 description "Apply to outer IP header";
               }
               enum "inet-both" {
                 description "Apply to both IP header";
               }
             }
           }
         }
         container ieee-802.1ad {
           junos:must "(!(\".. ieee-802.1\"))";
           junos:must-message "ieee-802.1ad and ieee-802.1 not allowed on same unit";
           junos:cli-feature "oneliner-plus";
           description "IEEE-802.1ad (DEI) rewrite rule";
           uses apply-advanced;
           leaf rewrite-rule-name {
             description "Name of rewrite rule to be applied";
             junos:cli-feature "nokeyword";
             type union {
               type string {
                 pattern "default";
               }
               type string {
                 length "1 .. 64";
               }
             }
           }
           leaf vlan-tag {
             description "One or more VLAN tags to which rewrite rule applies";
             type enumeration {
               enum "outer" {
                 description "Rewrite rule applies to outer VLAN tag";
               }
               enum "outer-and-inner" {
                 description "Rewrite rule applies to both outer and inner VLAN tags";
               }
             }
           }
         }
       }
     }
     container classifiers {
       description "Classifiers applied to incoming packets";
       uses apply-advanced;
       list dscp {
         key name;
         description "Differentiated Services code point classifier";
         leaf name {
           description "Name of classifier to be applied";
           junos:cli-feature "nokeyword";
           type union {
             type string {
               pattern "default";
             }
             type string {
               length "1 .. 64";
             }
           }
         }
         uses apply-advanced;
       }
       list dscp-ipv6 {
         key name;
         description "Differentiated Services code point classifier IPv6";
         leaf name {
           description "Name of classifier to be applied";
           junos:cli-feature "nokeyword";
           type union {
             type string {
               pattern "default";
             }
             type string {
               length "1 .. 64";
             }
           }
         }
         uses apply-advanced;
       }
       container ieee-802.1 {
         junos:cli-feature "oneliner";
         description "IEEE-802.1 classifier";
         leaf classifier-name {
           description "Name of classifier to be applied";
           junos:cli-feature "nokeyword";
           type union {
             type string {
               pattern "default";
             }
             type string {
               length "1 .. 64";
             }
           }
         }
         leaf vlan-tag {
           description "VLAN tag used for classification";
           type enumeration {
             enum "outer" {
               description "Classification based on outer VLAN tag";
             }
             enum "inner" {
               description "Classification based on inner VLAN tag";
             }
           }
         }
       }
       container ieee-802.1ad {
         junos:cli-feature "oneliner";
         junos:cli-feature "oneliner-plus";
         description "IEEE-802.1ad (DEI) classifier";
         leaf classifier-name {
           description "Name of classifier to be applied";
           junos:cli-feature "nokeyword";
           type union {
             type string {
               pattern "default";
             }
             type string {
               length "1 .. 64";
             }
           }
         }
         leaf vlan-tag {
           description "VLAN tag used for classification";
           type enumeration {
             enum "outer" {
               description "Classification based on outer VLAN tag";
             }
             enum "inner" {
               description "Classification based on inner VLAN tag";
             }
           }
         }
       }
       container inet-precedence {
         junos:cli-feature "oneliner";
         description "IPv4 precedence classifier";
         leaf classifier-name {
           description "Name of classifier to be applied";
           junos:cli-feature "nokeyword";
           type union {
             type string {
               pattern "default";
             }
             type string {
               length "1 .. 64";
             }
           }
         }
       }
     }
     leaf forwarding-class {
       description "Forwarding class assigned to incoming packets";
       type string {
         junos:posix-pattern "^.{1,64}$";
         junos:pattern-message "Must be string of 64 characters or less";
       }
     }
     container rewrite-rules {
       description "Rewrite rules applied to outgoing packets";
       uses apply-advanced;
       list dscp {
         key name;
         junos:cli-feature "oneliner";
         description "Differentiated Services code point rewrite rule";
         junos:must "(!(\".. inet-precedence\"))";
         junos:must-message "DSCP and inet-precedence not allowed on same unit";
         leaf name {
           description "Name of rewrite rule to be applied";
           junos:cli-feature "nokeyword";
           type union {
             type string {
               pattern "default";
             }
             type string {
               length "1 .. 64";
             }
           }
         }
       }
       list dscp-ipv6 {
         key name;
         junos:cli-feature "oneliner";
         description "Differentiated Services code point rewrite rule IPv6";
         junos:must "(!(\".. inet6-precedence\"))";
         junos:must-message "IPv6 DSCP and inet6-precedence not allowed on same unit";
         leaf name {
           description "Name of rewrite rule to be applied";
           junos:cli-feature "nokeyword";
           type union {
             type string {
               pattern "default";
             }
             type string {
               length "1 .. 64";
             }
           }
         }
       }
       container ieee-802.1 {
         junos:cli-feature "oneliner";
         description "IEEE-802.1 rewrite rule";
         leaf rewrite-rule-name {
           description "Name of rewrite rule to be applied";
           junos:cli-feature "nokeyword";
           type union {
             type string {
               pattern "default";
             }
             type string {
               length "1 .. 64";
             }
           }
         }
       }
       container ieee-802.1ad {
         junos:cli-feature "oneliner-plus";
         description "IEEE-802.1ad (DEI) rewrite rule";
         uses apply-advanced;
         leaf rewrite-rule-name {
           description "Name of rewrite rule to be applied";
           junos:cli-feature "nokeyword";
           type union {
             type string {
               pattern "default";
             }
             type string {
               length "1 .. 64";
             }
           }
         }
         leaf vlan-tag {
           description "One or more VLAN tags to which rewrite rule applies";
           type enumeration {
             enum "outer" {
               description "Rewrite rule applies to outer VLAN tag";
             }
           }
         }
       }
       list inet-precedence {
         key name;
         junos:cli-feature "oneliner";
         description "IPv4 precedence rewrite rule";
         leaf name {
           description "Name of rewrite rule to be applied";
           junos:cli-feature "nokeyword";
           type union {
             type string {
               pattern "default";
             }
             type string {
               length "1 .. 64";
             }
           }
         }
       }
     }
     container multi-destination {
       description "Multi-destination class of service";
       uses apply-advanced;
       container classifiers {
         junos:must "(!(\".. forwarding-class\"))";
         junos:must-message "Either Forwarding-class or Classifiers can be configured";
         description "Classifier applied to multi-destination traffic";
         uses apply-advanced;
         container ieee-802.1 {
           junos:cli-feature "oneliner";
           description "IEEE-802.1P classifier";
           leaf classifier-name {
             description "Name of classifier to be applied";
             junos:cli-feature "nokeyword";
             type string {
               length "1 .. 64";
             }
           }
         }
         container dscp {
           junos:must "(!(\".. inet-precedence\"))";
           junos:must-message "Either DSCP or Inet-Precedence can be configured";
           junos:cli-feature "oneliner";
           description "Differentiated services code point classifier";
           leaf classifier-name {
             description "Name of classifier to be applied";
             junos:cli-feature "nokeyword";
             type string {
               length "1 .. 64";
             }
           }
         }
         container dscp-ipv6 {
           junos:cli-feature "oneliner";
           description "Differentiated services code point classifier IPv6";
           leaf classifier-name {
             description "Name of classifier to be applied";
             junos:cli-feature "nokeyword";
             type string {
               length "1 .. 64";
             }
           }
         }
         container inet-precedence {
           junos:cli-feature "oneliner";
           description "IPv4 precedence classifier";
           leaf classifier-name {
             description "Name of classifier to be applied";
             junos:cli-feature "nokeyword";
             type string {
               length "1 .. 64";
             }
           }
         }
       }
       leaf forwarding-class {
         description "Forwarding class assigned to incoming Multi-destination packets";
         type string {
           junos:posix-pattern "^.{1,64}$";
           junos:pattern-message "Must be string of 64 characters or less";
         }
       }
     }
   }
   grouping juniper-dynamic-profile-varset-object {
     junos:cli-feature "homogeneous";
     leaf name {
       description "Profile varset associated with the profile";
       junos:cli-feature "nokeyword";
       type string {
         length "1 .. 80";
       }
     }
     uses apply-advanced;
     leaf junos-mep-id {
       description "Dynamic variable to substitute 'mep' value in the profile";
       type union {
         type string {
           pattern "<.*>|$.*";
         }
         type uint32 {
           range "1 .. 8191";
         }
       }
     }
     leaf junos-md-level {
       description "Dynamic variable to substitute 'level' value in the profile";
       type union {
         type string {
           pattern "<.*>|$.*";
         }
         type uint32 {
           range "0 .. 7";
         }
       }
     }
     leaf junos-remote-mep-id {
       description "Dynamic variable to substitute 'remote-mep' value in the profile";
       type union {
         type string {
           pattern "<.*>|$.*";
         }
         type uint32 {
           range "1 .. 8191";
         }
       }
     }
     leaf junos-md-name {
       description "Dynamic variable to substitute 'maintenance-domain' in profile";
       type string;
     }
     leaf junos-ma-name {
       description "Dynamic variable to substitute 'maintenance-association' in profile";
       type string {
         length "1 .. 32";
       }
     }
     leaf junos-loss-threshold {
       description "Dynamic variable to substitute 'loss-threshold' in profile";
       type union {
         type string {
           pattern "<.*>|$.*";
         }
         type uint32 {
           range "3 .. 256";
         }
       }
     }
     leaf junos-md-name-format {
       description "Dynamic variable to substitute 'name-format' in profile";
       type enumeration {
         enum "none" {
           description "No format specified";
         }
         enum "dns" {
           description "Character string similar to Domain Name System name";
         }
         enum "mac+2oct" {
           description "MAC address with 2 octet integer (xx:xx:xx:xx:xx:xx.Y format)";
         }
         enum "character-string" {
           description "Character string";
         }
       }
     }
     leaf junos-ma-name-format {
       description "Dynamic variable to substitute 'short-name-format' in profile";
       type enumeration {
         enum "2octet" {
           description "An integer in the range 0..65535";
         }
         enum "rfc-2685-vpn-id" {
           description "VPN identifier that complies with RFC 2685";
         }
         enum "vlan" {
           description "Primary VLAN identifier";
         }
         enum "character-string" {
           description "Character string";
         }
         enum "icc" {
           description "ITU Carrier Code";
         }
       }
     }
     leaf junos-ccm-interval {
       description "Dynamic variable to substitute 'interval' in profile";
       type enumeration {
         enum "10ms" {
           junos:must "(!(\"routing-options ppm no-delegate-processing\"))";
           junos:must-message "10ms interval for continuity-check is not supported with no-delegate-processing";
         }
         enum "100ms" {
         }
         enum "1s" {
         }
         enum "10s" {
         }
         enum "1m" {
         }
         enum "10m" {
         }
       }
     }
     leaf junos-action-profile {
       description "Dynamic variable to substitute 'action-profile' in profile";
       junos:must "(\"protocols oam ethernet connectivity-fault-management action-profile $$\")";
       junos:must-message "Action profile not configured";
       type string;
     }
     leaf junos-layer2-output-policer {
       description "Dynamic variable to substitute 'layer2 output-policer'";
       type string;
     }
   }
   grouping juniper-dynamic-variable-object {
     junos:cli-feature "homogeneous";
     junos:cli-feature "oneliner-plus";
     leaf name {
       description "Name of variable";
       junos:cli-feature "nokeyword";
       type string {
         junos:posix-pattern "^[a-zA-Z][a-zA-Z0-9_-]*$";
         junos:pattern-message "Variable names must start with letters a-z A-Z";
       }
     }
     uses apply-advanced;
     leaf equals {
       description "Computable expression of dynamic profile variables";
       type string;
     }
     leaf default-value {
       description "Default value for variable";
       type string;
     }
     leaf mandatory {
       description "Variable must be supplied by external server";
       type empty;
     }
     leaf uid-reference {
       description "Variable that refers to the uid variable";
       type empty;
     }
     leaf uid {
       description "Compute unique Id value for the variable";
       type empty;
     }
   }
   grouping juniper-protocols-pim {
     uses apply-advanced;
     leaf protocol-instance-name {
       description "Name of protocol instance under routing instance";
       type string;
     }
     container family {
       junos:cli-feature "homogeneous";
       description "Local address family";
       container any {
         presence "enable any";
         description "Default properties for all address families";
         uses apply-advanced;
         leaf disable {
           description "Disable all families";
           type empty;
         }
       }
       container inet {
         presence "enable inet";
         description "IPv4 specific properties";
         uses apply-advanced;
         choice enable-disable {
           case case_1 {
             leaf disable {
               description "Disable PIMv4 on all interfaces";
               type empty;
             }
           }
         }
       }
       container inet6 {
         presence "enable inet6";
         description "IPv6 specific properties";
         uses apply-advanced;
         choice enable-disable {
           case case_1 {
             leaf disable {
               description "Disable PIMv6 on all interfaces";
               type empty;
             }
           }
         }
       }
     }
     choice enable-disable {
       case case_1 {
         leaf disable {
           description "Disable PIM";
           type empty;
         }
       }
     }
     container nonstop-routing {
       junos:must "(\"routing-options nonstop-routing\")";
       junos:must-message "To disable PIM nonstop-routing, non-stop routing must be globally enabled.";
       description "Configure PIM nonstop-routing attributes";
       uses apply-advanced;
       choice enable-disable {
         case case_1 {
           leaf disable {
             description "Disable non-stop routing for PIM";
             type empty;
           }
         }
       }
     }
     container traceoptions {
       description "Trace options for PIM";
       uses apply-advanced;
       container file {
         junos:cli-feature "oneliner";
         description "Trace file options";
         leaf filename {
           description "Name of file in which to write trace information";
           junos:cli-feature "nokeyword";
           type string {
             length "1 .. 1024";
             junos:posix-pattern "![/ %]";
             junos:pattern-message "Must not contain \'/\', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         junos:cli-feature "oneliner";
         description "Tracing parameters";
         leaf name {
           junos:cli-feature "nokeyword";
           type enumeration {
             enum "route" {
               description "Trace routing information";
             }
             enum "packets" {
               description "Trace all PIM packets";
             }
             enum "hello" {
               description "Trace hello packets";
             }
             enum "register" {
               description "Trace register/register-stop messages";
             }
             enum "join" {
               description "Trace join/prune/graft/graft-ack messages";
             }
             enum "prune" {
               description "Trace join/prune/graft/graft-ack messages";
             }
             enum "graft" {
               description "Trace join/prune/graft/graft-ack messages";
             }
             enum "bootstrap" {
               description "Trace bootstrap/RP/auto-RP messages";
             }
             enum "rp" {
               description "Trace bootstrap/RP/auto-RP messages";
             }
             enum "autorp" {
               description "Trace bootstrap/RP/auto-RP messages";
             }
             enum "assert" {
               description "Trace assert messages";
             }
             enum "mdt" {
               description "Trace messages related to multicast data tunnels";
             }
             enum "nsr-synchronization" {
               description "Trace NSR synchronization events";
             }
             enum "bidirectional-df-election" {
               description "Trace bidirectional PIM DF election events";
             }
             enum "mofrr" {
               description "Trace Multicast only Fast Re-Route messages";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           junos:cli-feature "oneliner";
           uses pim_filter_obj;
         }
       }
     }
     container dense-groups {
       description "Dense mode groups for sparse-dense mode";
       uses apply-advanced;
       leaf dynamic-reject {
         description "Reject dynamic autorp negative dense-mode prefixes learnt from network";
         type empty;
       }
       list pim-dense-group-type {
         key name;
         ordered-by user;
         junos:cli-feature "nokeyword";
         junos:cli-feature "homogeneous";
         junos:cli-feature "oneliner";
         leaf name {
           description "Group address or range to forward in dense mode";
           junos:cli-feature "nokeyword";
           type jt:ipprefix;
         }
         choice dense-group-flags {
           case case_1 {
             leaf reject {
               description "Do not include prefix as dense mode; force sparse mode";
               type empty;
             }
           }
           case case_2 {
             leaf announce {
               description "Advertise as negative prefix in auto-RP announce messages";
               type empty;
             }
           }
         }
       }
     }
     leaf vpn-tunnel-source {
       description "Source address for the provider space mGRE tunnel";
       status deprecated;
       type jt:ipv4addr;
     }
     leaf vpn-group-address {
       description "Group address for the VPN in provider space";
       status deprecated;
       junos:must "(!(\".. .. .. provider-tunnel pim-ssm\"))";
       junos:must-message "'provider-tunnel pim-ssm' can not be configured with 'pim vpn-group-address'. Please disable one of them.";
       junos:must "((!(\".. .. .. provider-tunnel pim-asm\") || \".. .. .. provider-tunnel pim-asm group-address $$\"))";
       junos:must-message "MVPN inclusive provider-tunnel group-address must be same as 'vpn-group-address'";
       type jt:ipv4addr;
     }
     leaf-list tunnel-devices {
       ordered-by user;
       description "Tunnel devices to be used for creating mt interfaces";
       type union {
         type jt:interface-device;
         type string {
           pattern "<.*>|$.*";
         }
       }
     }
     container rpf-selection {
       description "Select RPF neighbor";
       uses apply-advanced;
       list group {
         key name;
         ordered-by user;
         description "IP prefix of multicast group";
         leaf name {
           description "IP prefix of group";
           junos:cli-feature "nokeyword";
           type jt:ipprefix;
         }
         uses apply-advanced;
         container wildcard-source {
           presence "enable wildcard-source";
           description "Select RPF for (*,g) and unspecified (s,g) joins";
           uses apply-advanced;
           leaf next-hop {
             description "Next-hop address";
             type jt:ipaddr;
           }
         }
         list source {
           key name;
           ordered-by user;
           description "IP prefix of one or more multicast sources";
           leaf name {
             description "IP prefix of source";
             junos:cli-feature "nokeyword";
             type jt:ipprefix;
           }
           uses apply-advanced;
           leaf next-hop {
             description "Next-hop address";
             type jt:ipaddr;
           }
         }
       }
       list prefix-list {
         key name;
         ordered-by user;
         description "Multicast group prefix list";
         leaf name {
           description "Name of prefix list to match against";
           junos:cli-feature "nokeyword";
           junos:must "(\"policy-options prefix-list $$\")";
           junos:must-message "This prefix-list must be configured in policy-options.";
           type string;
         }
         uses apply-advanced;
         container wildcard-source {
           presence "enable wildcard-source";
           description "Select RPF for (*,g) and unspecified (s,g) joins";
           uses apply-advanced;
           leaf next-hop {
             description "Next-hop address";
             type jt:ipaddr;
           }
         }
         list source {
           key name;
           ordered-by user;
           description "IP prefix of one or more multicast sources";
           leaf name {
             description "IP prefix of source";
             junos:cli-feature "nokeyword";
             type jt:ipprefix;
           }
           uses apply-advanced;
           leaf next-hop {
             description "Next-hop address";
             type jt:ipaddr;
           }
         }
       }
     }
     container mvpn {
       presence "enable mvpn";
       description "PIM MVPN control-plane options";
       uses apply-advanced;
       container autodiscovery {
         junos:must "(!(\".. .. vpn-group-address\"))";
         junos:must-message "PIM MVPN autodiscovery options cannot be configured with 'vpn-group-address'";
         junos:must "(\".. .. .. mvpn\")";
         junos:must-message "Autodiscovery for PIM MVPNs requires 'protocols mvpn'";
         junos:must "(!(\".. .. mdt\"))";
         junos:must-message "PIM MVPN auto-discovery cannot be configured with 'pim mdt'";
         description "PE router autodiscovery options for SSM MDTs";
         status deprecated;
         uses apply-advanced;
         leaf inet-mdt {
           description "MDT-SAFI PE autodiscovery for SSM MDTs";
           type empty;
         }
       }
       container family {
         description "PIM MVPN address family";
         uses apply-advanced;
         container inet {
           description "IPv4 PIM MVPN specific properties";
           uses apply-advanced;
           leaf rosen-mvpn {
             status deprecated;
             type empty;
           }
           leaf ngen-mvpn {
             status deprecated;
             junos:must "(\".. .. .. .. .. mvpn\")";
             junos:must-message "Requires 'protocols mvpn'";
             type empty;
           }
           container autodiscovery {
             junos:must "(!(\".. .. .. .. vpn-group-address\"))";
             junos:must-message "PIM MVPN autodiscovery options cannot be configured with 'vpn-group-address'";
             junos:must "(\".. .. .. .. .. mvpn\")";
             junos:must-message "Autodiscovery for PIM MVPNs requires 'protocols mvpn'";
             junos:must "(!(\".. .. .. .. mdt\"))";
             junos:must-message "PIM MVPN auto-discovery cannot be configured with 'pim mdt'";
             description "PE router autodiscovery options for SSM MDTs";
             uses apply-advanced;
             leaf inet-mdt {
               description "MDT-SAFI PE autodiscovery for SSM MDTs";
               type empty;
             }
           }
           leaf disable {
             description "Disable family IPv4";
             type empty;
           }
         }
         container inet6 {
           description "IPv6 PIM MVPN specific properties";
           uses apply-advanced;
           leaf rosen-mvpn {
             status deprecated;
             type empty;
           }
           leaf ngen-mvpn {
             status deprecated;
             junos:must "(\".. .. .. .. .. mvpn\")";
             junos:must-message "Requires 'protocols mvpn'";
             type empty;
           }
           container autodiscovery {
             junos:must "(!(\".. .. .. .. vpn-group-address\"))";
             junos:must-message "PIM MVPN autodiscovery options cannot be configured with 'vpn-group-address'";
             junos:must "(\".. .. .. .. .. mvpn\")";
             junos:must-message "Autodiscovery for PIM MVPNs requires 'protocols mvpn'";
             junos:must "(!(\".. .. .. .. mdt\"))";
             junos:must-message "PIM MVPN auto-discovery cannot be configured with 'pim mdt'";
             description "PE router autodiscovery options for SSM MDTs";
             uses apply-advanced;
             leaf inet-mdt {
               description "MDT-SAFI PE autodiscovery for SSM MDTs";
               type empty;
             }
           }
           leaf disable {
             description "Disable family IPv6";
             type empty;
           }
         }
       }
     }
     container rib-group {
       description "Routing table group";
       junos:cli-feature "oneliner-plus";
       uses rib_group_type;
     }
     leaf-list import {
       ordered-by user;
       description "PIM sparse import join policy";
       type jt:policy-algebra;
     }
     leaf-list export {
       ordered-by user;
       description "PIM sparse export join policy";
       type jt:policy-algebra;
     }
     container mldp-inband-signalling {
       presence "enable mldp-inband-signalling";
       junos:must "((!(\"system processes routing bgp rib-sharding\") || \"system processes routing bgp no-rib-sharding\"))";
       junos:must-message "Can't be configured together with rib-sharding";
       uses apply-advanced;
       leaf-list policy {
         ordered-by user;
         description "PIM MLDP join translation filter policy";
         type jt:policy-algebra;
       }
     }
     container rpf-vector {
       description "RPF vector TLV";
       uses apply-advanced;
       leaf-list policy {
         ordered-by user;
         description "RPF vector TLV include policy";
         type jt:policy-algebra;
       }
     }
     leaf assert-timeout {
       description "Set assert timeout";
       default "180";
       type union {
         type string {
           pattern "<.*>|$.*";
         }
         type uint32 {
           range "5 .. 210";
         }
       }
     }
     leaf assert-robust-count {
       description "Number of assert messages an assert winner sends in one cycle";
       default "2";
       type union {
         type string {
           pattern "<.*>|$.*";
         }
         type uint32 {
           range "1 .. 5";
         }
       }
     }
     leaf join-prune-timeout {
       description "Set join/prune timeout";
       default "210";
       type union {
         type string {
           pattern "<.*>|$.*";
         }
         type uint32 {
           range "210 .. 420";
         }
       }
     }
     container spt-threshold {
       description "Set shortest-path-tree threshold policy";
       uses apply-advanced;
       leaf-list infinity {
         ordered-by user;
         description "Apply policy to always remain on shared tree";
         type jt:policy-algebra;
       }
     }
     container sglimit {
       description "Set limit on number of (S,G) states ";
       uses apply-advanced;
       list family {
         key name;
         ordered-by user;
         description "Protocol family";
         junos:must "(!(\".. maximum\"))";
         junos:must-message "Family wise threshold cannot be configuredif global threshold is already configured";
         leaf name {
           junos:cli-feature "nokeyword";
           type enumeration {
             enum "inet" {
               description "IPv4 family";
             }
             enum "inet6" {
               description "IPv6 family";
             }
           }
         }
         uses apply-advanced;
         leaf maximum {
           description "Maximum limit above which additional entries are not accepted";
           type union {
             type string {
               pattern "<.*>|$.*";
             }
             type uint32 {
               range "1 .. 65535";
             }
           }
         }
         leaf threshold {
           description "Percentage of maximum at which to start generating warnings";
           junos:must "(\".. maximum\")";
           junos:must-message "To configure threshold, maximum must be configured";
           type union {
             type string {
               pattern "<.*>|$.*";
             }
             type uint32 {
               range "1 .. 100";
             }
           }
         }
         leaf log-interval {
           description "Time between successive log messages";
           junos:must "(\".. maximum\")";
           junos:must-message "To configure log-interval, maximum must be configured";
           type union {
             type string {
               pattern "<.*>|$.*";
             }
             type uint32 {
               range "1 .. 65535";
             }
           }
         }
       }
       leaf maximum {
         description "Maximum limit above which additional entries are not accepted";
         type union {
           type string {
             pattern "<.*>|$.*";
           }
           type uint32 {
             range "1 .. 65535";
           }
         }
       }
       leaf threshold {
         description "Percentage of maximum at which to start generating warnings";
         junos:must "(\".. maximum\")";
         junos:must-message "To configure threshold, maximum must be configured";
         type union {
           type string {
             pattern "<.*>|$.*";
           }
           type uint32 {
             range "1 .. 100";
           }
         }
       }
       leaf log-interval {
         description "Time between successive log messages";
         junos:must "(\".. maximum\")";
         junos:must-message "To configure log-interval, maximum must be configured";
         type union {
           type string {
             pattern "<.*>|$.*";
           }
           type uint32 {
             range "1 .. 65535";
           }
         }
       }
     }
     container rp {
       junos:must "(!(\" .. passive\"))";
       junos:must-message "pim rp cannot be configured with pim passive";
       description "Router's rendezvous point properties";
       uses apply-advanced;
       leaf bootstrap-priority {
         description "Eligibility to be the bootstrap router (IPv4 only)";
         type union {
           type string {
             pattern "<.*>|$.*";
           }
           type uint32 {
             range "0 .. 255";
           }
         }
       }
       leaf-list bootstrap-import {
         ordered-by user;
         description "Bootstrap import policy (IPv4 only)";
         type jt:policy-algebra;
       }
       leaf-list bootstrap-export {
         ordered-by user;
         description "Bootstrap export policy (IPv4 only)";
         type jt:policy-algebra;
       }
       container bootstrap {
         description "Bootstrap properties";
         uses apply-advanced;
         container family {
           junos:cli-feature "homogeneous";
           description "Bootstrap address family";
           container inet {
             description "IPv4 bootstrap properties";
             junos:must "(!((\".. .. .. bootstrap-priority\" || (\".. .. .. bootstrap-import\" || \".. .. .. bootstrap-export\"))))";
             junos:must-message "Duplicate IPv4 bootstrap configuration";
             uses pim_bootstrap_options_type;
           }
           container inet6 {
             description "IPv6 bootstrap properties";
             uses pim_bootstrap_options_type;
           }
         }
       }
       container register-limit {
         description "Set limit on incoming registers that create (S,G) state";
         uses apply-advanced;
         list family {
           key name;
           ordered-by user;
           description "Protocol family";
           junos:must "(!(\".. maximum\"))";
           junos:must-message "Family wise threshold cannot be configuredif global threshold is already configured";
           leaf name {
             junos:cli-feature "nokeyword";
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             junos:must "(\".. maximum\")";
             junos:must-message "To configure threshold, maximum must be configured";
             type union {
               type string {
                 pattern "<.*>|$.*";
               }
               type uint32 {
                 range "1 .. 100";
               }
             }
           }
           leaf log-interval {
             description "Time between successive log messages";
             junos:must "(\".. maximum\")";
             junos:must-message "To configure log-interval, maximum must be configured";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           junos:must "(\".. maximum\")";
           junos:must-message "To configure threshold, maximum must be configured";
           type union {
             type string {
               pattern "<.*>|$.*";
             }
             type uint32 {
               range "1 .. 100";
             }
           }
         }
         leaf log-interval {
           description "Time between successive log messages";
           junos:must "(\".. maximum\")";
           junos:must-message "To configure log-interval, maximum must be configured";
           type union {
             type string {
               pattern "<.*>|$.*";
             }
             type uint32 {
               range "1 .. 65535";
             }
           }
         }
       }
       container group-rp-mapping {
         description "Group-rp-mapping";
         uses apply-advanced;
         list family {
           key name;
           ordered-by user;
           description "Protocol family";
           junos:must "(!(\".. maximum\"))";
           junos:must-message "Family wise threshold cannot be configuredif global threshold is already configured";
           leaf name {
             junos:cli-feature "nokeyword";
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             junos:must "(\".. maximum\")";
             junos:must-message "To configure threshold, maximum must be configured";
             type union {
               type string {
                 pattern "<.*>|$.*";
               }
               type uint32 {
                 range "1 .. 100";
               }
             }
           }
           leaf log-interval {
             description "Time between successive log messages";
             junos:must "(\".. maximum\")";
             junos:must-message "To configure log-interval, maximum must be configured";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           junos:must "(\".. maximum\")";
           junos:must-message "To configure threshold, maximum must be configured";
           type union {
             type string {
               pattern "<.*>|$.*";
             }
             type uint32 {
               range "1 .. 100";
             }
           }
         }
         leaf log-interval {
           description "Time between successive log messages";
           junos:must "(\".. maximum\")";
           junos:must-message "To configure log-interval, maximum must be configured";
           type union {
             type string {
               pattern "<.*>|$.*";
             }
             type uint32 {
               range "1 .. 65535";
             }
           }
         }
       }
       leaf-list rp-register-policy {
         ordered-by user;
         description "RP policy applied to incoming register messages";
         type jt:policy-algebra;
       }
       leaf-list dr-register-policy {
         ordered-by user;
         description "DR policy applied to outgoing register messages";
         type jt:policy-algebra;
       }
       container local {
         description "Router's local RP properties";
         uses apply-advanced;
         leaf address {
           description "Local RP address (IPv4 only)";
           type jt:ipv4addr;
         }
         choice enable-disable {
           case case_1 {
             leaf disable {
               description "Disable this RP (IPv4 only)";
               type empty;
             }
           }
         }
         leaf priority {
           description "Router's priority for becoming an RP (IPv4 only)";
           type union {
             type string {
               pattern "<.*>|$.*";
             }
             type uint32 {
               range "0 .. 255";
             }
           }
         }
         leaf hold-time {
           description "How long neighbor considers this router to be up, in seconds (IPv4 only)";
           type union {
             type string {
               pattern "<.*>|$.*";
             }
             type uint32 {
               range "1 .. 65535";
             }
           }
         }
         list group-ranges {
           key name;
           ordered-by user;
           junos:cli-feature "homogeneous";
           description "Group address range for which this router can be an RP (IPv4 only)";
           leaf name {
             junos:cli-feature "nokeyword";
             type jt:ipv4prefix;
           }
           uses apply-advanced;
         }
         leaf override {
           description "Static RP mapping will take precedence over dynamic";
           type empty;
         }
         container family {
           junos:cli-feature "homogeneous";
           description "Local RP address family";
           container inet {
             description "IPv4 local RP properties";
             uses apply-advanced;
             leaf address {
               description "Local RP address";
               type jt:ipv4addr;
             }
             choice enable-disable {
               case case_1 {
                 leaf disable {
                   description "Disable this RP";
                   type empty;
                 }
               }
             }
             leaf priority {
               description "Router's priority for becoming an RP";
               type union {
                 type string {
                   pattern "<.*>|$.*";
                 }
                 type uint32 {
                   range "0 .. 255";
                 }
               }
             }
             leaf hold-time {
               description "How long neighbor considers this router to be up, in seconds";
               type union {
                 type string {
                   pattern "<.*>|$.*";
                 }
                 type uint32 {
                   range "1 .. 65535";
                 }
               }
             }
             list group-ranges {
               key name;
               ordered-by user;
               junos:cli-feature "homogeneous";
               description "Group address range for which this router can be an RP";
               leaf name {
                 junos:cli-feature "nokeyword";
                 type jt:ipv4prefix;
               }
               uses apply-advanced;
             }
             leaf override {
               description "Static RP mapping will take precedence over dynamic";
               type empty;
             }
             container anycast-pim {
               description "Attributes for IPv4 anycast PIM";
               uses apply-advanced;
               container rp-set {
                 description "Rendezvous points belonging to anycast RP set";
                 uses apply-advanced;
                 list address {
                   key name;
                   ordered-by user;
                   junos:cli-feature "oneliner-plus";
                   description "IPv4 address of one or more remote anycast RPs";
                   leaf name {
                     description "IPv4 address of remote anycast RP";
                     junos:cli-feature "nokeyword";
                     type jt:ipaddr;
                   }
                   uses apply-advanced;
                   leaf forward-msdp-sa {
                     description "Forward SAs learned from MSDP to this RP";
                     type empty;
                   }
                 }
               }
               leaf local-address {
                 description "Local address for replicating register messages to other RPs";
                 type jt:ipaddr;
               }
             }
           }
           container inet6 {
             description "IPv6 local RP properties";
             uses apply-advanced;
             leaf address {
               description "Local RP address";
               type jt:ipv6addr;
             }
             choice enable-disable {
               case case_1 {
                 leaf disable {
                   description "Disable this RP";
                   type empty;
                 }
               }
             }
             leaf priority {
               description "Router's priority for becoming an RP";
               type union {
                 type string {
                   pattern "<.*>|$.*";
                 }
                 type uint32 {
                   range "0 .. 255";
                 }
               }
             }
             leaf hold-time {
               description "How long neighbor considers this router to be up, in seconds";
               type union {
                 type string {
                   pattern "<.*>|$.*";
                 }
                 type uint32 {
                   range "1 .. 65535";
                 }
               }
             }
             list group-ranges {
               key name;
               ordered-by user;
               junos:cli-feature "homogeneous";
               description "Group address range for which this router can be an RP";
               leaf name {
                 junos:cli-feature "nokeyword";
                 type jt:ipv6prefix;
               }
               uses apply-advanced;
             }
             leaf override {
               description "Static RP mapping will take precedence over dynamic";
               type empty;
             }
             container anycast-pim {
               description "Attributes for IPv6 anycast PIM";
               uses apply-advanced;
               container rp-set {
                 description "Rendezvous points belonging to anycast RP set";
                 uses apply-advanced;
                 list address {
                   key name;
                   ordered-by user;
                   description "IPv6 address of one or more remote anycast RPs";
                   leaf name {
                     description "IPv6 address of remote anycast RP";
                     junos:cli-feature "nokeyword";
                     type jt:ipv6addr;
                   }
                   uses apply-advanced;
                 }
               }
               leaf local-address {
                 description "Local address for replicating register messages to other RPs";
                 type jt:ipv6addr;
               }
             }
           }
         }
       }
       container embedded-rp {
         presence "enable embedded-rp";
         description "Set embedded-RP mode (IPv6 only)";
         uses apply-advanced;
         list group-ranges {
           key name;
           ordered-by user;
           description "Group address range of RP";
           uses pim_rp_group_range_type;
           junos:cli-feature "homogeneous";
         }
         leaf maximum-rps {
           description "Maximum number of embedded RPs";
           default "100";
           type union {
             type string {
               pattern "<.*>|$.*";
             }
             type uint32 {
               range "1 .. 500";
             }
           }
         }
       }
       container auto-rp {
         junos:cli-feature "oneliner-plus";
         description "Set auto-RP mode (IPv4 only)";
         uses apply-advanced;
         choice autorp-mode {
           case case_1 {
             leaf discovery {
               description "Listen for auto-RP discovery messages";
               type empty;
             }
           }
           case case_2 {
             leaf announce {
               description "Transmit auto-RP announcement messages";
               type empty;
             }
           }
           case case_3 {
             leaf mapping {
               description "Transmit auto-RP mapping messages";
               type empty;
             }
           }
         }
         choice mapping-agent-election-choice {
           leaf mapping-agent-election {
             description "Consider higher-addressed mapping agents as authoritative";
             type empty;
           }
           leaf no-mapping-agent-election {
             description "Don't consider higher-addressed mapping agents as authoritative";
             type empty;
           }
         }
       }
       container static {
         description "Configure static PIM RPs";
         uses apply-advanced;
         list address {
           key name;
           ordered-by user;
           description "RP address";
           leaf name {
             description "IP address of RP";
             junos:cli-feature "nokeyword";
             type jt:ipaddr;
           }
           uses apply-advanced;
           leaf version {
             description "PIM version of RP";
             status deprecated;
             type union {
               type string {
                 pattern "<.*>|$.*";
               }
               type uint32 {
                 range "1 .. 2";
               }
             }
           }
           list group-ranges {
             key name;
             ordered-by user;
             description "Group address range of RP";
             uses pim_rp_group_range_type;
             junos:cli-feature "homogeneous";
           }
           leaf override {
             description "Static RP mapping will take precedence over dynamic";
             type empty;
           }
         }
       }
       container bidirectional {
         junos:must "((!(\".. .. .. .. .. .. routing-instances\") || any \".. .. .. .. .. .. routing-instances <*> instance-type virtual-router\"))";
         junos:must-message "Only master instance and routing-instances of type virtual-router support PIM-BIDIR.";
         description "Configure PIM bidirectional-mode RPs";
         uses apply-advanced;
         list address {
           key name;
           ordered-by user;
           description "RP address";
           leaf name {
             description "IP address of RP";
             junos:cli-feature "nokeyword";
             type jt:ipaddr;
           }
           uses apply-advanced;
           leaf priority {
             description "Router's priority for becoming an RP";
             type union {
               type string {
                 pattern "<.*>|$.*";
               }
               type uint32 {
                 range "0 .. 255";
               }
             }
           }
           leaf hold-time {
             description "How long neighbor considers this router to be up";
             units "seconds";
             type union {
               type string {
                 pattern "<.*>|$.*";
               }
               type uint32 {
                 range "1 .. 65535";
               }
             }
           }
           list group-ranges {
             key name;
             ordered-by user;
             description "Group address range of RP";
             uses pim_rp_group_range_type;
             junos:cli-feature "homogeneous";
           }
         }
       }
       leaf register-probe-time {
         description "Register probe time";
         default "5";
         units "seconds";
         type union {
           type string {
             pattern "<.*>|$.*";
           }
           type uint32 {
             range "5 .. 60";
           }
         }
       }
     }
     leaf passive {
       description "Configure PIM protocol in passive mode";
       junos:must "(!(any \".. interface <*> distributed-dr\"))";
       junos:must-message "pim passive cannot be configured with pim distributed-dr";
       junos:must "(!(\" .. rp\"))";
       junos:must-message "pim passive cannot be configured with pim rp";
       type empty;
     }
     list interface {
       key name;
       ordered-by user;
       description "PIM interface options";
       leaf name {
         description "Interface name";
         junos:cli-feature "nokeyword";
         junos:must "((((\"routing-options multicast interface $$ disable\" || (\"routing-options multicast interface $$ maximum-bandwidth\" || (\"routing-options multicast interface $$ nexthop-unicast-address\" || (\"routing-options multicast interface $$ reverse-oif-mapping\" || (\"routing-options multicast interface $$ subscriber-leave-timer\" || \"routing-options multicast interface $$ no-qos-adjust\"))))) && !(\"routing-options multicast interface $$ enable\")) || (\"protocols pim interface $$ disable\" || !((\"routing-options multicast interface $$\" || \"routing-options multicast interface $$ enable\")))))";
         junos:must-message "Multicast cannot be enabled on the same interface in the [edit routing-options] hierarchy";
         type string;
       }
       uses apply-advanced;
       container family {
         junos:cli-feature "homogeneous";
         description "Local address family";
         container any {
           presence "enable any";
           description "Default properties for all families";
           uses apply-advanced;
           leaf disable {
             description "Disable all families";
             type empty;
           }
         }
         container inet {
           presence "enable inet";
           description "IPv4 specific properties";
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
           leaf mcae-mac-synchronize {
             description "Mclag mac synchronization";
             type empty;
           }
           choice enable-disable {
             case case_1 {
               leaf disable {
                 description "Disable PIMv4 on this interface";
                 type empty;
               }
             }
           }
         }
         container inet6 {
           presence "enable inet6";
           description "IPv6 specific properties";
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
           choice enable-disable {
             case case_1 {
               leaf disable {
                 description "Disable PIMv6 on this interface";
                 type empty;
               }
             }
           }
         }
       }
       choice enable-disable {
         case case_1 {
           leaf disable {
             description "Disable PIM on this interface";
             type empty;
           }
         }
       }
       container bidirectional {
         junos:must "((!(\".. .. .. .. .. .. routing-instances\") || any \".. .. .. .. .. .. routing-instances <*> instance-type virtual-router\"))";
         junos:must-message "Only master instance and routing-instances of type virtual-router support PIM-BIDIR.";
         description "PIM bidirectional mode properties";
         uses apply-advanced;
         container df-election {
           description "Bidir designated forwarder properties";
           uses apply-advanced;
           leaf robustness-count {
             description "Election robustness count";
             type union {
               type string {
                 pattern "<.*>|$.*";
               }
               type uint32 {
                 range "1 .. 10";
               }
             }
           }
           leaf offer-period {
             description "Election offer message period";
             units "milliseconds";
             type union {
               type string {
                 pattern "<.*>|$.*";
               }
               type uint32 {
                 range "100 .. 10000";
               }
             }
           }
           leaf backoff-period {
             description "Election backoff period";
             units "milliseconds";
             type union {
               type string {
                 pattern "<.*>|$.*";
               }
               type uint32 {
                 range "100 .. 65535";
               }
             }
           }
         }
       }
       leaf mode {
         description "Mode of interface";
         type enumeration {
           enum "dense" {
             description "Dense mode";
           }
           enum "sparse" {
             description "Sparse mode";
           }
           enum "sparse-dense" {
             description "Sparse-dense mode";
           }
           enum "bidirectional-sparse" {
             description "Bidirectional-sparse mode";
             junos:must "((!(\".. .. .. .. .. .. routing-instances\") || any \".. .. .. .. .. .. routing-instances <*> instance-type virtual-router\"))";
             junos:must-message "Only master instance and routing-instances of type virtual-router support PIM-BIDIR.";
             junos:must "(!(\".. version $$={1}\"))";
             junos:must-message "PIM Bidirectional is not supported by PIMv1.";
           }
           enum "bidirectional-sparse-dense" {
             description "Bidirectional-sparse-dense mode";
             junos:must "((!(\".. .. .. .. .. .. routing-instances\") || any \".. .. .. .. .. .. routing-instances <*> instance-type virtual-router\"))";
             junos:must-message "Only master instance and routing-instances of type virtual-router support PIM-BIDIR.";
             junos:must "(!(\".. version $$={1}\"))";
             junos:must-message "PIM Bidirectional is not supported by PIMv1.";
           }
         }
       }
       leaf priority {
         description "Hello option DR priority";
         junos:must "((!(\".. mode dense\") || (\".. mode dense\" && \"protocols igmp interface ${interface} version 1\")))";
         junos:must-message "PIM DR Priority cannot be configured in Dense Mode unless IGMP V1 is configured";
         type union {
           type string {
             pattern "<.*>|$.*";
           }
           type uint32 {
             range "0 .. 4294967295";
           }
         }
       }
       container stickydr {
         presence "enable stickydr";
         description "Make DR sticky";
         uses apply-advanced;
       }
       container multiple-triggered-joins {
         presence "enable multiple-triggered-joins";
         description "Send multiple pim triggered joins in quick intervals";
         uses apply-advanced;
         leaf count {
           description "Set number of triggered joins to be sent";
           default "2";
           type union {
             type string {
               pattern "<.*>|$.*";
             }
             type uint16 {
               range "2 .. 15";
             }
           }
         }
         leaf interval {
           description "Set interval between multiple triggered joins to be sent in milliseconds";
           default "100";
           type union {
             type string {
               pattern "<.*>|$.*";
             }
             type uint16 {
               range "100 .. 1000";
             }
           }
         }
       }
       leaf version {
         description "Force PIM version";
         status deprecated;
         type union {
           type string {
             pattern "<.*>|$.*";
           }
           type uint32 {
             range "1 .. 2";
           }
         }
       }
       leaf hello-interval {
         description "Hello interval";
         units "seconds";
         type union {
           type string {
             pattern "<.*>|$.*";
           }
           type uint32 {
             range "0 .. 255";
           }
         }
       }
       leaf-list neighbor-policy {
         ordered-by user;
         description "PIM neighbor policy applied to incoming hello messages";
         type jt:policy-algebra;
       }
       leaf-list accept-join-always-from {
         ordered-by user;
         description "Accept pim join/prune messages based on the policy configured";
         type jt:policy-algebra;
       }
       leaf accept-remote-source {
         description "Accept traffic from remote source";
         type empty;
       }
       container dual-dr {
         presence "enable dual-dr";
         junos:must "(!(\" .. distributed-dr\"))";
         junos:must-message "pim dual-dr cannot be configured with pim distributed-dr";
         description "Configure PIM Dual DR";
         uses apply-advanced;
         leaf enhanced {
           description "Enable enhanced PIM Dual DR";
           type empty;
         }
       }
       leaf distributed-dr {
         description "PIM Distributed DR";
         junos:must "(!(\".. .. .. passive\"))";
         junos:must-message "pim distributed-dr cannot be configured with pim passive";
         junos:must "(!(\" .. dual-dr\"))";
         junos:must-message "pim distributed-dr cannot be configured with pim dual-dr";
         type empty;
       }
       leaf reset-tracking-bit {
         description "Clear tracking-bit in PIM Hello LAN Prune Delay Option";
         type empty;
       }
       leaf propagation-delay {
         description "Propagation delay value";
         default "500";
         units "milliseconds";
         type union {
           type string {
             pattern "<.*>|$.*";
           }
           type uint32 {
             range "250 .. 2000";
           }
         }
       }
       leaf override-interval {
         description "Override interval value";
         default "2000";
         units "milliseconds";
         type union {
           type string {
             pattern "<.*>|$.*";
           }
           type uint32 {
             range "500 .. 6000";
           }
         }
       }
       leaf control-driven-sg {
         description "Build forwarding states from PIM sg join";
         type empty;
       }
       leaf disable-packet-register {
         description "Disable PIM packet registers on first hop router";
         type empty;
       }
       container bfd-liveness-detection {
         description "Bidirectional Forwarding Detection options (ipv4 only)";
         status deprecated;
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             junos:must "(\".. algorithm\")";
             junos:must-message "May not be configured without algorithm";
             junos:must "(\"security authentication-key-chains key-chain $$\")";
             junos:must-message "Referenced key-chain must be defined";
             type string;
           }
           leaf algorithm {
             description "Algorithm name";
             junos:must "(\".. key-chain\")";
             junos:must-message "May not be configured without key-chain";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
     }
     container mdt {
       junos:must "((!(\" .. .. mvpn\") || \".. mvpn family inet rosen-mvpn\"))";
       junos:must-message "Data tunnels cannot be configured with 'protocols mvpn'";
       description "Configure multicast data tunnel parameters";
       status deprecated;
       uses apply-advanced;
       container threshold {
         description "Threshold for creation of multicast tunnels";
         uses apply-advanced;
         list group {
           key name;
           ordered-by user;
           description "IP prefix of multicast group";
           leaf name {
             description "IP prefix of group";
             junos:cli-feature "nokeyword";
             type jt:ipprefix;
           }
           uses apply-advanced;
           list source {
             key name;
             ordered-by user;
             description "IP prefix of one or more multicast sources ";
             leaf name {
               description "IP prefix of source";
               junos:cli-feature "nokeyword";
               type jt:ipprefix;
             }
             uses apply-advanced;
             leaf rate {
               description "Data threshold to create new tunnel";
               units "kilobits";
               type union {
                 type string {
                   pattern "<.*>|$.*";
                 }
                 type uint32 {
                   range "10 .. 1000000";
                 }
               }
             }
           }
         }
       }
       leaf data-mdt-reuse {
         description "Allow multiple customer streams to be transmitted over one data tunnel ";
         type empty;
       }
       leaf tunnel-limit {
         description "Maximum multicast data tunnels";
         type union {
           type string {
             pattern "<.*>|$.*";
           }
           type uint32 {
             range "0 .. 8192";
           }
         }
       }
       leaf group-range {
         description "Group address range for multicast data tunnels";
         type jt:ipprefix;
       }
     }
     container graceful-restart {
       description "Configure graceful restart attributes";
       uses apply-advanced;
       choice enable-disable {
         case case_1 {
           leaf disable {
             description "Disable PIM graceful restart capability";
             type empty;
           }
         }
       }
       leaf restart-duration {
         description "Maximum time for graceful restart to finish (seconds)";
         units "seconds";
         type union {
           type string {
             pattern "<.*>|$.*";
           }
           type uint32 {
             range "30 .. 300";
           }
         }
       }
       leaf no-bidirectional-mode {
         description "Disable PIM graceful restart for bidirectional mode";
         type empty;
       }
       leaf restart-complete-duration {
         description "Maximum time for graceful restart to complete (seconds)";
         units "seconds";
         type union {
           type string {
             pattern "<.*>|$.*";
           }
           type uint32 {
             range "5 .. 300";
           }
         }
       }
     }
     container join-load-balance {
       presence "enable join-load-balance";
       description "Configure PIM join load balancing";
       uses apply-advanced;
       leaf automatic {
         description "Enable automatic PIM join load balancing";
         type empty;
       }
     }
     container cluster-id {
       junos:cli-feature "oneliner";
       description "Configure pim Cluster indentifier";
       leaf identifier {
         description "PIM Cluster identifier";
         junos:cli-feature "nokeyword";
         type union {
           type string {
             pattern "<.*>|$.*";
           }
           type uint32 {
             range "1 .. 4294967295";
           }
         }
       }
       leaf private-tlv {
         description "Use cluster-id private tlv for inter-op purpose";
         type empty;
       }
     }
     container hello-options {
       description "Configure PIM hello options attributes";
       uses apply-advanced;
       leaf disable-interface-id-tlv {
         description "Disable interface-id TLV in PIM hellos";
         type empty;
       }
     }
     container hash-based-rpf-selection {
       presence "enable hash-based-rpf-selection";
       junos:must "(!(\".. rpf-selection\"))";
       junos:must-message "PIM hash-based-rpf-selection cannot be enabled with rpf-selection.";
       junos:must "(!(\".. join-load-balance\"))";
       junos:must-message "PIM hash-based-rpf-selection cannot be enabled with join-load-balance.";
       junos:must "(!(\".. .. .. routing-options multicast stream-protection\"))";
       junos:must-message "PIM hash-based-rpf-selection cannot be enabled with MoFRR.";
       description "Configure PIM hash based rpf selection";
     }
     leaf standby-path-creation-delay {
       description "Amount of time to wait before creating standby path";
       units "seconds";
       type union {
         type string {
           pattern "<.*>|$.*";
         }
         type uint32 {
           range "1 .. 300";
         }
       }
     }
     leaf idle-standby-path-switchover-delay {
       description "Amount of time to wait before switching over to idle standby path";
       units "seconds";
       type union {
         type string {
           pattern "<.*>|$.*";
         }
         type uint32 {
           range "1 .. 300";
         }
       }
     }
     leaf dr-election-on-p2p {
       description "Enable DR election on Point-to-Point Interfaces";
       type empty;
     }
     leaf no-wildcard-register-stop {
       description "Disable sending of wildcard register stop message";
       type empty;
     }
     leaf nexthop-hold-time {
       description "Nexthop hold time in milliseconds";
       units "milliseconds";
       type union {
         type string {
           pattern "<.*>|$.*";
         }
         type uint32 {
           range "1 .. 1000";
         }
       }
     }
     leaf mpls-internet-multicast {
       description "Enable support for Internet Multicast over MPLS";
       junos:must "(any \"routing-instances <*> instance-type mpls-internet-multicast\")";
       junos:must-message "The mpls-internet-multicast instance must be configured to support multicast over MPLS";
       type empty;
     }
     container join-make-before-break {
       description "Enable PIM Join Make-Before-Break during RPF neighbor change";
       uses apply-advanced;
       choice enable-disable {
         case case_1 {
           leaf disable {
             description "Disable Make-Before-Break for PIM RPF neighbor change";
             type empty;
           }
         }
       }
     }
     leaf reset-tracking-bit {
       description "Clear tracking-bit in PIM Hello LAN Prune Delay Option";
       type empty;
     }
     leaf propagation-delay {
       description "Propagation delay value";
       default "500";
       units "milliseconds";
       type union {
         type string {
           pattern "<.*>|$.*";
         }
         type uint32 {
           range "250 .. 2000";
         }
       }
     }
     leaf override-interval {
       description "Override interval value";
       default "2000";
       units "milliseconds";
       type union {
         type string {
           pattern "<.*>|$.*";
         }
         type uint32 {
           range "500 .. 6000";
         }
       }
     }
     leaf control-driven-sg {
       description "Build forwarding states from PIM sg join";
       type empty;
     }
     leaf disable-packet-register {
       description "Disable PIM packet registers on first hop router";
       type empty;
     }
     container default-vpn-source {
       presence "enable default-vpn-source";
       description "Let all VRFs use master loopback address for mt interfaces";
       uses apply-advanced;
       leaf interface-name {
         description "Master loopback interface name";
         junos:must "(\"interfaces $$-IFL family inet address\")";
         junos:must-message "Family inet address should be configured on this loopback interface";
         type union {
           type jt:interface-unit;
           type string {
             pattern "<.*>|$.*";
           }
         }
       }
     }
     container static {
       description "Static PIM Join";
       uses apply-advanced;
       leaf distributed {
         description "Distributed all PIM Joins";
         junos:must "(\"chassis network-services enhanced-ip\")";
         junos:must-message "distributed is supported only in enhanced-ip mode";
         type empty;
       }
       list group {
         key name;
         ordered-by user;
         description "IP multicast group address";
         leaf name {
           description "IP multicast group address";
           junos:cli-feature "nokeyword";
           type jt:ipaddr;
         }
         uses apply-advanced;
         leaf distributed {
           description "Distributed static group";
           junos:must "(\"chassis network-services enhanced-ip\")";
           junos:must-message "distributed is supported only in enhanced-ip mode";
           type empty;
         }
         list source {
           key name;
           ordered-by user;
           description "IP multicast source address";
           leaf name {
             description "IP multicast source address";
             junos:cli-feature "nokeyword";
             type jt:ipaddr;
           }
           uses apply-advanced;
           leaf distributed {
             description "Distributed static source";
             junos:must "(\"chassis network-services enhanced-ip\")";
             junos:must-message "distributed is supported only in enhanced-ip mode";
             type empty;
           }
           leaf no-upstream-join {
             description "Prevent sending PIM join";
             type empty;
           }
         }
       }
     }
   }
   grouping keepalives_type {
     junos:cli-feature "oneliner";
     uses apply-advanced;
     leaf interval {
       description "Keepalive period";
       units "seconds";
       type union {
         type string {
           pattern "<.*>|$.*";
         }
         type uint16 {
           range "1 .. 32767";
         }
       }
     }
     leaf up-count {
       description "Keepalive received to bring link up";
       type union {
         type string {
           pattern "<.*>|$.*";
         }
         type uint16 {
           range "1 .. 255";
         }
       }
     }
     leaf down-count {
       description "Keepalive missed to bring link down";
       type union {
         type string {
           pattern "<.*>|$.*";
         }
         type uint16 {
           range "1 .. 255";
         }
       }
     }
   }
   grouping log-object {
     description "Configure auditable security logs";
     uses apply-advanced;
     list exclude {
       key name;
       ordered-by user;
       junos:cli-feature "homogeneous";
       description "List of security log criteria to exclude from the audit log";
       status deprecated;
       leaf name {
         description "Exclude criteria name";
         junos:cli-feature "nokeyword";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         junos:cli-feature "homogeneous";
         description "List of security log criteria to exclude from the audit log";
         junos:must "(!(\".. .. exclude\"))";
         junos:must-message "'security log cache exclude' and 'security log exclude' are mutually exclusive";
         leaf name {
           description "Exclude criteria name";
           junos:cli-feature "nokeyword";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         junos:must "(!(\".. .. limit\"))";
         junos:must-message "'security log cache limit' and 'security log limit' are mutually exclusive";
         type union {
           type uint32;
           type string {
             pattern "<.*>|$.*";
           }
         }
       }
     }
   }
   grouping lsp_nh_obj {
     leaf name {
       description "LSP to use to reach destination";
       junos:cli-feature "nokeyword";
       type string;
     }
     uses apply-advanced;
     leaf preference {
       description "Preference of LSP next hop";
       type union {
         type uint32;
         type string {
           pattern "<.*>|$.*";
         }
       }
     }
     leaf metric {
       description "Metric of LSP next hop";
       type union {
         type uint32;
         type string {
           pattern "<.*>|$.*";
         }
       }
     }
   }
   grouping mac_list {
     description "MAC address";
     leaf name {
       junos:cli-feature "nokeyword";
       type jt:mac-addr;
     }
     uses apply-advanced;
     container policer {
       description "MAC policing";
       uses apply-advanced;
       leaf input {
         description "Name of policer applied to received packets";
         type string;
       }
       leaf output {
         description "Name of policer applied to transmitted packets";
         type string;
       }
     }
   }
   grouping macro-data-type {
     junos:cli-feature "nokeyword";
     junos:cli-feature "homogeneous";
     junos:cli-feature "oneliner";
     leaf name {
       description "Keyword part of the keyword-value pair";
       junos:cli-feature "nokeyword";
       type string;
     }
     leaf value {
       description "Value part of the keyword-value pair";
       junos:cli-feature "nokeyword";
       type string;
     }
   }
   grouping martian_type {
     junos:cli-feature "homogeneous";
     junos:cli-feature "oneliner";
     description "Invalid routes";
     leaf address {
       description "IP address or hostname";
       junos:cli-feature "nokeyword";
       type jt:ipprefix;
     }
     leaf choice-ident {
       type enumeration {
         enum "exact" {
         }
         enum "longer" {
         }
         enum "orlonger" {
         }
         enum "upto" {
         }
         enum "through" {
         }
         enum "prefix-length-range" {
         }
       }
     }
     leaf choice-value {
       type string;
     }
     leaf allow {
       type empty;
     }
   }
   grouping match_L2_flexible_mask {
     description "Define a flexible match";
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-length {
       description "Length of integer input (16 or 32 bits), Optional length of string input (1..128 bits)";
       type union {
         type uint32;
         type string {
           pattern "<.*>|$.*";
         }
       }
     }
     leaf mask-in-hex {
       description "Mask out bits in the packet data to be matched";
       type string {
         junos:posix-pattern "(^(0[xX])?[A-Fa-f0-9]{0,8}$)";
       }
     }
     leaf prefix {
       description "Value data/string to be matched";
       junos:must "((\".. flexible-mask-name\" || \".. match-start\"))";
       junos:must-message "To configure prefix, 'flexible-mask-name' or 'match-start' must be configured";
       type string {
         junos:posix-pattern "!^((__.*)|(.{65,}))$";
         junos:pattern-message "Must be a non-reserved string of 64 characters or less";
       }
     }
     leaf flexible-mask-name {
       description "Select a flexible match from predefined template field";
       junos:must "((!(\".. byte-offset\") && (!(\".. bit-offset\") && (!(\".. bit-length\") && !(\".. match-start\")))))";
       junos:must-message "To refer configured template, only prefix or prefix along with mask can be configured";
       type string;
     }
   }
   grouping match_L2_flexible_range {
     description "Define a flexible match";
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits";
       type union {
         type string {
           pattern "<.*>|$.*";
         }
         type uint32;
       }
     }
     choice range_choice {
       case case_1 {
         leaf range {
           description "Range of values to be matched";
           junos:must "((\".. flexible-range-name\" || (\".. match-start\" && \".. bit-length\")))";
           junos:must-message "To configure range, 'flexible-range-name' or 'match-start & bit-length' must be configured";
           type string;
         }
       }
       case case_2 {
         leaf range-except {
           description "Range of values to be not matched";
           junos:must "((\".. flexible-range-name\" || (\".. match-start\" && \".. bit-length\")))";
           junos:must-message "To configure range-except, 'flexible-range-name' or 'match-start & bit-length' must be configured";
           type string;
         }
       }
     }
     leaf flexible-range-name {
       description "Select a flexible match from predefined template field";
       junos:must "((!(\".. byte-offset\") && (!(\".. bit-offset\") && (!(\".. bit-length\") && !(\".. match-start\")))))";
       junos:must-message "To refer configured template, only range or range-except can be configured";
       type string;
     }
   }
   grouping match_L3_flexible_mask {
     description "Define a flexible match";
     uses apply-advanced;
     leaf match-start {
       description "Start point to match in packet";
       type enumeration {
         enum "layer-3" {
           description "Layer-3 match start";
         }
         enum "layer-4" {
           description "Layer-4 match start";
         }
         enum "udp-vxlan" {
           description "Match start for VXLAN encapsulated packets for UDP, VXLAN, and inner l2 or l3 header";
         }
         enum "vxlan-outer-layer-3" {
           description "Match start for VXLAN encapsulated packets for outer l3 header";
         }
         enum "payload" {
           description "Payload match start";
         }
       }
     }
     leaf byte-offset {
       description "Byte offset after the match start point";
       type union {
         type string {
           pattern "<.*>|$.*";
         }
         type uint32 {
           range "0 .. 255";
         }
       }
     }
     leaf bit-length {
       description "Length of integer input (16 or 32 bits), Optional length of string input (1..128 bits)";
       type union {
         type uint32;
         type string {
           pattern "<.*>|$.*";
         }
       }
     }
     leaf mask-in-hex {
       description "Mask out bits in the packet data to be matched";
       type string {
         junos:posix-pattern "(^(0[xX])?[A-Fa-f0-9]{0,8}$)";
       }
     }
     leaf prefix {
       description "Value data/string to be matched";
       junos:must "((\".. flexible-mask-name\" || \".. match-start\"))";
       junos:must-message "To configure prefix, 'flexible-mask-name' or 'match-start' must be configured";
       type string {
         junos:posix-pattern "!^((__.*)|(.{65,}))$";
         junos:pattern-message "Must be a non-reserved string of 64 characters or less";
       }
     }
     leaf flexible-mask-name {
       description "Select a flexible match from predefined template field";
       junos:must "((!(\".. byte-offset\") && (!(\".. bit-offset\") && (!(\".. bit-length\") && !(\".. match-start\")))))";
       junos:must-message "To refer configured template, only prefix or prefix along with mask can be configured";
       type string;
     }
   }
   grouping match_L3_flexible_range {
     description "Define a flexible match";
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits";
       type union {
         type string {
           pattern "<.*>|$.*";
         }
         type uint32;
       }
     }
     choice range_choice {
       case case_1 {
         leaf range {
           description "Range of values to be matched";
           junos:must "((\".. flexible-range-name\" || (\".. match-start\" && \".. bit-length\")))";
           junos:must-message "To configure range, 'flexible-range-name' or 'match-start & bit-length' must be configured";
           type string;
         }
       }
       case case_2 {
         leaf range-except {
           description "Range of values to be not matched";
           junos:must "((\".. flexible-range-name\" || (\".. match-start\" && \".. bit-length\")))";
           junos:must-message "To configure range-except, 'flexible-range-name' or 'match-start & bit-length' must be configured";
           type string;
         }
       }
     }
     leaf flexible-range-name {
       description "Select a flexible match from predefined template field";
       junos:must "((!(\".. byte-offset\") && (!(\".. bit-offset\") && (!(\".. bit-length\") && !(\".. match-start\")))))";
       junos:must-message "To refer configured template, only range or range-except can be configured";
       type string;
     }
   }
   grouping match_flags_value {
     description "Define a vxlan flag";
     uses apply-advanced;
     leaf value {
       description "Value data to be matched";
       junos:cli-feature "nokeyword";
       junos:must "(\".. mask-in-hex\")";
       junos:must-message "mask-in-hex must be set for vxlan flag";
       type string {
         junos:posix-pattern "^([0-9]|[1-9][0-9]|1[0-9][0-9]|2[0-4][0-9]|25[0-5]|0x[0-f]|0x[0-f][0-f])$";
         junos:pattern-message "Must be a numeric value";
       }
     }
     leaf mask-in-hex {
       description "Mask out bits in the packet data to be matched";
       type string {
         junos:posix-pattern "^([0-9]|[1-9][0-9]|1[0-9][0-9]|2[0-4][0-9]|25[0-5]|0x[0-f]|0x[0-f][0-f])$";
         junos:pattern-message "Must be a numeric value";
       }
     }
   }
   grouping match_interface_object {
     junos:cli-feature "oneliner";
     leaf name {
       description "Interface to match";
       junos:cli-feature "nokeyword";
       type union {
         type jt:interface-wildcard;
         type string {
           pattern "<.*>|$.*";
         }
       }
     }
   }
   grouping match_interface_object_oam {
     junos:cli-feature "oneliner";
     leaf name {
       description "Interface to match";
       junos:cli-feature "nokeyword";
       type union {
         type jt:interface-wildcard;
         type string {
           pattern "<.*>|$.*";
         }
       }
     }
   }
   grouping match_interface_set_object {
     junos:cli-feature "oneliner";
     leaf name {
       description "Interface set to match";
       junos:cli-feature "nokeyword";
       type string;
     }
   }
   grouping match_payload_ipv4_add {
     junos:cli-feature "homogeneous";
     junos:cli-feature "oneliner";
     leaf name {
       description "Payload ip address to match";
       junos:cli-feature "nokeyword";
       type jt:ipv4prefix;
     }
   }
   grouping match_payload_ipv6_add {
     junos:cli-feature "homogeneous";
     junos:cli-feature "oneliner";
     leaf name {
       description "Payload ipv6 address to match";
       junos:cli-feature "nokeyword";
       type jt:ipv6prefix;
     }
   }
   grouping match_simple_dscp_value {
     junos:cli-feature "oneliner-plus";
     uses apply-advanced;
     leaf value_keyword {
       junos:cli-feature "nokeyword";
       type string;
     }
   }
   grouping match_simple_port_value {
     junos:cli-feature "oneliner-plus";
     uses apply-advanced;
     leaf value_keyword {
       junos:cli-feature "nokeyword";
       type string;
     }
   }
   grouping match_simple_protocol_value {
     junos:cli-feature "oneliner-plus";
     uses apply-advanced;
     leaf value_keyword {
       junos:cli-feature "nokeyword";
       type string;
     }
   }
   grouping mpls_filter {
     description "Define an MPLS firewall filter";
     leaf name {
       description "Filter name";
       junos:cli-feature "nokeyword";
       type string {
         junos:posix-pattern "!^((__.*)|(.{65,}))$";
         junos:pattern-message "Must be a non-reserved string of 64 characters or less";
       }
     }
     uses apply-advanced;
     leaf-list accounting-profile {
       ordered-by user;
       description "Accounting profile name";
       junos:must "(\"accounting-options filter-profile\")";
       junos:must-message "referenced accounting profile must be defined";
       type string;
     }
     leaf interface-specific {
       description "Defined counters are interface specific";
       type empty;
     }
     leaf transient-filter {
       description "Transient filter to be used for filter modification";
       type string;
     }
     leaf layer2-policer {
       description "Layer2 policing for interface";
       type empty;
     }
     leaf physical-interface-filter {
       description "Filter is physical interface filter";
       type empty;
     }
     list term {
       key name;
       ordered-by user;
       description "Define a firewall term";
       leaf name {
         description "Term name";
         junos:cli-feature "nokeyword";
         type string {
           junos:posix-pattern "!^((__.*)|(.{65,}))$";
           junos:pattern-message "Must be a non-reserved string of 64 characters or less";
         }
       }
       uses apply-advanced;
       leaf filter {
         description "Filter to include";
         junos:must "(\"firewall family mpls filter $$\")";
         junos:must-message "Referenced filter is not defined";
         junos:must "((!(\".. from\") && !(\".. then\")))";
         junos:must-message "Not compatible with 'from or then'";
         type string {
           junos:posix-pattern "!^((__.*)|(.{65,}))$";
           junos:pattern-message "Must be a non-reserved string of 64 characters or less";
         }
       }
       container from {
         description "Define match criteria";
         uses apply-advanced;
         choice interface-group_choice {
           case case_1 {
             leaf-list interface-group {
               ordered-by user;
               description "Range of values";
               type string;
             }
           }
           case case_2 {
           }
         }
         container ip-version {
           description "Specify inner IP version";
           uses apply-advanced;
           container ipv4 {
             presence "enable ipv4";
             junos:must "(!(\".. ipv6\"))";
             junos:must-message "Same term cannot have both IPv4 & IPv6 IP version";
             description "Define L4 match items to match IPv4 packets";
             uses apply-advanced;
             list protocol {
               key name;
               ordered-by user;
               description "Specify inner IPv4 protocol";
               max-elements 1;
               leaf name {
                 description "IP protocol choices";
                 junos:cli-feature "nokeyword";
                 type string;
               }
               uses apply-advanced;
               choice source-port_choice {
                 case case_1 {
                   leaf-list source-port {
                     ordered-by user;
                     type string;
                   }
                 }
                 case case_2 {
                   leaf-list source-port-except {
                     ordered-by user;
                     type string;
                   }
                 }
               }
               choice destination-port_choice {
                 case case_1 {
                   leaf-list destination-port {
                     ordered-by user;
                     type string;
                   }
                 }
                 case case_2 {
                   leaf-list destination-port-except {
                     ordered-by user;
                     type string;
                   }
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             list source-address {
               key name;
               ordered-by user;
               description "Match IPv4 source address";
               uses firewall_addr_object;
               junos:cli-feature "homogeneous";
               junos:cli-feature "oneliner";
             }
             list destination-address {
               key name;
               ordered-by user;
               description "Match IPv4 destination address";
               uses firewall_addr_object;
               junos:cli-feature "homogeneous";
               junos:cli-feature "oneliner";
             }
             choice dscp_choice {
               case case_1 {
                 leaf-list dscp {
                   ordered-by user;
                   type string;
                 }
               }
               case case_2 {
               }
             }
             leaf fragment-flags {
               description "Match fragment flags (in symbolic or hex formats) - (Ingress only)";
               type string;
             }
             choice fragment-offset_choice {
               case case_1 {
               }
               case case_2 {
               }
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             leaf is-fragment {
               description "Match if packet is a fragment";
               type empty;
             }
             choice port_choice {
               case case_1 {
               }
               case case_2 {
               }
             }
             leaf tcp-initial {
               description "Match initial packet of a TCP connection";
               type empty;
             }
             leaf tcp-established {
               description "Match packet of an established TCP connection";
               type empty;
             }
             choice ip-options_choice {
               case case_1 {
               }
               case case_2 {
               }
             }
             choice ip-protocol_choice {
               case case_1 {
               }
               case case_2 {
               }
             }
           }
           container ipv6 {
             presence "enable ipv6";
             junos:must "(!(\".. ipv4\"))";
             junos:must-message "Same term cannot have both IPv4 & IPv6 IP version";
             description "Define L3/L4 match items to match IPv6 packets";
             uses apply-advanced;
             list protocol {
               key name;
               ordered-by user;
               description "Specify inner IPv6 next-header";
               max-elements 1;
               leaf name {
                 description "IP protocol choices";
                 junos:cli-feature "nokeyword";
                 type string;
               }
               uses apply-advanced;
               choice source-port_choice {
                 case case_1 {
                   leaf-list source-port {
                     ordered-by user;
                     type string;
                   }
                 }
                 case case_2 {
                   leaf-list source-port-except {
                     ordered-by user;
                     type string;
                   }
                 }
               }
               choice destination-port_choice {
                 case case_1 {
                   leaf-list destination-port {
                     ordered-by user;
                     type string;
                   }
                 }
                 case case_2 {
                   leaf-list destination-port-except {
                     ordered-by user;
                     type string;
                   }
                 }
               }
             }
             choice payload-protocol_choice {
               case case_1 {
               }
               case case_2 {
               }
             }
             list source-address {
               key name;
               ordered-by user;
               description "Match IPv6 source address";
               uses firewall_addr6_object;
               junos:cli-feature "homogeneous";
               junos:cli-feature "oneliner";
             }
             list destination-address {
               key name;
               ordered-by user;
               description "Match IPv6 destination address";
               uses firewall_addr6_object;
               junos:cli-feature "homogeneous";
               junos:cli-feature "oneliner";
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
               }
               case case_2 {
               }
             }
             leaf tcp-initial {
               description "Match initial packet of a TCP connection";
               type empty;
             }
             leaf tcp-established {
               description "Match packet of an established TCP connection";
               type empty;
             }
             choice traffic-class_choice {
               case case_1 {
                 leaf-list traffic-class {
                   ordered-by user;
                   type string;
                 }
               }
               case case_2 {
               }
             }
           }
         }
         leaf-list label1 {
           ordered-by user;
           description "Match MPLS label bits at Next 1 from Top Of Stack";
           type string;
         }
         list label {
           key name;
           ordered-by user;
           description "MPLS label bits";
           leaf name {
             description "Range of values between 0 and 1048575 in decimal or hexadecimal";
             junos:cli-feature "nokeyword";
             type string {
               junos:posix-pattern "^([0-9]{1,6}|10[0-3][0-9][0-9][0-9][0-9]|104[0-7][0-9][0-9][0-9]|1048[0-4][0-9][0-9]|10485[0-6][0-9]|104857[0-5]|0x[0-f][0-f][0-f][0-f]|0x[0-f]|0x[0-f][0-f]|0x[0-f][0-f][0-f]|0x[0-f][0-f][0-f][0-f][0-f]|0x[0-f][0-f][0-f][0-f][0-f][0-f])(-([0-9]{1,6}|10[0-3][0-9][0-9][0-9][0-9]|104[0-7][0-9][0-9][0-9]|1048[0-4][0-9][0-9]|10485[0-6][0-9]|104857[0-5]|0x[0-f][0-f][0-f][0-f]|0x[0-f]|0x[0-f][0-f]|0x[0-f][0-f][0-f]|0x[0-f][0-f][0-f][0-f][0-f]|0x[0-f][0-f][0-f][0-f][0-f][0-f]))?$";
               junos:pattern-message "Must be a numerical value or range between 0-1048575";
             }
           }
           uses apply-advanced;
           choice position {
             case case_1 {
             }
             case case_2 {
             }
           }
         }
         choice exp_choice {
           case case_1 {
             leaf-list exp {
               ordered-by user;
               description "Range of values between 0 and 7 in decimal, binary or hex";
               type string;
             }
           }
           case case_2 {
             leaf-list exp-except {
               ordered-by user;
               description "Range of values between 0 and 7 in decimal, binary or hex";
               type string;
             }
           }
         }
         choice ttl_choice {
           case case_1 {
             leaf-list ttl {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical TTL value or range between 0-255";
               }
             }
           }
           case case_2 {
           }
         }
         choice exp0_choice {
           case case_1 {
           }
           case case_2 {
           }
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice ttl0_choice {
           case case_1 {
             leaf-list ttl0 {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical TTL value or range between 0-255";
               }
             }
           }
           case case_2 {
             leaf-list ttl0-except {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical TTL value or range between 0-255";
               }
             }
           }
         }
         choice loss-priority_choice {
           case case_1 {
           }
           case case_2 {
           }
         }
         choice flex-mask_choice {
           case case_1 {
             container flexible-match-mask {
               description "Match flexible mask";
               presence "enable flexible-match-mask";
               uses match_mpls_flexible_mask;
             }
           }
         }
         choice flex-range_choice {
           case case_1 {
             container flexible-match-range {
               description "Match flexible range";
               presence "enable flexible-match-range";
               junos:must "(!(\".. flexible-match-ranges\"))";
               junos:must-message "'flexible-match-range' and 'flexible-match-ranges' are mutually exclusive";
               uses match_mpls_flexible_range;
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
         choice exp1_choice {
           case case_1 {
             leaf-list exp1 {
               ordered-by user;
               description "Range of values between 0 and 7 in decimal, binary or hex";
               type string;
             }
           }
           case case_2 {
             leaf-list exp1-except {
               ordered-by user;
               description "Range of values between 0 and 7 in decimal, binary or hex";
               type string;
             }
           }
         }
         choice ttl1_choice {
           case case_1 {
           }
           case case_2 {
           }
         }
         choice slice_choice {
           case case_1 {
           }
           case case_2 {
           }
         }
       }
       container then {
         junos:cli-feature "oneliner-plus";
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               junos:must "(!(\".. loss-priority\"))";
               junos:must-message "cannot support three-color-policer action if loss-priority is configured";
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
           }
           case case_4 {
           }
           case case_5 {
             leaf policer-charge {
               description "Name of policer-charge used to charge the policer";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         choice mplscnt {
           case case_1 {
             leaf traffic-class-count {
               description "Count the packet in the named traffic-class counter";
               type string {
                 junos:posix-pattern "!^((__.*)|(.{65,}))$";
                 junos:pattern-message "Must be a non-reserved string of 64 characters or less";
               }
             }
           }
           case case_2 {
             leaf count {
               description "Count the packet in the named counter";
               type string {
                 junos:posix-pattern "!^((__.*)|(.{65,}))$";
                 junos:pattern-message "Must be a non-reserved string of 64 characters or less";
               }
             }
           }
         }
         leaf sample {
           description "Sample the packet";
           junos:must "((\"forwarding-options sampling family mpls\" || (\"forwarding-options packet-capture\" || any \"forwarding-options sampling instance <*> family mpls\")))";
           junos:must-message "Requires forwarding-options sampling or packet-capture config";
           type empty;
         }
         leaf loss-priority {
           description "Classify packet to loss-priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
             junos:posix-pattern "^.{1,64}$";
             junos:pattern-message "Must be string of 64 characters or less";
           }
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf packet-mode {
           description "Bypass flow mode for the packet";
           type empty;
         }
         choice designation {
           case case_1 {
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
         }
       }
       container template {
         description "Refer a template";
         uses apply-advanced;
         leaf template-name {
           description "Template name";
           junos:cli-feature "nokeyword";
           type string {
             junos:posix-pattern "!^((__.*)|(.{65,}))$";
             junos:pattern-message "Must be a non-reserved string of 64 characters or less";
           }
         }
       }
     }
   }
   grouping match_mpls_flexible_mask {
     description "Define a flexible match";
     uses apply-advanced;
     leaf match-start {
       description "Start point to match in packet";
       type enumeration {
         enum "layer-3" {
           description "Layer-3 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of integer input (1..32 bits), Optional length of string input (1..128 bits)";
       type union {
         type uint32;
         type string {
           pattern "<.*>|$.*";
         }
       }
     }
     leaf mask-in-hex {
       description "Mask out bits in the packet data to be matched";
       type string {
         junos:posix-pattern "(^(0[xX])?[A-Fa-f0-9]{0,8}$)";
       }
     }
     leaf prefix {
       description "Value data/string to be matched";
       junos:must "((\".. flexible-mask-name\" || \".. match-start\"))";
       junos:must-message "To configure prefix, 'flexible-mask-name' or 'match-start' must be configured";
       type string {
         junos:posix-pattern "!^((__.*)|(.{65,}))$";
         junos:pattern-message "Must be a non-reserved string of 64 characters or less";
       }
     }
     leaf flexible-mask-name {
       description "Select a flexible match from predefined template field";
       junos:must "((!(\".. byte-offset\") && (!(\".. bit-offset\") && (!(\".. bit-length\") && !(\".. match-start\")))))";
       junos:must-message "To refer configured template, only prefix or prefix along with mask can be configured";
       type string;
     }
   }
   grouping match_mpls_flexible_range {
     description "Define a flexible match";
     uses apply-advanced;
     leaf match-start {
       description "Start point to match in packet";
       type enumeration {
         enum "layer-3" {
           description "Layer-3 match start";
         }
         enum "payload" {
           description "Payload match start";
         }
       }
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits";
       type union {
         type string {
           pattern "<.*>|$.*";
         }
         type uint32;
       }
     }
     choice range_choice {
       case case_1 {
         leaf range {
           description "Range of values to be matched";
           junos:must "((\".. flexible-range-name\" || (\".. match-start\" && \".. bit-length\")))";
           junos:must-message "To configure range, 'flexible-range-name' or 'match-start & bit-length' must be configured";
           type string;
         }
       }
       case case_2 {
         leaf range-except {
           description "Range of values to be not matched";
           junos:must "((\".. flexible-range-name\" || (\".. match-start\" && \".. bit-length\")))";
           junos:must-message "To configure range-except, 'flexible-range-name' or 'match-start & bit-length' must be configured";
           type string;
         }
       }
     }
     leaf flexible-range-name {
       description "Select a flexible match from predefined template field";
       junos:must "((!(\".. byte-offset\") && (!(\".. bit-offset\") && (!(\".. bit-length\") && !(\".. match-start\")))))";
       junos:must-message "To refer configured template, only range or range-except can be configured";
       type string;
     }
   }
   grouping mpls_ifd_options {
     uses apply-advanced;
     container pop-all-labels {
       presence "enable pop-all-labels";
       junos:cli-feature "oneliner-plus";
       description "Pop all MPLS labels off incoming packets";
       uses apply-advanced;
       leaf-list required-depth {
         ordered-by user;
         description "Required label depth of packet to pop all labels";
         type enumeration {
           enum "all" {
             description "Takes effect only in Stoli based FPCs, in all other FPCs equivalent to '[1 2]'";
           }
           enum "1" {
             description "Required label depth of packet to pop labels";
           }
           enum "2" {
             description "Required label depth of packet to pop labels";
           }
         }
       }
     }
   }
   grouping mpls_template {
     leaf name {
       description "Template name";
       junos:cli-feature "nokeyword";
       type string {
         junos:posix-pattern "!^((__.*)|(.{65,}))$";
         junos:pattern-message "Must be a non-reserved string of 64 characters or less";
       }
     }
     uses apply-advanced;
     container attributes {
       description "Template attributes";
       uses apply-advanced;
       leaf exp {
         description "Match MPLS EXP bits";
         type empty;
       }
       leaf exp-except {
         description "Do not match MPLS EXP bits";
         type empty;
       }
       leaf flexible-match-mask {
         description "Match flexible mask";
         type empty;
       }
       leaf flexible-match-range {
         description "Match flexible range";
         type empty;
       }
       leaf forwarding-class {
         description "Match forwarding class";
         type empty;
       }
       leaf forwarding-class-except {
         description "Do not match forwarding class";
         type empty;
       }
       leaf interface {
         description "Match interface name";
         type empty;
       }
       leaf interface-group {
         description "Match interface group";
         type empty;
       }
       leaf interface-set {
         description "Match interface in set";
         type empty;
       }
       leaf loss-priority {
         description "Match Loss Priority";
         type empty;
       }
       leaf loss-priority-except {
         description "Do not match Loss Priority";
         type empty;
       }
       leaf label {
         description "MPLS label bits";
         type empty;
       }
       leaf ttl {
         description "Match MPLS ttl type";
         type empty;
       }
     }
   }
   grouping multi-chassis-protection-group {
     leaf name {
       description "IP address for this peer";
       junos:cli-feature "nokeyword";
       junos:must "((\"protocols iccp peer $$\" || any \"logical-systems <*> protocols iccp peer $$\"))";
       junos:must-message "The peer ip must match with ones defined at <protocols iccp peer>";
       type jt:ipv4addr;
     }
     uses apply-advanced;
     leaf interface {
       description "Inter-Chassis protection link";
       junos:must "(((((!(any \"routing-instances <*> protocols rstp interface $$\") && !(any \"routing-instances <*> protocols rstp interface all\")) || any \"routing-instances <*> protocols rstp interface $$ disable\") && ((((!(any \"routing-instances <*> protocols vstp interface $$\") && !(any \"routing-instances <*> protocols vstp interface all\")) && (!(any \"routing-instances <*> protocols vstp vlan all interface all\") && (!(any \"routing-instances <*> protocols vstp vlan <*> interface $$\") && !(any \"routing-instances <*> protocols vstp vlan <*> interface all\")))) || any \"routing-instances <*> protocols vstp interface $$ disable\") && ((!(any \"routing-instances <*> protocols mstp interface $$\") && !(any \"routing-instances <*> protocols mstp interface all\")) || any \"routing-instances <*> protocols mstp interface $$ disable\"))) && (((!(\"protocols rstp interface $$\") && !(\"protocols rstp interface all\")) || \"protocols rstp interface $$ disable\") && ((((!(\"protocols vstp interface $$\") && !(\"protocols vstp interface all\")) && (!(\"protocols vstp vlan all interface all\") && (!(any \"protocols vstp vlan <*> interface $$\") && !(any \"protocols vstp vlan <*> interface all\")))) || \"protocols vstp interface $$ disable\") && ((!(\"protocols mstp interface $$\") && !(\"protocols mstp interface all\")) || \"protocols mstp interface $$ disable\")))))";
       junos:must-message "Inter-Chasis link interface cannot be an STP interface. Please disable xstp on this interface";
       type string {
         length "1 .. 40";
         junos:posix-pattern "^((ge-)|(mge-)|(xe-)|(ae)|(xle-)|(et-)|(sxe-))";
         junos:pattern-message "Only ae, ge, mge, xe, xle, sxe and et inteface is supported";
       }
     }
     leaf icl-down-delay {
       description "Time in seconds between ICL down and MCAEs moving to standby";
       default "1";
       units "seconds";
       type union {
         type string {
           pattern "<.*>|$.*";
         }
         type int32 {
           range "1 .. 6000";
         }
       }
     }
   }
   grouping multi-chassis-protection-group-ifl {
     leaf name {
       description "IP address for this peer";
       junos:cli-feature "nokeyword";
       junos:must "((\"protocols iccp peer $$\" || any \"logical-systems <*> protocols iccp peer $$\"))";
       junos:must-message "The peer ip must match with ones defined at <protocols iccp peer>";
       junos:must "(\".. .. .. .. .. protocols iccp peer $$\")";
       junos:must-message "iccp peer ip address does not match with the one configured under protocols iccp";
       type jt:ipv4addr;
     }
     uses apply-advanced;
     leaf interface {
       description "Inter-Chassis protection link";
       junos:must "(((((!(any \"routing-instances <*> protocols rstp interface $$\") && !(any \"routing-instances <*> protocols rstp interface all\")) || any \"routing-instances <*> protocols rstp interface $$ disable\") && ((((!(any \"routing-instances <*> protocols vstp interface $$\") && !(any \"routing-instances <*> protocols vstp interface all\")) && (!(any \"routing-instances <*> protocols vstp vlan all interface all\") && (!(any \"routing-instances <*> protocols vstp vlan <*> interface $$\") && !(any \"routing-instances <*> protocols vstp vlan <*> interface all\")))) || any \"routing-instances <*> protocols vstp interface $$ disable\") && ((!(any \"routing-instances <*> protocols mstp interface $$\") && !(any \"routing-instances <*> protocols mstp interface all\")) || any \"routing-instances <*> protocols mstp interface $$ disable\"))) && (((!(\"protocols rstp interface $$\") && !(\"protocols rstp interface all\")) || \"protocols rstp interface $$ disable\") && ((((!(\"protocols vstp interface $$\") && !(\"protocols vstp interface all\")) && (!(\"protocols vstp vlan all interface all\") && (!(any \"protocols vstp vlan <*> interface $$\") && !(any \"protocols vstp vlan <*> interface all\")))) || \"protocols vstp interface $$ disable\") && ((!(\"protocols mstp interface $$\") && !(\"protocols mstp interface all\")) || \"protocols mstp interface $$ disable\")))))";
       junos:must-message "Inter-Chasis link interface cannot be an STP interface. Please disable xstp on this interface";
       type string {
         length "1 .. 40";
         junos:posix-pattern "^((ge-)|(mge-)|(xe-)|(ae)|(xle-)|(et-)|(sxe-))";
         junos:pattern-message "Only ae, ge, mge, xe, xle, sxe and et inteface is supported";
       }
     }
     leaf icl-down-delay {
       description "Time in seconds between ICL down and MCAEs moving to standby";
       default "1";
       units "seconds";
       type union {
         type string {
           pattern "<.*>|$.*";
         }
         type int32 {
           range "1 .. 6000";
         }
       }
     }
   }
   grouping multicast_interface_options_type {
     junos:cli-feature "oneliner-plus";
     description "Multicast interface options";
     leaf name {
       description "Interface name";
       junos:cli-feature "nokeyword";
       type union {
         type jt:interface-unit;
         type string {
           pattern "<.*>|$.*";
         }
       }
     }
     uses apply-advanced;
     container maximum-bandwidth {
       presence "enable maximum-bandwidth";
       junos:cli-feature "oneliner";
       description "Maximum multicast bandwidth for the interface";
       leaf bandwidth-limit {
         description "Maximum multicast bandwidth on the interface";
         junos:cli-feature "nokeyword";
         units "bps";
         type string;
       }
     }
     choice enable-disable {
       case case_1 {
         leaf enable {
           description "Enable Multicast";
           status deprecated;
           type empty;
         }
       }
       case case_2 {
         leaf disable {
           description "Disable Multicast";
           status deprecated;
           type empty;
         }
       }
     }
     container reverse-oif-mapping {
       presence "enable reverse-oif-mapping";
       description "Enable reverse OIF mapping on the multicast interface";
       uses apply-advanced;
       leaf no-qos-adjust {
         description "Disable reverse OIF mapping QoS adjustment";
         type empty;
       }
     }
     leaf subscriber-leave-timer {
       description "Timeout in seconds to credit back the bandwidth on the subscriber interface";
       units "seconds";
       junos:must "(\".. reverse-oif-mapping\")";
       junos:must-message "reverse-oif-mapping must be set";
       type union {
         type string {
           pattern "<.*>|$.*";
         }
         type uint32 {
           range "0 .. 30";
         }
       }
     }
     leaf no-qos-adjust {
       description "Disable QoS adjustment for this interface";
       type empty;
     }
   }
   grouping och-attributes {
     description "Optical channel configuration attributes";
     uses apply-advanced;
     leaf rate {
       description "Data rate of the OCH payload";
       type enumeration {
         enum "100g" {
           description "100Gbit OCH data rate";
         }
       }
     }
     leaf modulation {
       description "Optical modulation format";
       type enumeration {
         enum "qpsk" {
           description "QPSK Modulation Format";
         }
       }
     }
     leaf encoding {
       description "Optical encoding";
       type enumeration {
         enum "differential" {
           description "Differential encoding";
         }
       }
     }
     choice channel-number {
       case case_1 {
         leaf wavelength {
           description "Optical channel wavelength in nanometers";
           type enumeration {
             enum "1611.79" {
               description "1611.79 nm/186.000000 THz 3.125/6.25/12.5/50/75/100GHz spacing";
             }
             enum "1611.76" {
               description "1611.76 nm/186.003125 THz 3.125GHz spacing";
             }
             enum "1611.73" {
               description "1611.73 nm/186.006250 THz 3.125/6.25GHz spacing";
             }
             enum "1611.71" {
               description "1611.71 nm/186.009375 THz 3.125GHz spacing";
             }
             enum "1611.68" {
               description "1611.68 nm/186.012500 THz 3.125/6.25/12.5GHz spacing";
             }
             enum "1611.65" {
               description "1611.65 nm/186.015625 THz 3.125GHz spacing";
             }
             enum "1611.62" {
               description "1611.62 nm/186.018750 THz 3.125/6.25GHz spacing";
             }
             enum "1611.60" {
               description "1611.60 nm/186.021875 THz 3.125GHz spacing";
             }
             enum "1611.57" {
               description "1611.57 nm/186.025000 THz 3.125/6.25/12.5GHz spacing";
             }
             enum "1611.54" {
               description "1611.54 nm/186.028125 THz 3.125GHz spacing";
             }
             enum "1611.52" {
               description "1611.52 nm/186.031250 THz 3.125/6.25GHz spacing";
             }
             enum "1611.49" {
               description "1611.49 nm/186.034375 THz 3.125GHz spacing";
             }
             enum "1611.46" {
               description "1611.46 nm/186.037500 THz 3.125/6.25/12.5GHz spacing";
             }
             enum "1611.44" {
               description "1611.44 nm/186.040625 THz 3.125GHz spacing";
             }
             enum "1611.41" {
               description "1611.41 nm/186.043750 THz 3.125/6.25GHz spacing";
             }
             enum "1611.38" {
               description "1611.38 nm/186.046875 THz 3.125GHz spacing";
             }
             enum "1611.35" {
               description "1611.35 nm/186.050000 THz 3.125/6.25/12.5/50/75GHz spacing";
             }
             enum "1611.33" {
               description "1611.33 nm/186.053125 THz 3.125GHz spacing";
             }
             enum "1611.30" {
               description "1611.30 nm/186.056250 THz 3.125/6.25GHz spacing";
             }
             enum "1611.27" {
               description "1611.27 nm/186.059375 THz 3.125GHz spacing";
             }
             enum "1611.25" {
               description "1611.25 nm/186.062500 THz 3.125/6.25/12.5GHz spacing";
             }
             enum "1611.22" {
               description "1611.22 nm/186.065625 THz 3.125GHz spacing";
             }
             enum "1611.19" {
               description "1611.19 nm/186.068750 THz 3.125/6.25GHz spacing";
             }
             enum "1611.16" {
               description "1611.16 nm/186.071875 THz 3.125GHz spacing";
             }
             enum "1611.14" {
               description "1611.14 nm/186.075000 THz 3.125/6.25/12.5GHz spacing";
             }
             enum "1611.11" {
               description "1611.11 nm/186.078125 THz 3.125GHz spacing";
             }
             enum "1611.08" {
               description "1611.08 nm/186.081250 THz 3.125/6.25GHz spacing";
             }
             enum "1611.06" {
               description "1611.06 nm/186.084375 THz 3.125GHz spacing";
             }
             enum "1611.03" {
               description "1611.03 nm/186.087500 THz 3.125/6.25/12.5GHz spacing";
             }
             enum "1611.00" {
               description "1611.00 nm/186.090625 THz 3.125GHz spacing";
             }
             enum "1610.98" {
               description "1610.98 nm/186.093750 THz 3.125/6.25GHz spacing";
             }
             enum "1610.95" {
               description "1610.95 nm/186.096875 THz 3.125GHz spacing";
             }
             enum "1610.92" {
               description "1610.92 nm/186.100000 THz 3.125/6.25/12.5/100GHz spacing";
             }
             enum "1610.89" {
               description "1610.89 nm/186.103125 THz 3.125GHz spacing";
             }
             enum "1610.87" {
               description "1610.87 nm/186.106250 THz 3.125/6.25GHz spacing";
             }
             enum "1610.84" {
               description "1610.84 nm/186.109375 THz 3.125GHz spacing";
             }
             enum "1610.81" {
               description "1610.81 nm/186.112500 THz 3.125/6.25/12.5GHz spacing";
             }
             enum "1610.79" {
               description "1610.79 nm/186.115625 THz 3.125GHz spacing";
             }
             enum "1610.76" {
               description "1610.76 nm/186.118750 THz 3.125/6.25GHz spacing";
             }
             enum "1610.73" {
               description "1610.73 nm/186.121875 THz 3.125GHz spacing";
             }
             enum "1610.70" {
               description "1610.70 nm/186.125000 THz 3.125/6.25/12.5/75GHz spacing";
             }
             enum "1610.68" {
               description "1610.68 nm/186.128125 THz 3.125GHz spacing";
             }
             enum "1610.65" {
               description "1610.65 nm/186.131250 THz 3.125/6.25GHz spacing";
             }
             enum "1610.62" {
               description "1610.62 nm/186.134375 THz 3.125GHz spacing";
             }
             enum "1610.60" {
               description "1610.60 nm/186.137500 THz 3.125/6.25/12.5GHz spacing";
             }
             enum "1610.57" {
               description "1610.57 nm/186.140625 THz 3.125GHz spacing";
             }
             enum "1610.54" {
               description "1610.54 nm/186.143750 THz 3.125/6.25GHz spacing";
             }
             enum "1610.52" {
               description "1610.52 nm/186.146875 THz 3.125GHz spacing";
             }
             enum "1610.49" {
               description "1610.49 nm/186.150000 THz 3.125/6.25/12.5/50GHz spacing";
             }
             enum "1610.46" {
               description "1610.46 nm/186.153125 THz 3.125GHz spacing";
             }
             enum "1610.43" {
               description "1610.43 nm/186.156250 THz 3.125/6.25GHz spacing";
             }
             enum "1610.41" {
               description "1610.41 nm/186.159375 THz 3.125GHz spacing";
             }
             enum "1610.38" {
               description "1610.38 nm/186.162500 THz 3.125/6.25/12.5GHz spacing";
             }
             enum "1610.35" {
               description "1610.35 nm/186.165625 THz 3.125GHz spacing";
             }
             enum "1610.33" {
               description "1610.33 nm/186.168750 THz 3.125/6.25GHz spacing";
             }
             enum "1610.30" {
               description "1610.30 nm/186.171875 THz 3.125GHz spacing";
             }
             enum "1610.27" {
               description "1610.27 nm/186.175000 THz 3.125/6.25/12.5GHz spacing";
             }
             enum "1610.25" {
               description "1610.25 nm/186.178125 THz 3.125GHz spacing";
             }
             enum "1610.22" {
               description "1610.22 nm/186.181250 THz 3.125/6.25GHz spacing";
             }
             enum "1610.19" {
               description "1610.19 nm/186.184375 THz 3.125GHz spacing";
             }
             enum "1610.16" {
               description "1610.16 nm/186.187500 THz 3.125/6.25/12.5GHz spacing";
             }
             enum "1610.14" {
               description "1610.14 nm/186.190625 THz 3.125GHz spacing";
             }
             enum "1610.11" {
               description "1610.11 nm/186.193750 THz 3.125/6.25GHz spacing";
             }
             enum "1610.08" {
               description "1610.08 nm/186.196875 THz 3.125GHz spacing";
             }
             enum "1610.06" {
               description "1610.06 nm/186.200000 THz 3.125/6.25/12.5/100GHz spacing";
             }
             enum "1610.03" {
               description "1610.03 nm/186.203125 THz 3.125GHz spacing";
             }
             enum "1610.00" {
               description "1610.00 nm/186.206250 THz 3.125/6.25GHz spacing";
             }
             enum "1609.98" {
               description "1609.98 nm/186.209375 THz 3.125GHz spacing";
             }
             enum "1609.95" {
               description "1609.95 nm/186.212500 THz 3.125/6.25/12.5GHz spacing";
             }
             enum "1609.92" {
               description "1609.92 nm/186.215625 THz 3.125GHz spacing";
             }
             enum "1609.89" {
               description "1609.89 nm/186.218750 THz 3.125/6.25GHz spacing";
             }
             enum "1609.87" {
               description "1609.87 nm/186.221875 THz 3.125GHz spacing";
             }
             enum "1609.84" {
               description "1609.84 nm/186.225000 THz 3.125/6.25/12.5GHz spacing";
             }
             enum "1609.81" {
               description "1609.81 nm/186.228125 THz 3.125GHz spacing";
             }
             enum "1609.79" {
               description "1609.79 nm/186.231250 THz 3.125/6.25GHz spacing";
             }
             enum "1609.76" {
               description "1609.76 nm/186.234375 THz 3.125GHz spacing";
             }
             enum "1609.73" {
               description "1609.73 nm/186.237500 THz 3.125/6.25/12.5GHz spacing";
             }
             enum "1609.70" {
               description "1609.70 nm/186.240625 THz 3.125GHz spacing";
             }
             enum "1609.68" {
               description "1609.68 nm/186.243750 THz 3.125/6.25GHz spacing";
             }
             enum "1609.65" {
               description "1609.65 nm/186.246875 THz 3.125GHz spacing";
             }
             enum "1609.62" {
               description "1609.62 nm/186.250000 THz 3.125/6.25/12.5/50GHz spacing";
             }
             enum "1609.60" {
               description "1609.60 nm/186.253125 THz 3.125GHz spacing";
             }
             enum "1609.57" {
               description "1609.57 nm/186.256250 THz 3.125/6.25GHz spacing";
             }
             enum "1609.54" {
               description "1609.54 nm/186.259375 THz 3.125GHz spacing";
             }
             enum "1609.52" {
               description "1609.52 nm/186.262500 THz 3.125/6.25/12.5GHz spacing";
             }
             enum "1609.49" {
               description "1609.49 nm/186.265625 THz 3.125GHz spacing";
             }
             enum "1609.46" {
               description "1609.46 nm/186.268750 THz 3.125/6.25GHz spacing";
             }
             enum "1609.43" {
               description "1609.43 nm/186.271875 THz 3.125GHz spacing";
             }
             enum "1609.41" {
               description "1609.41 nm/186.275000 THz 3.125/6.25/12.5/75GHz spacing";
             }
             enum "1609.38" {
               description "1609.38 nm/186.278125 THz 3.125GHz spacing";
             }
             enum "1609.35" {
               description "1609.35 nm/186.281250 THz 3.125/6.25GHz spacing";
             }
             enum "1609.33" {
               description "1609.33 nm/186.284375 THz 3.125GHz spacing";
             }
             enum "1609.30" {
               description "1609.30 nm/186.287500 THz 3.125/6.25/12.5GHz spacing";
             }
             enum "1609.27" {
               description "1609.27 nm/186.290625 THz 3.125GHz spacing";
             }
             enum "1609.25" {
               description "1609.25 nm/186.293750 THz 3.125/6.25GHz spacing";
             }
             enum "1609.22" {
               description "1609.22 nm/186.296875 THz 3.125GHz spacing";
             }
             enum "1609.19" {
               description "1609.19 nm/186.300000 THz 3.125/6.25/12.5/50/75/100GHz spacing";
             }
             enum "1609.16" {
               description "1609.16 nm/186.303125 THz 3.125GHz spacing";
             }
             enum "1609.14" {
               description "1609.14 nm/186.306250 THz 3.125/6.25GHz spacing";
             }
             enum "1609.11" {
               description "1609.11 nm/186.309375 THz 3.125GHz spacing";
             }
             enum "1609.08" {
               description "1609.08 nm/186.312500 THz 3.125/6.25/12.5GHz spacing";
             }
             enum "1609.06" {
               description "1609.06 nm/186.315625 THz 3.125GHz spacing";
             }
             enum "1609.03" {
               description "1609.03 nm/186.318750 THz 3.125/6.25GHz spacing";
             }
             enum "1609.00" {
               description "1609.00 nm/186.321875 THz 3.125GHz spacing";
             }
             enum "1608.98" {
               description "1608.98 nm/186.325000 THz 3.125/6.25/12.5GHz spacing";
             }
             enum "1608.95" {
               description "1608.95 nm/186.328125 THz 3.125GHz spacing";
             }
             enum "1608.92" {
               description "1608.92 nm/186.331250 THz 3.125/6.25GHz spacing";
             }
             enum "1608.90" {
               description "1608.90 nm/186.334375 THz 3.125GHz spacing";
             }
             enum "1608.87" {
               description "1608.87 nm/186.337500 THz 3.125/6.25/12.5GHz spacing";
             }
             enum "1608.84" {
               description "1608.84 nm/186.340625 THz 3.125GHz spacing";
             }
             enum "1608.81" {
               description "1608.81 nm/186.343750 THz 3.125/6.25GHz spacing";
             }
             enum "1608.79" {
               description "1608.79 nm/186.346875 THz 3.125GHz spacing";
             }
             enum "1608.76" {
               description "1608.76 nm/186.350000 THz 3.125/6.25/12.5/50/75GHz spacing";
             }
             enum "1608.73" {
               description "1608.73 nm/186.353125 THz 3.125GHz spacing";
             }
             enum "1608.71" {
               description "1608.71 nm/186.356250 THz 3.125/6.25GHz spacing";
             }
             enum "1608.68" {
               description "1608.68 nm/186.359375 THz 3.125GHz spacing";
             }
             enum "1608.65" {
               description "1608.65 nm/186.362500 THz 3.125/6.25/12.5GHz spacing";
             }
             enum "1608.63" {
               description "1608.63 nm/186.365625 THz 3.125GHz spacing";
             }
             enum "1608.60" {
               description "1608.60 nm/186.368750 THz 3.125/6.25GHz spacing";
             }
             enum "1608.57" {
               description "1608.57 nm/186.371875 THz 3.125GHz spacing";
             }
             enum "1608.54" {
               description "1608.54 nm/186.375000 THz 3.125/6.25/12.5GHz spacing";
             }
             enum "1608.52" {
               description "1608.52 nm/186.378125 THz 3.125GHz spacing";
             }
             enum "1608.49" {
               description "1608.49 nm/186.381250 THz 3.125/6.25GHz spacing";
             }
             enum "1608.46" {
               description "1608.46 nm/186.384375 THz 3.125GHz spacing";
             }
             enum "1608.44" {
               description "1608.44 nm/186.387500 THz 3.125/6.25/12.5GHz spacing";
             }
             enum "1608.41" {
               description "1608.41 nm/186.390625 THz 3.125GHz spacing";
             }
             enum "1608.38" {
               description "1608.38 nm/186.393750 THz 3.125/6.25GHz spacing";
             }
             enum "1608.36" {
               description "1608.36 nm/186.396875 THz 3.125GHz spacing";
             }
             enum "1608.33" {
               description "1608.33 nm/186.400000 THz 3.125/6.25/12.5/100GHz spacing";
             }
             enum "1608.30" {
               description "1608.30 nm/186.403125 THz 3.125GHz spacing";
             }
             enum "1608.27" {
               description "1608.27 nm/186.406250 THz 3.125/6.25GHz spacing";
             }
             enum "1608.25" {
               description "1608.25 nm/186.409375 THz 3.125GHz spacing";
             }
             enum "1608.22" {
               description "1608.22 nm/186.412500 THz 3.125/6.25/12.5GHz spacing";
             }
             enum "1608.19" {
               description "1608.19 nm/186.415625 THz 3.125GHz spacing";
             }
             enum "1608.17" {
               description "1608.17 nm/186.418750 THz 3.125/6.25GHz spacing";
             }
             enum "1608.14" {
               description "1608.14 nm/186.421875 THz 3.125GHz spacing";
             }
             enum "1608.11" {
               description "1608.11 nm/186.425000 THz 3.125/6.25/12.5/75GHz spacing";
             }
             enum "1608.09" {
               description "1608.09 nm/186.428125 THz 3.125GHz spacing";
             }
             enum "1608.06" {
               description "1608.06 nm/186.431250 THz 3.125/6.25GHz spacing";
             }
             enum "1608.03" {
               description "1608.03 nm/186.434375 THz 3.125GHz spacing";
             }
             enum "1608.01" {
               description "1608.01 nm/186.437500 THz 3.125/6.25/12.5GHz spacing";
             }
             enum "1607.98" {
               description "1607.98 nm/186.440625 THz 3.125GHz spacing";
             }
             enum "1607.95" {
               description "1607.95 nm/186.443750 THz 3.125/6.25GHz spacing";
             }
             enum "1607.92" {
               description "1607.92 nm/186.446875 THz 3.125GHz spacing";
             }
             enum "1607.90" {
               description "1607.90 nm/186.450000 THz 3.125/6.25/12.5/50GHz spacing";
             }
             enum "1607.87" {
               description "1607.87 nm/186.453125 THz 3.125GHz spacing";
             }
             enum "1607.84" {
               description "1607.84 nm/186.456250 THz 3.125/6.25GHz spacing";
             }
             enum "1607.82" {
               description "1607.82 nm/186.459375 THz 3.125GHz spacing";
             }
             enum "1607.79" {
               description "1607.79 nm/186.462500 THz 3.125/6.25/12.5GHz spacing";
             }
             enum "1607.76" {
               description "1607.76 nm/186.465625 THz 3.125GHz spacing";
             }
             enum "1607.74" {
               description "1607.74 nm/186.468750 THz 3.125/6.25GHz spacing";
             }
             enum "1607.71" {
               description "1607.71 nm/186.471875 THz 3.125GHz spacing";
             }
             enum "1607.68" {
               description "1607.68 nm/186.475000 THz 3.125/6.25/12.5GHz spacing";
             }
             enum "1607.65" {
               description "1607.65 nm/186.478125 THz 3.125GHz spacing";
             }
             enum "1607.63" {
               description "1607.63 nm/186.481250 THz 3.125/6.25GHz spacing";
             }
             enum "1607.60" {
               description "1607.60 nm/186.484375 THz 3.125GHz spacing";
             }
             enum "1607.57" {
               description "1607.57 nm/186.487500 THz 3.125/6.25/12.5GHz spacing";
             }
             enum "1607.55" {
               description "1607.55 nm/186.490625 THz 3.125GHz spacing";
             }
             enum "1607.52" {
               description "1607.52 nm/186.493750 THz 3.125/6.25GHz spacing";
             }
             enum "1607.49" {
               description "1607.49 nm/186.496875 THz 3.125GHz spacing";
             }
             enum "1607.47" {
               description "1607.47 nm/186.500000 THz 3.125/6.25/12.5/100GHz spacing";
             }
             enum "1607.44" {
               description "1607.44 nm/186.503125 THz 3.125GHz spacing";
             }
             enum "1607.41" {
               description "1607.41 nm/186.506250 THz 3.125/6.25GHz spacing";
             }
             enum "1607.39" {
               description "1607.39 nm/186.509375 THz 3.125GHz spacing";
             }
             enum "1607.36" {
               description "1607.36 nm/186.512500 THz 3.125/6.25/12.5GHz spacing";
             }
             enum "1607.33" {
               description "1607.33 nm/186.515625 THz 3.125GHz spacing";
             }
             enum "1607.30" {
               description "1607.30 nm/186.518750 THz 3.125/6.25GHz spacing";
             }
             enum "1607.28" {
               description "1607.28 nm/186.521875 THz 3.125GHz spacing";
             }
             enum "1607.25" {
               description "1607.25 nm/186.525000 THz 3.125/6.25/12.5GHz spacing";
             }
             enum "1607.22" {
               description "1607.22 nm/186.528125 THz 3.125GHz spacing";
             }
             enum "1607.20" {
               description "1607.20 nm/186.531250 THz 3.125/6.25GHz spacing";
             }
             enum "1607.17" {
               description "1607.17 nm/186.534375 THz 3.125GHz spacing";
             }
             enum "1607.14" {
               description "1607.14 nm/186.537500 THz 3.125/6.25/12.5GHz spacing";
             }
             enum "1607.12" {
               description "1607.12 nm/186.540625 THz 3.125GHz spacing";
             }
             enum "1607.09" {
               description "1607.09 nm/186.543750 THz 3.125/6.25GHz spacing";
             }
             enum "1607.06" {
               description "1607.06 nm/186.546875 THz 3.125GHz spacing";
             }
             enum "1607.04" {
               description "1607.04 nm/186.550000 THz 3.125/6.25/12.5/50GHz spacing";
             }
             enum "1607.01" {
               description "1607.01 nm/186.553125 THz 3.125GHz spacing";
             }
             enum "1606.98" {
               description "1606.98 nm/186.556250 THz 3.125/6.25GHz spacing";
             }
             enum "1606.95" {
               description "1606.95 nm/186.559375 THz 3.125GHz spacing";
             }
             enum "1606.93" {
               description "1606.93 nm/186.562500 THz 3.125/6.25/12.5GHz spacing";
             }
             enum "1606.90" {
               description "1606.90 nm/186.565625 THz 3.125GHz spacing";
             }
             enum "1606.87" {
               description "1606.87 nm/186.568750 THz 3.125/6.25GHz spacing";
             }
             enum "1606.85" {
               description "1606.85 nm/186.571875 THz 3.125GHz spacing";
             }
             enum "1606.82" {
               description "1606.82 nm/186.575000 THz 3.125/6.25/12.5/75GHz spacing";
             }
             enum "1606.79" {
               description "1606.79 nm/186.578125 THz 3.125GHz spacing";
             }
             enum "1606.77" {
               description "1606.77 nm/186.581250 THz 3.125/6.25GHz spacing";
             }
             enum "1606.74" {
               description "1606.74 nm/186.584375 THz 3.125GHz spacing";
             }
             enum "1606.71" {
               description "1606.71 nm/186.587500 THz 3.125/6.25/12.5GHz spacing";
             }
             enum "1606.69" {
               description "1606.69 nm/186.590625 THz 3.125GHz spacing";
             }
             enum "1606.66" {
               description "1606.66 nm/186.593750 THz 3.125/6.25GHz spacing";
             }
             enum "1606.63" {
               description "1606.63 nm/186.596875 THz 3.125GHz spacing";
             }
             enum "1606.60" {
               description "1606.60 nm/186.600000 THz 3.125/6.25/12.5/50/75/100GHz spacing";
             }
             enum "1606.58" {
               description "1606.58 nm/186.603125 THz 3.125GHz spacing";
             }
             enum "1606.55" {
               description "1606.55 nm/186.606250 THz 3.125/6.25GHz spacing";
             }
             enum "1606.52" {
               description "1606.52 nm/186.609375 THz 3.125GHz spacing";
             }
             enum "1606.50" {
               description "1606.50 nm/186.612500 THz 3.125/6.25/12.5GHz spacing";
             }
             enum "1606.47" {
               description "1606.47 nm/186.615625 THz 3.125GHz spacing";
             }
             enum "1606.44" {
               description "1606.44 nm/186.618750 THz 3.125/6.25GHz spacing";
             }
             enum "1606.42" {
               description "1606.42 nm/186.621875 THz 3.125GHz spacing";
             }
             enum "1606.39" {
               description "1606.39 nm/186.625000 THz 3.125/6.25/12.5GHz spacing";
             }
             enum "1606.36" {
               description "1606.36 nm/186.628125 THz 3.125GHz spacing";
             }
             enum "1606.34" {
               description "1606.34 nm/186.631250 THz 3.125/6.25GHz spacing";
             }
             enum "1606.31" {
               description "1606.31 nm/186.634375 THz 3.125GHz spacing";
             }
             enum "1606.28" {
               description "1606.28 nm/186.637500 THz 3.125/6.25/12.5GHz spacing";
             }
             enum "1606.26" {
               description "1606.26 nm/186.640625 THz 3.125GHz spacing";
             }
             enum "1606.23" {
               description "1606.23 nm/186.643750 THz 3.125/6.25GHz spacing";
             }
             enum "1606.20" {
               description "1606.20 nm/186.646875 THz 3.125GHz spacing";
             }
             enum "1606.17" {
               description "1606.17 nm/186.650000 THz 3.125/6.25/12.5/50/75GHz spacing";
             }
             enum "1606.15" {
               description "1606.15 nm/186.653125 THz 3.125GHz spacing";
             }
             enum "1606.12" {
               description "1606.12 nm/186.656250 THz 3.125/6.25GHz spacing";
             }
             enum "1606.09" {
               description "1606.09 nm/186.659375 THz 3.125GHz spacing";
             }
             enum "1606.07" {
               description "1606.07 nm/186.662500 THz 3.125/6.25/12.5GHz spacing";
             }
             enum "1606.04" {
               description "1606.04 nm/186.665625 THz 3.125GHz spacing";
             }
             enum "1606.01" {
               description "1606.01 nm/186.668750 THz 3.125/6.25GHz spacing";
             }
             enum "1605.99" {
               description "1605.99 nm/186.671875 THz 3.125GHz spacing";
             }
             enum "1605.96" {
               description "1605.96 nm/186.675000 THz 3.125/6.25/12.5GHz spacing";
             }
             enum "1605.93" {
               description "1605.93 nm/186.678125 THz 3.125GHz spacing";
             }
             enum "1605.91" {
               description "1605.91 nm/186.681250 THz 3.125/6.25GHz spacing";
             }
             enum "1605.88" {
               description "1605.88 nm/186.684375 THz 3.125GHz spacing";
             }
             enum "1605.85" {
               description "1605.85 nm/186.687500 THz 3.125/6.25/12.5GHz spacing";
             }
             enum "1605.82" {
               description "1605.82 nm/186.690625 THz 3.125GHz spacing";
             }
             enum "1605.80" {
               description "1605.80 nm/186.693750 THz 3.125/6.25GHz spacing";
             }
             enum "1605.77" {
               description "1605.77 nm/186.696875 THz 3.125GHz spacing";
             }
             enum "1605.74" {
               description "1605.74 nm/186.700000 THz 3.125/6.25/12.5/100GHz spacing";
             }
             enum "1605.72" {
               description "1605.72 nm/186.703125 THz 3.125GHz spacing";
             }
             enum "1605.69" {
               description "1605.69 nm/186.706250 THz 3.125/6.25GHz spacing";
             }
             enum "1605.66" {
               description "1605.66 nm/186.709375 THz 3.125GHz spacing";
             }
             enum "1605.64" {
               description "1605.64 nm/186.712500 THz 3.125/6.25/12.5GHz spacing";
             }
             enum "1605.61" {
               description "1605.61 nm/186.715625 THz 3.125GHz spacing";
             }
             enum "1605.58" {
               description "1605.58 nm/186.718750 THz 3.125/6.25GHz spacing";
             }
             enum "1605.56" {
               description "1605.56 nm/186.721875 THz 3.125GHz spacing";
             }
             enum "1605.53" {
               description "1605.53 nm/186.725000 THz 3.125/6.25/12.5/75GHz spacing";
             }
             enum "1605.50" {
               description "1605.50 nm/186.728125 THz 3.125GHz spacing";
             }
             enum "1605.48" {
               description "1605.48 nm/186.731250 THz 3.125/6.25GHz spacing";
             }
             enum "1605.45" {
               description "1605.45 nm/186.734375 THz 3.125GHz spacing";
             }
             enum "1605.42" {
               description "1605.42 nm/186.737500 THz 3.125/6.25/12.5GHz spacing";
             }
             enum "1605.39" {
               description "1605.39 nm/186.740625 THz 3.125GHz spacing";
             }
             enum "1605.37" {
               description "1605.37 nm/186.743750 THz 3.125/6.25GHz spacing";
             }
             enum "1605.34" {
               description "1605.34 nm/186.746875 THz 3.125GHz spacing";
             }
             enum "1605.31" {
               description "1605.31 nm/186.750000 THz 3.125/6.25/12.5/50GHz spacing";
             }
             enum "1605.29" {
               description "1605.29 nm/186.753125 THz 3.125GHz spacing";
             }
             enum "1605.26" {
               description "1605.26 nm/186.756250 THz 3.125/6.25GHz spacing";
             }
             enum "1605.23" {
               description "1605.23 nm/186.759375 THz 3.125GHz spacing";
             }
             enum "1605.21" {
               description "1605.21 nm/186.762500 THz 3.125/6.25/12.5GHz spacing";
             }
             enum "1605.18" {
               description "1605.18 nm/186.765625 THz 3.125GHz spacing";
             }
             enum "1605.15" {
               description "1605.15 nm/186.768750 THz 3.125/6.25GHz spacing";
             }
             enum "1605.13" {
               description "1605.13 nm/186.771875 THz 3.125GHz spacing";
             }
             enum "1605.10" {
               description "1605.10 nm/186.775000 THz 3.125/6.25/12.5GHz spacing";
             }
             enum "1605.07" {
               description "1605.07 nm/186.778125 THz 3.125GHz spacing";
             }
             enum "1605.05" {
               description "1605.05 nm/186.781250 THz 3.125/6.25GHz spacing";
             }
             enum "1605.02" {
               description "1605.02 nm/186.784375 THz 3.125GHz spacing";
             }
             enum "1604.99" {
               description "1604.99 nm/186.787500 THz 3.125/6.25/12.5GHz spacing";
             }
             enum "1604.97" {
               description "1604.97 nm/186.790625 THz 3.125GHz spacing";
             }
             enum "1604.94" {
               description "1604.94 nm/186.793750 THz 3.125/6.25GHz spacing";
             }
             enum "1604.91" {
               description "1604.91 nm/186.796875 THz 3.125GHz spacing";
             }
             enum "1604.88" {
               description "1604.88 nm/186.800000 THz 3.125/6.25/12.5/100GHz spacing";
             }
             enum "1604.86" {
               description "1604.86 nm/186.803125 THz 3.125GHz spacing";
             }
             enum "1604.83" {
               description "1604.83 nm/186.806250 THz 3.125/6.25GHz spacing";
             }
             enum "1604.80" {
               description "1604.80 nm/186.809375 THz 3.125GHz spacing";
             }
             enum "1604.78" {
               description "1604.78 nm/186.812500 THz 3.125/6.25/12.5GHz spacing";
             }
             enum "1604.75" {
               description "1604.75 nm/186.815625 THz 3.125GHz spacing";
             }
             enum "1604.72" {
               description "1604.72 nm/186.818750 THz 3.125/6.25GHz spacing";
             }
             enum "1604.70" {
               description "1604.70 nm/186.821875 THz 3.125GHz spacing";
             }
             enum "1604.67" {
               description "1604.67 nm/186.825000 THz 3.125/6.25/12.5GHz spacing";
             }
             enum "1604.64" {
               description "1604.64 nm/186.828125 THz 3.125GHz spacing";
             }
             enum "1604.62" {
               description "1604.62 nm/186.831250 THz 3.125/6.25GHz spacing";
             }
             enum "1604.59" {
               description "1604.59 nm/186.834375 THz 3.125GHz spacing";
             }
             enum "1604.56" {
               description "1604.56 nm/186.837500 THz 3.125/6.25/12.5GHz spacing";
             }
             enum "1604.54" {
               description "1604.54 nm/186.840625 THz 3.125GHz spacing";
             }
             enum "1604.51" {
               description "1604.51 nm/186.843750 THz 3.125/6.25GHz spacing";
             }
             enum "1604.48" {
               description "1604.48 nm/186.846875 THz 3.125GHz spacing";
             }
             enum "1604.46" {
               description "1604.46 nm/186.850000 THz 3.125/6.25/12.5/50GHz spacing";
             }
             enum "1604.43" {
               description "1604.43 nm/186.853125 THz 3.125GHz spacing";
             }
             enum "1604.40" {
               description "1604.40 nm/186.856250 THz 3.125/6.25GHz spacing";
             }
             enum "1604.37" {
               description "1604.37 nm/186.859375 THz 3.125GHz spacing";
             }
             enum "1604.35" {
               description "1604.35 nm/186.862500 THz 3.125/6.25/12.5GHz spacing";
             }
             enum "1604.32" {
               description "1604.32 nm/186.865625 THz 3.125GHz spacing";
             }
             enum "1604.29" {
               description "1604.29 nm/186.868750 THz 3.125/6.25GHz spacing";
             }
             enum "1604.27" {
               description "1604.27 nm/186.871875 THz 3.125GHz spacing";
             }
             enum "1604.24" {
               description "1604.24 nm/186.875000 THz 3.125/6.25/12.5/75GHz spacing";
             }
             enum "1604.21" {
               description "1604.21 nm/186.878125 THz 3.125GHz spacing";
             }
             enum "1604.19" {
               description "1604.19 nm/186.881250 THz 3.125/6.25GHz spacing";
             }
             enum "1604.16" {
               description "1604.16 nm/186.884375 THz 3.125GHz spacing";
             }
             enum "1604.13" {
               description "1604.13 nm/186.887500 THz 3.125/6.25/12.5GHz spacing";
             }
             enum "1604.11" {
               description "1604.11 nm/186.890625 THz 3.125GHz spacing";
             }
             enum "1604.08" {
               description "1604.08 nm/186.893750 THz 3.125/6.25GHz spacing";
             }
             enum "1604.05" {
               description "1604.05 nm/186.896875 THz 3.125GHz spacing";
             }
             enum "1604.03" {
               description "1604.03 nm/186.900000 THz 3.125/6.25/12.5/50/75/100GHz spacing";
             }
             enum "1604.00" {
               description "1604.00 nm/186.903125 THz 3.125GHz spacing";
             }
             enum "1603.97" {
               description "1603.97 nm/186.906250 THz 3.125/6.25GHz spacing";
             }
             enum "1603.95" {
               description "1603.95 nm/186.909375 THz 3.125GHz spacing";
             }
             enum "1603.92" {
               description "1603.92 nm/186.912500 THz 3.125/6.25/12.5GHz spacing";
             }
             enum "1603.89" {
               description "1603.89 nm/186.915625 THz 3.125GHz spacing";
             }
             enum "1603.87" {
               description "1603.87 nm/186.918750 THz 3.125/6.25GHz spacing";
             }
             enum "1603.84" {
               description "1603.84 nm/186.921875 THz 3.125GHz spacing";
             }
             enum "1603.81" {
               description "1603.81 nm/186.925000 THz 3.125/6.25/12.5GHz spacing";
             }
             enum "1603.78" {
               description "1603.78 nm/186.928125 THz 3.125GHz spacing";
             }
             enum "1603.76" {
               description "1603.76 nm/186.931250 THz 3.125/6.25GHz spacing";
             }
             enum "1603.73" {
               description "1603.73 nm/186.934375 THz 3.125GHz spacing";
             }
             enum "1603.70" {
               description "1603.70 nm/186.937500 THz 3.125/6.25/12.5GHz spacing";
             }
             enum "1603.68" {
               description "1603.68 nm/186.940625 THz 3.125GHz spacing";
             }
             enum "1603.65" {
               description "1603.65 nm/186.943750 THz 3.125/6.25GHz spacing";
             }
             enum "1603.62" {
               description "1603.62 nm/186.946875 THz 3.125GHz spacing";
             }
             enum "1603.60" {
               description "1603.60 nm/186.950000 THz 3.125/6.25/12.5/50/75GHz spacing";
             }
             enum "1603.57" {
               description "1603.57 nm/186.953125 THz 3.125GHz spacing";
             }
             enum "1603.54" {
               description "1603.54 nm/186.956250 THz 3.125/6.25GHz spacing";
             }
             enum "1603.52" {
               description "1603.52 nm/186.959375 THz 3.125GHz spacing";
             }
             enum "1603.49" {
               description "1603.49 nm/186.962500 THz 3.125/6.25/12.5GHz spacing";
             }
             enum "1603.46" {
               description "1603.46 nm/186.965625 THz 3.125GHz spacing";
             }
             enum "1603.44" {
               description "1603.44 nm/186.968750 THz 3.125/6.25GHz spacing";
             }
             enum "1603.41" {
               description "1603.41 nm/186.971875 THz 3.125GHz spacing";
             }
             enum "1603.38" {
               description "1603.38 nm/186.975000 THz 3.125/6.25/12.5GHz spacing";
             }
             enum "1603.36" {
               description "1603.36 nm/186.978125 THz 3.125GHz spacing";
             }
             enum "1603.33" {
               description "1603.33 nm/186.981250 THz 3.125/6.25GHz spacing";
             }
             enum "1603.30" {
               description "1603.30 nm/186.984375 THz 3.125GHz spacing";
             }
             enum "1603.28" {
               description "1603.28 nm/186.987500 THz 3.125/6.25/12.5GHz spacing";
             }
             enum "1603.25" {
               description "1603.25 nm/186.990625 THz 3.125GHz spacing";
             }
             enum "1603.22" {
               description "1603.22 nm/186.993750 THz 3.125/6.25GHz spacing";
             }
             enum "1603.20" {
               description "1603.20 nm/186.996875 THz 3.125GHz spacing";
             }
             enum "1603.17" {
               description "1603.17 nm/187.000000 THz 3.125/6.25/12.5/100GHz spacing";
             }
             enum "1603.14" {
               description "1603.14 nm/187.003125 THz 3.125GHz spacing";
             }
             enum "1603.11" {
               description "1603.11 nm/187.006250 THz 3.125/6.25GHz spacing";
             }
             enum "1603.09" {
               description "1603.09 nm/187.009375 THz 3.125GHz spacing";
             }
             enum "1603.06" {
               description "1603.06 nm/187.012500 THz 3.125/6.25/12.5GHz spacing";
             }
             enum "1603.03" {
               description "1603.03 nm/187.015625 THz 3.125GHz spacing";
             }
             enum "1603.01" {
               description "1603.01 nm/187.018750 THz 3.125/6.25GHz spacing";
             }
             enum "1602.98" {
               description "1602.98 nm/187.021875 THz 3.125GHz spacing";
             }
             enum "1602.95" {
               description "1602.95 nm/187.025000 THz 3.125/6.25/12.5/75GHz spacing";
             }
             enum "1602.93" {
               description "1602.93 nm/187.028125 THz 3.125GHz spacing";
             }
             enum "1602.90" {
               description "1602.90 nm/187.031250 THz 3.125/6.25GHz spacing";
             }
             enum "1602.87" {
               description "1602.87 nm/187.034375 THz 3.125GHz spacing";
             }
             enum "1602.85" {
               description "1602.85 nm/187.037500 THz 3.125/6.25/12.5GHz spacing";
             }
             enum "1602.82" {
               description "1602.82 nm/187.040625 THz 3.125GHz spacing";
             }
             enum "1602.79" {
               description "1602.79 nm/187.043750 THz 3.125/6.25GHz spacing";
             }
             enum "1602.77" {
               description "1602.77 nm/187.046875 THz 3.125GHz spacing";
             }
             enum "1602.74" {
               description "1602.74 nm/187.050000 THz 3.125/6.25/12.5/50GHz spacing";
             }
             enum "1602.71" {
               description "1602.71 nm/187.053125 THz 3.125GHz spacing";
             }
             enum "1602.69" {
               description "1602.69 nm/187.056250 THz 3.125/6.25GHz spacing";
             }
             enum "1602.66" {
               description "1602.66 nm/187.059375 THz 3.125GHz spacing";
             }
             enum "1602.63" {
               description "1602.63 nm/187.062500 THz 3.125/6.25/12.5GHz spacing";
             }
             enum "1602.61" {
               description "1602.61 nm/187.065625 THz 3.125GHz spacing";
             }
             enum "1602.58" {
               description "1602.58 nm/187.068750 THz 3.125/6.25GHz spacing";
             }
             enum "1602.55" {
               description "1602.55 nm/187.071875 THz 3.125GHz spacing";
             }
             enum "1602.53" {
               description "1602.53 nm/187.075000 THz 3.125/6.25/12.5GHz spacing";
             }
             enum "1602.50" {
               description "1602.50 nm/187.078125 THz 3.125GHz spacing";
             }
             enum "1602.47" {
               description "1602.47 nm/187.081250 THz 3.125/6.25GHz spacing";
             }
             enum "1602.45" {
               description "1602.45 nm/187.084375 THz 3.125GHz spacing";
             }
             enum "1602.42" {
               description "1602.42 nm/187.087500 THz 3.125/6.25/12.5GHz spacing";
             }
             enum "1602.39" {
               description "1602.39 nm/187.090625 THz 3.125GHz spacing";
             }
             enum "1602.36" {
               description "1602.36 nm/187.093750 THz 3.125/6.25GHz spacing";
             }
             enum "1602.34" {
               description "1602.34 nm/187.096875 THz 3.125GHz spacing";
             }
             enum "1602.31" {
               description "1602.31 nm/187.100000 THz 3.125/6.25/12.5/100GHz spacing";
             }
             enum "1602.28" {
               description "1602.28 nm/187.103125 THz 3.125GHz spacing";
             }
             enum "1602.26" {
               description "1602.26 nm/187.106250 THz 3.125/6.25GHz spacing";
             }
             enum "1602.23" {
               description "1602.23 nm/187.109375 THz 3.125GHz spacing";
             }
             enum "1602.20" {
               description "1602.20 nm/187.112500 THz 3.125/6.25/12.5GHz spacing";
             }
             enum "1602.18" {
               description "1602.18 nm/187.115625 THz 3.125GHz spacing";
             }
             enum "1602.15" {
               description "1602.15 nm/187.118750 THz 3.125/6.25GHz spacing";
             }
             enum "1602.12" {
               description "1602.12 nm/187.121875 THz 3.125GHz spacing";
             }
             enum "1602.10" {
               description "1602.10 nm/187.125000 THz 3.125/6.25/12.5GHz spacing";
             }
             enum "1602.07" {
               description "1602.07 nm/187.128125 THz 3.125GHz spacing";
             }
             enum "1602.04" {
               description "1602.04 nm/187.131250 THz 3.125/6.25GHz spacing";
             }
             enum "1602.02" {
               description "1602.02 nm/187.134375 THz 3.125GHz spacing";
             }
             enum "1601.99" {
               description "1601.99 nm/187.137500 THz 3.125/6.25/12.5GHz spacing";
             }
             enum "1601.96" {
               description "1601.96 nm/187.140625 THz 3.125GHz spacing";
             }
             enum "1601.94" {
               description "1601.94 nm/187.143750 THz 3.125/6.25GHz spacing";
             }
             enum "1601.91" {
               description "1601.91 nm/187.146875 THz 3.125GHz spacing";
             }
             enum "1601.88" {
               description "1601.88 nm/187.150000 THz 3.125/6.25/12.5/50GHz spacing";
             }
             enum "1601.86" {
               description "1601.86 nm/187.153125 THz 3.125GHz spacing";
             }
             enum "1601.83" {
               description "1601.83 nm/187.156250 THz 3.125/6.25GHz spacing";
             }
             enum "1601.80" {
               description "1601.80 nm/187.159375 THz 3.125GHz spacing";
             }
             enum "1601.78" {
               description "1601.78 nm/187.162500 THz 3.125/6.25/12.5GHz spacing";
             }
             enum "1601.75" {
               description "1601.75 nm/187.165625 THz 3.125GHz spacing";
             }
             enum "1601.72" {
               description "1601.72 nm/187.168750 THz 3.125/6.25GHz spacing";
             }
             enum "1601.70" {
               description "1601.70 nm/187.171875 THz 3.125GHz spacing";
             }
             enum "1601.67" {
               description "1601.67 nm/187.175000 THz 3.125/6.25/12.5/75GHz spacing";
             }
             enum "1601.64" {
               description "1601.64 nm/187.178125 THz 3.125GHz spacing";
             }
             enum "1601.62" {
               description "1601.62 nm/187.181250 THz 3.125/6.25GHz spacing";
             }
             enum "1601.59" {
               description "1601.59 nm/187.184375 THz 3.125GHz spacing";
             }
             enum "1601.56" {
               description "1601.56 nm/187.187500 THz 3.125/6.25/12.5GHz spacing";
             }
             enum "1601.54" {
               description "1601.54 nm/187.190625 THz 3.125GHz spacing";
             }
             enum "1601.51" {
               description "1601.51 nm/187.193750 THz 3.125/6.25GHz spacing";
             }
             enum "1601.48" {
               description "1601.48 nm/187.196875 THz 3.125GHz spacing";
             }
             enum "1601.46" {
               description "1601.46 nm/187.200000 THz 3.125/6.25/12.5/50/75/100GHz spacing";
             }
             enum "1601.43" {
               description "1601.43 nm/187.203125 THz 3.125GHz spacing";
             }
             enum "1601.40" {
               description "1601.40 nm/187.206250 THz 3.125/6.25GHz spacing";
             }
             enum "1601.38" {
               description "1601.38 nm/187.209375 THz 3.125GHz spacing";
             }
             enum "1601.35" {
               description "1601.35 nm/187.212500 THz 3.125/6.25/12.5GHz spacing";
             }
             enum "1601.32" {
               description "1601.32 nm/187.215625 THz 3.125GHz spacing";
             }
             enum "1601.30" {
               description "1601.30 nm/187.218750 THz 3.125/6.25GHz spacing";
             }
             enum "1601.27" {
               description "1601.27 nm/187.221875 THz 3.125GHz spacing";
             }
             enum "1601.24" {
               description "1601.24 nm/187.225000 THz 3.125/6.25/12.5GHz spacing";
             }
             enum "1601.21" {
               description "1601.21 nm/187.228125 THz 3.125GHz spacing";
             }
             enum "1601.19" {
               description "1601.19 nm/187.231250 THz 3.125/6.25GHz spacing";
             }
             enum "1601.16" {
               description "1601.16 nm/187.234375 THz 3.125GHz spacing";
             }
             enum "1601.13" {
               description "1601.13 nm/187.237500 THz 3.125/6.25/12.5GHz spacing";
             }
             enum "1601.11" {
               description "1601.11 nm/187.240625 THz 3.125GHz spacing";
             }
             enum "1601.08" {
               description "1601.08 nm/187.243750 THz 3.125/6.25GHz spacing";
             }
             enum "1601.05" {
               description "1601.05 nm/187.246875 THz 3.125GHz spacing";
             }
             enum "1601.03" {
               description "1601.03 nm/187.250000 THz 3.125/6.25/12.5/50/75GHz spacing";
             }
             enum "1601.00" {
               description "1601.00 nm/187.253125 THz 3.125GHz spacing";
             }
             enum "1600.97" {
               description "1600.97 nm/187.256250 THz 3.125/6.25GHz spacing";
             }
             enum "1600.95" {
               description "1600.95 nm/187.259375 THz 3.125GHz spacing";
             }
             enum "1600.92" {
               description "1600.92 nm/187.262500 THz 3.125/6.25/12.5GHz spacing";
             }
             enum "1600.89" {
               description "1600.89 nm/187.265625 THz 3.125GHz spacing";
             }
             enum "1600.87" {
               description "1600.87 nm/187.268750 THz 3.125/6.25GHz spacing";
             }
             enum "1600.84" {
               description "1600.84 nm/187.271875 THz 3.125GHz spacing";
             }
             enum "1600.81" {
               description "1600.81 nm/187.275000 THz 3.125/6.25/12.5GHz spacing";
             }
             enum "1600.79" {
               description "1600.79 nm/187.278125 THz 3.125GHz spacing";
             }
             enum "1600.76" {
               description "1600.76 nm/187.281250 THz 3.125/6.25GHz spacing";
             }
             enum "1600.73" {
               description "1600.73 nm/187.284375 THz 3.125GHz spacing";
             }
             enum "1600.71" {
               description "1600.71 nm/187.287500 THz 3.125/6.25/12.5GHz spacing";
             }
             enum "1600.68" {
               description "1600.68 nm/187.290625 THz 3.125GHz spacing";
             }
             enum "1600.65" {
               description "1600.65 nm/187.293750 THz 3.125/6.25GHz spacing";
             }
             enum "1600.63" {
               description "1600.63 nm/187.296875 THz 3.125GHz spacing";
             }
             enum "1600.60" {
               description "1600.60 nm/187.300000 THz 3.125/6.25/12.5/100GHz spacing";
             }
             enum "1600.57" {
               description "1600.57 nm/187.303125 THz 3.125GHz spacing";
             }
             enum "1600.55" {
               description "1600.55 nm/187.306250 THz 3.125/6.25GHz spacing";
             }
             enum "1600.52" {
               description "1600.52 nm/187.309375 THz 3.125GHz spacing";
             }
             enum "1600.49" {
               description "1600.49 nm/187.312500 THz 3.125/6.25/12.5GHz spacing";
             }
             enum "1600.47" {
               description "1600.47 nm/187.315625 THz 3.125GHz spacing";
             }
             enum "1600.44" {
               description "1600.44 nm/187.318750 THz 3.125/6.25GHz spacing";
             }
             enum "1600.41" {
               description "1600.41 nm/187.321875 THz 3.125GHz spacing";
             }
             enum "1600.39" {
               description "1600.39 nm/187.325000 THz 3.125/6.25/12.5/75GHz spacing";
             }
             enum "1600.36" {
               description "1600.36 nm/187.328125 THz 3.125GHz spacing";
             }
             enum "1600.33" {
               description "1600.33 nm/187.331250 THz 3.125/6.25GHz spacing";
             }
             enum "1600.31" {
               description "1600.31 nm/187.334375 THz 3.125GHz spacing";
             }
             enum "1600.28" {
               description "1600.28 nm/187.337500 THz 3.125/6.25/12.5GHz spacing";
             }
             enum "1600.25" {
               description "1600.25 nm/187.340625 THz 3.125GHz spacing";
             }
             enum "1600.23" {
               description "1600.23 nm/187.343750 THz 3.125/6.25GHz spacing";
             }
             enum "1600.20" {
               description "1600.20 nm/187.346875 THz 3.125GHz spacing";
             }
             enum "1600.17" {
               description "1600.17 nm/187.350000 THz 3.125/6.25/12.5/50GHz spacing";
             }
             enum "1600.15" {
               description "1600.15 nm/187.353125 THz 3.125GHz spacing";
             }
             enum "1600.12" {
               description "1600.12 nm/187.356250 THz 3.125/6.25GHz spacing";
             }
             enum "1600.09" {
               description "1600.09 nm/187.359375 THz 3.125GHz spacing";
             }
             enum "1600.07" {
               description "1600.07 nm/187.362500 THz 3.125/6.25/12.5GHz spacing";
             }
             enum "1600.04" {
               description "1600.04 nm/187.365625 THz 3.125GHz spacing";
             }
             enum "1600.01" {
               description "1600.01 nm/187.368750 THz 3.125/6.25GHz spacing";
             }
             enum "1599.99" {
               description "1599.99 nm/187.371875 THz 3.125GHz spacing";
             }
             enum "1599.96" {
               description "1599.96 nm/187.375000 THz 3.125/6.25/12.5GHz spacing";
             }
             enum "1599.93" {
               description "1599.93 nm/187.378125 THz 3.125GHz spacing";
             }
             enum "1599.91" {
               description "1599.91 nm/187.381250 THz 3.125/6.25GHz spacing";
             }
             enum "1599.88" {
               description "1599.88 nm/187.384375 THz 3.125GHz spacing";
             }
             enum "1599.85" {
               description "1599.85 nm/187.387500 THz 3.125/6.25/12.5GHz spacing";
             }
             enum "1599.83" {
               description "1599.83 nm/187.390625 THz 3.125GHz spacing";
             }
             enum "1599.80" {
               description "1599.80 nm/187.393750 THz 3.125/6.25GHz spacing";
             }
             enum "1599.77" {
               description "1599.77 nm/187.396875 THz 3.125GHz spacing";
             }
             enum "1599.75" {
               description "1599.75 nm/187.400000 THz 3.125/6.25/12.5/100GHz spacing";
             }
             enum "1599.72" {
               description "1599.72 nm/187.403125 THz 3.125GHz spacing";
             }
             enum "1599.69" {
               description "1599.69 nm/187.406250 THz 3.125/6.25GHz spacing";
             }
             enum "1599.67" {
               description "1599.67 nm/187.409375 THz 3.125GHz spacing";
             }
             enum "1599.64" {
               description "1599.64 nm/187.412500 THz 3.125/6.25/12.5GHz spacing";
             }
             enum "1599.61" {
               description "1599.61 nm/187.415625 THz 3.125GHz spacing";
             }
             enum "1599.59" {
               description "1599.59 nm/187.418750 THz 3.125/6.25GHz spacing";
             }
             enum "1599.56" {
               description "1599.56 nm/187.421875 THz 3.125GHz spacing";
             }
             enum "1599.53" {
               description "1599.53 nm/187.425000 THz 3.125/6.25/12.5GHz spacing";
             }
             enum "1599.51" {
               description "1599.51 nm/187.428125 THz 3.125GHz spacing";
             }
             enum "1599.48" {
               description "1599.48 nm/187.431250 THz 3.125/6.25GHz spacing";
             }
             enum "1599.45" {
               description "1599.45 nm/187.434375 THz 3.125GHz spacing";
             }
             enum "1599.43" {
               description "1599.43 nm/187.437500 THz 3.125/6.25/12.5GHz spacing";
             }
             enum "1599.40" {
               description "1599.40 nm/187.440625 THz 3.125GHz spacing";
             }
             enum "1599.37" {
               description "1599.37 nm/187.443750 THz 3.125/6.25GHz spacing";
             }
             enum "1599.35" {
               description "1599.35 nm/187.446875 THz 3.125GHz spacing";
             }
             enum "1599.32" {
               description "1599.32 nm/187.450000 THz 3.125/6.25/12.5/50GHz spacing";
             }
             enum "1599.29" {
               description "1599.29 nm/187.453125 THz 3.125GHz spacing";
             }
             enum "1599.27" {
               description "1599.27 nm/187.456250 THz 3.125/6.25GHz spacing";
             }
             enum "1599.24" {
               description "1599.24 nm/187.459375 THz 3.125GHz spacing";
             }
             enum "1599.21" {
               description "1599.21 nm/187.462500 THz 3.125/6.25/12.5GHz spacing";
             }
             enum "1599.19" {
               description "1599.19 nm/187.465625 THz 3.125GHz spacing";
             }
             enum "1599.16" {
               description "1599.16 nm/187.468750 THz 3.125/6.25GHz spacing";
             }
             enum "1599.13" {
               description "1599.13 nm/187.471875 THz 3.125GHz spacing";
             }
             enum "1599.11" {
               description "1599.11 nm/187.475000 THz 3.125/6.25/12.5/75GHz spacing";
             }
             enum "1599.08" {
               description "1599.08 nm/187.478125 THz 3.125GHz spacing";
             }
             enum "1599.05" {
               description "1599.05 nm/187.481250 THz 3.125/6.25GHz spacing";
             }
             enum "1599.03" {
               description "1599.03 nm/187.484375 THz 3.125GHz spacing";
             }
             enum "1599.00" {
               description "1599.00 nm/187.487500 THz 3.125/6.25/12.5GHz spacing";
             }
             enum "1598.97" {
               description "1598.97 nm/187.490625 THz 3.125GHz spacing";
             }
             enum "1598.95" {
               description "1598.95 nm/187.493750 THz 3.125/6.25GHz spacing";
             }
             enum "1598.92" {
               description "1598.92 nm/187.496875 THz 3.125GHz spacing";
             }
             enum "1598.89" {
               description "1598.89 nm/187.500000 THz 3.125/6.25/12.5/50/75/100GHz spacing";
             }
             enum "1598.87" {
               description "1598.87 nm/187.503125 THz 3.125GHz spacing";
             }
             enum "1598.84" {
               description "1598.84 nm/187.506250 THz 3.125/6.25GHz spacing";
             }
             enum "1598.81" {
               description "1598.81 nm/187.509375 THz 3.125GHz spacing";
             }
             enum "1598.79" {
               description "1598.79 nm/187.512500 THz 3.125/6.25/12.5GHz spacing";
             }
             enum "1598.76" {
               description "1598.76 nm/187.515625 THz 3.125GHz spacing";
             }
             enum "1598.73" {
               description "1598.73 nm/187.518750 THz 3.125/6.25GHz spacing";
             }
             enum "1598.71" {
               description "1598.71 nm/187.521875 THz 3.125GHz spacing";
             }
             enum "1598.68" {
               description "1598.68 nm/187.525000 THz 3.125/6.25/12.5GHz spacing";
             }
             enum "1598.65" {
               description "1598.65 nm/187.528125 THz 3.125GHz spacing";
             }
             enum "1598.63" {
               description "1598.63 nm/187.531250 THz 3.125/6.25GHz spacing";
             }
             enum "1598.60" {
               description "1598.60 nm/187.534375 THz 3.125GHz spacing";
             }
             enum "1598.57" {
               description "1598.57 nm/187.537500 THz 3.125/6.25/12.5GHz spacing";
             }
             enum "1598.55" {
               description "1598.55 nm/187.540625 THz 3.125GHz spacing";
             }
             enum "1598.52" {
               description "1598.52 nm/187.543750 THz 3.125/6.25GHz spacing";
             }
             enum "1598.49" {
               description "1598.49 nm/187.546875 THz 3.125GHz spacing";
             }
             enum "1598.47" {
               description "1598.47 nm/187.550000 THz 3.125/6.25/12.5/50/75GHz spacing";
             }
             enum "1598.44" {
               description "1598.44 nm/187.553125 THz 3.125GHz spacing";
             }
             enum "1598.41" {
               description "1598.41 nm/187.556250 THz 3.125/6.25GHz spacing";
             }
             enum "1598.39" {
               description "1598.39 nm/187.559375 THz 3.125GHz spacing";
             }
             enum "1598.36" {
               description "1598.36 nm/187.562500 THz 3.125/6.25/12.5GHz spacing";
             }
             enum "1598.33" {
               description "1598.33 nm/187.565625 THz 3.125GHz spacing";
             }
             enum "1598.31" {
               description "1598.31 nm/187.568750 THz 3.125/6.25GHz spacing";
             }
             enum "1598.28" {
               description "1598.28 nm/187.571875 THz 3.125GHz spacing";
             }
             enum "1598.25" {
               description "1598.25 nm/187.575000 THz 3.125/6.25/12.5GHz spacing";
             }
             enum "1598.23" {
               description "1598.23 nm/187.578125 THz 3.125GHz spacing";
             }
             enum "1598.20" {
               description "1598.20 nm/187.581250 THz 3.125/6.25GHz spacing";
             }
             enum "1598.17" {
               description "1598.17 nm/187.584375 THz 3.125GHz spacing";
             }
             enum "1598.15" {
               description "1598.15 nm/187.587500 THz 3.125/6.25/12.5GHz spacing";
             }
             enum "1598.12" {
               description "1598.12 nm/187.590625 THz 3.125GHz spacing";
             }
             enum "1598.09" {
               description "1598.09 nm/187.593750 THz 3.125/6.25GHz spacing";
             }
             enum "1598.07" {
               description "1598.07 nm/187.596875 THz 3.125GHz spacing";
             }
             enum "1598.04" {
               description "1598.04 nm/187.600000 THz 3.125/6.25/12.5/100GHz spacing";
             }
             enum "1598.01" {
               description "1598.01 nm/187.603125 THz 3.125GHz spacing";
             }
             enum "1597.99" {
               description "1597.99 nm/187.606250 THz 3.125/6.25GHz spacing";
             }
             enum "1597.96" {
               description "1597.96 nm/187.609375 THz 3.125GHz spacing";
             }
             enum "1597.93" {
               description "1597.93 nm/187.612500 THz 3.125/6.25/12.5GHz spacing";
             }
             enum "1597.91" {
               description "1597.91 nm/187.615625 THz 3.125GHz spacing";
             }
             enum "1597.88" {
               description "1597.88 nm/187.618750 THz 3.125/6.25GHz spacing";
             }
             enum "1597.85" {
               description "1597.85 nm/187.621875 THz 3.125GHz spacing";
             }
             enum "1597.83" {
               description "1597.83 nm/187.625000 THz 3.125/6.25/12.5/75GHz spacing";
             }
             enum "1597.80" {
               description "1597.80 nm/187.628125 THz 3.125GHz spacing";
             }
             enum "1597.77" {
               description "1597.77 nm/187.631250 THz 3.125/6.25GHz spacing";
             }
             enum "1597.75" {
               description "1597.75 nm/187.634375 THz 3.125GHz spacing";
             }
             enum "1597.72" {
               description "1597.72 nm/187.637500 THz 3.125/6.25/12.5GHz spacing";
             }
             enum "1597.69" {
               description "1597.69 nm/187.640625 THz 3.125GHz spacing";
             }
             enum "1597.67" {
               description "1597.67 nm/187.643750 THz 3.125/6.25GHz spacing";
             }
             enum "1597.64" {
               description "1597.64 nm/187.646875 THz 3.125GHz spacing";
             }
             enum "1597.62" {
               description "1597.62 nm/187.650000 THz 3.125/6.25/12.5/50GHz spacing";
             }
             enum "1597.59" {
               description "1597.59 nm/187.653125 THz 3.125GHz spacing";
             }
             enum "1597.56" {
               description "1597.56 nm/187.656250 THz 3.125/6.25GHz spacing";
             }
             enum "1597.54" {
               description "1597.54 nm/187.659375 THz 3.125GHz spacing";
             }
             enum "1597.51" {
               description "1597.51 nm/187.662500 THz 3.125/6.25/12.5GHz spacing";
             }
             enum "1597.48" {
               description "1597.48 nm/187.665625 THz 3.125GHz spacing";
             }
             enum "1597.46" {
               description "1597.46 nm/187.668750 THz 3.125/6.25GHz spacing";
             }
             enum "1597.43" {
               description "1597.43 nm/187.671875 THz 3.125GHz spacing";
             }
             enum "1597.40" {
               description "1597.40 nm/187.675000 THz 3.125/6.25/12.5GHz spacing";
             }
             enum "1597.38" {
               description "1597.38 nm/187.678125 THz 3.125GHz spacing";
             }
             enum "1597.35" {
               description "1597.35 nm/187.681250 THz 3.125/6.25GHz spacing";
             }
             enum "1597.32" {
               description "1597.32 nm/187.684375 THz 3.125GHz spacing";
             }
             enum "1597.30" {
               description "1597.30 nm/187.687500 THz 3.125/6.25/12.5GHz spacing";
             }
             enum "1597.27" {
               description "1597.27 nm/187.690625 THz 3.125GHz spacing";
             }
             enum "1597.24" {
               description "1597.24 nm/187.693750 THz 3.125/6.25GHz spacing";
             }
             enum "1597.22" {
               description "1597.22 nm/187.696875 THz 3.125GHz spacing";
             }
             enum "1597.19" {
               description "1597.19 nm/187.700000 THz 3.125/6.25/12.5/100GHz spacing";
             }
             enum "1597.16" {
               description "1597.16 nm/187.703125 THz 3.125GHz spacing";
             }
             enum "1597.14" {
               description "1597.14 nm/187.706250 THz 3.125/6.25GHz spacing";
             }
             enum "1597.11" {
               description "1597.11 nm/187.709375 THz 3.125GHz spacing";
             }
             enum "1597.08" {
               description "1597.08 nm/187.712500 THz 3.125/6.25/12.5GHz spacing";
             }
             enum "1597.06" {
               description "1597.06 nm/187.715625 THz 3.125GHz spacing";
             }
             enum "1597.03" {
               description "1597.03 nm/187.718750 THz 3.125/6.25GHz spacing";
             }
             enum "1597.00" {
               description "1597.00 nm/187.721875 THz 3.125GHz spacing";
             }
             enum "1596.98" {
               description "1596.98 nm/187.725000 THz 3.125/6.25/12.5GHz spacing";
             }
             enum "1596.95" {
               description "1596.95 nm/187.728125 THz 3.125GHz spacing";
             }
             enum "1596.92" {
               description "1596.92 nm/187.731250 THz 3.125/6.25GHz spacing";
             }
             enum "1596.90" {
               description "1596.90 nm/187.734375 THz 3.125GHz spacing";
             }
             enum "1596.87" {
               description "1596.87 nm/187.737500 THz 3.125/6.25/12.5GHz spacing";
             }
             enum "1596.84" {
               description "1596.84 nm/187.740625 THz 3.125GHz spacing";
             }
             enum "1596.82" {
               description "1596.82 nm/187.743750 THz 3.125/6.25GHz spacing";
             }
             enum "1596.79" {
               description "1596.79 nm/187.746875 THz 3.125GHz spacing";
             }
             enum "1596.76" {
               description "1596.76 nm/187.750000 THz 3.125/6.25/12.5/50GHz spacing";
             }
             enum "1596.74" {
               description "1596.74 nm/187.753125 THz 3.125GHz spacing";
             }
             enum "1596.71" {
               description "1596.71 nm/187.756250 THz 3.125/6.25GHz spacing";
             }
             enum "1596.68" {
               description "1596.68 nm/187.759375 THz 3.125GHz spacing";
             }
             enum "1596.66" {
               description "1596.66 nm/187.762500 THz 3.125/6.25/12.5GHz spacing";
             }
             enum "1596.63" {
               description "1596.63 nm/187.765625 THz 3.125GHz spacing";
             }
             enum "1596.60" {
               description "1596.60 nm/187.768750 THz 3.125/6.25GHz spacing";
             }
             enum "1596.58" {
               description "1596.58 nm/187.771875 THz 3.125GHz spacing";
             }
             enum "1596.55" {
               description "1596.55 nm/187.775000 THz 3.125/6.25/12.5/75GHz spacing";
             }
             enum "1596.52" {
               description "1596.52 nm/187.778125 THz 3.125GHz spacing";
             }
             enum "1596.50" {
               description "1596.50 nm/187.781250 THz 3.125/6.25GHz spacing";
             }
             enum "1596.47" {
               description "1596.47 nm/187.784375 THz 3.125GHz spacing";
             }
             enum "1596.45" {
               description "1596.45 nm/187.787500 THz 3.125/6.25/12.5GHz spacing";
             }
             enum "1596.42" {
               description "1596.42 nm/187.790625 THz 3.125GHz spacing";
             }
             enum "1596.39" {
               description "1596.39 nm/187.793750 THz 3.125/6.25GHz spacing";
             }
             enum "1596.37" {
               description "1596.37 nm/187.796875 THz 3.125GHz spacing";
             }
             enum "1596.34" {
               description "1596.34 nm/187.800000 THz 3.125/6.25/12.5/50/75/100GHz spacing";
             }
             enum "1596.31" {
               description "1596.31 nm/187.803125 THz 3.125GHz spacing";
             }
             enum "1596.29" {
               description "1596.29 nm/187.806250 THz 3.125/6.25GHz spacing";
             }
             enum "1596.26" {
               description "1596.26 nm/187.809375 THz 3.125GHz spacing";
             }
             enum "1596.23" {
               description "1596.23 nm/187.812500 THz 3.125/6.25/12.5GHz spacing";
             }
             enum "1596.21" {
               description "1596.21 nm/187.815625 THz 3.125GHz spacing";
             }
             enum "1596.18" {
               description "1596.18 nm/187.818750 THz 3.125/6.25GHz spacing";
             }
             enum "1596.15" {
               description "1596.15 nm/187.821875 THz 3.125GHz spacing";
             }
             enum "1596.13" {
               description "1596.13 nm/187.825000 THz 3.125/6.25/12.5GHz spacing";
             }
             enum "1596.10" {
               description "1596.10 nm/187.828125 THz 3.125GHz spacing";
             }
             enum "1596.07" {
               description "1596.07 nm/187.831250 THz 3.125/6.25GHz spacing";
             }
             enum "1596.05" {
               description "1596.05 nm/187.834375 THz 3.125GHz spacing";
             }
             enum "1596.02" {
               description "1596.02 nm/187.837500 THz 3.125/6.25/12.5GHz spacing";
             }
             enum "1595.99" {
               description "1595.99 nm/187.840625 THz 3.125GHz spacing";
             }
             enum "1595.97" {
               description "1595.97 nm/187.843750 THz 3.125/6.25GHz spacing";
             }
             enum "1595.94" {
               description "1595.94 nm/187.846875 THz 3.125GHz spacing";
             }
             enum "1595.91" {
               description "1595.91 nm/187.850000 THz 3.125/6.25/12.5/50/75GHz spacing";
             }
             enum "1595.89" {
               description "1595.89 nm/187.853125 THz 3.125GHz spacing";
             }
             enum "1595.86" {
               description "1595.86 nm/187.856250 THz 3.125/6.25GHz spacing";
             }
             enum "1595.83" {
               description "1595.83 nm/187.859375 THz 3.125GHz spacing";
             }
             enum "1595.81" {
               description "1595.81 nm/187.862500 THz 3.125/6.25/12.5GHz spacing";
             }
             enum "1595.78" {
               description "1595.78 nm/187.865625 THz 3.125GHz spacing";
             }
             enum "1595.75" {
               description "1595.75 nm/187.868750 THz 3.125/6.25GHz spacing";
             }
             enum "1595.73" {
               description "1595.73 nm/187.871875 THz 3.125GHz spacing";
             }
             enum "1595.70" {
               description "1595.70 nm/187.875000 THz 3.125/6.25/12.5GHz spacing";
             }
             enum "1595.68" {
               description "1595.68 nm/187.878125 THz 3.125GHz spacing";
             }
             enum "1595.65" {
               description "1595.65 nm/187.881250 THz 3.125/6.25GHz spacing";
             }
             enum "1595.62" {
               description "1595.62 nm/187.884375 THz 3.125GHz spacing";
             }
             enum "1595.60" {
               description "1595.60 nm/187.887500 THz 3.125/6.25/12.5GHz spacing";
             }
             enum "1595.57" {
               description "1595.57 nm/187.890625 THz 3.125GHz spacing";
             }
             enum "1595.54" {
               description "1595.54 nm/187.893750 THz 3.125/6.25GHz spacing";
             }
             enum "1595.52" {
               description "1595.52 nm/187.896875 THz 3.125GHz spacing";
             }
             enum "1595.49" {
               description "1595.49 nm/187.900000 THz 3.125/6.25/12.5/100GHz spacing";
             }
             enum "1595.46" {
               description "1595.46 nm/187.903125 THz 3.125GHz spacing";
             }
             enum "1595.44" {
               description "1595.44 nm/187.906250 THz 3.125/6.25GHz spacing";
             }
             enum "1595.41" {
               description "1595.41 nm/187.909375 THz 3.125GHz spacing";
             }
             enum "1595.38" {
               description "1595.38 nm/187.912500 THz 3.125/6.25/12.5GHz spacing";
             }
             enum "1595.36" {
               description "1595.36 nm/187.915625 THz 3.125GHz spacing";
             }
             enum "1595.33" {
               description "1595.33 nm/187.918750 THz 3.125/6.25GHz spacing";
             }
             enum "1595.30" {
               description "1595.30 nm/187.921875 THz 3.125GHz spacing";
             }
             enum "1595.28" {
               description "1595.28 nm/187.925000 THz 3.125/6.25/12.5/75GHz spacing";
             }
             enum "1595.25" {
               description "1595.25 nm/187.928125 THz 3.125GHz spacing";
             }
             enum "1595.22" {
               description "1595.22 nm/187.931250 THz 3.125/6.25GHz spacing";
             }
             enum "1595.20" {
               description "1595.20 nm/187.934375 THz 3.125GHz spacing";
             }
             enum "1595.17" {
               description "1595.17 nm/187.937500 THz 3.125/6.25/12.5GHz spacing";
             }
             enum "1595.14" {
               description "1595.14 nm/187.940625 THz 3.125GHz spacing";
             }
             enum "1595.12" {
               description "1595.12 nm/187.943750 THz 3.125/6.25GHz spacing";
             }
             enum "1595.09" {
               description "1595.09 nm/187.946875 THz 3.125GHz spacing";
             }
             enum "1595.06" {
               description "1595.06 nm/187.950000 THz 3.125/6.25/12.5/50GHz spacing";
             }
             enum "1595.04" {
               description "1595.04 nm/187.953125 THz 3.125GHz spacing";
             }
             enum "1595.01" {
               description "1595.01 nm/187.956250 THz 3.125/6.25GHz spacing";
             }
             enum "1594.99" {
               description "1594.99 nm/187.959375 THz 3.125GHz spacing";
             }
             enum "1594.96" {
               description "1594.96 nm/187.962500 THz 3.125/6.25/12.5GHz spacing";
             }
             enum "1594.93" {
               description "1594.93 nm/187.965625 THz 3.125GHz spacing";
             }
             enum "1594.91" {
               description "1594.91 nm/187.968750 THz 3.125/6.25GHz spacing";
             }
             enum "1594.88" {
               description "1594.88 nm/187.971875 THz 3.125GHz spacing";
             }
             enum "1594.85" {
               description "1594.85 nm/187.975000 THz 3.125/6.25/12.5GHz spacing";
             }
             enum "1594.83" {
               description "1594.83 nm/187.978125 THz 3.125GHz spacing";
             }
             enum "1594.80" {
               description "1594.80 nm/187.981250 THz 3.125/6.25GHz spacing";
             }
             enum "1594.77" {
               description "1594.77 nm/187.984375 THz 3.125GHz spacing";
             }
             enum "1594.75" {
               description "1594.75 nm/187.987500 THz 3.125/6.25/12.5GHz spacing";
             }
             enum "1594.72" {
               description "1594.72 nm/187.990625 THz 3.125GHz spacing";
             }
             enum "1594.69" {
               description "1594.69 nm/187.993750 THz 3.125/6.25GHz spacing";
             }
             enum "1594.67" {
               description "1594.67 nm/187.996875 THz 3.125GHz spacing";
             }
             enum "1594.64" {
               description "1594.64 nm/188.000000 THz 3.125/6.25/12.5/100GHz spacing";
             }
             enum "1594.61" {
               description "1594.61 nm/188.003125 THz 3.125GHz spacing";
             }
             enum "1594.59" {
               description "1594.59 nm/188.006250 THz 3.125/6.25GHz spacing";
             }
             enum "1594.56" {
               description "1594.56 nm/188.009375 THz 3.125GHz spacing";
             }
             enum "1594.53" {
               description "1594.53 nm/188.012500 THz 3.125/6.25/12.5GHz spacing";
             }
             enum "1594.51" {
               description "1594.51 nm/188.015625 THz 3.125GHz spacing";
             }
             enum "1594.48" {
               description "1594.48 nm/188.018750 THz 3.125/6.25GHz spacing";
             }
             enum "1594.46" {
               description "1594.46 nm/188.021875 THz 3.125GHz spacing";
             }
             enum "1594.43" {
               description "1594.43 nm/188.025000 THz 3.125/6.25/12.5GHz spacing";
             }
             enum "1594.40" {
               description "1594.40 nm/188.028125 THz 3.125GHz spacing";
             }
             enum "1594.38" {
               description "1594.38 nm/188.031250 THz 3.125/6.25GHz spacing";
             }
             enum "1594.35" {
               description "1594.35 nm/188.034375 THz 3.125GHz spacing";
             }
             enum "1594.32" {
               description "1594.32 nm/188.037500 THz 3.125/6.25/12.5GHz spacing";
             }
             enum "1594.30" {
               description "1594.30 nm/188.040625 THz 3.125GHz spacing";
             }
             enum "1594.27" {
               description "1594.27 nm/188.043750 THz 3.125/6.25GHz spacing";
             }
             enum "1594.24" {
               description "1594.24 nm/188.046875 THz 3.125GHz spacing";
             }
             enum "1594.22" {
               description "1594.22 nm/188.050000 THz 3.125/6.25/12.5/50GHz spacing";
             }
             enum "1594.19" {
               description "1594.19 nm/188.053125 THz 3.125GHz spacing";
             }
             enum "1594.16" {
               description "1594.16 nm/188.056250 THz 3.125/6.25GHz spacing";
             }
             enum "1594.14" {
               description "1594.14 nm/188.059375 THz 3.125GHz spacing";
             }
             enum "1594.11" {
               description "1594.11 nm/188.062500 THz 3.125/6.25/12.5GHz spacing";
             }
             enum "1594.08" {
               description "1594.08 nm/188.065625 THz 3.125GHz spacing";
             }
             enum "1594.06" {
               description "1594.06 nm/188.068750 THz 3.125/6.25GHz spacing";
             }
             enum "1594.03" {
               description "1594.03 nm/188.071875 THz 3.125GHz spacing";
             }
             enum "1594.00" {
               description "1594.00 nm/188.075000 THz 3.125/6.25/12.5/75GHz spacing";
             }
             enum "1593.98" {
               description "1593.98 nm/188.078125 THz 3.125GHz spacing";
             }
             enum "1593.95" {
               description "1593.95 nm/188.081250 THz 3.125/6.25GHz spacing";
             }
             enum "1593.93" {
               description "1593.93 nm/188.084375 THz 3.125GHz spacing";
             }
             enum "1593.90" {
               description "1593.90 nm/188.087500 THz 3.125/6.25/12.5GHz spacing";
             }
             enum "1593.87" {
               description "1593.87 nm/188.090625 THz 3.125GHz spacing";
             }
             enum "1593.85" {
               description "1593.85 nm/188.093750 THz 3.125/6.25GHz spacing";
             }
             enum "1593.82" {
               description "1593.82 nm/188.096875 THz 3.125GHz spacing";
             }
             enum "1593.79" {
               description "1593.79 nm/188.100000 THz 3.125/6.25/12.5/50/75/100GHz spacing";
             }
             enum "1593.77" {
               description "1593.77 nm/188.103125 THz 3.125GHz spacing";
             }
             enum "1593.74" {
               description "1593.74 nm/188.106250 THz 3.125/6.25GHz spacing";
             }
             enum "1593.71" {
               description "1593.71 nm/188.109375 THz 3.125GHz spacing";
             }
             enum "1593.69" {
               description "1593.69 nm/188.112500 THz 3.125/6.25/12.5GHz spacing";
             }
             enum "1593.66" {
               description "1593.66 nm/188.115625 THz 3.125GHz spacing";
             }
             enum "1593.63" {
               description "1593.63 nm/188.118750 THz 3.125/6.25GHz spacing";
             }
             enum "1593.61" {
               description "1593.61 nm/188.121875 THz 3.125GHz spacing";
             }
             enum "1593.58" {
               description "1593.58 nm/188.125000 THz 3.125/6.25/12.5GHz spacing";
             }
             enum "1593.55" {
               description "1593.55 nm/188.128125 THz 3.125GHz spacing";
             }
             enum "1593.53" {
               description "1593.53 nm/188.131250 THz 3.125/6.25GHz spacing";
             }
             enum "1593.50" {
               description "1593.50 nm/188.134375 THz 3.125GHz spacing";
             }
             enum "1593.48" {
               description "1593.48 nm/188.137500 THz 3.125/6.25/12.5GHz spacing";
             }
             enum "1593.45" {
               description "1593.45 nm/188.140625 THz 3.125GHz spacing";
             }
             enum "1593.42" {
               description "1593.42 nm/188.143750 THz 3.125/6.25GHz spacing";
             }
             enum "1593.40" {
               description "1593.40 nm/188.146875 THz 3.125GHz spacing";
             }
             enum "1593.37" {
               description "1593.37 nm/188.150000 THz 3.125/6.25/12.5/50/75GHz spacing";
             }
             enum "1593.34" {
               description "1593.34 nm/188.153125 THz 3.125GHz spacing";
             }
             enum "1593.32" {
               description "1593.32 nm/188.156250 THz 3.125/6.25GHz spacing";
             }
             enum "1593.29" {
               description "1593.29 nm/188.159375 THz 3.125GHz spacing";
             }
             enum "1593.26" {
               description "1593.26 nm/188.162500 THz 3.125/6.25/12.5GHz spacing";
             }
             enum "1593.24" {
               description "1593.24 nm/188.165625 THz 3.125GHz spacing";
             }
             enum "1593.21" {
               description "1593.21 nm/188.168750 THz 3.125/6.25GHz spacing";
             }
             enum "1593.18" {
               description "1593.18 nm/188.171875 THz 3.125GHz spacing";
             }
             enum "1593.16" {
               description "1593.16 nm/188.175000 THz 3.125/6.25/12.5GHz spacing";
             }
             enum "1593.13" {
               description "1593.13 nm/188.178125 THz 3.125GHz spacing";
             }
             enum "1593.10" {
               description "1593.10 nm/188.181250 THz 3.125/6.25GHz spacing";
             }
             enum "1593.08" {
               description "1593.08 nm/188.184375 THz 3.125GHz spacing";
             }
             enum "1593.05" {
               description "1593.05 nm/188.187500 THz 3.125/6.25/12.5GHz spacing";
             }
             enum "1593.03" {
               description "1593.03 nm/188.190625 THz 3.125GHz spacing";
             }
             enum "1593.00" {
               description "1593.00 nm/188.193750 THz 3.125/6.25GHz spacing";
             }
             enum "1592.97" {
               description "1592.97 nm/188.196875 THz 3.125GHz spacing";
             }
             enum "1592.95" {
               description "1592.95 nm/188.200000 THz 3.125/6.25/12.5/100GHz spacing";
             }
             enum "1592.92" {
               description "1592.92 nm/188.203125 THz 3.125GHz spacing";
             }
             enum "1592.89" {
               description "1592.89 nm/188.206250 THz 3.125/6.25GHz spacing";
             }
             enum "1592.87" {
               description "1592.87 nm/188.209375 THz 3.125GHz spacing";
             }
             enum "1592.84" {
               description "1592.84 nm/188.212500 THz 3.125/6.25/12.5GHz spacing";
             }
             enum "1592.81" {
               description "1592.81 nm/188.215625 THz 3.125GHz spacing";
             }
             enum "1592.79" {
               description "1592.79 nm/188.218750 THz 3.125/6.25GHz spacing";
             }
             enum "1592.76" {
               description "1592.76 nm/188.221875 THz 3.125GHz spacing";
             }
             enum "1592.73" {
               description "1592.73 nm/188.225000 THz 3.125/6.25/12.5/75GHz spacing";
             }
             enum "1592.71" {
               description "1592.71 nm/188.228125 THz 3.125GHz spacing";
             }
             enum "1592.68" {
               description "1592.68 nm/188.231250 THz 3.125/6.25GHz spacing";
             }
             enum "1592.66" {
               description "1592.66 nm/188.234375 THz 3.125GHz spacing";
             }
             enum "1592.63" {
               description "1592.63 nm/188.237500 THz 3.125/6.25/12.5GHz spacing";
             }
             enum "1592.60" {
               description "1592.60 nm/188.240625 THz 3.125GHz spacing";
             }
             enum "1592.58" {
               description "1592.58 nm/188.243750 THz 3.125/6.25GHz spacing";
             }
             enum "1592.55" {
               description "1592.55 nm/188.246875 THz 3.125GHz spacing";
             }
             enum "1592.52" {
               description "1592.52 nm/188.250000 THz 3.125/6.25/12.5/50GHz spacing";
             }
             enum "1592.50" {
               description "1592.50 nm/188.253125 THz 3.125GHz spacing";
             }
             enum "1592.47" {
               description "1592.47 nm/188.256250 THz 3.125/6.25GHz spacing";
             }
             enum "1592.44" {
               description "1592.44 nm/188.259375 THz 3.125GHz spacing";
             }
             enum "1592.42" {
               description "1592.42 nm/188.262500 THz 3.125/6.25/12.5GHz spacing";
             }
             enum "1592.39" {
               description "1592.39 nm/188.265625 THz 3.125GHz spacing";
             }
             enum "1592.36" {
               description "1592.36 nm/188.268750 THz 3.125/6.25GHz spacing";
             }
             enum "1592.34" {
               description "1592.34 nm/188.271875 THz 3.125GHz spacing";
             }
             enum "1592.31" {
               description "1592.31 nm/188.275000 THz 3.125/6.25/12.5GHz spacing";
             }
             enum "1592.29" {
               description "1592.29 nm/188.278125 THz 3.125GHz spacing";
             }
             enum "1592.26" {
               description "1592.26 nm/188.281250 THz 3.125/6.25GHz spacing";
             }
             enum "1592.23" {
               description "1592.23 nm/188.284375 THz 3.125GHz spacing";
             }
             enum "1592.21" {
               description "1592.21 nm/188.287500 THz 3.125/6.25/12.5GHz spacing";
             }
             enum "1592.18" {
               description "1592.18 nm/188.290625 THz 3.125GHz spacing";
             }
             enum "1592.15" {
               description "1592.15 nm/188.293750 THz 3.125/6.25GHz spacing";
             }
             enum "1592.13" {
               description "1592.13 nm/188.296875 THz 3.125GHz spacing";
             }
             enum "1592.10" {
               description "1592.10 nm/188.300000 THz 3.125/6.25/12.5/100GHz spacing";
             }
             enum "1592.07" {
               description "1592.07 nm/188.303125 THz 3.125GHz spacing";
             }
             enum "1592.05" {
               description "1592.05 nm/188.306250 THz 3.125/6.25GHz spacing";
             }
             enum "1592.02" {
               description "1592.02 nm/188.309375 THz 3.125GHz spacing";
             }
             enum "1591.99" {
               description "1591.99 nm/188.312500 THz 3.125/6.25/12.5GHz spacing";
             }
             enum "1591.97" {
               description "1591.97 nm/188.315625 THz 3.125GHz spacing";
             }
             enum "1591.94" {
               description "1591.94 nm/188.318750 THz 3.125/6.25GHz spacing";
             }
             enum "1591.92" {
               description "1591.92 nm/188.321875 THz 3.125GHz spacing";
             }
             enum "1591.89" {
               description "1591.89 nm/188.325000 THz 3.125/6.25/12.5GHz spacing";
             }
             enum "1591.86" {
               description "1591.86 nm/188.328125 THz 3.125GHz spacing";
             }
             enum "1591.84" {
               description "1591.84 nm/188.331250 THz 3.125/6.25GHz spacing";
             }
             enum "1591.81" {
               description "1591.81 nm/188.334375 THz 3.125GHz spacing";
             }
             enum "1591.78" {
               description "1591.78 nm/188.337500 THz 3.125/6.25/12.5GHz spacing";
             }
             enum "1591.76" {
               description "1591.76 nm/188.340625 THz 3.125GHz spacing";
             }
             enum "1591.73" {
               description "1591.73 nm/188.343750 THz 3.125/6.25GHz spacing";
             }
             enum "1591.70" {
               description "1591.70 nm/188.346875 THz 3.125GHz spacing";
             }
             enum "1591.68" {
               description "1591.68 nm/188.350000 THz 3.125/6.25/12.5/50GHz spacing";
             }
             enum "1591.65" {
               description "1591.65 nm/188.353125 THz 3.125GHz spacing";
             }
             enum "1591.62" {
               description "1591.62 nm/188.356250 THz 3.125/6.25GHz spacing";
             }
             enum "1591.60" {
               description "1591.60 nm/188.359375 THz 3.125GHz spacing";
             }
             enum "1591.57" {
               description "1591.57 nm/188.362500 THz 3.125/6.25/12.5GHz spacing";
             }
             enum "1591.55" {
               description "1591.55 nm/188.365625 THz 3.125GHz spacing";
             }
             enum "1591.52" {
               description "1591.52 nm/188.368750 THz 3.125/6.25GHz spacing";
             }
             enum "1591.49" {
               description "1591.49 nm/188.371875 THz 3.125GHz spacing";
             }
             enum "1591.47" {
               description "1591.47 nm/188.375000 THz 3.125/6.25/12.5/75GHz spacing";
             }
             enum "1591.44" {
               description "1591.44 nm/188.378125 THz 3.125GHz spacing";
             }
             enum "1591.41" {
               description "1591.41 nm/188.381250 THz 3.125/6.25GHz spacing";
             }
             enum "1591.39" {
               description "1591.39 nm/188.384375 THz 3.125GHz spacing";
             }
             enum "1591.36" {
               description "1591.36 nm/188.387500 THz 3.125/6.25/12.5GHz spacing";
             }
             enum "1591.33" {
               description "1591.33 nm/188.390625 THz 3.125GHz spacing";
             }
             enum "1591.31" {
               description "1591.31 nm/188.393750 THz 3.125/6.25GHz spacing";
             }
             enum "1591.28" {
               description "1591.28 nm/188.396875 THz 3.125GHz spacing";
             }
             enum "1591.26" {
               description "1591.26 nm/188.400000 THz 3.125/6.25/12.5/50/75/100GHz spacing";
             }
             enum "1591.23" {
               description "1591.23 nm/188.403125 THz 3.125GHz spacing";
             }
             enum "1591.20" {
               description "1591.20 nm/188.406250 THz 3.125/6.25GHz spacing";
             }
             enum "1591.18" {
               description "1591.18 nm/188.409375 THz 3.125GHz spacing";
             }
             enum "1591.15" {
               description "1591.15 nm/188.412500 THz 3.125/6.25/12.5GHz spacing";
             }
             enum "1591.12" {
               description "1591.12 nm/188.415625 THz 3.125GHz spacing";
             }
             enum "1591.10" {
               description "1591.10 nm/188.418750 THz 3.125/6.25GHz spacing";
             }
             enum "1591.07" {
               description "1591.07 nm/188.421875 THz 3.125GHz spacing";
             }
             enum "1591.04" {
               description "1591.04 nm/188.425000 THz 3.125/6.25/12.5GHz spacing";
             }
             enum "1591.02" {
               description "1591.02 nm/188.428125 THz 3.125GHz spacing";
             }
             enum "1590.99" {
               description "1590.99 nm/188.431250 THz 3.125/6.25GHz spacing";
             }
             enum "1590.96" {
               description "1590.96 nm/188.434375 THz 3.125GHz spacing";
             }
             enum "1590.94" {
               description "1590.94 nm/188.437500 THz 3.125/6.25/12.5GHz spacing";
             }
             enum "1590.91" {
               description "1590.91 nm/188.440625 THz 3.125GHz spacing";
             }
             enum "1590.89" {
               description "1590.89 nm/188.443750 THz 3.125/6.25GHz spacing";
             }
             enum "1590.86" {
               description "1590.86 nm/188.446875 THz 3.125GHz spacing";
             }
             enum "1590.83" {
               description "1590.83 nm/188.450000 THz 3.125/6.25/12.5/50/75GHz spacing";
             }
             enum "1590.81" {
               description "1590.81 nm/188.453125 THz 3.125GHz spacing";
             }
             enum "1590.78" {
               description "1590.78 nm/188.456250 THz 3.125/6.25GHz spacing";
             }
             enum "1590.75" {
               description "1590.75 nm/188.459375 THz 3.125GHz spacing";
             }
             enum "1590.73" {
               description "1590.73 nm/188.462500 THz 3.125/6.25/12.5GHz spacing";
             }
             enum "1590.70" {
               description "1590.70 nm/188.465625 THz 3.125GHz spacing";
             }
             enum "1590.67" {
               description "1590.67 nm/188.468750 THz 3.125/6.25GHz spacing";
             }
             enum "1590.65" {
               description "1590.65 nm/188.471875 THz 3.125GHz spacing";
             }
             enum "1590.62" {
               description "1590.62 nm/188.475000 THz 3.125/6.25/12.5GHz spacing";
             }
             enum "1590.60" {
               description "1590.60 nm/188.478125 THz 3.125GHz spacing";
             }
             enum "1590.57" {
               description "1590.57 nm/188.481250 THz 3.125/6.25GHz spacing";
             }
             enum "1590.54" {
               description "1590.54 nm/188.484375 THz 3.125GHz spacing";
             }
             enum "1590.52" {
               description "1590.52 nm/188.487500 THz 3.125/6.25/12.5GHz spacing";
             }
             enum "1590.49" {
               description "1590.49 nm/188.490625 THz 3.125GHz spacing";
             }
             enum "1590.46" {
               description "1590.46 nm/188.493750 THz 3.125/6.25GHz spacing";
             }
             enum "1590.44" {
               description "1590.44 nm/188.496875 THz 3.125GHz spacing";
             }
             enum "1590.41" {
               description "1590.41 nm/188.500000 THz 3.125/6.25/12.5/100GHz spacing";
             }
             enum "1590.38" {
               description "1590.38 nm/188.503125 THz 3.125GHz spacing";
             }
             enum "1590.36" {
               description "1590.36 nm/188.506250 THz 3.125/6.25GHz spacing";
             }
             enum "1590.33" {
               description "1590.33 nm/188.509375 THz 3.125GHz spacing";
             }
             enum "1590.31" {
               description "1590.31 nm/188.512500 THz 3.125/6.25/12.5GHz spacing";
             }
             enum "1590.28" {
               description "1590.28 nm/188.515625 THz 3.125GHz spacing";
             }
             enum "1590.25" {
               description "1590.25 nm/188.518750 THz 3.125/6.25GHz spacing";
             }
             enum "1590.23" {
               description "1590.23 nm/188.521875 THz 3.125GHz spacing";
             }
             enum "1590.20" {
               description "1590.20 nm/188.525000 THz 3.125/6.25/12.5/75GHz spacing";
             }
             enum "1590.17" {
               description "1590.17 nm/188.528125 THz 3.125GHz spacing";
             }
             enum "1590.15" {
               description "1590.15 nm/188.531250 THz 3.125/6.25GHz spacing";
             }
             enum "1590.12" {
               description "1590.12 nm/188.534375 THz 3.125GHz spacing";
             }
             enum "1590.09" {
               description "1590.09 nm/188.537500 THz 3.125/6.25/12.5GHz spacing";
             }
             enum "1590.07" {
               description "1590.07 nm/188.540625 THz 3.125GHz spacing";
             }
             enum "1590.04" {
               description "1590.04 nm/188.543750 THz 3.125/6.25GHz spacing";
             }
             enum "1590.02" {
               description "1590.02 nm/188.546875 THz 3.125GHz spacing";
             }
             enum "1589.99" {
               description "1589.99 nm/188.550000 THz 3.125/6.25/12.5/50GHz spacing";
             }
             enum "1589.96" {
               description "1589.96 nm/188.553125 THz 3.125GHz spacing";
             }
             enum "1589.94" {
               description "1589.94 nm/188.556250 THz 3.125/6.25GHz spacing";
             }
             enum "1589.91" {
               description "1589.91 nm/188.559375 THz 3.125GHz spacing";
             }
             enum "1589.88" {
               description "1589.88 nm/188.562500 THz 3.125/6.25/12.5GHz spacing";
             }
             enum "1589.86" {
               description "1589.86 nm/188.565625 THz 3.125GHz spacing";
             }
             enum "1589.83" {
               description "1589.83 nm/188.568750 THz 3.125/6.25GHz spacing";
             }
             enum "1589.80" {
               description "1589.80 nm/188.571875 THz 3.125GHz spacing";
             }
             enum "1589.78" {
               description "1589.78 nm/188.575000 THz 3.125/6.25/12.5GHz spacing";
             }
             enum "1589.75" {
               description "1589.75 nm/188.578125 THz 3.125GHz spacing";
             }
             enum "1589.73" {
               description "1589.73 nm/188.581250 THz 3.125/6.25GHz spacing";
             }
             enum "1589.70" {
               description "1589.70 nm/188.584375 THz 3.125GHz spacing";
             }
             enum "1589.67" {
               description "1589.67 nm/188.587500 THz 3.125/6.25/12.5GHz spacing";
             }
             enum "1589.65" {
               description "1589.65 nm/188.590625 THz 3.125GHz spacing";
             }
             enum "1589.62" {
               description "1589.62 nm/188.593750 THz 3.125/6.25GHz spacing";
             }
             enum "1589.59" {
               description "1589.59 nm/188.596875 THz 3.125GHz spacing";
             }
             enum "1589.57" {
               description "1589.57 nm/188.600000 THz 3.125/6.25/12.5/100GHz spacing";
             }
             enum "1589.54" {
               description "1589.54 nm/188.603125 THz 3.125GHz spacing";
             }
             enum "1589.51" {
               description "1589.51 nm/188.606250 THz 3.125/6.25GHz spacing";
             }
             enum "1589.49" {
               description "1589.49 nm/188.609375 THz 3.125GHz spacing";
             }
             enum "1589.46" {
               description "1589.46 nm/188.612500 THz 3.125/6.25/12.5GHz spacing";
             }
             enum "1589.44" {
               description "1589.44 nm/188.615625 THz 3.125GHz spacing";
             }
             enum "1589.41" {
               description "1589.41 nm/188.618750 THz 3.125/6.25GHz spacing";
             }
             enum "1589.38" {
               description "1589.38 nm/188.621875 THz 3.125GHz spacing";
             }
             enum "1589.36" {
               description "1589.36 nm/188.625000 THz 3.125/6.25/12.5GHz spacing";
             }
             enum "1589.33" {
               description "1589.33 nm/188.628125 THz 3.125GHz spacing";
             }
             enum "1589.30" {
               description "1589.30 nm/188.631250 THz 3.125/6.25GHz spacing";
             }
             enum "1589.28" {
               description "1589.28 nm/188.634375 THz 3.125GHz spacing";
             }
             enum "1589.25" {
               description "1589.25 nm/188.637500 THz 3.125/6.25/12.5GHz spacing";
             }
             enum "1589.23" {
               description "1589.23 nm/188.640625 THz 3.125GHz spacing";
             }
             enum "1589.20" {
               description "1589.20 nm/188.643750 THz 3.125/6.25GHz spacing";
             }
             enum "1589.17" {
               description "1589.17 nm/188.646875 THz 3.125GHz spacing";
             }
             enum "1589.15" {
               description "1589.15 nm/188.650000 THz 3.125/6.25/12.5/50GHz spacing";
             }
             enum "1589.12" {
               description "1589.12 nm/188.653125 THz 3.125GHz spacing";
             }
             enum "1589.09" {
               description "1589.09 nm/188.656250 THz 3.125/6.25GHz spacing";
             }
             enum "1589.07" {
               description "1589.07 nm/188.659375 THz 3.125GHz spacing";
             }
             enum "1589.04" {
               description "1589.04 nm/188.662500 THz 3.125/6.25/12.5GHz spacing";
             }
             enum "1589.01" {
               description "1589.01 nm/188.665625 THz 3.125GHz spacing";
             }
             enum "1588.99" {
               description "1588.99 nm/188.668750 THz 3.125/6.25GHz spacing";
             }
             enum "1588.96" {
               description "1588.96 nm/188.671875 THz 3.125GHz spacing";
             }
             enum "1588.94" {
               description "1588.94 nm/188.675000 THz 3.125/6.25/12.5/75GHz spacing";
             }
             enum "1588.91" {
               description "1588.91 nm/188.678125 THz 3.125GHz spacing";
             }
             enum "1588.88" {
               description "1588.88 nm/188.681250 THz 3.125/6.25GHz spacing";
             }
             enum "1588.86" {
               description "1588.86 nm/188.684375 THz 3.125GHz spacing";
             }
             enum "1588.83" {
               description "1588.83 nm/188.687500 THz 3.125/6.25/12.5GHz spacing";
             }
             enum "1588.80" {
               description "1588.80 nm/188.690625 THz 3.125GHz spacing";
             }
             enum "1588.78" {
               description "1588.78 nm/188.693750 THz 3.125/6.25GHz spacing";
             }
             enum "1588.75" {
               description "1588.75 nm/188.696875 THz 3.125GHz spacing";
             }
             enum "1588.73" {
               description "1588.73 nm/188.700000 THz 3.125/6.25/12.5/50/75/100GHz spacing";
             }
             enum "1588.70" {
               description "1588.70 nm/188.703125 THz 3.125GHz spacing";
             }
             enum "1588.67" {
               description "1588.67 nm/188.706250 THz 3.125/6.25GHz spacing";
             }
             enum "1588.65" {
               description "1588.65 nm/188.709375 THz 3.125GHz spacing";
             }
             enum "1588.62" {
               description "1588.62 nm/188.712500 THz 3.125/6.25/12.5GHz spacing";
             }
             enum "1588.59" {
               description "1588.59 nm/188.715625 THz 3.125GHz spacing";
             }
             enum "1588.57" {
               description "1588.57 nm/188.718750 THz 3.125/6.25GHz spacing";
             }
             enum "1588.54" {
               description "1588.54 nm/188.721875 THz 3.125GHz spacing";
             }
             enum "1588.51" {
               description "1588.51 nm/188.725000 THz 3.125/6.25/12.5GHz spacing";
             }
             enum "1588.49" {
               description "1588.49 nm/188.728125 THz 3.125GHz spacing";
             }
             enum "1588.46" {
               description "1588.46 nm/188.731250 THz 3.125/6.25GHz spacing";
             }
             enum "1588.44" {
               description "1588.44 nm/188.734375 THz 3.125GHz spacing";
             }
             enum "1588.41" {
               description "1588.41 nm/188.737500 THz 3.125/6.25/12.5GHz spacing";
             }
             enum "1588.38" {
               description "1588.38 nm/188.740625 THz 3.125GHz spacing";
             }
             enum "1588.36" {
               description "1588.36 nm/188.743750 THz 3.125/6.25GHz spacing";
             }
             enum "1588.33" {
               description "1588.33 nm/188.746875 THz 3.125GHz spacing";
             }
             enum "1588.30" {
               description "1588.30 nm/188.750000 THz 3.125/6.25/12.5/50/75GHz spacing";
             }
             enum "1588.28" {
               description "1588.28 nm/188.753125 THz 3.125GHz spacing";
             }
             enum "1588.25" {
               description "1588.25 nm/188.756250 THz 3.125/6.25GHz spacing";
             }
             enum "1588.23" {
               description "1588.23 nm/188.759375 THz 3.125GHz spacing";
             }
             enum "1588.20" {
               description "1588.20 nm/188.762500 THz 3.125/6.25/12.5GHz spacing";
             }
             enum "1588.17" {
               description "1588.17 nm/188.765625 THz 3.125GHz spacing";
             }
             enum "1588.15" {
               description "1588.15 nm/188.768750 THz 3.125/6.25GHz spacing";
             }
             enum "1588.12" {
               description "1588.12 nm/188.771875 THz 3.125GHz spacing";
             }
             enum "1588.09" {
               description "1588.09 nm/188.775000 THz 3.125/6.25/12.5GHz spacing";
             }
             enum "1588.07" {
               description "1588.07 nm/188.778125 THz 3.125GHz spacing";
             }
             enum "1588.04" {
               description "1588.04 nm/188.781250 THz 3.125/6.25GHz spacing";
             }
             enum "1588.02" {
               description "1588.02 nm/188.784375 THz 3.125GHz spacing";
             }
             enum "1587.99" {
               description "1587.99 nm/188.787500 THz 3.125/6.25/12.5GHz spacing";
             }
             enum "1587.96" {
               description "1587.96 nm/188.790625 THz 3.125GHz spacing";
             }
             enum "1587.94" {
               description "1587.94 nm/188.793750 THz 3.125/6.25GHz spacing";
             }
             enum "1587.91" {
               description "1587.91 nm/188.796875 THz 3.125GHz spacing";
             }
             enum "1587.88" {
               description "1587.88 nm/188.800000 THz 3.125/6.25/12.5/100GHz spacing";
             }
             enum "1587.86" {
               description "1587.86 nm/188.803125 THz 3.125GHz spacing";
             }
             enum "1587.83" {
               description "1587.83 nm/188.806250 THz 3.125/6.25GHz spacing";
             }
             enum "1587.80" {
               description "1587.80 nm/188.809375 THz 3.125GHz spacing";
             }
             enum "1587.78" {
               description "1587.78 nm/188.812500 THz 3.125/6.25/12.5GHz spacing";
             }
             enum "1587.75" {
               description "1587.75 nm/188.815625 THz 3.125GHz spacing";
             }
             enum "1587.73" {
               description "1587.73 nm/188.818750 THz 3.125/6.25GHz spacing";
             }
             enum "1587.70" {
               description "1587.70 nm/188.821875 THz 3.125GHz spacing";
             }
             enum "1587.67" {
               description "1587.67 nm/188.825000 THz 3.125/6.25/12.5/75GHz spacing";
             }
             enum "1587.65" {
               description "1587.65 nm/188.828125 THz 3.125GHz spacing";
             }
             enum "1587.62" {
               description "1587.62 nm/188.831250 THz 3.125/6.25GHz spacing";
             }
             enum "1587.59" {
               description "1587.59 nm/188.834375 THz 3.125GHz spacing";
             }
             enum "1587.57" {
               description "1587.57 nm/188.837500 THz 3.125/6.25/12.5GHz spacing";
             }
             enum "1587.54" {
               description "1587.54 nm/188.840625 THz 3.125GHz spacing";
             }
             enum "1587.52" {
               description "1587.52 nm/188.843750 THz 3.125/6.25GHz spacing";
             }
             enum "1587.49" {
               description "1587.49 nm/188.846875 THz 3.125GHz spacing";
             }
             enum "1587.46" {
               description "1587.46 nm/188.850000 THz 3.125/6.25/12.5/50GHz spacing";
             }
             enum "1587.44" {
               description "1587.44 nm/188.853125 THz 3.125GHz spacing";
             }
             enum "1587.41" {
               description "1587.41 nm/188.856250 THz 3.125/6.25GHz spacing";
             }
             enum "1587.38" {
               description "1587.38 nm/188.859375 THz 3.125GHz spacing";
             }
             enum "1587.36" {
               description "1587.36 nm/188.862500 THz 3.125/6.25/12.5GHz spacing";
             }
             enum "1587.33" {
               description "1587.33 nm/188.865625 THz 3.125GHz spacing";
             }
             enum "1587.31" {
               description "1587.31 nm/188.868750 THz 3.125/6.25GHz spacing";
             }
             enum "1587.28" {
               description "1587.28 nm/188.871875 THz 3.125GHz spacing";
             }
             enum "1587.25" {
               description "1587.25 nm/188.875000 THz 3.125/6.25/12.5GHz spacing";
             }
             enum "1587.23" {
               description "1587.23 nm/188.878125 THz 3.125GHz spacing";
             }
             enum "1587.20" {
               description "1587.20 nm/188.881250 THz 3.125/6.25GHz spacing";
             }
             enum "1587.17" {
               description "1587.17 nm/188.884375 THz 3.125GHz spacing";
             }
             enum "1587.15" {
               description "1587.15 nm/188.887500 THz 3.125/6.25/12.5GHz spacing";
             }
             enum "1587.12" {
               description "1587.12 nm/188.890625 THz 3.125GHz spacing";
             }
             enum "1587.10" {
               description "1587.10 nm/188.893750 THz 3.125/6.25GHz spacing";
             }
             enum "1587.07" {
               description "1587.07 nm/188.896875 THz 3.125GHz spacing";
             }
             enum "1587.04" {
               description "1587.04 nm/188.900000 THz 3.125/6.25/12.5/100GHz spacing";
             }
             enum "1587.02" {
               description "1587.02 nm/188.903125 THz 3.125GHz spacing";
             }
             enum "1586.99" {
               description "1586.99 nm/188.906250 THz 3.125/6.25GHz spacing";
             }
             enum "1586.96" {
               description "1586.96 nm/188.909375 THz 3.125GHz spacing";
             }
             enum "1586.94" {
               description "1586.94 nm/188.912500 THz 3.125/6.25/12.5GHz spacing";
             }
             enum "1586.91" {
               description "1586.91 nm/188.915625 THz 3.125GHz spacing";
             }
             enum "1586.89" {
               description "1586.89 nm/188.918750 THz 3.125/6.25GHz spacing";
             }
             enum "1586.86" {
               description "1586.86 nm/188.921875 THz 3.125GHz spacing";
             }
             enum "1586.83" {
               description "1586.83 nm/188.925000 THz 3.125/6.25/12.5GHz spacing";
             }
             enum "1586.81" {
               description "1586.81 nm/188.928125 THz 3.125GHz spacing";
             }
             enum "1586.78" {
               description "1586.78 nm/188.931250 THz 3.125/6.25GHz spacing";
             }
             enum "1586.75" {
               description "1586.75 nm/188.934375 THz 3.125GHz spacing";
             }
             enum "1586.73" {
               description "1586.73 nm/188.937500 THz 3.125/6.25/12.5GHz spacing";
             }
             enum "1586.70" {
               description "1586.70 nm/188.940625 THz 3.125GHz spacing";
             }
             enum "1586.68" {
               description "1586.68 nm/188.943750 THz 3.125/6.25GHz spacing";
             }
             enum "1586.65" {
               description "1586.65 nm/188.946875 THz 3.125GHz spacing";
             }
             enum "1586.62" {
               description "1586.62 nm/188.950000 THz 3.125/6.25/12.5/50GHz spacing";
             }
             enum "1586.60" {
               description "1586.60 nm/188.953125 THz 3.125GHz spacing";
             }
             enum "1586.57" {
               description "1586.57 nm/188.956250 THz 3.125/6.25GHz spacing";
             }
             enum "1586.54" {
               description "1586.54 nm/188.959375 THz 3.125GHz spacing";
             }
             enum "1586.52" {
               description "1586.52 nm/188.962500 THz 3.125/6.25/12.5GHz spacing";
             }
             enum "1586.49" {
               description "1586.49 nm/188.965625 THz 3.125GHz spacing";
             }
             enum "1586.47" {
               description "1586.47 nm/188.968750 THz 3.125/6.25GHz spacing";
             }
             enum "1586.44" {
               description "1586.44 nm/188.971875 THz 3.125GHz spacing";
             }
             enum "1586.41" {
               description "1586.41 nm/188.975000 THz 3.125/6.25/12.5/75GHz spacing";
             }
             enum "1586.39" {
               description "1586.39 nm/188.978125 THz 3.125GHz spacing";
             }
             enum "1586.36" {
               description "1586.36 nm/188.981250 THz 3.125/6.25GHz spacing";
             }
             enum "1586.33" {
               description "1586.33 nm/188.984375 THz 3.125GHz spacing";
             }
             enum "1586.31" {
               description "1586.31 nm/188.987500 THz 3.125/6.25/12.5GHz spacing";
             }
             enum "1586.28" {
               description "1586.28 nm/188.990625 THz 3.125GHz spacing";
             }
             enum "1586.26" {
               description "1586.26 nm/188.993750 THz 3.125/6.25GHz spacing";
             }
             enum "1586.23" {
               description "1586.23 nm/188.996875 THz 3.125GHz spacing";
             }
             enum "1586.20" {
               description "1586.20 nm/189.000000 THz 3.125/6.25/12.5/50/75/100GHz spacing";
             }
             enum "1586.18" {
               description "1586.18 nm/189.003125 THz 3.125GHz spacing";
             }
             enum "1586.15" {
               description "1586.15 nm/189.006250 THz 3.125/6.25GHz spacing";
             }
             enum "1586.12" {
               description "1586.12 nm/189.009375 THz 3.125GHz spacing";
             }
             enum "1586.10" {
               description "1586.10 nm/189.012500 THz 3.125/6.25/12.5GHz spacing";
             }
             enum "1586.07" {
               description "1586.07 nm/189.015625 THz 3.125GHz spacing";
             }
             enum "1586.05" {
               description "1586.05 nm/189.018750 THz 3.125/6.25GHz spacing";
             }
             enum "1586.02" {
               description "1586.02 nm/189.021875 THz 3.125GHz spacing";
             }
             enum "1585.99" {
               description "1585.99 nm/189.025000 THz 3.125/6.25/12.5GHz spacing";
             }
             enum "1585.97" {
               description "1585.97 nm/189.028125 THz 3.125GHz spacing";
             }
             enum "1585.94" {
               description "1585.94 nm/189.031250 THz 3.125/6.25GHz spacing";
             }
             enum "1585.92" {
               description "1585.92 nm/189.034375 THz 3.125GHz spacing";
             }
             enum "1585.89" {
               description "1585.89 nm/189.037500 THz 3.125/6.25/12.5GHz spacing";
             }
             enum "1585.86" {
               description "1585.86 nm/189.040625 THz 3.125GHz spacing";
             }
             enum "1585.84" {
               description "1585.84 nm/189.043750 THz 3.125/6.25GHz spacing";
             }
             enum "1585.81" {
               description "1585.81 nm/189.046875 THz 3.125GHz spacing";
             }
             enum "1585.78" {
               description "1585.78 nm/189.050000 THz 3.125/6.25/12.5/50/75GHz spacing";
             }
             enum "1585.76" {
               description "1585.76 nm/189.053125 THz 3.125GHz spacing";
             }
             enum "1585.73" {
               description "1585.73 nm/189.056250 THz 3.125/6.25GHz spacing";
             }
             enum "1585.71" {
               description "1585.71 nm/189.059375 THz 3.125GHz spacing";
             }
             enum "1585.68" {
               description "1585.68 nm/189.062500 THz 3.125/6.25/12.5GHz spacing";
             }
             enum "1585.65" {
               description "1585.65 nm/189.065625 THz 3.125GHz spacing";
             }
             enum "1585.63" {
               description "1585.63 nm/189.068750 THz 3.125/6.25GHz spacing";
             }
             enum "1585.60" {
               description "1585.60 nm/189.071875 THz 3.125GHz spacing";
             }
             enum "1585.57" {
               description "1585.57 nm/189.075000 THz 3.125/6.25/12.5GHz spacing";
             }
             enum "1585.55" {
               description "1585.55 nm/189.078125 THz 3.125GHz spacing";
             }
             enum "1585.52" {
               description "1585.52 nm/189.081250 THz 3.125/6.25GHz spacing";
             }
             enum "1585.50" {
               description "1585.50 nm/189.084375 THz 3.125GHz spacing";
             }
             enum "1585.47" {
               description "1585.47 nm/189.087500 THz 3.125/6.25/12.5GHz spacing";
             }
             enum "1585.44" {
               description "1585.44 nm/189.090625 THz 3.125GHz spacing";
             }
             enum "1585.42" {
               description "1585.42 nm/189.093750 THz 3.125/6.25GHz spacing";
             }
             enum "1585.39" {
               description "1585.39 nm/189.096875 THz 3.125GHz spacing";
             }
             enum "1585.36" {
               description "1585.36 nm/189.100000 THz 3.125/6.25/12.5/100GHz spacing";
             }
             enum "1585.34" {
               description "1585.34 nm/189.103125 THz 3.125GHz spacing";
             }
             enum "1585.31" {
               description "1585.31 nm/189.106250 THz 3.125/6.25GHz spacing";
             }
             enum "1585.29" {
               description "1585.29 nm/189.109375 THz 3.125GHz spacing";
             }
             enum "1585.26" {
               description "1585.26 nm/189.112500 THz 3.125/6.25/12.5GHz spacing";
             }
             enum "1585.23" {
               description "1585.23 nm/189.115625 THz 3.125GHz spacing";
             }
             enum "1585.21" {
               description "1585.21 nm/189.118750 THz 3.125/6.25GHz spacing";
             }
             enum "1585.18" {
               description "1585.18 nm/189.121875 THz 3.125GHz spacing";
             }
             enum "1585.16" {
               description "1585.16 nm/189.125000 THz 3.125/6.25/12.5/75GHz spacing";
             }
             enum "1585.13" {
               description "1585.13 nm/189.128125 THz 3.125GHz spacing";
             }
             enum "1585.10" {
               description "1585.10 nm/189.131250 THz 3.125/6.25GHz spacing";
             }
             enum "1585.08" {
               description "1585.08 nm/189.134375 THz 3.125GHz spacing";
             }
             enum "1585.05" {
               description "1585.05 nm/189.137500 THz 3.125/6.25/12.5GHz spacing";
             }
             enum "1585.02" {
               description "1585.02 nm/189.140625 THz 3.125GHz spacing";
             }
             enum "1585.00" {
               description "1585.00 nm/189.143750 THz 3.125/6.25GHz spacing";
             }
             enum "1584.97" {
               description "1584.97 nm/189.146875 THz 3.125GHz spacing";
             }
             enum "1584.95" {
               description "1584.95 nm/189.150000 THz 3.125/6.25/12.5/50GHz spacing";
             }
             enum "1584.92" {
               description "1584.92 nm/189.153125 THz 3.125GHz spacing";
             }
             enum "1584.89" {
               description "1584.89 nm/189.156250 THz 3.125/6.25GHz spacing";
             }
             enum "1584.87" {
               description "1584.87 nm/189.159375 THz 3.125GHz spacing";
             }
             enum "1584.84" {
               description "1584.84 nm/189.162500 THz 3.125/6.25/12.5GHz spacing";
             }
             enum "1584.81" {
               description "1584.81 nm/189.165625 THz 3.125GHz spacing";
             }
             enum "1584.79" {
               description "1584.79 nm/189.168750 THz 3.125/6.25GHz spacing";
             }
             enum "1584.76" {
               description "1584.76 nm/189.171875 THz 3.125GHz spacing";
             }
             enum "1584.74" {
               description "1584.74 nm/189.175000 THz 3.125/6.25/12.5GHz spacing";
             }
             enum "1584.71" {
               description "1584.71 nm/189.178125 THz 3.125GHz spacing";
             }
             enum "1584.68" {
               description "1584.68 nm/189.181250 THz 3.125/6.25GHz spacing";
             }
             enum "1584.66" {
               description "1584.66 nm/189.184375 THz 3.125GHz spacing";
             }
             enum "1584.63" {
               description "1584.63 nm/189.187500 THz 3.125/6.25/12.5GHz spacing";
             }
             enum "1584.61" {
               description "1584.61 nm/189.190625 THz 3.125GHz spacing";
             }
             enum "1584.58" {
               description "1584.58 nm/189.193750 THz 3.125/6.25GHz spacing";
             }
             enum "1584.55" {
               description "1584.55 nm/189.196875 THz 3.125GHz spacing";
             }
             enum "1584.53" {
               description "1584.53 nm/189.200000 THz 3.125/6.25/12.5/100GHz spacing";
             }
             enum "1584.50" {
               description "1584.50 nm/189.203125 THz 3.125GHz spacing";
             }
             enum "1584.47" {
               description "1584.47 nm/189.206250 THz 3.125/6.25GHz spacing";
             }
             enum "1584.45" {
               description "1584.45 nm/189.209375 THz 3.125GHz spacing";
             }
             enum "1584.42" {
               description "1584.42 nm/189.212500 THz 3.125/6.25/12.5GHz spacing";
             }
             enum "1584.40" {
               description "1584.40 nm/189.215625 THz 3.125GHz spacing";
             }
             enum "1584.37" {
               description "1584.37 nm/189.218750 THz 3.125/6.25GHz spacing";
             }
             enum "1584.34" {
               description "1584.34 nm/189.221875 THz 3.125GHz spacing";
             }
             enum "1584.32" {
               description "1584.32 nm/189.225000 THz 3.125/6.25/12.5GHz spacing";
             }
             enum "1584.29" {
               description "1584.29 nm/189.228125 THz 3.125GHz spacing";
             }
             enum "1584.27" {
               description "1584.27 nm/189.231250 THz 3.125/6.25GHz spacing";
             }
             enum "1584.24" {
               description "1584.24 nm/189.234375 THz 3.125GHz spacing";
             }
             enum "1584.21" {
               description "1584.21 nm/189.237500 THz 3.125/6.25/12.5GHz spacing";
             }
             enum "1584.19" {
               description "1584.19 nm/189.240625 THz 3.125GHz spacing";
             }
             enum "1584.16" {
               description "1584.16 nm/189.243750 THz 3.125/6.25GHz spacing";
             }
             enum "1584.13" {
               description "1584.13 nm/189.246875 THz 3.125GHz spacing";
             }
             enum "1584.11" {
               description "1584.11 nm/189.250000 THz 3.125/6.25/12.5/50GHz spacing";
             }
             enum "1584.08" {
               description "1584.08 nm/189.253125 THz 3.125GHz spacing";
             }
             enum "1584.06" {
               description "1584.06 nm/189.256250 THz 3.125/6.25GHz spacing";
             }
             enum "1584.03" {
               description "1584.03 nm/189.259375 THz 3.125GHz spacing";
             }
             enum "1584.00" {
               description "1584.00 nm/189.262500 THz 3.125/6.25/12.5GHz spacing";
             }
             enum "1583.98" {
               description "1583.98 nm/189.265625 THz 3.125GHz spacing";
             }
             enum "1583.95" {
               description "1583.95 nm/189.268750 THz 3.125/6.25GHz spacing";
             }
             enum "1583.93" {
               description "1583.93 nm/189.271875 THz 3.125GHz spacing";
             }
             enum "1583.90" {
               description "1583.90 nm/189.275000 THz 3.125/6.25/12.5/75GHz spacing";
             }
             enum "1583.87" {
               description "1583.87 nm/189.278125 THz 3.125GHz spacing";
             }
             enum "1583.85" {
               description "1583.85 nm/189.281250 THz 3.125/6.25GHz spacing";
             }
             enum "1583.82" {
               description "1583.82 nm/189.284375 THz 3.125GHz spacing";
             }
             enum "1583.79" {
               description "1583.79 nm/189.287500 THz 3.125/6.25/12.5GHz spacing";
             }
             enum "1583.77" {
               description "1583.77 nm/189.290625 THz 3.125GHz spacing";
             }
             enum "1583.74" {
               description "1583.74 nm/189.293750 THz 3.125/6.25GHz spacing";
             }
             enum "1583.72" {
               description "1583.72 nm/189.296875 THz 3.125GHz spacing";
             }
             enum "1583.69" {
               description "1583.69 nm/189.300000 THz 3.125/6.25/12.5/50/75/100GHz spacing";
             }
             enum "1583.66" {
               description "1583.66 nm/189.303125 THz 3.125GHz spacing";
             }
             enum "1583.64" {
               description "1583.64 nm/189.306250 THz 3.125/6.25GHz spacing";
             }
             enum "1583.61" {
               description "1583.61 nm/189.309375 THz 3.125GHz spacing";
             }
             enum "1583.59" {
               description "1583.59 nm/189.312500 THz 3.125/6.25/12.5GHz spacing";
             }
             enum "1583.56" {
               description "1583.56 nm/189.315625 THz 3.125GHz spacing";
             }
             enum "1583.53" {
               description "1583.53 nm/189.318750 THz 3.125/6.25GHz spacing";
             }
             enum "1583.51" {
               description "1583.51 nm/189.321875 THz 3.125GHz spacing";
             }
             enum "1583.48" {
               description "1583.48 nm/189.325000 THz 3.125/6.25/12.5GHz spacing";
             }
             enum "1583.45" {
               description "1583.45 nm/189.328125 THz 3.125GHz spacing";
             }
             enum "1583.43" {
               description "1583.43 nm/189.331250 THz 3.125/6.25GHz spacing";
             }
             enum "1583.40" {
               description "1583.40 nm/189.334375 THz 3.125GHz spacing";
             }
             enum "1583.38" {
               description "1583.38 nm/189.337500 THz 3.125/6.25/12.5GHz spacing";
             }
             enum "1583.35" {
               description "1583.35 nm/189.340625 THz 3.125GHz spacing";
             }
             enum "1583.32" {
               description "1583.32 nm/189.343750 THz 3.125/6.25GHz spacing";
             }
             enum "1583.30" {
               description "1583.30 nm/189.346875 THz 3.125GHz spacing";
             }
             enum "1583.27" {
               description "1583.27 nm/189.350000 THz 3.125/6.25/12.5/50/75GHz spacing";
             }
             enum "1583.25" {
               description "1583.25 nm/189.353125 THz 3.125GHz spacing";
             }
             enum "1583.22" {
               description "1583.22 nm/189.356250 THz 3.125/6.25GHz spacing";
             }
             enum "1583.19" {
               description "1583.19 nm/189.359375 THz 3.125GHz spacing";
             }
             enum "1583.17" {
               description "1583.17 nm/189.362500 THz 3.125/6.25/12.5GHz spacing";
             }
             enum "1583.14" {
               description "1583.14 nm/189.365625 THz 3.125GHz spacing";
             }
             enum "1583.11" {
               description "1583.11 nm/189.368750 THz 3.125/6.25GHz spacing";
             }
             enum "1583.09" {
               description "1583.09 nm/189.371875 THz 3.125GHz spacing";
             }
             enum "1583.06" {
               description "1583.06 nm/189.375000 THz 3.125/6.25/12.5GHz spacing";
             }
             enum "1583.04" {
               description "1583.04 nm/189.378125 THz 3.125GHz spacing";
             }
             enum "1583.01" {
               description "1583.01 nm/189.381250 THz 3.125/6.25GHz spacing";
             }
             enum "1582.98" {
               description "1582.98 nm/189.384375 THz 3.125GHz spacing";
             }
             enum "1582.96" {
               description "1582.96 nm/189.387500 THz 3.125/6.25/12.5GHz spacing";
             }
             enum "1582.93" {
               description "1582.93 nm/189.390625 THz 3.125GHz spacing";
             }
             enum "1582.91" {
               description "1582.91 nm/189.393750 THz 3.125/6.25GHz spacing";
             }
             enum "1582.88" {
               description "1582.88 nm/189.396875 THz 3.125GHz spacing";
             }
             enum "1582.85" {
               description "1582.85 nm/189.400000 THz 3.125/6.25/12.5/100GHz spacing";
             }
             enum "1582.83" {
               description "1582.83 nm/189.403125 THz 3.125GHz spacing";
             }
             enum "1582.80" {
               description "1582.80 nm/189.406250 THz 3.125/6.25GHz spacing";
             }
             enum "1582.78" {
               description "1582.78 nm/189.409375 THz 3.125GHz spacing";
             }
             enum "1582.75" {
               description "1582.75 nm/189.412500 THz 3.125/6.25/12.5GHz spacing";
             }
             enum "1582.72" {
               description "1582.72 nm/189.415625 THz 3.125GHz spacing";
             }
             enum "1582.70" {
               description "1582.70 nm/189.418750 THz 3.125/6.25GHz spacing";
             }
             enum "1582.67" {
               description "1582.67 nm/189.421875 THz 3.125GHz spacing";
             }
             enum "1582.64" {
               description "1582.64 nm/189.425000 THz 3.125/6.25/12.5/75GHz spacing";
             }
             enum "1582.62" {
               description "1582.62 nm/189.428125 THz 3.125GHz spacing";
             }
             enum "1582.59" {
               description "1582.59 nm/189.431250 THz 3.125/6.25GHz spacing";
             }
             enum "1582.57" {
               description "1582.57 nm/189.434375 THz 3.125GHz spacing";
             }
             enum "1582.54" {
               description "1582.54 nm/189.437500 THz 3.125/6.25/12.5GHz spacing";
             }
             enum "1582.51" {
               description "1582.51 nm/189.440625 THz 3.125GHz spacing";
             }
             enum "1582.49" {
               description "1582.49 nm/189.443750 THz 3.125/6.25GHz spacing";
             }
             enum "1582.46" {
               description "1582.46 nm/189.446875 THz 3.125GHz spacing";
             }
             enum "1582.44" {
               description "1582.44 nm/189.450000 THz 3.125/6.25/12.5/50GHz spacing";
             }
             enum "1582.41" {
               description "1582.41 nm/189.453125 THz 3.125GHz spacing";
             }
             enum "1582.38" {
               description "1582.38 nm/189.456250 THz 3.125/6.25GHz spacing";
             }
             enum "1582.36" {
               description "1582.36 nm/189.459375 THz 3.125GHz spacing";
             }
             enum "1582.33" {
               description "1582.33 nm/189.462500 THz 3.125/6.25/12.5GHz spacing";
             }
             enum "1582.31" {
               description "1582.31 nm/189.465625 THz 3.125GHz spacing";
             }
             enum "1582.28" {
               description "1582.28 nm/189.468750 THz 3.125/6.25GHz spacing";
             }
             enum "1582.25" {
               description "1582.25 nm/189.471875 THz 3.125GHz spacing";
             }
             enum "1582.23" {
               description "1582.23 nm/189.475000 THz 3.125/6.25/12.5GHz spacing";
             }
             enum "1582.20" {
               description "1582.20 nm/189.478125 THz 3.125GHz spacing";
             }
             enum "1582.17" {
               description "1582.17 nm/189.481250 THz 3.125/6.25GHz spacing";
             }
             enum "1582.15" {
               description "1582.15 nm/189.484375 THz 3.125GHz spacing";
             }
             enum "1582.12" {
               description "1582.12 nm/189.487500 THz 3.125/6.25/12.5GHz spacing";
             }
             enum "1582.10" {
               description "1582.10 nm/189.490625 THz 3.125GHz spacing";
             }
             enum "1582.07" {
               description "1582.07 nm/189.493750 THz 3.125/6.25GHz spacing";
             }
             enum "1582.04" {
               description "1582.04 nm/189.496875 THz 3.125GHz spacing";
             }
             enum "1582.02" {
               description "1582.02 nm/189.500000 THz 3.125/6.25/12.5/100GHz spacing";
             }
             enum "1581.99" {
               description "1581.99 nm/189.503125 THz 3.125GHz spacing";
             }
             enum "1581.97" {
               description "1581.97 nm/189.506250 THz 3.125/6.25GHz spacing";
             }
             enum "1581.94" {
               description "1581.94 nm/189.509375 THz 3.125GHz spacing";
             }
             enum "1581.91" {
               description "1581.91 nm/189.512500 THz 3.125/6.25/12.5GHz spacing";
             }
             enum "1581.89" {
               description "1581.89 nm/189.515625 THz 3.125GHz spacing";
             }
             enum "1581.86" {
               description "1581.86 nm/189.518750 THz 3.125/6.25GHz spacing";
             }
             enum "1581.84" {
               description "1581.84 nm/189.521875 THz 3.125GHz spacing";
             }
             enum "1581.81" {
               description "1581.81 nm/189.525000 THz 3.125/6.25/12.5GHz spacing";
             }
             enum "1581.78" {
               description "1581.78 nm/189.528125 THz 3.125GHz spacing";
             }
             enum "1581.76" {
               description "1581.76 nm/189.531250 THz 3.125/6.25GHz spacing";
             }
             enum "1581.73" {
               description "1581.73 nm/189.534375 THz 3.125GHz spacing";
             }
             enum "1581.71" {
               description "1581.71 nm/189.537500 THz 3.125/6.25/12.5GHz spacing";
             }
             enum "1581.68" {
               description "1581.68 nm/189.540625 THz 3.125GHz spacing";
             }
             enum "1581.65" {
               description "1581.65 nm/189.543750 THz 3.125/6.25GHz spacing";
             }
             enum "1581.63" {
               description "1581.63 nm/189.546875 THz 3.125GHz spacing";
             }
             enum "1581.60" {
               description "1581.60 nm/189.550000 THz 3.125/6.25/12.5/50GHz spacing";
             }
             enum "1581.57" {
               description "1581.57 nm/189.553125 THz 3.125GHz spacing";
             }
             enum "1581.55" {
               description "1581.55 nm/189.556250 THz 3.125/6.25GHz spacing";
             }
             enum "1581.52" {
               description "1581.52 nm/189.559375 THz 3.125GHz spacing";
             }
             enum "1581.50" {
               description "1581.50 nm/189.562500 THz 3.125/6.25/12.5GHz spacing";
             }
             enum "1581.47" {
               description "1581.47 nm/189.565625 THz 3.125GHz spacing";
             }
             enum "1581.44" {
               description "1581.44 nm/189.568750 THz 3.125/6.25GHz spacing";
             }
             enum "1581.42" {
               description "1581.42 nm/189.571875 THz 3.125GHz spacing";
             }
             enum "1581.39" {
               description "1581.39 nm/189.575000 THz 3.125/6.25/12.5/75GHz spacing";
             }
             enum "1581.37" {
               description "1581.37 nm/189.578125 THz 3.125GHz spacing";
             }
             enum "1581.34" {
               description "1581.34 nm/189.581250 THz 3.125/6.25GHz spacing";
             }
             enum "1581.31" {
               description "1581.31 nm/189.584375 THz 3.125GHz spacing";
             }
             enum "1581.29" {
               description "1581.29 nm/189.587500 THz 3.125/6.25/12.5GHz spacing";
             }
             enum "1581.26" {
               description "1581.26 nm/189.590625 THz 3.125GHz spacing";
             }
             enum "1581.24" {
               description "1581.24 nm/189.593750 THz 3.125/6.25GHz spacing";
             }
             enum "1581.21" {
               description "1581.21 nm/189.596875 THz 3.125GHz spacing";
             }
             enum "1581.18" {
               description "1581.18 nm/189.600000 THz 3.125/6.25/12.5/50/75/100GHz spacing";
             }
             enum "1581.16" {
               description "1581.16 nm/189.603125 THz 3.125GHz spacing";
             }
             enum "1581.13" {
               description "1581.13 nm/189.606250 THz 3.125/6.25GHz spacing";
             }
             enum "1581.11" {
               description "1581.11 nm/189.609375 THz 3.125GHz spacing";
             }
             enum "1581.08" {
               description "1581.08 nm/189.612500 THz 3.125/6.25/12.5GHz spacing";
             }
             enum "1581.05" {
               description "1581.05 nm/189.615625 THz 3.125GHz spacing";
             }
             enum "1581.03" {
               description "1581.03 nm/189.618750 THz 3.125/6.25GHz spacing";
             }
             enum "1581.00" {
               description "1581.00 nm/189.621875 THz 3.125GHz spacing";
             }
             enum "1580.98" {
               description "1580.98 nm/189.625000 THz 3.125/6.25/12.5GHz spacing";
             }
             enum "1580.95" {
               description "1580.95 nm/189.628125 THz 3.125GHz spacing";
             }
             enum "1580.92" {
               description "1580.92 nm/189.631250 THz 3.125/6.25GHz spacing";
             }
             enum "1580.90" {
               description "1580.90 nm/189.634375 THz 3.125GHz spacing";
             }
             enum "1580.87" {
               description "1580.87 nm/189.637500 THz 3.125/6.25/12.5GHz spacing";
             }
             enum "1580.85" {
               description "1580.85 nm/189.640625 THz 3.125GHz spacing";
             }
             enum "1580.82" {
               description "1580.82 nm/189.643750 THz 3.125/6.25GHz spacing";
             }
             enum "1580.79" {
               description "1580.79 nm/189.646875 THz 3.125GHz spacing";
             }
             enum "1580.77" {
               description "1580.77 nm/189.650000 THz 3.125/6.25/12.5/50/75GHz spacing";
             }
             enum "1580.74" {
               description "1580.74 nm/189.653125 THz 3.125GHz spacing";
             }
             enum "1580.71" {
               description "1580.71 nm/189.656250 THz 3.125/6.25GHz spacing";
             }
             enum "1580.69" {
               description "1580.69 nm/189.659375 THz 3.125GHz spacing";
             }
             enum "1580.66" {
               description "1580.66 nm/189.662500 THz 3.125/6.25/12.5GHz spacing";
             }
             enum "1580.64" {
               description "1580.64 nm/189.665625 THz 3.125GHz spacing";
             }
             enum "1580.61" {
               description "1580.61 nm/189.668750 THz 3.125/6.25GHz spacing";
             }
             enum "1580.58" {
               description "1580.58 nm/189.671875 THz 3.125GHz spacing";
             }
             enum "1580.56" {
               description "1580.56 nm/189.675000 THz 3.125/6.25/12.5GHz spacing";
             }
             enum "1580.53" {
               description "1580.53 nm/189.678125 THz 3.125GHz spacing";
             }
             enum "1580.51" {
               description "1580.51 nm/189.681250 THz 3.125/6.25GHz spacing";
             }
             enum "1580.48" {
               description "1580.48 nm/189.684375 THz 3.125GHz spacing";
             }
             enum "1580.45" {
               description "1580.45 nm/189.687500 THz 3.125/6.25/12.5GHz spacing";
             }
             enum "1580.43" {
               description "1580.43 nm/189.690625 THz 3.125GHz spacing";
             }
             enum "1580.40" {
               description "1580.40 nm/189.693750 THz 3.125/6.25GHz spacing";
             }
             enum "1580.38" {
               description "1580.38 nm/189.696875 THz 3.125GHz spacing";
             }
             enum "1580.35" {
               description "1580.35 nm/189.700000 THz 3.125/6.25/12.5/100GHz spacing";
             }
             enum "1580.32" {
               description "1580.32 nm/189.703125 THz 3.125GHz spacing";
             }
             enum "1580.30" {
               description "1580.30 nm/189.706250 THz 3.125/6.25GHz spacing";
             }
             enum "1580.27" {
               description "1580.27 nm/189.709375 THz 3.125GHz spacing";
             }
             enum "1580.25" {
               description "1580.25 nm/189.712500 THz 3.125/6.25/12.5GHz spacing";
             }
             enum "1580.22" {
               description "1580.22 nm/189.715625 THz 3.125GHz spacing";
             }
             enum "1580.19" {
               description "1580.19 nm/189.718750 THz 3.125/6.25GHz spacing";
             }
             enum "1580.17" {
               description "1580.17 nm/189.721875 THz 3.125GHz spacing";
             }
             enum "1580.14" {
               description "1580.14 nm/189.725000 THz 3.125/6.25/12.5/75GHz spacing";
             }
             enum "1580.12" {
               description "1580.12 nm/189.728125 THz 3.125GHz spacing";
             }
             enum "1580.09" {
               description "1580.09 nm/189.731250 THz 3.125/6.25GHz spacing";
             }
             enum "1580.06" {
               description "1580.06 nm/189.734375 THz 3.125GHz spacing";
             }
             enum "1580.04" {
               description "1580.04 nm/189.737500 THz 3.125/6.25/12.5GHz spacing";
             }
             enum "1580.01" {
               description "1580.01 nm/189.740625 THz 3.125GHz spacing";
             }
             enum "1579.99" {
               description "1579.99 nm/189.743750 THz 3.125/6.25GHz spacing";
             }
             enum "1579.96" {
               description "1579.96 nm/189.746875 THz 3.125GHz spacing";
             }
             enum "1579.93" {
               description "1579.93 nm/189.750000 THz 3.125/6.25/12.5/50GHz spacing";
             }
             enum "1579.91" {
               description "1579.91 nm/189.753125 THz 3.125GHz spacing";
             }
             enum "1579.88" {
               description "1579.88 nm/189.756250 THz 3.125/6.25GHz spacing";
             }
             enum "1579.86" {
               description "1579.86 nm/189.759375 THz 3.125GHz spacing";
             }
             enum "1579.83" {
               description "1579.83 nm/189.762500 THz 3.125/6.25/12.5GHz spacing";
             }
             enum "1579.80" {
               description "1579.80 nm/189.765625 THz 3.125GHz spacing";
             }
             enum "1579.78" {
               description "1579.78 nm/189.768750 THz 3.125/6.25GHz spacing";
             }
             enum "1579.75" {
               description "1579.75 nm/189.771875 THz 3.125GHz spacing";
             }
             enum "1579.73" {
               description "1579.73 nm/189.775000 THz 3.125/6.25/12.5GHz spacing";
             }
             enum "1579.70" {
               description "1579.70 nm/189.778125 THz 3.125GHz spacing";
             }
             enum "1579.67" {
               description "1579.67 nm/189.781250 THz 3.125/6.25GHz spacing";
             }
             enum "1579.65" {
               description "1579.65 nm/189.784375 THz 3.125GHz spacing";
             }
             enum "1579.62" {
               description "1579.62 nm/189.787500 THz 3.125/6.25/12.5GHz spacing";
             }
             enum "1579.60" {
               description "1579.60 nm/189.790625 THz 3.125GHz spacing";
             }
             enum "1579.57" {
               description "1579.57 nm/189.793750 THz 3.125/6.25GHz spacing";
             }
             enum "1579.54" {
               description "1579.54 nm/189.796875 THz 3.125GHz spacing";
             }
             enum "1579.52" {
               description "1579.52 nm/189.800000 THz 3.125/6.25/12.5/100GHz spacing";
             }
             enum "1579.49" {
               description "1579.49 nm/189.803125 THz 3.125GHz spacing";
             }
             enum "1579.47" {
               description "1579.47 nm/189.806250 THz 3.125/6.25GHz spacing";
             }
             enum "1579.44" {
               description "1579.44 nm/189.809375 THz 3.125GHz spacing";
             }
             enum "1579.41" {
               description "1579.41 nm/189.812500 THz 3.125/6.25/12.5GHz spacing";
             }
             enum "1579.39" {
               description "1579.39 nm/189.815625 THz 3.125GHz spacing";
             }
             enum "1579.36" {
               description "1579.36 nm/189.818750 THz 3.125/6.25GHz spacing";
             }
             enum "1579.34" {
               description "1579.34 nm/189.821875 THz 3.125GHz spacing";
             }
             enum "1579.31" {
               description "1579.31 nm/189.825000 THz 3.125/6.25/12.5GHz spacing";
             }
             enum "1579.28" {
               description "1579.28 nm/189.828125 THz 3.125GHz spacing";
             }
             enum "1579.26" {
               description "1579.26 nm/189.831250 THz 3.125/6.25GHz spacing";
             }
             enum "1579.23" {
               description "1579.23 nm/189.834375 THz 3.125GHz spacing";
             }
             enum "1579.21" {
               description "1579.21 nm/189.837500 THz 3.125/6.25/12.5GHz spacing";
             }
             enum "1579.18" {
               description "1579.18 nm/189.840625 THz 3.125GHz spacing";
             }
             enum "1579.15" {
               description "1579.15 nm/189.843750 THz 3.125/6.25GHz spacing";
             }
             enum "1579.13" {
               description "1579.13 nm/189.846875 THz 3.125GHz spacing";
             }
             enum "1579.10" {
               description "1579.10 nm/189.850000 THz 3.125/6.25/12.5/50GHz spacing";
             }
             enum "1579.08" {
               description "1579.08 nm/189.853125 THz 3.125GHz spacing";
             }
             enum "1579.05" {
               description "1579.05 nm/189.856250 THz 3.125/6.25GHz spacing";
             }
             enum "1579.02" {
               description "1579.02 nm/189.859375 THz 3.125GHz spacing";
             }
             enum "1579.00" {
               description "1579.00 nm/189.862500 THz 3.125/6.25/12.5GHz spacing";
             }
             enum "1578.97" {
               description "1578.97 nm/189.865625 THz 3.125GHz spacing";
             }
             enum "1578.95" {
               description "1578.95 nm/189.868750 THz 3.125/6.25GHz spacing";
             }
             enum "1578.92" {
               description "1578.92 nm/189.871875 THz 3.125GHz spacing";
             }
             enum "1578.89" {
               description "1578.89 nm/189.875000 THz 3.125/6.25/12.5/75GHz spacing";
             }
             enum "1578.87" {
               description "1578.87 nm/189.878125 THz 3.125GHz spacing";
             }
             enum "1578.84" {
               description "1578.84 nm/189.881250 THz 3.125/6.25GHz spacing";
             }
             enum "1578.82" {
               description "1578.82 nm/189.884375 THz 3.125GHz spacing";
             }
             enum "1578.79" {
               description "1578.79 nm/189.887500 THz 3.125/6.25/12.5GHz spacing";
             }
             enum "1578.76" {
               description "1578.76 nm/189.890625 THz 3.125GHz spacing";
             }
             enum "1578.74" {
               description "1578.74 nm/189.893750 THz 3.125/6.25GHz spacing";
             }
             enum "1578.71" {
               description "1578.71 nm/189.896875 THz 3.125GHz spacing";
             }
             enum "1578.69" {
               description "1578.69 nm/189.900000 THz 3.125/6.25/12.5/50/75/100GHz spacing";
             }
             enum "1578.66" {
               description "1578.66 nm/189.903125 THz 3.125GHz spacing";
             }
             enum "1578.63" {
               description "1578.63 nm/189.906250 THz 3.125/6.25GHz spacing";
             }
             enum "1578.61" {
               description "1578.61 nm/189.909375 THz 3.125GHz spacing";
             }
             enum "1578.58" {
               description "1578.58 nm/189.912500 THz 3.125/6.25/12.5GHz spacing";
             }
             enum "1578.56" {
               description "1578.56 nm/189.915625 THz 3.125GHz spacing";
             }
             enum "1578.53" {
               description "1578.53 nm/189.918750 THz 3.125/6.25GHz spacing";
             }
             enum "1578.50" {
               description "1578.50 nm/189.921875 THz 3.125GHz spacing";
             }
             enum "1578.48" {
               description "1578.48 nm/189.925000 THz 3.125/6.25/12.5GHz spacing";
             }
             enum "1578.45" {
               description "1578.45 nm/189.928125 THz 3.125GHz spacing";
             }
             enum "1578.43" {
               description "1578.43 nm/189.931250 THz 3.125/6.25GHz spacing";
             }
             enum "1578.40" {
               description "1578.40 nm/189.934375 THz 3.125GHz spacing";
             }
             enum "1578.37" {
               description "1578.37 nm/189.937500 THz 3.125/6.25/12.5GHz spacing";
             }
             enum "1578.35" {
               description "1578.35 nm/189.940625 THz 3.125GHz spacing";
             }
             enum "1578.32" {
               description "1578.32 nm/189.943750 THz 3.125/6.25GHz spacing";
             }
             enum "1578.30" {
               description "1578.30 nm/189.946875 THz 3.125GHz spacing";
             }
             enum "1578.27" {
               description "1578.27 nm/189.950000 THz 3.125/6.25/12.5/50/75GHz spacing";
             }
             enum "1578.24" {
               description "1578.24 nm/189.953125 THz 3.125GHz spacing";
             }
             enum "1578.22" {
               description "1578.22 nm/189.956250 THz 3.125/6.25GHz spacing";
             }
             enum "1578.19" {
               description "1578.19 nm/189.959375 THz 3.125GHz spacing";
             }
             enum "1578.17" {
               description "1578.17 nm/189.962500 THz 3.125/6.25/12.5GHz spacing";
             }
             enum "1578.14" {
               description "1578.14 nm/189.965625 THz 3.125GHz spacing";
             }
             enum "1578.11" {
               description "1578.11 nm/189.968750 THz 3.125/6.25GHz spacing";
             }
             enum "1578.09" {
               description "1578.09 nm/189.971875 THz 3.125GHz spacing";
             }
             enum "1578.06" {
               description "1578.06 nm/189.975000 THz 3.125/6.25/12.5GHz spacing";
             }
             enum "1578.04" {
               description "1578.04 nm/189.978125 THz 3.125GHz spacing";
             }
             enum "1578.01" {
               description "1578.01 nm/189.981250 THz 3.125/6.25GHz spacing";
             }
             enum "1577.98" {
               description "1577.98 nm/189.984375 THz 3.125GHz spacing";
             }
             enum "1577.96" {
               description "1577.96 nm/189.987500 THz 3.125/6.25/12.5GHz spacing";
             }
             enum "1577.93" {
               description "1577.93 nm/189.990625 THz 3.125GHz spacing";
             }
             enum "1577.91" {
               description "1577.91 nm/189.993750 THz 3.125/6.25GHz spacing";
             }
             enum "1577.88" {
               description "1577.88 nm/189.996875 THz 3.125GHz spacing";
             }
             enum "1577.86" {
               description "1577.86 nm/190.000000 THz 3.125/6.25/12.5/100GHz spacing";
             }
             enum "1577.83" {
               description "1577.83 nm/190.003125 THz 3.125GHz spacing";
             }
             enum "1577.80" {
               description "1577.80 nm/190.006250 THz 3.125/6.25GHz spacing";
             }
             enum "1577.78" {
               description "1577.78 nm/190.009375 THz 3.125GHz spacing";
             }
             enum "1577.75" {
               description "1577.75 nm/190.012500 THz 3.125/6.25/12.5GHz spacing";
             }
             enum "1577.73" {
               description "1577.73 nm/190.015625 THz 3.125GHz spacing";
             }
             enum "1577.70" {
               description "1577.70 nm/190.018750 THz 3.125/6.25GHz spacing";
             }
             enum "1577.67" {
               description "1577.67 nm/190.021875 THz 3.125GHz spacing";
             }
             enum "1577.65" {
               description "1577.65 nm/190.025000 THz 3.125/6.25/12.5/75GHz spacing";
             }
             enum "1577.62" {
               description "1577.62 nm/190.028125 THz 3.125GHz spacing";
             }
             enum "1577.60" {
               description "1577.60 nm/190.031250 THz 3.125/6.25GHz spacing";
             }
             enum "1577.57" {
               description "1577.57 nm/190.034375 THz 3.125GHz spacing";
             }
             enum "1577.54" {
               description "1577.54 nm/190.037500 THz 3.125/6.25/12.5GHz spacing";
             }
             enum "1577.52" {
               description "1577.52 nm/190.040625 THz 3.125GHz spacing";
             }
             enum "1577.49" {
               description "1577.49 nm/190.043750 THz 3.125/6.25GHz spacing";
             }
             enum "1577.47" {
               description "1577.47 nm/190.046875 THz 3.125GHz spacing";
             }
             enum "1577.44" {
               description "1577.44 nm/190.050000 THz 3.125/6.25/12.5/50GHz spacing";
             }
             enum "1577.41" {
               description "1577.41 nm/190.053125 THz 3.125GHz spacing";
             }
             enum "1577.39" {
               description "1577.39 nm/190.056250 THz 3.125/6.25GHz spacing";
             }
             enum "1577.36" {
               description "1577.36 nm/190.059375 THz 3.125GHz spacing";
             }
             enum "1577.34" {
               description "1577.34 nm/190.062500 THz 3.125/6.25/12.5GHz spacing";
             }
             enum "1577.31" {
               description "1577.31 nm/190.065625 THz 3.125GHz spacing";
             }
             enum "1577.28" {
               description "1577.28 nm/190.068750 THz 3.125/6.25GHz spacing";
             }
             enum "1577.26" {
               description "1577.26 nm/190.071875 THz 3.125GHz spacing";
             }
             enum "1577.23" {
               description "1577.23 nm/190.075000 THz 3.125/6.25/12.5GHz spacing";
             }
             enum "1577.21" {
               description "1577.21 nm/190.078125 THz 3.125GHz spacing";
             }
             enum "1577.18" {
               description "1577.18 nm/190.081250 THz 3.125/6.25GHz spacing";
             }
             enum "1577.15" {
               description "1577.15 nm/190.084375 THz 3.125GHz spacing";
             }
             enum "1577.13" {
               description "1577.13 nm/190.087500 THz 3.125/6.25/12.5GHz spacing";
             }
             enum "1577.10" {
               description "1577.10 nm/190.090625 THz 3.125GHz spacing";
             }
             enum "1577.08" {
               description "1577.08 nm/190.093750 THz 3.125/6.25GHz spacing";
             }
             enum "1577.05" {
               description "1577.05 nm/190.096875 THz 3.125GHz spacing";
             }
             enum "1577.03" {
               description "1577.03 nm/190.100000 THz 3.125/6.25/12.5/100GHz spacing";
             }
             enum "1577.00" {
               description "1577.00 nm/190.103125 THz 3.125GHz spacing";
             }
             enum "1576.97" {
               description "1576.97 nm/190.106250 THz 3.125/6.25GHz spacing";
             }
             enum "1576.95" {
               description "1576.95 nm/190.109375 THz 3.125GHz spacing";
             }
             enum "1576.92" {
               description "1576.92 nm/190.112500 THz 3.125/6.25/12.5GHz spacing";
             }
             enum "1576.90" {
               description "1576.90 nm/190.115625 THz 3.125GHz spacing";
             }
             enum "1576.87" {
               description "1576.87 nm/190.118750 THz 3.125/6.25GHz spacing";
             }
             enum "1576.84" {
               description "1576.84 nm/190.121875 THz 3.125GHz spacing";
             }
             enum "1576.82" {
               description "1576.82 nm/190.125000 THz 3.125/6.25/12.5GHz spacing";
             }
             enum "1576.79" {
               description "1576.79 nm/190.128125 THz 3.125GHz spacing";
             }
             enum "1576.77" {
               description "1576.77 nm/190.131250 THz 3.125/6.25GHz spacing";
             }
             enum "1576.74" {
               description "1576.74 nm/190.134375 THz 3.125GHz spacing";
             }
             enum "1576.71" {
               description "1576.71 nm/190.137500 THz 3.125/6.25/12.5GHz spacing";
             }
             enum "1576.69" {
               description "1576.69 nm/190.140625 THz 3.125GHz spacing";
             }
             enum "1576.66" {
               description "1576.66 nm/190.143750 THz 3.125/6.25GHz spacing";
             }
             enum "1576.64" {
               description "1576.64 nm/190.146875 THz 3.125GHz spacing";
             }
             enum "1576.61" {
               description "1576.61 nm/190.150000 THz 3.125/6.25/12.5/50GHz spacing";
             }
             enum "1576.58" {
               description "1576.58 nm/190.153125 THz 3.125GHz spacing";
             }
             enum "1576.56" {
               description "1576.56 nm/190.156250 THz 3.125/6.25GHz spacing";
             }
             enum "1576.53" {
               description "1576.53 nm/190.159375 THz 3.125GHz spacing";
             }
             enum "1576.51" {
               description "1576.51 nm/190.162500 THz 3.125/6.25/12.5GHz spacing";
             }
             enum "1576.48" {
               description "1576.48 nm/190.165625 THz 3.125GHz spacing";
             }
             enum "1576.45" {
               description "1576.45 nm/190.168750 THz 3.125/6.25GHz spacing";
             }
             enum "1576.43" {
               description "1576.43 nm/190.171875 THz 3.125GHz spacing";
             }
             enum "1576.40" {
               description "1576.40 nm/190.175000 THz 3.125/6.25/12.5/75GHz spacing";
             }
             enum "1576.38" {
               description "1576.38 nm/190.178125 THz 3.125GHz spacing";
             }
             enum "1576.35" {
               description "1576.35 nm/190.181250 THz 3.125/6.25GHz spacing";
             }
             enum "1576.33" {
               description "1576.33 nm/190.184375 THz 3.125GHz spacing";
             }
             enum "1576.30" {
               description "1576.30 nm/190.187500 THz 3.125/6.25/12.5GHz spacing";
             }
             enum "1576.27" {
               description "1576.27 nm/190.190625 THz 3.125GHz spacing";
             }
             enum "1576.25" {
               description "1576.25 nm/190.193750 THz 3.125/6.25GHz spacing";
             }
             enum "1576.22" {
               description "1576.22 nm/190.196875 THz 3.125GHz spacing";
             }
             enum "1576.20" {
               description "1576.20 nm/190.200000 THz 3.125/6.25/12.5/50/75/100GHz spacing";
             }
             enum "1576.17" {
               description "1576.17 nm/190.203125 THz 3.125GHz spacing";
             }
             enum "1576.14" {
               description "1576.14 nm/190.206250 THz 3.125/6.25GHz spacing";
             }
             enum "1576.12" {
               description "1576.12 nm/190.209375 THz 3.125GHz spacing";
             }
             enum "1576.09" {
               description "1576.09 nm/190.212500 THz 3.125/6.25/12.5GHz spacing";
             }
             enum "1576.07" {
               description "1576.07 nm/190.215625 THz 3.125GHz spacing";
             }
             enum "1576.04" {
               description "1576.04 nm/190.218750 THz 3.125/6.25GHz spacing";
             }
             enum "1576.01" {
               description "1576.01 nm/190.221875 THz 3.125GHz spacing";
             }
             enum "1575.99" {
               description "1575.99 nm/190.225000 THz 3.125/6.25/12.5GHz spacing";
             }
             enum "1575.96" {
               description "1575.96 nm/190.228125 THz 3.125GHz spacing";
             }
             enum "1575.94" {
               description "1575.94 nm/190.231250 THz 3.125/6.25GHz spacing";
             }
             enum "1575.91" {
               description "1575.91 nm/190.234375 THz 3.125GHz spacing";
             }
             enum "1575.89" {
               description "1575.89 nm/190.237500 THz 3.125/6.25/12.5GHz spacing";
             }
             enum "1575.86" {
               description "1575.86 nm/190.240625 THz 3.125GHz spacing";
             }
             enum "1575.83" {
               description "1575.83 nm/190.243750 THz 3.125/6.25GHz spacing";
             }
             enum "1575.81" {
               description "1575.81 nm/190.246875 THz 3.125GHz spacing";
             }
             enum "1575.78" {
               description "1575.78 nm/190.250000 THz 3.125/6.25/12.5/50/75GHz spacing";
             }
             enum "1575.76" {
               description "1575.76 nm/190.253125 THz 3.125GHz spacing";
             }
             enum "1575.73" {
               description "1575.73 nm/190.256250 THz 3.125/6.25GHz spacing";
             }
             enum "1575.70" {
               description "1575.70 nm/190.259375 THz 3.125GHz spacing";
             }
             enum "1575.68" {
               description "1575.68 nm/190.262500 THz 3.125/6.25/12.5GHz spacing";
             }
             enum "1575.65" {
               description "1575.65 nm/190.265625 THz 3.125GHz spacing";
             }
             enum "1575.63" {
               description "1575.63 nm/190.268750 THz 3.125/6.25GHz spacing";
             }
             enum "1575.60" {
               description "1575.60 nm/190.271875 THz 3.125GHz spacing";
             }
             enum "1575.57" {
               description "1575.57 nm/190.275000 THz 3.125/6.25/12.5GHz spacing";
             }
             enum "1575.55" {
               description "1575.55 nm/190.278125 THz 3.125GHz spacing";
             }
             enum "1575.52" {
               description "1575.52 nm/190.281250 THz 3.125/6.25GHz spacing";
             }
             enum "1575.50" {
               description "1575.50 nm/190.284375 THz 3.125GHz spacing";
             }
             enum "1575.47" {
               description "1575.47 nm/190.287500 THz 3.125/6.25/12.5GHz spacing";
             }
             enum "1575.45" {
               description "1575.45 nm/190.290625 THz 3.125GHz spacing";
             }
             enum "1575.42" {
               description "1575.42 nm/190.293750 THz 3.125/6.25GHz spacing";
             }
             enum "1575.39" {
               description "1575.39 nm/190.296875 THz 3.125GHz spacing";
             }
             enum "1575.37" {
               description "1575.37 nm/190.300000 THz 3.125/6.25/12.5/100GHz spacing";
             }
             enum "1575.34" {
               description "1575.34 nm/190.303125 THz 3.125GHz spacing";
             }
             enum "1575.32" {
               description "1575.32 nm/190.306250 THz 3.125/6.25GHz spacing";
             }
             enum "1575.29" {
               description "1575.29 nm/190.309375 THz 3.125GHz spacing";
             }
             enum "1575.26" {
               description "1575.26 nm/190.312500 THz 3.125/6.25/12.5GHz spacing";
             }
             enum "1575.24" {
               description "1575.24 nm/190.315625 THz 3.125GHz spacing";
             }
             enum "1575.21" {
               description "1575.21 nm/190.318750 THz 3.125/6.25GHz spacing";
             }
             enum "1575.19" {
               description "1575.19 nm/190.321875 THz 3.125GHz spacing";
             }
             enum "1575.16" {
               description "1575.16 nm/190.325000 THz 3.125/6.25/12.5/75GHz spacing";
             }
             enum "1575.13" {
               description "1575.13 nm/190.328125 THz 3.125GHz spacing";
             }
             enum "1575.11" {
               description "1575.11 nm/190.331250 THz 3.125/6.25GHz spacing";
             }
             enum "1575.08" {
               description "1575.08 nm/190.334375 THz 3.125GHz spacing";
             }
             enum "1575.06" {
               description "1575.06 nm/190.337500 THz 3.125/6.25/12.5GHz spacing";
             }
             enum "1575.03" {
               description "1575.03 nm/190.340625 THz 3.125GHz spacing";
             }
             enum "1575.01" {
               description "1575.01 nm/190.343750 THz 3.125/6.25GHz spacing";
             }
             enum "1574.98" {
               description "1574.98 nm/190.346875 THz 3.125GHz spacing";
             }
             enum "1574.95" {
               description "1574.95 nm/190.350000 THz 3.125/6.25/12.5/50GHz spacing";
             }
             enum "1574.93" {
               description "1574.93 nm/190.353125 THz 3.125GHz spacing";
             }
             enum "1574.90" {
               description "1574.90 nm/190.356250 THz 3.125/6.25GHz spacing";
             }
             enum "1574.88" {
               description "1574.88 nm/190.359375 THz 3.125GHz spacing";
             }
             enum "1574.85" {
               description "1574.85 nm/190.362500 THz 3.125/6.25/12.5GHz spacing";
             }
             enum "1574.82" {
               description "1574.82 nm/190.365625 THz 3.125GHz spacing";
             }
             enum "1574.80" {
               description "1574.80 nm/190.368750 THz 3.125/6.25GHz spacing";
             }
             enum "1574.77" {
               description "1574.77 nm/190.371875 THz 3.125GHz spacing";
             }
             enum "1574.75" {
               description "1574.75 nm/190.375000 THz 3.125/6.25/12.5GHz spacing";
             }
             enum "1574.72" {
               description "1574.72 nm/190.378125 THz 3.125GHz spacing";
             }
             enum "1574.70" {
               description "1574.70 nm/190.381250 THz 3.125/6.25GHz spacing";
             }
             enum "1574.67" {
               description "1574.67 nm/190.384375 THz 3.125GHz spacing";
             }
             enum "1574.64" {
               description "1574.64 nm/190.387500 THz 3.125/6.25/12.5GHz spacing";
             }
             enum "1574.62" {
               description "1574.62 nm/190.390625 THz 3.125GHz spacing";
             }
             enum "1574.59" {
               description "1574.59 nm/190.393750 THz 3.125/6.25GHz spacing";
             }
             enum "1574.57" {
               description "1574.57 nm/190.396875 THz 3.125GHz spacing";
             }
             enum "1574.54" {
               description "1574.54 nm/190.400000 THz 3.125/6.25/12.5/100GHz spacing";
             }
             enum "1574.51" {
               description "1574.51 nm/190.403125 THz 3.125GHz spacing";
             }
             enum "1574.49" {
               description "1574.49 nm/190.406250 THz 3.125/6.25GHz spacing";
             }
             enum "1574.46" {
               description "1574.46 nm/190.409375 THz 3.125GHz spacing";
             }
             enum "1574.44" {
               description "1574.44 nm/190.412500 THz 3.125/6.25/12.5GHz spacing";
             }
             enum "1574.41" {
               description "1574.41 nm/190.415625 THz 3.125GHz spacing";
             }
             enum "1574.39" {
               description "1574.39 nm/190.418750 THz 3.125/6.25GHz spacing";
             }
             enum "1574.36" {
               description "1574.36 nm/190.421875 THz 3.125GHz spacing";
             }
             enum "1574.33" {
               description "1574.33 nm/190.425000 THz 3.125/6.25/12.5GHz spacing";
             }
             enum "1574.31" {
               description "1574.31 nm/190.428125 THz 3.125GHz spacing";
             }
             enum "1574.28" {
               description "1574.28 nm/190.431250 THz 3.125/6.25GHz spacing";
             }
             enum "1574.26" {
               description "1574.26 nm/190.434375 THz 3.125GHz spacing";
             }
             enum "1574.23" {
               description "1574.23 nm/190.437500 THz 3.125/6.25/12.5GHz spacing";
             }
             enum "1574.20" {
               description "1574.20 nm/190.440625 THz 3.125GHz spacing";
             }
             enum "1574.18" {
               description "1574.18 nm/190.443750 THz 3.125/6.25GHz spacing";
             }
             enum "1574.15" {
               description "1574.15 nm/190.446875 THz 3.125GHz spacing";
             }
             enum "1574.13" {
               description "1574.13 nm/190.450000 THz 3.125/6.25/12.5/50GHz spacing";
             }
             enum "1574.10" {
               description "1574.10 nm/190.453125 THz 3.125GHz spacing";
             }
             enum "1574.08" {
               description "1574.08 nm/190.456250 THz 3.125/6.25GHz spacing";
             }
             enum "1574.05" {
               description "1574.05 nm/190.459375 THz 3.125GHz spacing";
             }
             enum "1574.02" {
               description "1574.02 nm/190.462500 THz 3.125/6.25/12.5GHz spacing";
             }
             enum "1574.00" {
               description "1574.00 nm/190.465625 THz 3.125GHz spacing";
             }
             enum "1573.97" {
               description "1573.97 nm/190.468750 THz 3.125/6.25GHz spacing";
             }
             enum "1573.95" {
               description "1573.95 nm/190.471875 THz 3.125GHz spacing";
             }
             enum "1573.92" {
               description "1573.92 nm/190.475000 THz 3.125/6.25/12.5/75GHz spacing";
             }
             enum "1573.89" {
               description "1573.89 nm/190.478125 THz 3.125GHz spacing";
             }
             enum "1573.87" {
               description "1573.87 nm/190.481250 THz 3.125/6.25GHz spacing";
             }
             enum "1573.84" {
               description "1573.84 nm/190.484375 THz 3.125GHz spacing";
             }
             enum "1573.82" {
               description "1573.82 nm/190.487500 THz 3.125/6.25/12.5GHz spacing";
             }
             enum "1573.79" {
               description "1573.79 nm/190.490625 THz 3.125GHz spacing";
             }
             enum "1573.77" {
               description "1573.77 nm/190.493750 THz 3.125/6.25GHz spacing";
             }
             enum "1573.74" {
               description "1573.74 nm/190.496875 THz 3.125GHz spacing";
             }
             enum "1573.71" {
               description "1573.71 nm/190.500000 THz 3.125/6.25/12.5/50/75/100GHz spacing";
             }
             enum "1573.69" {
               description "1573.69 nm/190.503125 THz 3.125GHz spacing";
             }
             enum "1573.66" {
               description "1573.66 nm/190.506250 THz 3.125/6.25GHz spacing";
             }
             enum "1573.64" {
               description "1573.64 nm/190.509375 THz 3.125GHz spacing";
             }
             enum "1573.61" {
               description "1573.61 nm/190.512500 THz 3.125/6.25/12.5GHz spacing";
             }
             enum "1573.58" {
               description "1573.58 nm/190.515625 THz 3.125GHz spacing";
             }
             enum "1573.56" {
               description "1573.56 nm/190.518750 THz 3.125/6.25GHz spacing";
             }
             enum "1573.53" {
               description "1573.53 nm/190.521875 THz 3.125GHz spacing";
             }
             enum "1573.51" {
               description "1573.51 nm/190.525000 THz 3.125/6.25/12.5GHz spacing";
             }
             enum "1573.48" {
               description "1573.48 nm/190.528125 THz 3.125GHz spacing";
             }
             enum "1573.46" {
               description "1573.46 nm/190.531250 THz 3.125/6.25GHz spacing";
             }
             enum "1573.43" {
               description "1573.43 nm/190.534375 THz 3.125GHz spacing";
             }
             enum "1573.40" {
               description "1573.40 nm/190.537500 THz 3.125/6.25/12.5GHz spacing";
             }
             enum "1573.38" {
               description "1573.38 nm/190.540625 THz 3.125GHz spacing";
             }
             enum "1573.35" {
               description "1573.35 nm/190.543750 THz 3.125/6.25GHz spacing";
             }
             enum "1573.33" {
               description "1573.33 nm/190.546875 THz 3.125GHz spacing";
             }
             enum "1573.30" {
               description "1573.30 nm/190.550000 THz 3.125/6.25/12.5/50/75GHz spacing";
             }
             enum "1573.27" {
               description "1573.27 nm/190.553125 THz 3.125GHz spacing";
             }
             enum "1573.25" {
               description "1573.25 nm/190.556250 THz 3.125/6.25GHz spacing";
             }
             enum "1573.22" {
               description "1573.22 nm/190.559375 THz 3.125GHz spacing";
             }
             enum "1573.20" {
               description "1573.20 nm/190.562500 THz 3.125/6.25/12.5GHz spacing";
             }
             enum "1573.17" {
               description "1573.17 nm/190.565625 THz 3.125GHz spacing";
             }
             enum "1573.15" {
               description "1573.15 nm/190.568750 THz 3.125/6.25GHz spacing";
             }
             enum "1573.12" {
               description "1573.12 nm/190.571875 THz 3.125GHz spacing";
             }
             enum "1573.09" {
               description "1573.09 nm/190.575000 THz 3.125/6.25/12.5GHz spacing";
             }
             enum "1573.07" {
               description "1573.07 nm/190.578125 THz 3.125GHz spacing";
             }
             enum "1573.04" {
               description "1573.04 nm/190.581250 THz 3.125/6.25GHz spacing";
             }
             enum "1573.02" {
               description "1573.02 nm/190.584375 THz 3.125GHz spacing";
             }
             enum "1572.99" {
               description "1572.99 nm/190.587500 THz 3.125/6.25/12.5GHz spacing";
             }
             enum "1572.97" {
               description "1572.97 nm/190.590625 THz 3.125GHz spacing";
             }
             enum "1572.94" {
               description "1572.94 nm/190.593750 THz 3.125/6.25GHz spacing";
             }
             enum "1572.91" {
               description "1572.91 nm/190.596875 THz 3.125GHz spacing";
             }
             enum "1572.89" {
               description "1572.89 nm/190.600000 THz 3.125/6.25/12.5/100GHz spacing";
             }
             enum "1572.86" {
               description "1572.86 nm/190.603125 THz 3.125GHz spacing";
             }
             enum "1572.84" {
               description "1572.84 nm/190.606250 THz 3.125/6.25GHz spacing";
             }
             enum "1572.81" {
               description "1572.81 nm/190.609375 THz 3.125GHz spacing";
             }
             enum "1572.78" {
               description "1572.78 nm/190.612500 THz 3.125/6.25/12.5GHz spacing";
             }
             enum "1572.76" {
               description "1572.76 nm/190.615625 THz 3.125GHz spacing";
             }
             enum "1572.73" {
               description "1572.73 nm/190.618750 THz 3.125/6.25GHz spacing";
             }
             enum "1572.71" {
               description "1572.71 nm/190.621875 THz 3.125GHz spacing";
             }
             enum "1572.68" {
               description "1572.68 nm/190.625000 THz 3.125/6.25/12.5/75GHz spacing";
             }
             enum "1572.66" {
               description "1572.66 nm/190.628125 THz 3.125GHz spacing";
             }
             enum "1572.63" {
               description "1572.63 nm/190.631250 THz 3.125/6.25GHz spacing";
             }
             enum "1572.60" {
               description "1572.60 nm/190.634375 THz 3.125GHz spacing";
             }
             enum "1572.58" {
               description "1572.58 nm/190.637500 THz 3.125/6.25/12.5GHz spacing";
             }
             enum "1572.55" {
               description "1572.55 nm/190.640625 THz 3.125GHz spacing";
             }
             enum "1572.53" {
               description "1572.53 nm/190.643750 THz 3.125/6.25GHz spacing";
             }
             enum "1572.50" {
               description "1572.50 nm/190.646875 THz 3.125GHz spacing";
             }
             enum "1572.48" {
               description "1572.48 nm/190.650000 THz 3.125/6.25/12.5/50GHz spacing";
             }
             enum "1572.45" {
               description "1572.45 nm/190.653125 THz 3.125GHz spacing";
             }
             enum "1572.42" {
               description "1572.42 nm/190.656250 THz 3.125/6.25GHz spacing";
             }
             enum "1572.40" {
               description "1572.40 nm/190.659375 THz 3.125GHz spacing";
             }
             enum "1572.37" {
               description "1572.37 nm/190.662500 THz 3.125/6.25/12.5GHz spacing";
             }
             enum "1572.35" {
               description "1572.35 nm/190.665625 THz 3.125GHz spacing";
             }
             enum "1572.32" {
               description "1572.32 nm/190.668750 THz 3.125/6.25GHz spacing";
             }
             enum "1572.30" {
               description "1572.30 nm/190.671875 THz 3.125GHz spacing";
             }
             enum "1572.27" {
               description "1572.27 nm/190.675000 THz 3.125/6.25/12.5GHz spacing";
             }
             enum "1572.24" {
               description "1572.24 nm/190.678125 THz 3.125GHz spacing";
             }
             enum "1572.22" {
               description "1572.22 nm/190.681250 THz 3.125/6.25GHz spacing";
             }
             enum "1572.19" {
               description "1572.19 nm/190.684375 THz 3.125GHz spacing";
             }
             enum "1572.17" {
               description "1572.17 nm/190.687500 THz 3.125/6.25/12.5GHz spacing";
             }
             enum "1572.14" {
               description "1572.14 nm/190.690625 THz 3.125GHz spacing";
             }
             enum "1572.11" {
               description "1572.11 nm/190.693750 THz 3.125/6.25GHz spacing";
             }
             enum "1572.09" {
               description "1572.09 nm/190.696875 THz 3.125GHz spacing";
             }
             enum "1572.06" {
               description "1572.06 nm/190.700000 THz 3.125/6.25/12.5/100GHz spacing";
             }
             enum "1572.04" {
               description "1572.04 nm/190.703125 THz 3.125GHz spacing";
             }
             enum "1572.01" {
               description "1572.01 nm/190.706250 THz 3.125/6.25GHz spacing";
             }
             enum "1571.99" {
               description "1571.99 nm/190.709375 THz 3.125GHz spacing";
             }
             enum "1571.96" {
               description "1571.96 nm/190.712500 THz 3.125/6.25/12.5GHz spacing";
             }
             enum "1571.93" {
               description "1571.93 nm/190.715625 THz 3.125GHz spacing";
             }
             enum "1571.91" {
               description "1571.91 nm/190.718750 THz 3.125/6.25GHz spacing";
             }
             enum "1571.88" {
               description "1571.88 nm/190.721875 THz 3.125GHz spacing";
             }
             enum "1571.86" {
               description "1571.86 nm/190.725000 THz 3.125/6.25/12.5GHz spacing";
             }
             enum "1571.83" {
               description "1571.83 nm/190.728125 THz 3.125GHz spacing";
             }
             enum "1571.81" {
               description "1571.81 nm/190.731250 THz 3.125/6.25GHz spacing";
             }
             enum "1571.78" {
               description "1571.78 nm/190.734375 THz 3.125GHz spacing";
             }
             enum "1571.75" {
               description "1571.75 nm/190.737500 THz 3.125/6.25/12.5GHz spacing";
             }
             enum "1571.73" {
               description "1571.73 nm/190.740625 THz 3.125GHz spacing";
             }
             enum "1571.70" {
               description "1571.70 nm/190.743750 THz 3.125/6.25GHz spacing";
             }
             enum "1571.68" {
               description "1571.68 nm/190.746875 THz 3.125GHz spacing";
             }
             enum "1571.65" {
               description "1571.65 nm/190.750000 THz 3.125/6.25/12.5/50GHz spacing";
             }
             enum "1571.63" {
               description "1571.63 nm/190.753125 THz 3.125GHz spacing";
             }
             enum "1571.60" {
               description "1571.60 nm/190.756250 THz 3.125/6.25GHz spacing";
             }
             enum "1571.57" {
               description "1571.57 nm/190.759375 THz 3.125GHz spacing";
             }
             enum "1571.55" {
               description "1571.55 nm/190.762500 THz 3.125/6.25/12.5GHz spacing";
             }
             enum "1571.52" {
               description "1571.52 nm/190.765625 THz 3.125GHz spacing";
             }
             enum "1571.50" {
               description "1571.50 nm/190.768750 THz 3.125/6.25GHz spacing";
             }
             enum "1571.47" {
               description "1571.47 nm/190.771875 THz 3.125GHz spacing";
             }
             enum "1571.45" {
               description "1571.45 nm/190.775000 THz 3.125/6.25/12.5/75GHz spacing";
             }
             enum "1571.42" {
               description "1571.42 nm/190.778125 THz 3.125GHz spacing";
             }
             enum "1571.39" {
               description "1571.39 nm/190.781250 THz 3.125/6.25GHz spacing";
             }
             enum "1571.37" {
               description "1571.37 nm/190.784375 THz 3.125GHz spacing";
             }
             enum "1571.34" {
               description "1571.34 nm/190.787500 THz 3.125/6.25/12.5GHz spacing";
             }
             enum "1571.32" {
               description "1571.32 nm/190.790625 THz 3.125GHz spacing";
             }
             enum "1571.29" {
               description "1571.29 nm/190.793750 THz 3.125/6.25GHz spacing";
             }
             enum "1571.27" {
               description "1571.27 nm/190.796875 THz 3.125GHz spacing";
             }
             enum "1571.24" {
               description "1571.24 nm/190.800000 THz 3.125/6.25/12.5/50/75/100GHz spacing";
             }
             enum "1571.21" {
               description "1571.21 nm/190.803125 THz 3.125GHz spacing";
             }
             enum "1571.19" {
               description "1571.19 nm/190.806250 THz 3.125/6.25GHz spacing";
             }
             enum "1571.16" {
               description "1571.16 nm/190.809375 THz 3.125GHz spacing";
             }
             enum "1571.14" {
               description "1571.14 nm/190.812500 THz 3.125/6.25/12.5GHz spacing";
             }
             enum "1571.11" {
               description "1571.11 nm/190.815625 THz 3.125GHz spacing";
             }
             enum "1571.08" {
               description "1571.08 nm/190.818750 THz 3.125/6.25GHz spacing";
             }
             enum "1571.06" {
               description "1571.06 nm/190.821875 THz 3.125GHz spacing";
             }
             enum "1571.03" {
               description "1571.03 nm/190.825000 THz 3.125/6.25/12.5GHz spacing";
             }
             enum "1571.01" {
               description "1571.01 nm/190.828125 THz 3.125GHz spacing";
             }
             enum "1570.98" {
               description "1570.98 nm/190.831250 THz 3.125/6.25GHz spacing";
             }
             enum "1570.96" {
               description "1570.96 nm/190.834375 THz 3.125GHz spacing";
             }
             enum "1570.93" {
               description "1570.93 nm/190.837500 THz 3.125/6.25/12.5GHz spacing";
             }
             enum "1570.90" {
               description "1570.90 nm/190.840625 THz 3.125GHz spacing";
             }
             enum "1570.88" {
               description "1570.88 nm/190.843750 THz 3.125/6.25GHz spacing";
             }
             enum "1570.85" {
               description "1570.85 nm/190.846875 THz 3.125GHz spacing";
             }
             enum "1570.83" {
               description "1570.83 nm/190.850000 THz 3.125/6.25/12.5/50/75GHz spacing";
             }
             enum "1570.80" {
               description "1570.80 nm/190.853125 THz 3.125GHz spacing";
             }
             enum "1570.78" {
               description "1570.78 nm/190.856250 THz 3.125/6.25GHz spacing";
             }
             enum "1570.75" {
               description "1570.75 nm/190.859375 THz 3.125GHz spacing";
             }
             enum "1570.72" {
               description "1570.72 nm/190.862500 THz 3.125/6.25/12.5GHz spacing";
             }
             enum "1570.70" {
               description "1570.70 nm/190.865625 THz 3.125GHz spacing";
             }
             enum "1570.67" {
               description "1570.67 nm/190.868750 THz 3.125/6.25GHz spacing";
             }
             enum "1570.65" {
               description "1570.65 nm/190.871875 THz 3.125GHz spacing";
             }
             enum "1570.62" {
               description "1570.62 nm/190.875000 THz 3.125/6.25/12.5GHz spacing";
             }
             enum "1570.60" {
               description "1570.60 nm/190.878125 THz 3.125GHz spacing";
             }
             enum "1570.57" {
               description "1570.57 nm/190.881250 THz 3.125/6.25GHz spacing";
             }
             enum "1570.54" {
               description "1570.54 nm/190.884375 THz 3.125GHz spacing";
             }
             enum "1570.52" {
               description "1570.52 nm/190.887500 THz 3.125/6.25/12.5GHz spacing";
             }
             enum "1570.49" {
               description "1570.49 nm/190.890625 THz 3.125GHz spacing";
             }
             enum "1570.47" {
               description "1570.47 nm/190.893750 THz 3.125/6.25GHz spacing";
             }
             enum "1570.44" {
               description "1570.44 nm/190.896875 THz 3.125GHz spacing";
             }
             enum "1570.42" {
               description "1570.42 nm/190.900000 THz 3.125/6.25/12.5/100GHz spacing";
             }
             enum "1570.39" {
               description "1570.39 nm/190.903125 THz 3.125GHz spacing";
             }
             enum "1570.36" {
               description "1570.36 nm/190.906250 THz 3.125/6.25GHz spacing";
             }
             enum "1570.34" {
               description "1570.34 nm/190.909375 THz 3.125GHz spacing";
             }
             enum "1570.31" {
               description "1570.31 nm/190.912500 THz 3.125/6.25/12.5GHz spacing";
             }
             enum "1570.29" {
               description "1570.29 nm/190.915625 THz 3.125GHz spacing";
             }
             enum "1570.26" {
               description "1570.26 nm/190.918750 THz 3.125/6.25GHz spacing";
             }
             enum "1570.24" {
               description "1570.24 nm/190.921875 THz 3.125GHz spacing";
             }
             enum "1570.21" {
               description "1570.21 nm/190.925000 THz 3.125/6.25/12.5/75GHz spacing";
             }
             enum "1570.18" {
               description "1570.18 nm/190.928125 THz 3.125GHz spacing";
             }
             enum "1570.16" {
               description "1570.16 nm/190.931250 THz 3.125/6.25GHz spacing";
             }
             enum "1570.13" {
               description "1570.13 nm/190.934375 THz 3.125GHz spacing";
             }
             enum "1570.11" {
               description "1570.11 nm/190.937500 THz 3.125/6.25/12.5GHz spacing";
             }
             enum "1570.08" {
               description "1570.08 nm/190.940625 THz 3.125GHz spacing";
             }
             enum "1570.06" {
               description "1570.06 nm/190.943750 THz 3.125/6.25GHz spacing";
             }
             enum "1570.03" {
               description "1570.03 nm/190.946875 THz 3.125GHz spacing";
             }
             enum "1570.01" {
               description "1570.01 nm/190.950000 THz 3.125/6.25/12.5/50GHz spacing";
             }
             enum "1569.98" {
               description "1569.98 nm/190.953125 THz 3.125GHz spacing";
             }
             enum "1569.95" {
               description "1569.95 nm/190.956250 THz 3.125/6.25GHz spacing";
             }
             enum "1569.93" {
               description "1569.93 nm/190.959375 THz 3.125GHz spacing";
             }
             enum "1569.90" {
               description "1569.90 nm/190.962500 THz 3.125/6.25/12.5GHz spacing";
             }
             enum "1569.88" {
               description "1569.88 nm/190.965625 THz 3.125GHz spacing";
             }
             enum "1569.85" {
               description "1569.85 nm/190.968750 THz 3.125/6.25GHz spacing";
             }
             enum "1569.83" {
               description "1569.83 nm/190.971875 THz 3.125GHz spacing";
             }
             enum "1569.80" {
               description "1569.80 nm/190.975000 THz 3.125/6.25/12.5GHz spacing";
             }
             enum "1569.77" {
               description "1569.77 nm/190.978125 THz 3.125GHz spacing";
             }
             enum "1569.75" {
               description "1569.75 nm/190.981250 THz 3.125/6.25GHz spacing";
             }
             enum "1569.72" {
               description "1569.72 nm/190.984375 THz 3.125GHz spacing";
             }
             enum "1569.70" {
               description "1569.70 nm/190.987500 THz 3.125/6.25/12.5GHz spacing";
             }
             enum "1569.67" {
               description "1569.67 nm/190.990625 THz 3.125GHz spacing";
             }
             enum "1569.65" {
               description "1569.65 nm/190.993750 THz 3.125/6.25GHz spacing";
             }
             enum "1569.62" {
               description "1569.62 nm/190.996875 THz 3.125GHz spacing";
             }
             enum "1569.59" {
               description "1569.59 nm/191.000000 THz 3.125/6.25/12.5/100GHz spacing";
             }
             enum "1568.77" {
               description "1568.77 nm/191.1003 THz 50/100Ghz spacing";
             }
             enum "1568.36" {
               description "1568.36 nm/191.150000 THz 3.125/6.25/12.5/50/75GHz spacing";
             }
             enum "1568.34" {
               description "1568.34 nm/191.153125 THz 3.125GHz spacing";
             }
             enum "1568.31" {
               description "1568.31 nm/191.156250 THz 3.125/6.25GHz spacing";
             }
             enum "1568.29" {
               description "1568.29 nm/191.159375 THz 3.125GHz spacing";
             }
             enum "1568.26" {
               description "1568.26 nm/191.162500 THz 3.125/6.25/12.5GHz spacing";
             }
             enum "1568.23" {
               description "1568.23 nm/191.165625 THz 3.125GHz spacing";
             }
             enum "1568.21" {
               description "1568.21 nm/191.168750 THz 3.125/6.25GHz spacing";
             }
             enum "1568.18" {
               description "1568.18 nm/191.171875 THz 3.125GHz spacing";
             }
             enum "1568.16" {
               description "1568.16 nm/191.175000 THz 3.125/6.25/12.5/75GHz spacing";
             }
             enum "1568.13" {
               description "1568.13 nm/191.178125 THz 3.125GHz spacing";
             }
             enum "1568.11" {
               description "1568.11 nm/191.181250 THz 3.125/6.25GHz spacing";
             }
             enum "1568.08" {
               description "1568.08 nm/191.184375 THz 3.125GHz spacing";
             }
             enum "1568.05" {
               description "1568.05 nm/191.187500 THz 3.125/6.25/12.5GHz spacing";
             }
             enum "1568.03" {
               description "1568.03 nm/191.190625 THz 3.125GHz spacing";
             }
             enum "1568.00" {
               description "1568.00 nm/191.193750 THz 3.125/6.25GHz spacing";
             }
             enum "1567.98" {
               description "1567.98 nm/191.196875 THz 3.125GHz spacing";
             }
             enum "1567.95" {
               description "1567.95 nm/191.200000 THz 3.125/6.25/12.5/100GHz spacing";
             }
             enum "1567.93" {
               description "1567.93 nm/191.203125 THz 3.125GHz spacing";
             }
             enum "1567.90" {
               description "1567.90 nm/191.206250 THz 3.125/6.25GHz spacing";
             }
             enum "1567.88" {
               description "1567.88 nm/191.209375 THz 3.125GHz spacing";
             }
             enum "1567.85" {
               description "1567.85 nm/191.212500 THz 3.125/6.25/12.5GHz spacing";
             }
             enum "1567.82" {
               description "1567.82 nm/191.215625 THz 3.125GHz spacing";
             }
             enum "1567.80" {
               description "1567.80 nm/191.218750 THz 3.125/6.25GHz spacing";
             }
             enum "1567.77" {
               description "1567.77 nm/191.221875 THz 3.125GHz spacing";
             }
             enum "1567.75" {
               description "1567.75 nm/191.225000 THz 3.125/6.25/12.5/75GHz spacing";
             }
             enum "1567.72" {
               description "1567.72 nm/191.228125 THz 3.125GHz spacing";
             }
             enum "1567.70" {
               description "1567.70 nm/191.231250 THz 3.125/6.25GHz spacing";
             }
             enum "1567.67" {
               description "1567.67 nm/191.234375 THz 3.125GHz spacing";
             }
             enum "1567.64" {
               description "1567.64 nm/191.237500 THz 3.125/6.25/12.5GHz spacing";
             }
             enum "1567.62" {
               description "1567.62 nm/191.240625 THz 3.125GHz spacing";
             }
             enum "1567.59" {
               description "1567.59 nm/191.243750 THz 3.125/6.25GHz spacing";
             }
             enum "1567.57" {
               description "1567.57 nm/191.246875 THz 3.125GHz spacing";
             }
             enum "1567.54" {
               description "1567.54 nm/191.250000 THz 3.125/6.25/12.5/50/75GHz spacing";
             }
             enum "1567.52" {
               description "1567.52 nm/191.253125 THz 3.125GHz spacing";
             }
             enum "1567.49" {
               description "1567.49 nm/191.256250 THz 3.125/6.25GHz spacing";
             }
             enum "1567.47" {
               description "1567.47 nm/191.259375 THz 3.125GHz spacing";
             }
             enum "1567.44" {
               description "1567.44 nm/191.262500 THz 3.125/6.25/12.5GHz spacing";
             }
             enum "1567.41" {
               description "1567.41 nm/191.265625 THz 3.125GHz spacing";
             }
             enum "1567.39" {
               description "1567.39 nm/191.268750 THz 3.125/6.25GHz spacing";
             }
             enum "1567.36" {
               description "1567.36 nm/191.271875 THz 3.125GHz spacing";
             }
             enum "1567.34" {
               description "1567.34 nm/191.275000 THz 3.125/6.25/12.5GHz spacing";
             }
             enum "1567.31" {
               description "1567.31 nm/191.278125 THz 3.125GHz spacing";
             }
             enum "1567.29" {
               description "1567.29 nm/191.281250 THz 3.125/6.25GHz spacing";
             }
             enum "1567.26" {
               description "1567.26 nm/191.284375 THz 3.125GHz spacing";
             }
             enum "1567.23" {
               description "1567.23 nm/191.287500 THz 3.125/6.25/12.5GHz spacing";
             }
             enum "1567.21" {
               description "1567.21 nm/191.290625 THz 3.125GHz spacing";
             }
             enum "1567.18" {
               description "1567.18 nm/191.293750 THz 3.125/6.25GHz spacing";
             }
             enum "1567.16" {
               description "1567.16 nm/191.296875 THz 3.125GHz spacing";
             }
             enum "1567.13" {
               description "1567.13 nm/191.300000 THz 3.125/6.25/12.5/100GHz spacing";
             }
             enum "1567.11" {
               description "1567.11 nm/191.303125 THz 3.125GHz spacing";
             }
             enum "1567.08" {
               description "1567.08 nm/191.306250 THz 3.125/6.25GHz spacing";
             }
             enum "1567.06" {
               description "1567.06 nm/191.309375 THz 3.125GHz spacing";
             }
             enum "1567.03" {
               description "1567.03 nm/191.312500 THz 3.125/6.25/12.5GHz spacing";
             }
             enum "1567.00" {
               description "1567.00 nm/191.315625 THz 3.125GHz spacing";
             }
             enum "1566.98" {
               description "1566.98 nm/191.318750 THz 3.125/6.25GHz spacing";
             }
             enum "1566.95" {
               description "1566.95 nm/191.321875 THz 3.125GHz spacing";
             }
             enum "1566.93" {
               description "1566.93 nm/191.325000 THz 3.125/6.25/12.5/75GHz spacing";
             }
             enum "1566.90" {
               description "1566.90 nm/191.328125 THz 3.125GHz spacing";
             }
             enum "1566.88" {
               description "1566.88 nm/191.331250 THz 3.125/6.25GHz spacing";
             }
             enum "1566.85" {
               description "1566.85 nm/191.334375 THz 3.125GHz spacing";
             }
             enum "1566.83" {
               description "1566.83 nm/191.337500 THz 3.125/6.25/12.5GHz spacing";
             }
             enum "1566.80" {
               description "1566.80 nm/191.340625 THz 3.125GHz spacing";
             }
             enum "1566.77" {
               description "1566.77 nm/191.343750 THz 3.125/6.25GHz spacing";
             }
             enum "1566.75" {
               description "1566.75 nm/191.346875 THz 3.125GHz spacing";
             }
             enum "1566.72" {
               description "1566.72 nm/191.350000 THz 3.125/6.25/12.5/50GHz spacing";
             }
             enum "1566.70" {
               description "1566.70 nm/191.353125 THz 3.125GHz spacing";
             }
             enum "1566.67" {
               description "1566.67 nm/191.356250 THz 3.125/6.25GHz spacing";
             }
             enum "1566.65" {
               description "1566.65 nm/191.359375 THz 3.125GHz spacing";
             }
             enum "1566.62" {
               description "1566.62 nm/191.362500 THz 3.125/6.25/12.5GHz spacing";
             }
             enum "1566.60" {
               description "1566.60 nm/191.365625 THz 3.125GHz spacing";
             }
             enum "1566.57" {
               description "1566.57 nm/191.368750 THz 3.125/6.25GHz spacing";
             }
             enum "1566.54" {
               description "1566.54 nm/191.371875 THz 3.125GHz spacing";
             }
             enum "1566.52" {
               description "1566.52 nm/191.375000 THz 3.125/6.25/12.5GHz spacing";
             }
             enum "1566.49" {
               description "1566.49 nm/191.378125 THz 3.125GHz spacing";
             }
             enum "1566.47" {
               description "1566.47 nm/191.381250 THz 3.125/6.25GHz spacing";
             }
             enum "1566.44" {
               description "1566.44 nm/191.384375 THz 3.125GHz spacing";
             }
             enum "1566.42" {
               description "1566.42 nm/191.387500 THz 3.125/6.25/12.5GHz spacing";
             }
             enum "1566.39" {
               description "1566.39 nm/191.390625 THz 3.125GHz spacing";
             }
             enum "1566.36" {
               description "1566.36 nm/191.393750 THz 3.125/6.25GHz spacing";
             }
             enum "1566.34" {
               description "1566.34 nm/191.396875 THz 3.125GHz spacing";
             }
             enum "1566.31" {
               description "1566.31 nm/191.400000 THz 3.125/6.25/12.5/50/75/100GHz spacing";
             }
             enum "1566.29" {
               description "1566.29 nm/191.403125 THz 3.125GHz spacing";
             }
             enum "1566.26" {
               description "1566.26 nm/191.406250 THz 3.125/6.25GHz spacing";
             }
             enum "1566.24" {
               description "1566.24 nm/191.409375 THz 3.125GHz spacing";
             }
             enum "1566.21" {
               description "1566.21 nm/191.412500 THz 3.125/6.25/12.5GHz spacing";
             }
             enum "1566.19" {
               description "1566.19 nm/191.415625 THz 3.125GHz spacing";
             }
             enum "1566.16" {
               description "1566.16 nm/191.418750 THz 3.125/6.25GHz spacing";
             }
             enum "1566.13" {
               description "1566.13 nm/191.421875 THz 3.125GHz spacing";
             }
             enum "1566.11" {
               description "1566.11 nm/191.425000 THz 3.125/6.25/12.5GHz spacing";
             }
             enum "1566.08" {
               description "1566.08 nm/191.428125 THz 3.125GHz spacing";
             }
             enum "1566.06" {
               description "1566.06 nm/191.431250 THz 3.125/6.25GHz spacing";
             }
             enum "1566.03" {
               description "1566.03 nm/191.434375 THz 3.125GHz spacing";
             }
             enum "1566.01" {
               description "1566.01 nm/191.437500 THz 3.125/6.25/12.5GHz spacing";
             }
             enum "1565.98" {
               description "1565.98 nm/191.440625 THz 3.125GHz spacing";
             }
             enum "1565.96" {
               description "1565.96 nm/191.443750 THz 3.125/6.25GHz spacing";
             }
             enum "1565.93" {
               description "1565.93 nm/191.446875 THz 3.125GHz spacing";
             }
             enum "1565.90" {
               description "1565.90 nm/191.450000 THz 3.125/6.25/12.5/50GHz spacing";
             }
             enum "1565.88" {
               description "1565.88 nm/191.453125 THz 3.125GHz spacing";
             }
             enum "1565.85" {
               description "1565.85 nm/191.456250 THz 3.125/6.25GHz spacing";
             }
             enum "1565.83" {
               description "1565.83 nm/191.459375 THz 3.125GHz spacing";
             }
             enum "1565.80" {
               description "1565.80 nm/191.462500 THz 3.125/6.25/12.5GHz spacing";
             }
             enum "1565.78" {
               description "1565.78 nm/191.465625 THz 3.125GHz spacing";
             }
             enum "1565.75" {
               description "1565.75 nm/191.468750 THz 3.125/6.25GHz spacing";
             }
             enum "1565.73" {
               description "1565.73 nm/191.471875 THz 3.125GHz spacing";
             }
             enum "1565.70" {
               description "1565.70 nm/191.475000 THz 3.125/6.25/12.5/75GHz spacing";
             }
             enum "1565.67" {
               description "1565.67 nm/191.478125 THz 3.125GHz spacing";
             }
             enum "1565.65" {
               description "1565.65 nm/191.481250 THz 3.125/6.25GHz spacing";
             }
             enum "1565.62" {
               description "1565.62 nm/191.484375 THz 3.125GHz spacing";
             }
             enum "1565.60" {
               description "1565.60 nm/191.487500 THz 3.125/6.25/12.5GHz spacing";
             }
             enum "1565.57" {
               description "1565.57 nm/191.490625 THz 3.125GHz spacing";
             }
             enum "1565.55" {
               description "1565.55 nm/191.493750 THz 3.125/6.25GHz spacing";
             }
             enum "1565.52" {
               description "1565.52 nm/191.496875 THz 3.125GHz spacing";
             }
             enum "1565.50" {
               description "1565.50 nm/191.500000 THz 3.125/6.25/12.5/100GHz spacing";
             }
             enum "1565.47" {
               description "1565.47 nm/191.503125 THz 3.125GHz spacing";
             }
             enum "1565.44" {
               description "1565.44 nm/191.506250 THz 3.125/6.25GHz spacing";
             }
             enum "1565.42" {
               description "1565.42 nm/191.509375 THz 3.125GHz spacing";
             }
             enum "1565.39" {
               description "1565.39 nm/191.512500 THz 3.125/6.25/12.5GHz spacing";
             }
             enum "1565.37" {
               description "1565.37 nm/191.515625 THz 3.125GHz spacing";
             }
             enum "1565.34" {
               description "1565.34 nm/191.518750 THz 3.125/6.25GHz spacing";
             }
             enum "1565.32" {
               description "1565.32 nm/191.521875 THz 3.125GHz spacing";
             }
             enum "1565.29" {
               description "1565.29 nm/191.525000 THz 3.125/6.25/12.5GHz spacing";
             }
             enum "1565.27" {
               description "1565.27 nm/191.528125 THz 3.125GHz spacing";
             }
             enum "1565.24" {
               description "1565.24 nm/191.531250 THz 3.125/6.25GHz spacing";
             }
             enum "1565.21" {
               description "1565.21 nm/191.534375 THz 3.125GHz spacing";
             }
             enum "1565.19" {
               description "1565.19 nm/191.537500 THz 3.125/6.25/12.5GHz spacing";
             }
             enum "1565.16" {
               description "1565.16 nm/191.540625 THz 3.125GHz spacing";
             }
             enum "1565.14" {
               description "1565.14 nm/191.543750 THz 3.125/6.25GHz spacing";
             }
             enum "1565.11" {
               description "1565.11 nm/191.546875 THz 3.125GHz spacing";
             }
             enum "1565.09" {
               description "1565.09 nm/191.550000 THz 3.125/6.25/12.5/50/75GHz spacing";
             }
             enum "1565.06" {
               description "1565.06 nm/191.553125 THz 3.125GHz spacing";
             }
             enum "1565.04" {
               description "1565.04 nm/191.556250 THz 3.125/6.25GHz spacing";
             }
             enum "1565.01" {
               description "1565.01 nm/191.559375 THz 3.125GHz spacing";
             }
             enum "1564.99" {
               description "1564.99 nm/191.562500 THz 3.125/6.25/12.5GHz spacing";
             }
             enum "1564.96" {
               description "1564.96 nm/191.565625 THz 3.125GHz spacing";
             }
             enum "1564.93" {
               description "1564.93 nm/191.568750 THz 3.125/6.25GHz spacing";
             }
             enum "1564.91" {
               description "1564.91 nm/191.571875 THz 3.125GHz spacing";
             }
             enum "1564.88" {
               description "1564.88 nm/191.575000 THz 3.125/6.25/12.5GHz spacing";
             }
             enum "1564.86" {
               description "1564.86 nm/191.578125 THz 3.125GHz spacing";
             }
             enum "1564.83" {
               description "1564.83 nm/191.581250 THz 3.125/6.25GHz spacing";
             }
             enum "1564.81" {
               description "1564.81 nm/191.584375 THz 3.125GHz spacing";
             }
             enum "1564.78" {
               description "1564.78 nm/191.587500 THz 3.125/6.25/12.5GHz spacing";
             }
             enum "1564.76" {
               description "1564.76 nm/191.590625 THz 3.125GHz spacing";
             }
             enum "1564.73" {
               description "1564.73 nm/191.593750 THz 3.125/6.25GHz spacing";
             }
             enum "1564.70" {
               description "1564.70 nm/191.596875 THz 3.125GHz spacing";
             }
             enum "1564.68" {
               description "1564.68 nm/191.600000 THz 3.125/6.25/12.5/100GHz spacing";
             }
             enum "1564.65" {
               description "1564.65 nm/191.603125 THz 3.125GHz spacing";
             }
             enum "1564.63" {
               description "1564.63 nm/191.606250 THz 3.125/6.25GHz spacing";
             }
             enum "1564.60" {
               description "1564.60 nm/191.609375 THz 3.125GHz spacing";
             }
             enum "1564.58" {
               description "1564.58 nm/191.612500 THz 3.125/6.25/12.5GHz spacing";
             }
             enum "1564.55" {
               description "1564.55 nm/191.615625 THz 3.125GHz spacing";
             }
             enum "1564.53" {
               description "1564.53 nm/191.618750 THz 3.125/6.25GHz spacing";
             }
             enum "1564.50" {
               description "1564.50 nm/191.621875 THz 3.125GHz spacing";
             }
             enum "1564.47" {
               description "1564.47 nm/191.625000 THz 3.125/6.25/12.5/75GHz spacing";
             }
             enum "1564.45" {
               description "1564.45 nm/191.628125 THz 3.125GHz spacing";
             }
             enum "1564.42" {
               description "1564.42 nm/191.631250 THz 3.125/6.25GHz spacing";
             }
             enum "1564.40" {
               description "1564.40 nm/191.634375 THz 3.125GHz spacing";
             }
             enum "1564.37" {
               description "1564.37 nm/191.637500 THz 3.125/6.25/12.5GHz spacing";
             }
             enum "1564.35" {
               description "1564.35 nm/191.640625 THz 3.125GHz spacing";
             }
             enum "1564.32" {
               description "1564.32 nm/191.643750 THz 3.125/6.25GHz spacing";
             }
             enum "1564.30" {
               description "1564.30 nm/191.646875 THz 3.125GHz spacing";
             }
             enum "1564.27" {
               description "1564.27 nm/191.650000 THz 3.125/6.25/12.5/50GHz spacing";
             }
             enum "1564.25" {
               description "1564.25 nm/191.653125 THz 3.125GHz spacing";
             }
             enum "1564.22" {
               description "1564.22 nm/191.656250 THz 3.125/6.25GHz spacing";
             }
             enum "1564.19" {
               description "1564.19 nm/191.659375 THz 3.125GHz spacing";
             }
             enum "1564.17" {
               description "1564.17 nm/191.662500 THz 3.125/6.25/12.5GHz spacing";
             }
             enum "1564.14" {
               description "1564.14 nm/191.665625 THz 3.125GHz spacing";
             }
             enum "1564.12" {
               description "1564.12 nm/191.668750 THz 3.125/6.25GHz spacing";
             }
             enum "1564.09" {
               description "1564.09 nm/191.671875 THz 3.125GHz spacing";
             }
             enum "1564.07" {
               description "1564.07 nm/191.675000 THz 3.125/6.25/12.5GHz spacing";
             }
             enum "1564.04" {
               description "1564.04 nm/191.678125 THz 3.125GHz spacing";
             }
             enum "1564.02" {
               description "1564.02 nm/191.681250 THz 3.125/6.25GHz spacing";
             }
             enum "1563.99" {
               description "1563.99 nm/191.684375 THz 3.125GHz spacing";
             }
             enum "1563.96" {
               description "1563.96 nm/191.687500 THz 3.125/6.25/12.5GHz spacing";
             }
             enum "1563.94" {
               description "1563.94 nm/191.690625 THz 3.125GHz spacing";
             }
             enum "1563.91" {
               description "1563.91 nm/191.693750 THz 3.125/6.25GHz spacing";
             }
             enum "1563.89" {
               description "1563.89 nm/191.696875 THz 3.125GHz spacing";
             }
             enum "1563.86" {
               description "1563.86 nm/191.700000 THz 3.125/6.25/12.5/50/75/100GHz spacing";
             }
             enum "1563.84" {
               description "1563.84 nm/191.703125 THz 3.125GHz spacing";
             }
             enum "1563.81" {
               description "1563.81 nm/191.706250 THz 3.125/6.25GHz spacing";
             }
             enum "1563.79" {
               description "1563.79 nm/191.709375 THz 3.125GHz spacing";
             }
             enum "1563.76" {
               description "1563.76 nm/191.712500 THz 3.125/6.25/12.5GHz spacing";
             }
             enum "1563.74" {
               description "1563.74 nm/191.715625 THz 3.125GHz spacing";
             }
             enum "1563.71" {
               description "1563.71 nm/191.718750 THz 3.125/6.25GHz spacing";
             }
             enum "1563.68" {
               description "1563.68 nm/191.721875 THz 3.125GHz spacing";
             }
             enum "1563.66" {
               description "1563.66 nm/191.725000 THz 3.125/6.25/12.5GHz spacing";
             }
             enum "1563.63" {
               description "1563.63 nm/191.728125 THz 3.125GHz spacing";
             }
             enum "1563.61" {
               description "1563.61 nm/191.731250 THz 3.125/6.25GHz spacing";
             }
             enum "1563.58" {
               description "1563.58 nm/191.734375 THz 3.125GHz spacing";
             }
             enum "1563.56" {
               description "1563.56 nm/191.737500 THz 3.125/6.25/12.5GHz spacing";
             }
             enum "1563.53" {
               description "1563.53 nm/191.740625 THz 3.125GHz spacing";
             }
             enum "1563.51" {
               description "1563.51 nm/191.743750 THz 3.125/6.25GHz spacing";
             }
             enum "1563.48" {
               description "1563.48 nm/191.746875 THz 3.125GHz spacing";
             }
             enum "1563.45" {
               description "1563.45 nm/191.750000 THz 3.125/6.25/12.5/50GHz spacing";
             }
             enum "1563.43" {
               description "1563.43 nm/191.753125 THz 3.125GHz spacing";
             }
             enum "1563.40" {
               description "1563.40 nm/191.756250 THz 3.125/6.25GHz spacing";
             }
             enum "1563.38" {
               description "1563.38 nm/191.759375 THz 3.125GHz spacing";
             }
             enum "1563.35" {
               description "1563.35 nm/191.762500 THz 3.125/6.25/12.5GHz spacing";
             }
             enum "1563.33" {
               description "1563.33 nm/191.765625 THz 3.125GHz spacing";
             }
             enum "1563.30" {
               description "1563.30 nm/191.768750 THz 3.125/6.25GHz spacing";
             }
             enum "1563.28" {
               description "1563.28 nm/191.771875 THz 3.125GHz spacing";
             }
             enum "1563.25" {
               description "1563.25 nm/191.775000 THz 3.125/6.25/12.5/75GHz spacing";
             }
             enum "1563.23" {
               description "1563.23 nm/191.778125 THz 3.125GHz spacing";
             }
             enum "1563.20" {
               description "1563.20 nm/191.781250 THz 3.125/6.25GHz spacing";
             }
             enum "1563.17" {
               description "1563.17 nm/191.784375 THz 3.125GHz spacing";
             }
             enum "1563.15" {
               description "1563.15 nm/191.787500 THz 3.125/6.25/12.5GHz spacing";
             }
             enum "1563.12" {
               description "1563.12 nm/191.790625 THz 3.125GHz spacing";
             }
             enum "1563.10" {
               description "1563.10 nm/191.793750 THz 3.125/6.25GHz spacing";
             }
             enum "1563.07" {
               description "1563.07 nm/191.796875 THz 3.125GHz spacing";
             }
             enum "1563.05" {
               description "1563.05 nm/191.800000 THz 3.125/6.25/12.5/100GHz spacing";
             }
             enum "1563.02" {
               description "1563.02 nm/191.803125 THz 3.125GHz spacing";
             }
             enum "1563.00" {
               description "1563.00 nm/191.806250 THz 3.125/6.25GHz spacing";
             }
             enum "1562.97" {
               description "1562.97 nm/191.809375 THz 3.125GHz spacing";
             }
             enum "1562.95" {
               description "1562.95 nm/191.812500 THz 3.125/6.25/12.5GHz spacing";
             }
             enum "1562.92" {
               description "1562.92 nm/191.815625 THz 3.125GHz spacing";
             }
             enum "1562.89" {
               description "1562.89 nm/191.818750 THz 3.125/6.25GHz spacing";
             }
             enum "1562.87" {
               description "1562.87 nm/191.821875 THz 3.125GHz spacing";
             }
             enum "1562.84" {
               description "1562.84 nm/191.825000 THz 3.125/6.25/12.5GHz spacing";
             }
             enum "1562.82" {
               description "1562.82 nm/191.828125 THz 3.125GHz spacing";
             }
             enum "1562.79" {
               description "1562.79 nm/191.831250 THz 3.125/6.25GHz spacing";
             }
             enum "1562.77" {
               description "1562.77 nm/191.834375 THz 3.125GHz spacing";
             }
             enum "1562.74" {
               description "1562.74 nm/191.837500 THz 3.125/6.25/12.5GHz spacing";
             }
             enum "1562.72" {
               description "1562.72 nm/191.840625 THz 3.125GHz spacing";
             }
             enum "1562.69" {
               description "1562.69 nm/191.843750 THz 3.125/6.25GHz spacing";
             }
             enum "1562.67" {
               description "1562.67 nm/191.846875 THz 3.125GHz spacing";
             }
             enum "1562.64" {
               description "1562.64 nm/191.850000 THz 3.125/6.25/12.5/50/75GHz spacing";
             }
             enum "1562.61" {
               description "1562.61 nm/191.853125 THz 3.125GHz spacing";
             }
             enum "1562.59" {
               description "1562.59 nm/191.856250 THz 3.125/6.25GHz spacing";
             }
             enum "1562.56" {
               description "1562.56 nm/191.859375 THz 3.125GHz spacing";
             }
             enum "1562.54" {
               description "1562.54 nm/191.862500 THz 3.125/6.25/12.5GHz spacing";
             }
             enum "1562.51" {
               description "1562.51 nm/191.865625 THz 3.125GHz spacing";
             }
             enum "1562.49" {
               description "1562.49 nm/191.868750 THz 3.125/6.25GHz spacing";
             }
             enum "1562.46" {
               description "1562.46 nm/191.871875 THz 3.125GHz spacing";
             }
             enum "1562.44" {
               description "1562.44 nm/191.875000 THz 3.125/6.25/12.5GHz spacing";
             }
             enum "1562.41" {
               description "1562.41 nm/191.878125 THz 3.125GHz spacing";
             }
             enum "1562.39" {
               description "1562.39 nm/191.881250 THz 3.125/6.25GHz spacing";
             }
             enum "1562.36" {
               description "1562.36 nm/191.884375 THz 3.125GHz spacing";
             }
             enum "1562.33" {
               description "1562.33 nm/191.887500 THz 3.125/6.25/12.5GHz spacing";
             }
             enum "1562.31" {
               description "1562.31 nm/191.890625 THz 3.125GHz spacing";
             }
             enum "1562.28" {
               description "1562.28 nm/191.893750 THz 3.125/6.25GHz spacing";
             }
             enum "1562.26" {
               description "1562.26 nm/191.896875 THz 3.125GHz spacing";
             }
             enum "1562.23" {
               description "1562.23 nm/191.900000 THz 3.125/6.25/12.5/100GHz spacing";
             }
             enum "1562.21" {
               description "1562.21 nm/191.903125 THz 3.125GHz spacing";
             }
             enum "1562.18" {
               description "1562.18 nm/191.906250 THz 3.125/6.25GHz spacing";
             }
             enum "1562.16" {
               description "1562.16 nm/191.909375 THz 3.125GHz spacing";
             }
             enum "1562.13" {
               description "1562.13 nm/191.912500 THz 3.125/6.25/12.5GHz spacing";
             }
             enum "1562.11" {
               description "1562.11 nm/191.915625 THz 3.125GHz spacing";
             }
             enum "1562.08" {
               description "1562.08 nm/191.918750 THz 3.125/6.25GHz spacing";
             }
             enum "1562.05" {
               description "1562.05 nm/191.921875 THz 3.125GHz spacing";
             }
             enum "1562.03" {
               description "1562.03 nm/191.925000 THz 3.125/6.25/12.5/75GHz spacing";
             }
             enum "1562.00" {
               description "1562.00 nm/191.928125 THz 3.125GHz spacing";
             }
             enum "1561.98" {
               description "1561.98 nm/191.931250 THz 3.125/6.25GHz spacing";
             }
             enum "1561.95" {
               description "1561.95 nm/191.934375 THz 3.125GHz spacing";
             }
             enum "1561.93" {
               description "1561.93 nm/191.937500 THz 3.125/6.25/12.5GHz spacing";
             }
             enum "1561.90" {
               description "1561.90 nm/191.940625 THz 3.125GHz spacing";
             }
             enum "1561.88" {
               description "1561.88 nm/191.943750 THz 3.125/6.25GHz spacing";
             }
             enum "1561.85" {
               description "1561.85 nm/191.946875 THz 3.125GHz spacing";
             }
             enum "1561.83" {
               description "1561.83 nm/191.950000 THz 3.125/6.25/12.5/50GHz spacing";
             }
             enum "1561.80" {
               description "1561.80 nm/191.953125 THz 3.125GHz spacing";
             }
             enum "1561.77" {
               description "1561.77 nm/191.956250 THz 3.125/6.25GHz spacing";
             }
             enum "1561.75" {
               description "1561.75 nm/191.959375 THz 3.125GHz spacing";
             }
             enum "1561.72" {
               description "1561.72 nm/191.962500 THz 3.125/6.25/12.5GHz spacing";
             }
             enum "1561.70" {
               description "1561.70 nm/191.965625 THz 3.125GHz spacing";
             }
             enum "1561.67" {
               description "1561.67 nm/191.968750 THz 3.125/6.25GHz spacing";
             }
             enum "1561.65" {
               description "1561.65 nm/191.971875 THz 3.125GHz spacing";
             }
             enum "1561.62" {
               description "1561.62 nm/191.975000 THz 3.125/6.25/12.5GHz spacing";
             }
             enum "1561.60" {
               description "1561.60 nm/191.978125 THz 3.125GHz spacing";
             }
             enum "1561.57" {
               description "1561.57 nm/191.981250 THz 3.125/6.25GHz spacing";
             }
             enum "1561.55" {
               description "1561.55 nm/191.984375 THz 3.125GHz spacing";
             }
             enum "1561.52" {
               description "1561.52 nm/191.987500 THz 3.125/6.25/12.5GHz spacing";
             }
             enum "1561.50" {
               description "1561.50 nm/191.990625 THz 3.125GHz spacing";
             }
             enum "1561.47" {
               description "1561.47 nm/191.993750 THz 3.125/6.25GHz spacing";
             }
             enum "1561.44" {
               description "1561.44 nm/191.996875 THz 3.125GHz spacing";
             }
             enum "1561.42" {
               description "1561.42 nm/192.000000 THz 3.125/6.25/12.5/50/75/100GHz spacing";
             }
             enum "1561.39" {
               description "1561.39 nm/192.003125 THz 3.125GHz spacing";
             }
             enum "1561.37" {
               description "1561.37 nm/192.006250 THz 3.125/6.25GHz spacing";
             }
             enum "1561.34" {
               description "1561.34 nm/192.009375 THz 3.125GHz spacing";
             }
             enum "1561.32" {
               description "1561.32 nm/192.012500 THz 3.125/6.25/12.5GHz spacing";
             }
             enum "1561.29" {
               description "1561.29 nm/192.015625 THz 3.125GHz spacing";
             }
             enum "1561.27" {
               description "1561.27 nm/192.018750 THz 3.125/6.25GHz spacing";
             }
             enum "1561.24" {
               description "1561.24 nm/192.021875 THz 3.125GHz spacing";
             }
             enum "1561.22" {
               description "1561.22 nm/192.025000 THz 3.125/6.25/12.5GHz spacing";
             }
             enum "1561.19" {
               description "1561.19 nm/192.028125 THz 3.125GHz spacing";
             }
             enum "1561.16" {
               description "1561.16 nm/192.031250 THz 3.125/6.25GHz spacing";
             }
             enum "1561.14" {
               description "1561.14 nm/192.034375 THz 3.125GHz spacing";
             }
             enum "1561.11" {
               description "1561.11 nm/192.037500 THz 3.125/6.25/12.5GHz spacing";
             }
             enum "1561.09" {
               description "1561.09 nm/192.040625 THz 3.125GHz spacing";
             }
             enum "1561.06" {
               description "1561.06 nm/192.043750 THz 3.125/6.25GHz spacing";
             }
             enum "1561.04" {
               description "1561.04 nm/192.046875 THz 3.125GHz spacing";
             }
             enum "1561.01" {
               description "1561.01 nm/192.050000 THz 3.125/6.25/12.5/50GHz spacing";
             }
             enum "1560.99" {
               description "1560.99 nm/192.053125 THz 3.125GHz spacing";
             }
             enum "1560.96" {
               description "1560.96 nm/192.056250 THz 3.125/6.25GHz spacing";
             }
             enum "1560.94" {
               description "1560.94 nm/192.059375 THz 3.125GHz spacing";
             }
             enum "1560.91" {
               description "1560.91 nm/192.062500 THz 3.125/6.25/12.5GHz spacing";
             }
             enum "1560.89" {
               description "1560.89 nm/192.065625 THz 3.125GHz spacing";
             }
             enum "1560.86" {
               description "1560.86 nm/192.068750 THz 3.125/6.25GHz spacing";
             }
             enum "1560.83" {
               description "1560.83 nm/192.071875 THz 3.125GHz spacing";
             }
             enum "1560.81" {
               description "1560.81 nm/192.075000 THz 3.125/6.25/12.5/75GHz spacing";
             }
             enum "1560.78" {
               description "1560.78 nm/192.078125 THz 3.125GHz spacing";
             }
             enum "1560.76" {
               description "1560.76 nm/192.081250 THz 3.125/6.25GHz spacing";
             }
             enum "1560.73" {
               description "1560.73 nm/192.084375 THz 3.125GHz spacing";
             }
             enum "1560.71" {
               description "1560.71 nm/192.087500 THz 3.125/6.25/12.5GHz spacing";
             }
             enum "1560.68" {
               description "1560.68 nm/192.090625 THz 3.125GHz spacing";
             }
             enum "1560.66" {
               description "1560.66 nm/192.093750 THz 3.125/6.25GHz spacing";
             }
             enum "1560.63" {
               description "1560.63 nm/192.096875 THz 3.125GHz spacing";
             }
             enum "1560.61" {
               description "1560.61 nm/192.100000 THz 3.125/6.25/12.5/100GHz spacing";
             }
             enum "1560.58" {
               description "1560.58 nm/192.103125 THz 3.125GHz spacing";
             }
             enum "1560.56" {
               description "1560.56 nm/192.106250 THz 3.125/6.25GHz spacing";
             }
             enum "1560.53" {
               description "1560.53 nm/192.109375 THz 3.125GHz spacing";
             }
             enum "1560.50" {
               description "1560.50 nm/192.112500 THz 3.125/6.25/12.5GHz spacing";
             }
             enum "1560.48" {
               description "1560.48 nm/192.115625 THz 3.125GHz spacing";
             }
             enum "1560.45" {
               description "1560.45 nm/192.118750 THz 3.125/6.25GHz spacing";
             }
             enum "1560.43" {
               description "1560.43 nm/192.121875 THz 3.125GHz spacing";
             }
             enum "1560.40" {
               description "1560.40 nm/192.125000 THz 3.125/6.25/12.5GHz spacing";
             }
             enum "1560.38" {
               description "1560.38 nm/192.128125 THz 3.125GHz spacing";
             }
             enum "1560.35" {
               description "1560.35 nm/192.131250 THz 3.125/6.25GHz spacing";
             }
             enum "1560.33" {
               description "1560.33 nm/192.134375 THz 3.125GHz spacing";
             }
             enum "1560.30" {
               description "1560.30 nm/192.137500 THz 3.125/6.25/12.5GHz spacing";
             }
             enum "1560.28" {
               description "1560.28 nm/192.140625 THz 3.125GHz spacing";
             }
             enum "1560.25" {
               description "1560.25 nm/192.143750 THz 3.125/6.25GHz spacing";
             }
             enum "1560.23" {
               description "1560.23 nm/192.146875 THz 3.125GHz spacing";
             }
             enum "1560.20" {
               description "1560.20 nm/192.150000 THz 3.125/6.25/12.5/50/75GHz spacing";
             }
             enum "1560.17" {
               description "1560.17 nm/192.153125 THz 3.125GHz spacing";
             }
             enum "1560.15" {
               description "1560.15 nm/192.156250 THz 3.125/6.25GHz spacing";
             }
             enum "1560.12" {
               description "1560.12 nm/192.159375 THz 3.125GHz spacing";
             }
             enum "1560.10" {
               description "1560.10 nm/192.162500 THz 3.125/6.25/12.5GHz spacing";
             }
             enum "1560.07" {
               description "1560.07 nm/192.165625 THz 3.125GHz spacing";
             }
             enum "1560.05" {
               description "1560.05 nm/192.168750 THz 3.125/6.25GHz spacing";
             }
             enum "1560.02" {
               description "1560.02 nm/192.171875 THz 3.125GHz spacing";
             }
             enum "1560.00" {
               description "1560.00 nm/192.175000 THz 3.125/6.25/12.5GHz spacing";
             }
             enum "1559.97" {
               description "1559.97 nm/192.178125 THz 3.125GHz spacing";
             }
             enum "1559.95" {
               description "1559.95 nm/192.181250 THz 3.125/6.25GHz spacing";
             }
             enum "1559.92" {
               description "1559.92 nm/192.184375 THz 3.125GHz spacing";
             }
             enum "1559.90" {
               description "1559.90 nm/192.187500 THz 3.125/6.25/12.5GHz spacing";
             }
             enum "1559.87" {
               description "1559.87 nm/192.190625 THz 3.125GHz spacing";
             }
             enum "1559.84" {
               description "1559.84 nm/192.193750 THz 3.125/6.25GHz spacing";
             }
             enum "1559.82" {
               description "1559.82 nm/192.196875 THz 3.125GHz spacing";
             }
             enum "1559.79" {
               description "1559.79 nm/192.200000 THz 3.125/6.25/12.5/100GHz spacing";
             }
             enum "1559.77" {
               description "1559.77 nm/192.203125 THz 3.125GHz spacing";
             }
             enum "1559.74" {
               description "1559.74 nm/192.206250 THz 3.125/6.25GHz spacing";
             }
             enum "1559.72" {
               description "1559.72 nm/192.209375 THz 3.125GHz spacing";
             }
             enum "1559.69" {
               description "1559.69 nm/192.212500 THz 3.125/6.25/12.5GHz spacing";
             }
             enum "1559.67" {
               description "1559.67 nm/192.215625 THz 3.125GHz spacing";
             }
             enum "1559.64" {
               description "1559.64 nm/192.218750 THz 3.125/6.25GHz spacing";
             }
             enum "1559.62" {
               description "1559.62 nm/192.221875 THz 3.125GHz spacing";
             }
             enum "1559.59" {
               description "1559.59 nm/192.225000 THz 3.125/6.25/12.5/75GHz spacing";
             }
             enum "1559.57" {
               description "1559.57 nm/192.228125 THz 3.125GHz spacing";
             }
             enum "1559.54" {
               description "1559.54 nm/192.231250 THz 3.125/6.25GHz spacing";
             }
             enum "1559.52" {
               description "1559.52 nm/192.234375 THz 3.125GHz spacing";
             }
             enum "1559.49" {
               description "1559.49 nm/192.237500 THz 3.125/6.25/12.5GHz spacing";
             }
             enum "1559.46" {
               description "1559.46 nm/192.240625 THz 3.125GHz spacing";
             }
             enum "1559.44" {
               description "1559.44 nm/192.243750 THz 3.125/6.25GHz spacing";
             }
             enum "1559.41" {
               description "1559.41 nm/192.246875 THz 3.125GHz spacing";
             }
             enum "1559.39" {
               description "1559.39 nm/192.250000 THz 3.125/6.25/12.5/50GHz spacing";
             }
             enum "1559.36" {
               description "1559.36 nm/192.253125 THz 3.125GHz spacing";
             }
             enum "1559.34" {
               description "1559.34 nm/192.256250 THz 3.125/6.25GHz spacing";
             }
             enum "1559.31" {
               description "1559.31 nm/192.259375 THz 3.125GHz spacing";
             }
             enum "1559.29" {
               description "1559.29 nm/192.262500 THz 3.125/6.25/12.5GHz spacing";
             }
             enum "1559.26" {
               description "1559.26 nm/192.265625 THz 3.125GHz spacing";
             }
             enum "1559.24" {
               description "1559.24 nm/192.268750 THz 3.125/6.25GHz spacing";
             }
             enum "1559.21" {
               description "1559.21 nm/192.271875 THz 3.125GHz spacing";
             }
             enum "1559.19" {
               description "1559.19 nm/192.275000 THz 3.125/6.25/12.5GHz spacing";
             }
             enum "1559.16" {
               description "1559.16 nm/192.278125 THz 3.125GHz spacing";
             }
             enum "1559.14" {
               description "1559.14 nm/192.281250 THz 3.125/6.25GHz spacing";
             }
             enum "1559.11" {
               description "1559.11 nm/192.284375 THz 3.125GHz spacing";
             }
             enum "1559.08" {
               description "1559.08 nm/192.287500 THz 3.125/6.25/12.5GHz spacing";
             }
             enum "1559.06" {
               description "1559.06 nm/192.290625 THz 3.125GHz spacing";
             }
             enum "1559.03" {
               description "1559.03 nm/192.293750 THz 3.125/6.25GHz spacing";
             }
             enum "1559.01" {
               description "1559.01 nm/192.296875 THz 3.125GHz spacing";
             }
             enum "1558.98" {
               description "1558.98 nm/192.300000 THz 3.125/6.25/12.5/50/75/100GHz spacing";
             }
             enum "1558.96" {
               description "1558.96 nm/192.303125 THz 3.125GHz spacing";
             }
             enum "1558.93" {
               description "1558.93 nm/192.306250 THz 3.125/6.25GHz spacing";
             }
             enum "1558.91" {
               description "1558.91 nm/192.309375 THz 3.125GHz spacing";
             }
             enum "1558.88" {
               description "1558.88 nm/192.312500 THz 3.125/6.25/12.5GHz spacing";
             }
             enum "1558.86" {
               description "1558.86 nm/192.315625 THz 3.125GHz spacing";
             }
             enum "1558.83" {
               description "1558.83 nm/192.318750 THz 3.125/6.25GHz spacing";
             }
             enum "1558.81" {
               description "1558.81 nm/192.321875 THz 3.125GHz spacing";
             }
             enum "1558.78" {
               description "1558.78 nm/192.325000 THz 3.125/6.25/12.5GHz spacing";
             }
             enum "1558.76" {
               description "1558.76 nm/192.328125 THz 3.125GHz spacing";
             }
             enum "1558.73" {
               description "1558.73 nm/192.331250 THz 3.125/6.25GHz spacing";
             }
             enum "1558.70" {
               description "1558.70 nm/192.334375 THz 3.125GHz spacing";
             }
             enum "1558.68" {
               description "1558.68 nm/192.337500 THz 3.125/6.25/12.5GHz spacing";
             }
             enum "1558.65" {
               description "1558.65 nm/192.340625 THz 3.125GHz spacing";
             }
             enum "1558.63" {
               description "1558.63 nm/192.343750 THz 3.125/6.25GHz spacing";
             }
             enum "1558.60" {
               description "1558.60 nm/192.346875 THz 3.125GHz spacing";
             }
             enum "1558.58" {
               description "1558.58 nm/192.350000 THz 3.125/6.25/12.5/50GHz spacing";
             }
             enum "1558.55" {
               description "1558.55 nm/192.353125 THz 3.125GHz spacing";
             }
             enum "1558.53" {
               description "1558.53 nm/192.356250 THz 3.125/6.25GHz spacing";
             }
             enum "1558.50" {
               description "1558.50 nm/192.359375 THz 3.125GHz spacing";
             }
             enum "1558.48" {
               description "1558.48 nm/192.362500 THz 3.125/6.25/12.5GHz spacing";
             }
             enum "1558.45" {
               description "1558.45 nm/192.365625 THz 3.125GHz spacing";
             }
             enum "1558.43" {
               description "1558.43 nm/192.368750 THz 3.125/6.25GHz spacing";
             }
             enum "1558.40" {
               description "1558.40 nm/192.371875 THz 3.125GHz spacing";
             }
             enum "1558.38" {
               description "1558.38 nm/192.375000 THz 3.125/6.25/12.5/75GHz spacing";
             }
             enum "1558.35" {
               description "1558.35 nm/192.378125 THz 3.125GHz spacing";
             }
             enum "1558.32" {
               description "1558.32 nm/192.381250 THz 3.125/6.25GHz spacing";
             }
             enum "1558.30" {
               description "1558.30 nm/192.384375 THz 3.125GHz spacing";
             }
             enum "1558.27" {
               description "1558.27 nm/192.387500 THz 3.125/6.25/12.5GHz spacing";
             }
             enum "1558.25" {
               description "1558.25 nm/192.390625 THz 3.125GHz spacing";
             }
             enum "1558.22" {
               description "1558.22 nm/192.393750 THz 3.125/6.25GHz spacing";
             }
             enum "1558.20" {
               description "1558.20 nm/192.396875 THz 3.125GHz spacing";
             }
             enum "1558.17" {
               description "1558.17 nm/192.400000 THz 3.125/6.25/12.5/100GHz spacing";
             }
             enum "1558.15" {
               description "1558.15 nm/192.403125 THz 3.125GHz spacing";
             }
             enum "1558.12" {
               description "1558.12 nm/192.406250 THz 3.125/6.25GHz spacing";
             }
             enum "1558.10" {
               description "1558.10 nm/192.409375 THz 3.125GHz spacing";
             }
             enum "1558.07" {
               description "1558.07 nm/192.412500 THz 3.125/6.25/12.5GHz spacing";
             }
             enum "1558.05" {
               description "1558.05 nm/192.415625 THz 3.125GHz spacing";
             }
             enum "1558.02" {
               description "1558.02 nm/192.418750 THz 3.125/6.25GHz spacing";
             }
             enum "1558.00" {
               description "1558.00 nm/192.421875 THz 3.125GHz spacing";
             }
             enum "1557.97" {
               description "1557.97 nm/192.425000 THz 3.125/6.25/12.5GHz spacing";
             }
             enum "1557.95" {
               description "1557.95 nm/192.428125 THz 3.125GHz spacing";
             }
             enum "1557.92" {
               description "1557.92 nm/192.431250 THz 3.125/6.25GHz spacing";
             }
             enum "1557.89" {
               description "1557.89 nm/192.434375 THz 3.125GHz spacing";
             }
             enum "1557.87" {
               description "1557.87 nm/192.437500 THz 3.125/6.25/12.5GHz spacing";
             }
             enum "1557.84" {
               description "1557.84 nm/192.440625 THz 3.125GHz spacing";
             }
             enum "1557.82" {
               description "1557.82 nm/192.443750 THz 3.125/6.25GHz spacing";
             }
             enum "1557.79" {
               description "1557.79 nm/192.446875 THz 3.125GHz spacing";
             }
             enum "1557.77" {
               description "1557.77 nm/192.450000 THz 3.125/6.25/12.5/50/75GHz spacing";
             }
             enum "1557.74" {
               description "1557.74 nm/192.453125 THz 3.125GHz spacing";
             }
             enum "1557.72" {
               description "1557.72 nm/192.456250 THz 3.125/6.25GHz spacing";
             }
             enum "1557.69" {
               description "1557.69 nm/192.459375 THz 3.125GHz spacing";
             }
             enum "1557.67" {
               description "1557.67 nm/192.462500 THz 3.125/6.25/12.5GHz spacing";
             }
             enum "1557.64" {
               description "1557.64 nm/192.465625 THz 3.125GHz spacing";
             }
             enum "1557.62" {
               description "1557.62 nm/192.468750 THz 3.125/6.25GHz spacing";
             }
             enum "1557.59" {
               description "1557.59 nm/192.471875 THz 3.125GHz spacing";
             }
             enum "1557.57" {
               description "1557.57 nm/192.475000 THz 3.125/6.25/12.5GHz spacing";
             }
             enum "1557.54" {
               description "1557.54 nm/192.478125 THz 3.125GHz spacing";
             }
             enum "1557.52" {
               description "1557.52 nm/192.481250 THz 3.125/6.25GHz spacing";
             }
             enum "1557.49" {
               description "1557.49 nm/192.484375 THz 3.125GHz spacing";
             }
             enum "1557.46" {
               description "1557.46 nm/192.487500 THz 3.125/6.25/12.5GHz spacing";
             }
             enum "1557.44" {
               description "1557.44 nm/192.490625 THz 3.125GHz spacing";
             }
             enum "1557.41" {
               description "1557.41 nm/192.493750 THz 3.125/6.25GHz spacing";
             }
             enum "1557.39" {
               description "1557.39 nm/192.496875 THz 3.125GHz spacing";
             }
             enum "1557.36" {
               description "1557.36 nm/192.500000 THz 3.125/6.25/12.5/100GHz spacing";
             }
             enum "1557.34" {
               description "1557.34 nm/192.503125 THz 3.125GHz spacing";
             }
             enum "1557.31" {
               description "1557.31 nm/192.506250 THz 3.125/6.25GHz spacing";
             }
             enum "1557.29" {
               description "1557.29 nm/192.509375 THz 3.125GHz spacing";
             }
             enum "1557.26" {
               description "1557.26 nm/192.512500 THz 3.125/6.25/12.5GHz spacing";
             }
             enum "1557.24" {
               description "1557.24 nm/192.515625 THz 3.125GHz spacing";
             }
             enum "1557.21" {
               description "1557.21 nm/192.518750 THz 3.125/6.25GHz spacing";
             }
             enum "1557.19" {
               description "1557.19 nm/192.521875 THz 3.125GHz spacing";
             }
             enum "1557.16" {
               description "1557.16 nm/192.525000 THz 3.125/6.25/12.5/75GHz spacing";
             }
             enum "1557.14" {
               description "1557.14 nm/192.528125 THz 3.125GHz spacing";
             }
             enum "1557.11" {
               description "1557.11 nm/192.531250 THz 3.125/6.25GHz spacing";
             }
             enum "1557.09" {
               description "1557.09 nm/192.534375 THz 3.125GHz spacing";
             }
             enum "1557.06" {
               description "1557.06 nm/192.537500 THz 3.125/6.25/12.5GHz spacing";
             }
             enum "1557.03" {
               description "1557.03 nm/192.540625 THz 3.125GHz spacing";
             }
             enum "1557.01" {
               description "1557.01 nm/192.543750 THz 3.125/6.25GHz spacing";
             }
             enum "1556.98" {
               description "1556.98 nm/192.546875 THz 3.125GHz spacing";
             }
             enum "1556.96" {
               description "1556.96 nm/192.550000 THz 3.125/6.25/12.5/50GHz spacing";
             }
             enum "1556.93" {
               description "1556.93 nm/192.553125 THz 3.125GHz spacing";
             }
             enum "1556.91" {
               description "1556.91 nm/192.556250 THz 3.125/6.25GHz spacing";
             }
             enum "1556.88" {
               description "1556.88 nm/192.559375 THz 3.125GHz spacing";
             }
             enum "1556.86" {
               description "1556.86 nm/192.562500 THz 3.125/6.25/12.5GHz spacing";
             }
             enum "1556.83" {
               description "1556.83 nm/192.565625 THz 3.125GHz spacing";
             }
             enum "1556.81" {
               description "1556.81 nm/192.568750 THz 3.125/6.25GHz spacing";
             }
             enum "1556.78" {
               description "1556.78 nm/192.571875 THz 3.125GHz spacing";
             }
             enum "1556.76" {
               description "1556.76 nm/192.575000 THz 3.125/6.25/12.5GHz spacing";
             }
             enum "1556.73" {
               description "1556.73 nm/192.578125 THz 3.125GHz spacing";
             }
             enum "1556.71" {
               description "1556.71 nm/192.581250 THz 3.125/6.25GHz spacing";
             }
             enum "1556.68" {
               description "1556.68 nm/192.584375 THz 3.125GHz spacing";
             }
             enum "1556.66" {
               description "1556.66 nm/192.587500 THz 3.125/6.25/12.5GHz spacing";
             }
             enum "1556.63" {
               description "1556.63 nm/192.590625 THz 3.125GHz spacing";
             }
             enum "1556.61" {
               description "1556.61 nm/192.593750 THz 3.125/6.25GHz spacing";
             }
             enum "1556.58" {
               description "1556.58 nm/192.596875 THz 3.125GHz spacing";
             }
             enum "1556.55" {
               description "1556.55 nm/192.600000 THz 3.125/6.25/12.5/50/75/100GHz spacing";
             }
             enum "1556.53" {
               description "1556.53 nm/192.603125 THz 3.125GHz spacing";
             }
             enum "1556.50" {
               description "1556.50 nm/192.606250 THz 3.125/6.25GHz spacing";
             }
             enum "1556.48" {
               description "1556.48 nm/192.609375 THz 3.125GHz spacing";
             }
             enum "1556.45" {
               description "1556.45 nm/192.612500 THz 3.125/6.25/12.5GHz spacing";
             }
             enum "1556.43" {
               description "1556.43 nm/192.615625 THz 3.125GHz spacing";
             }
             enum "1556.40" {
               description "1556.40 nm/192.618750 THz 3.125/6.25GHz spacing";
             }
             enum "1556.38" {
               description "1556.38 nm/192.621875 THz 3.125GHz spacing";
             }
             enum "1556.35" {
               description "1556.35 nm/192.625000 THz 3.125/6.25/12.5GHz spacing";
             }
             enum "1556.33" {
               description "1556.33 nm/192.628125 THz 3.125GHz spacing";
             }
             enum "1556.30" {
               description "1556.30 nm/192.631250 THz 3.125/6.25GHz spacing";
             }
             enum "1556.28" {
               description "1556.28 nm/192.634375 THz 3.125GHz spacing";
             }
             enum "1556.25" {
               description "1556.25 nm/192.637500 THz 3.125/6.25/12.5GHz spacing";
             }
             enum "1556.23" {
               description "1556.23 nm/192.640625 THz 3.125GHz spacing";
             }
             enum "1556.20" {
               description "1556.20 nm/192.643750 THz 3.125/6.25GHz spacing";
             }
             enum "1556.18" {
               description "1556.18 nm/192.646875 THz 3.125GHz spacing";
             }
             enum "1556.15" {
               description "1556.15 nm/192.650000 THz 3.125/6.25/12.5/50GHz spacing";
             }
             enum "1556.13" {
               description "1556.13 nm/192.653125 THz 3.125GHz spacing";
             }
             enum "1556.10" {
               description "1556.10 nm/192.656250 THz 3.125/6.25GHz spacing";
             }
             enum "1556.08" {
               description "1556.08 nm/192.659375 THz 3.125GHz spacing";
             }
             enum "1556.05" {
               description "1556.05 nm/192.662500 THz 3.125/6.25/12.5GHz spacing";
             }
             enum "1556.02" {
               description "1556.02 nm/192.665625 THz 3.125GHz spacing";
             }
             enum "1556.00" {
               description "1556.00 nm/192.668750 THz 3.125/6.25GHz spacing";
             }
             enum "1555.97" {
               description "1555.97 nm/192.671875 THz 3.125GHz spacing";
             }
             enum "1555.95" {
               description "1555.95 nm/192.675000 THz 3.125/6.25/12.5/75GHz spacing";
             }
             enum "1555.92" {
               description "1555.92 nm/192.678125 THz 3.125GHz spacing";
             }
             enum "1555.90" {
               description "1555.90 nm/192.681250 THz 3.125/6.25GHz spacing";
             }
             enum "1555.87" {
               description "1555.87 nm/192.684375 THz 3.125GHz spacing";
             }
             enum "1555.85" {
               description "1555.85 nm/192.687500 THz 3.125/6.25/12.5GHz spacing";
             }
             enum "1555.82" {
               description "1555.82 nm/192.690625 THz 3.125GHz spacing";
             }
             enum "1555.80" {
               description "1555.80 nm/192.693750 THz 3.125/6.25GHz spacing";
             }
             enum "1555.77" {
               description "1555.77 nm/192.696875 THz 3.125GHz spacing";
             }
             enum "1555.75" {
               description "1555.75 nm/192.700000 THz 3.125/6.25/12.5/100GHz spacing";
             }
             enum "1555.72" {
               description "1555.72 nm/192.703125 THz 3.125GHz spacing";
             }
             enum "1555.70" {
               description "1555.70 nm/192.706250 THz 3.125/6.25GHz spacing";
             }
             enum "1555.67" {
               description "1555.67 nm/192.709375 THz 3.125GHz spacing";
             }
             enum "1555.65" {
               description "1555.65 nm/192.712500 THz 3.125/6.25/12.5GHz spacing";
             }
             enum "1555.62" {
               description "1555.62 nm/192.715625 THz 3.125GHz spacing";
             }
             enum "1555.60" {
               description "1555.60 nm/192.718750 THz 3.125/6.25GHz spacing";
             }
             enum "1555.57" {
               description "1555.57 nm/192.721875 THz 3.125GHz spacing";
             }
             enum "1555.55" {
               description "1555.55 nm/192.725000 THz 3.125/6.25/12.5GHz spacing";
             }
             enum "1555.52" {
               description "1555.52 nm/192.728125 THz 3.125GHz spacing";
             }
             enum "1555.49" {
               description "1555.49 nm/192.731250 THz 3.125/6.25GHz spacing";
             }
             enum "1555.47" {
               description "1555.47 nm/192.734375 THz 3.125GHz spacing";
             }
             enum "1555.44" {
               description "1555.44 nm/192.737500 THz 3.125/6.25/12.5GHz spacing";
             }
             enum "1555.42" {
               description "1555.42 nm/192.740625 THz 3.125GHz spacing";
             }
             enum "1555.39" {
               description "1555.39 nm/192.743750 THz 3.125/6.25GHz spacing";
             }
             enum "1555.37" {
               description "1555.37 nm/192.746875 THz 3.125GHz spacing";
             }
             enum "1555.34" {
               description "1555.34 nm/192.750000 THz 3.125/6.25/12.5/50/75GHz spacing";
             }
             enum "1555.32" {
               description "1555.32 nm/192.753125 THz 3.125GHz spacing";
             }
             enum "1555.29" {
               description "1555.29 nm/192.756250 THz 3.125/6.25GHz spacing";
             }
             enum "1555.27" {
               description "1555.27 nm/192.759375 THz 3.125GHz spacing";
             }
             enum "1555.24" {
               description "1555.24 nm/192.762500 THz 3.125/6.25/12.5GHz spacing";
             }
             enum "1555.22" {
               description "1555.22 nm/192.765625 THz 3.125GHz spacing";
             }
             enum "1555.19" {
               description "1555.19 nm/192.768750 THz 3.125/6.25GHz spacing";
             }
             enum "1555.17" {
               description "1555.17 nm/192.771875 THz 3.125GHz spacing";
             }
             enum "1555.14" {
               description "1555.14 nm/192.775000 THz 3.125/6.25/12.5GHz spacing";
             }
             enum "1555.12" {
               description "1555.12 nm/192.778125 THz 3.125GHz spacing";
             }
             enum "1555.09" {
               description "1555.09 nm/192.781250 THz 3.125/6.25GHz spacing";
             }
             enum "1555.07" {
               description "1555.07 nm/192.784375 THz 3.125GHz spacing";
             }
             enum "1555.04" {
               description "1555.04 nm/192.787500 THz 3.125/6.25/12.5GHz spacing";
             }
             enum "1555.02" {
               description "1555.02 nm/192.790625 THz 3.125GHz spacing";
             }
             enum "1554.99" {
               description "1554.99 nm/192.793750 THz 3.125/6.25GHz spacing";
             }
             enum "1554.97" {
               description "1554.97 nm/192.796875 THz 3.125GHz spacing";
             }
             enum "1554.94" {
               description "1554.94 nm/192.800000 THz 3.125/6.25/12.5/100GHz spacing";
             }
             enum "1554.91" {
               description "1554.91 nm/192.803125 THz 3.125GHz spacing";
             }
             enum "1554.89" {
               description "1554.89 nm/192.806250 THz 3.125/6.25GHz spacing";
             }
             enum "1554.86" {
               description "1554.86 nm/192.809375 THz 3.125GHz spacing";
             }
             enum "1554.84" {
               description "1554.84 nm/192.812500 THz 3.125/6.25/12.5GHz spacing";
             }
             enum "1554.81" {
               description "1554.81 nm/192.815625 THz 3.125GHz spacing";
             }
             enum "1554.79" {
               description "1554.79 nm/192.818750 THz 3.125/6.25GHz spacing";
             }
             enum "1554.76" {
               description "1554.76 nm/192.821875 THz 3.125GHz spacing";
             }
             enum "1554.74" {
               description "1554.74 nm/192.825000 THz 3.125/6.25/12.5/75GHz spacing";
             }
             enum "1554.71" {
               description "1554.71 nm/192.828125 THz 3.125GHz spacing";
             }
             enum "1554.69" {
               description "1554.69 nm/192.831250 THz 3.125/6.25GHz spacing";
             }
             enum "1554.66" {
               description "1554.66 nm/192.834375 THz 3.125GHz spacing";
             }
             enum "1554.64" {
               description "1554.64 nm/192.837500 THz 3.125/6.25/12.5GHz spacing";
             }
             enum "1554.61" {
               description "1554.61 nm/192.840625 THz 3.125GHz spacing";
             }
             enum "1554.59" {
               description "1554.59 nm/192.843750 THz 3.125/6.25GHz spacing";
             }
             enum "1554.56" {
               description "1554.56 nm/192.846875 THz 3.125GHz spacing";
             }
             enum "1554.54" {
               description "1554.54 nm/192.850000 THz 3.125/6.25/12.5/50GHz spacing";
             }
             enum "1554.51" {
               description "1554.51 nm/192.853125 THz 3.125GHz spacing";
             }
             enum "1554.49" {
               description "1554.49 nm/192.856250 THz 3.125/6.25GHz spacing";
             }
             enum "1554.46" {
               description "1554.46 nm/192.859375 THz 3.125GHz spacing";
             }
             enum "1554.44" {
               description "1554.44 nm/192.862500 THz 3.125/6.25/12.5GHz spacing";
             }
             enum "1554.41" {
               description "1554.41 nm/192.865625 THz 3.125GHz spacing";
             }
             enum "1554.39" {
               description "1554.39 nm/192.868750 THz 3.125/6.25GHz spacing";
             }
             enum "1554.36" {
               description "1554.36 nm/192.871875 THz 3.125GHz spacing";
             }
             enum "1554.34" {
               description "1554.34 nm/192.875000 THz 3.125/6.25/12.5GHz spacing";
             }
             enum "1554.31" {
               description "1554.31 nm/192.878125 THz 3.125GHz spacing";
             }
             enum "1554.29" {
               description "1554.29 nm/192.881250 THz 3.125/6.25GHz spacing";
             }
             enum "1554.26" {
               description "1554.26 nm/192.884375 THz 3.125GHz spacing";
             }
             enum "1554.23" {
               description "1554.23 nm/192.887500 THz 3.125/6.25/12.5GHz spacing";
             }
             enum "1554.21" {
               description "1554.21 nm/192.890625 THz 3.125GHz spacing";
             }
             enum "1554.18" {
               description "1554.18 nm/192.893750 THz 3.125/6.25GHz spacing";
             }
             enum "1554.16" {
               description "1554.16 nm/192.896875 THz 3.125GHz spacing";
             }
             enum "1554.13" {
               description "1554.13 nm/192.900000 THz 3.125/6.25/12.5/50/75/100GHz spacing";
             }
             enum "1554.11" {
               description "1554.11 nm/192.903125 THz 3.125GHz spacing";
             }
             enum "1554.08" {
               description "1554.08 nm/192.906250 THz 3.125/6.25GHz spacing";
             }
             enum "1554.06" {
               description "1554.06 nm/192.909375 THz 3.125GHz spacing";
             }
             enum "1554.03" {
               description "1554.03 nm/192.912500 THz 3.125/6.25/12.5GHz spacing";
             }
             enum "1554.01" {
               description "1554.01 nm/192.915625 THz 3.125GHz spacing";
             }
             enum "1553.98" {
               description "1553.98 nm/192.918750 THz 3.125/6.25GHz spacing";
             }
             enum "1553.96" {
               description "1553.96 nm/192.921875 THz 3.125GHz spacing";
             }
             enum "1553.93" {
               description "1553.93 nm/192.925000 THz 3.125/6.25/12.5GHz spacing";
             }
             enum "1553.91" {
               description "1553.91 nm/192.928125 THz 3.125GHz spacing";
             }
             enum "1553.88" {
               description "1553.88 nm/192.931250 THz 3.125/6.25GHz spacing";
             }
             enum "1553.86" {
               description "1553.86 nm/192.934375 THz 3.125GHz spacing";
             }
             enum "1553.83" {
               description "1553.83 nm/192.937500 THz 3.125/6.25/12.5GHz spacing";
             }
             enum "1553.81" {
               description "1553.81 nm/192.940625 THz 3.125GHz spacing";
             }
             enum "1553.78" {
               description "1553.78 nm/192.943750 THz 3.125/6.25GHz spacing";
             }
             enum "1553.76" {
               description "1553.76 nm/192.946875 THz 3.125GHz spacing";
             }
             enum "1553.73" {
               description "1553.73 nm/192.950000 THz 3.125/6.25/12.5/50GHz spacing";
             }
             enum "1553.71" {
               description "1553.71 nm/192.953125 THz 3.125GHz spacing";
             }
             enum "1553.68" {
               description "1553.68 nm/192.956250 THz 3.125/6.25GHz spacing";
             }
             enum "1553.66" {
               description "1553.66 nm/192.959375 THz 3.125GHz spacing";
             }
             enum "1553.63" {
               description "1553.63 nm/192.962500 THz 3.125/6.25/12.5GHz spacing";
             }
             enum "1553.61" {
               description "1553.61 nm/192.965625 THz 3.125GHz spacing";
             }
             enum "1553.58" {
               description "1553.58 nm/192.968750 THz 3.125/6.25GHz spacing";
             }
             enum "1553.56" {
               description "1553.56 nm/192.971875 THz 3.125GHz spacing";
             }
             enum "1553.53" {
               description "1553.53 nm/192.975000 THz 3.125/6.25/12.5/75GHz spacing";
             }
             enum "1553.50" {
               description "1553.50 nm/192.978125 THz 3.125GHz spacing";
             }
             enum "1553.48" {
               description "1553.48 nm/192.981250 THz 3.125/6.25GHz spacing";
             }
             enum "1553.45" {
               description "1553.45 nm/192.984375 THz 3.125GHz spacing";
             }
             enum "1553.43" {
               description "1553.43 nm/192.987500 THz 3.125/6.25/12.5GHz spacing";
             }
             enum "1553.40" {
               description "1553.40 nm/192.990625 THz 3.125GHz spacing";
             }
             enum "1553.38" {
               description "1553.38 nm/192.993750 THz 3.125/6.25GHz spacing";
             }
             enum "1553.35" {
               description "1553.35 nm/192.996875 THz 3.125GHz spacing";
             }
             enum "1553.33" {
               description "1553.33 nm/193.000000 THz 3.125/6.25/12.5/100GHz spacing";
             }
             enum "1553.30" {
               description "1553.30 nm/193.003125 THz 3.125GHz spacing";
             }
             enum "1553.28" {
               description "1553.28 nm/193.006250 THz 3.125/6.25GHz spacing";
             }
             enum "1553.25" {
               description "1553.25 nm/193.009375 THz 3.125GHz spacing";
             }
             enum "1553.23" {
               description "1553.23 nm/193.012500 THz 3.125/6.25/12.5GHz spacing";
             }
             enum "1553.20" {
               description "1553.20 nm/193.015625 THz 3.125GHz spacing";
             }
             enum "1553.18" {
               description "1553.18 nm/193.018750 THz 3.125/6.25GHz spacing";
             }
             enum "1553.15" {
               description "1553.15 nm/193.021875 THz 3.125GHz spacing";
             }
             enum "1553.13" {
               description "1553.13 nm/193.025000 THz 3.125/6.25/12.5GHz spacing";
             }
             enum "1553.10" {
               description "1553.10 nm/193.028125 THz 3.125GHz spacing";
             }
             enum "1553.08" {
               description "1553.08 nm/193.031250 THz 3.125/6.25GHz spacing";
             }
             enum "1553.05" {
               description "1553.05 nm/193.034375 THz 3.125GHz spacing";
             }
             enum "1553.03" {
               description "1553.03 nm/193.037500 THz 3.125/6.25/12.5GHz spacing";
             }
             enum "1553.00" {
               description "1553.00 nm/193.040625 THz 3.125GHz spacing";
             }
             enum "1552.98" {
               description "1552.98 nm/193.043750 THz 3.125/6.25GHz spacing";
             }
             enum "1552.95" {
               description "1552.95 nm/193.046875 THz 3.125GHz spacing";
             }
             enum "1552.93" {
               description "1552.93 nm/193.050000 THz 3.125/6.25/12.5/50/75GHz spacing";
             }
             enum "1552.90" {
               description "1552.90 nm/193.053125 THz 3.125GHz spacing";
             }
             enum "1552.88" {
               description "1552.88 nm/193.056250 THz 3.125/6.25GHz spacing";
             }
             enum "1552.85" {
               description "1552.85 nm/193.059375 THz 3.125GHz spacing";
             }
             enum "1552.83" {
               description "1552.83 nm/193.062500 THz 3.125/6.25/12.5GHz spacing";
             }
             enum "1552.80" {
               description "1552.80 nm/193.065625 THz 3.125GHz spacing";
             }
             enum "1552.78" {
               description "1552.78 nm/193.068750 THz 3.125/6.25GHz spacing";
             }
             enum "1552.75" {
               description "1552.75 nm/193.071875 THz 3.125GHz spacing";
             }
             enum "1552.73" {
               description "1552.73 nm/193.075000 THz 3.125/6.25/12.5GHz spacing";
             }
             enum "1552.70" {
               description "1552.70 nm/193.078125 THz 3.125GHz spacing";
             }
             enum "1552.68" {
               description "1552.68 nm/193.081250 THz 3.125/6.25GHz spacing";
             }
             enum "1552.65" {
               description "1552.65 nm/193.084375 THz 3.125GHz spacing";
             }
             enum "1552.62" {
               description "1552.62 nm/193.087500 THz 3.125/6.25/12.5GHz spacing";
             }
             enum "1552.60" {
               description "1552.60 nm/193.090625 THz 3.125GHz spacing";
             }
             enum "1552.57" {
               description "1552.57 nm/193.093750 THz 3.125/6.25GHz spacing";
             }
             enum "1552.55" {
               description "1552.55 nm/193.096875 THz 3.125GHz spacing";
             }
             enum "1552.52" {
               description "1552.52 nm/193.100000 THz 3.125/6.25/12.5/100GHz spacing";
             }
             enum "1552.50" {
               description "1552.50 nm/193.103125 THz 3.125GHz spacing";
             }
             enum "1552.47" {
               description "1552.47 nm/193.106250 THz 3.125/6.25GHz spacing";
             }
             enum "1552.45" {
               description "1552.45 nm/193.109375 THz 3.125GHz spacing";
             }
             enum "1552.42" {
               description "1552.42 nm/193.112500 THz 3.125/6.25/12.5GHz spacing";
             }
             enum "1552.40" {
               description "1552.40 nm/193.115625 THz 3.125GHz spacing";
             }
             enum "1552.37" {
               description "1552.37 nm/193.118750 THz 3.125/6.25GHz spacing";
             }
             enum "1552.35" {
               description "1552.35 nm/193.121875 THz 3.125GHz spacing";
             }
             enum "1552.32" {
               description "1552.32 nm/193.125000 THz 3.125/6.25/12.5/75GHz spacing";
             }
             enum "1552.30" {
               description "1552.30 nm/193.128125 THz 3.125GHz spacing";
             }
             enum "1552.27" {
               description "1552.27 nm/193.131250 THz 3.125/6.25GHz spacing";
             }
             enum "1552.25" {
               description "1552.25 nm/193.134375 THz 3.125GHz spacing";
             }
             enum "1552.22" {
               description "1552.22 nm/193.137500 THz 3.125/6.25/12.5GHz spacing";
             }
             enum "1552.20" {
               description "1552.20 nm/193.140625 THz 3.125GHz spacing";
             }
             enum "1552.17" {
               description "1552.17 nm/193.143750 THz 3.125/6.25GHz spacing";
             }
             enum "1552.15" {
               description "1552.15 nm/193.146875 THz 3.125GHz spacing";
             }
             enum "1552.12" {
               description "1552.12 nm/193.150000 THz 3.125/6.25/12.5/50GHz spacing";
             }
             enum "1552.10" {
               description "1552.10 nm/193.153125 THz 3.125GHz spacing";
             }
             enum "1552.07" {
               description "1552.07 nm/193.156250 THz 3.125/6.25GHz spacing";
             }
             enum "1552.05" {
               description "1552.05 nm/193.159375 THz 3.125GHz spacing";
             }
             enum "1552.02" {
               description "1552.02 nm/193.162500 THz 3.125/6.25/12.5GHz spacing";
             }
             enum "1552.00" {
               description "1552.00 nm/193.165625 THz 3.125GHz spacing";
             }
             enum "1551.97" {
               description "1551.97 nm/193.168750 THz 3.125/6.25GHz spacing";
             }
             enum "1551.95" {
               description "1551.95 nm/193.171875 THz 3.125GHz spacing";
             }
             enum "1551.92" {
               description "1551.92 nm/193.175000 THz 3.125/6.25/12.5GHz spacing";
             }
             enum "1551.90" {
               description "1551.90 nm/193.178125 THz 3.125GHz spacing";
             }
             enum "1551.87" {
               description "1551.87 nm/193.181250 THz 3.125/6.25GHz spacing";
             }
             enum "1551.85" {
               description "1551.85 nm/193.184375 THz 3.125GHz spacing";
             }
             enum "1551.82" {
               description "1551.82 nm/193.187500 THz 3.125/6.25/12.5GHz spacing";
             }
             enum "1551.80" {
               description "1551.80 nm/193.190625 THz 3.125GHz spacing";
             }
             enum "1551.77" {
               description "1551.77 nm/193.193750 THz 3.125/6.25GHz spacing";
             }
             enum "1551.75" {
               description "1551.75 nm/193.196875 THz 3.125GHz spacing";
             }
             enum "1551.72" {
               description "1551.72 nm/193.200000 THz 3.125/6.25/12.5/50/75/100GHz spacing";
             }
             enum "1551.70" {
               description "1551.70 nm/193.203125 THz 3.125GHz spacing";
             }
             enum "1551.67" {
               description "1551.67 nm/193.206250 THz 3.125/6.25GHz spacing";
             }
             enum "1551.65" {
               description "1551.65 nm/193.209375 THz 3.125GHz spacing";
             }
             enum "1551.62" {
               description "1551.62 nm/193.212500 THz 3.125/6.25/12.5GHz spacing";
             }
             enum "1551.60" {
               description "1551.60 nm/193.215625 THz 3.125GHz spacing";
             }
             enum "1551.57" {
               description "1551.57 nm/193.218750 THz 3.125/6.25GHz spacing";
             }
             enum "1551.55" {
               description "1551.55 nm/193.221875 THz 3.125GHz spacing";
             }
             enum "1551.52" {
               description "1551.52 nm/193.225000 THz 3.125/6.25/12.5GHz spacing";
             }
             enum "1551.49" {
               description "1551.49 nm/193.228125 THz 3.125GHz spacing";
             }
             enum "1551.47" {
               description "1551.47 nm/193.231250 THz 3.125/6.25GHz spacing";
             }
             enum "1551.44" {
               description "1551.44 nm/193.234375 THz 3.125GHz spacing";
             }
             enum "1551.42" {
               description "1551.42 nm/193.237500 THz 3.125/6.25/12.5GHz spacing";
             }
             enum "1551.39" {
               description "1551.39 nm/193.240625 THz 3.125GHz spacing";
             }
             enum "1551.37" {
               description "1551.37 nm/193.243750 THz 3.125/6.25GHz spacing";
             }
             enum "1551.34" {
               description "1551.34 nm/193.246875 THz 3.125GHz spacing";
             }
             enum "1551.32" {
               description "1551.32 nm/193.250000 THz 3.125/6.25/12.5/50GHz spacing";
             }
             enum "1551.29" {
               description "1551.29 nm/193.253125 THz 3.125GHz spacing";
             }
             enum "1551.27" {
               description "1551.27 nm/193.256250 THz 3.125/6.25GHz spacing";
             }
             enum "1551.24" {
               description "1551.24 nm/193.259375 THz 3.125GHz spacing";
             }
             enum "1551.22" {
               description "1551.22 nm/193.262500 THz 3.125/6.25/12.5GHz spacing";
             }
             enum "1551.19" {
               description "1551.19 nm/193.265625 THz 3.125GHz spacing";
             }
             enum "1551.17" {
               description "1551.17 nm/193.268750 THz 3.125/6.25GHz spacing";
             }
             enum "1551.14" {
               description "1551.14 nm/193.271875 THz 3.125GHz spacing";
             }
             enum "1551.12" {
               description "1551.12 nm/193.275000 THz 3.125/6.25/12.5/75GHz spacing";
             }
             enum "1551.09" {
               description "1551.09 nm/193.278125 THz 3.125GHz spacing";
             }
             enum "1551.07" {
               description "1551.07 nm/193.281250 THz 3.125/6.25GHz spacing";
             }
             enum "1551.04" {
               description "1551.04 nm/193.284375 THz 3.125GHz spacing";
             }
             enum "1551.02" {
               description "1551.02 nm/193.287500 THz 3.125/6.25/12.5GHz spacing";
             }
             enum "1550.99" {
               description "1550.99 nm/193.290625 THz 3.125GHz spacing";
             }
             enum "1550.97" {
               description "1550.97 nm/193.293750 THz 3.125/6.25GHz spacing";
             }
             enum "1550.94" {
               description "1550.94 nm/193.296875 THz 3.125GHz spacing";
             }
             enum "1550.92" {
               description "1550.92 nm/193.300000 THz 3.125/6.25/12.5/100GHz spacing";
             }
             enum "1550.89" {
               description "1550.89 nm/193.303125 THz 3.125GHz spacing";
             }
             enum "1550.87" {
               description "1550.87 nm/193.306250 THz 3.125/6.25GHz spacing";
             }
             enum "1550.84" {
               description "1550.84 nm/193.309375 THz 3.125GHz spacing";
             }
             enum "1550.82" {
               description "1550.82 nm/193.312500 THz 3.125/6.25/12.5GHz spacing";
             }
             enum "1550.79" {
               description "1550.79 nm/193.315625 THz 3.125GHz spacing";
             }
             enum "1550.77" {
               description "1550.77 nm/193.318750 THz 3.125/6.25GHz spacing";
             }
             enum "1550.74" {
               description "1550.74 nm/193.321875 THz 3.125GHz spacing";
             }
             enum "1550.72" {
               description "1550.72 nm/193.325000 THz 3.125/6.25/12.5GHz spacing";
             }
             enum "1550.69" {
               description "1550.69 nm/193.328125 THz 3.125GHz spacing";
             }
             enum "1550.67" {
               description "1550.67 nm/193.331250 THz 3.125/6.25GHz spacing";
             }
             enum "1550.64" {
               description "1550.64 nm/193.334375 THz 3.125GHz spacing";
             }
             enum "1550.62" {
               description "1550.62 nm/193.337500 THz 3.125/6.25/12.5GHz spacing";
             }
             enum "1550.59" {
               description "1550.59 nm/193.340625 THz 3.125GHz spacing";
             }
             enum "1550.57" {
               description "1550.57 nm/193.343750 THz 3.125/6.25GHz spacing";
             }
             enum "1550.54" {
               description "1550.54 nm/193.346875 THz 3.125GHz spacing";
             }
             enum "1550.52" {
               description "1550.52 nm/193.350000 THz 3.125/6.25/12.5/50/75GHz spacing";
             }
             enum "1550.49" {
               description "1550.49 nm/193.353125 THz 3.125GHz spacing";
             }
             enum "1550.47" {
               description "1550.47 nm/193.356250 THz 3.125/6.25GHz spacing";
             }
             enum "1550.44" {
               description "1550.44 nm/193.359375 THz 3.125GHz spacing";
             }
             enum "1550.42" {
               description "1550.42 nm/193.362500 THz 3.125/6.25/12.5GHz spacing";
             }
             enum "1550.39" {
               description "1550.39 nm/193.365625 THz 3.125GHz spacing";
             }
             enum "1550.37" {
               description "1550.37 nm/193.368750 THz 3.125/6.25GHz spacing";
             }
             enum "1550.34" {
               description "1550.34 nm/193.371875 THz 3.125GHz spacing";
             }
             enum "1550.32" {
               description "1550.32 nm/193.375000 THz 3.125/6.25/12.5GHz spacing";
             }
             enum "1550.29" {
               description "1550.29 nm/193.378125 THz 3.125GHz spacing";
             }
             enum "1550.27" {
               description "1550.27 nm/193.381250 THz 3.125/6.25GHz spacing";
             }
             enum "1550.24" {
               description "1550.24 nm/193.384375 THz 3.125GHz spacing";
             }
             enum "1550.22" {
               description "1550.22 nm/193.387500 THz 3.125/6.25/12.5GHz spacing";
             }
             enum "1550.19" {
               description "1550.19 nm/193.390625 THz 3.125GHz spacing";
             }
             enum "1550.17" {
               description "1550.17 nm/193.393750 THz 3.125/6.25GHz spacing";
             }
             enum "1550.14" {
               description "1550.14 nm/193.396875 THz 3.125GHz spacing";
             }
             enum "1550.12" {
               description "1550.12 nm/193.400000 THz 3.125/6.25/12.5/100GHz spacing";
             }
             enum "1550.09" {
               description "1550.09 nm/193.403125 THz 3.125GHz spacing";
             }
             enum "1550.07" {
               description "1550.07 nm/193.406250 THz 3.125/6.25GHz spacing";
             }
             enum "1550.04" {
               description "1550.04 nm/193.409375 THz 3.125GHz spacing";
             }
             enum "1550.02" {
               description "1550.02 nm/193.412500 THz 3.125/6.25/12.5GHz spacing";
             }
             enum "1549.99" {
               description "1549.99 nm/193.415625 THz 3.125GHz spacing";
             }
             enum "1549.97" {
               description "1549.97 nm/193.418750 THz 3.125/6.25GHz spacing";
             }
             enum "1549.94" {
               description "1549.94 nm/193.421875 THz 3.125GHz spacing";
             }
             enum "1549.92" {
               description "1549.92 nm/193.425000 THz 3.125/6.25/12.5/75GHz spacing";
             }
             enum "1549.89" {
               description "1549.89 nm/193.428125 THz 3.125GHz spacing";
             }
             enum "1549.87" {
               description "1549.87 nm/193.431250 THz 3.125/6.25GHz spacing";
             }
             enum "1549.84" {
               description "1549.84 nm/193.434375 THz 3.125GHz spacing";
             }
             enum "1549.82" {
               description "1549.82 nm/193.437500 THz 3.125/6.25/12.5GHz spacing";
             }
             enum "1549.79" {
               description "1549.79 nm/193.440625 THz 3.125GHz spacing";
             }
             enum "1549.77" {
               description "1549.77 nm/193.443750 THz 3.125/6.25GHz spacing";
             }
             enum "1549.74" {
               description "1549.74 nm/193.446875 THz 3.125GHz spacing";
             }
             enum "1549.72" {
               description "1549.72 nm/193.450000 THz 3.125/6.25/12.5/50GHz spacing";
             }
             enum "1549.69" {
               description "1549.69 nm/193.453125 THz 3.125GHz spacing";
             }
             enum "1549.67" {
               description "1549.67 nm/193.456250 THz 3.125/6.25GHz spacing";
             }
             enum "1549.64" {
               description "1549.64 nm/193.459375 THz 3.125GHz spacing";
             }
             enum "1549.62" {
               description "1549.62 nm/193.462500 THz 3.125/6.25/12.5GHz spacing";
             }
             enum "1549.59" {
               description "1549.59 nm/193.465625 THz 3.125GHz spacing";
             }
             enum "1549.57" {
               description "1549.57 nm/193.468750 THz 3.125/6.25GHz spacing";
             }
             enum "1549.54" {
               description "1549.54 nm/193.471875 THz 3.125GHz spacing";
             }
             enum "1549.52" {
               description "1549.52 nm/193.475000 THz 3.125/6.25/12.5GHz spacing";
             }
             enum "1549.49" {
               description "1549.49 nm/193.478125 THz 3.125GHz spacing";
             }
             enum "1549.47" {
               description "1549.47 nm/193.481250 THz 3.125/6.25GHz spacing";
             }
             enum "1549.44" {
               description "1549.44 nm/193.484375 THz 3.125GHz spacing";
             }
             enum "1549.42" {
               description "1549.42 nm/193.487500 THz 3.125/6.25/12.5GHz spacing";
             }
             enum "1549.39" {
               description "1549.39 nm/193.490625 THz 3.125GHz spacing";
             }
             enum "1549.37" {
               description "1549.37 nm/193.493750 THz 3.125/6.25GHz spacing";
             }
             enum "1549.34" {
               description "1549.34 nm/193.496875 THz 3.125GHz spacing";
             }
             enum "1549.32" {
               description "1549.32 nm/193.500000 THz 3.125/6.25/12.5/50/75/100GHz spacing";
             }
             enum "1549.29" {
               description "1549.29 nm/193.503125 THz 3.125GHz spacing";
             }
             enum "1549.26" {
               description "1549.26 nm/193.506250 THz 3.125/6.25GHz spacing";
             }
             enum "1549.24" {
               description "1549.24 nm/193.509375 THz 3.125GHz spacing";
             }
             enum "1549.21" {
               description "1549.21 nm/193.512500 THz 3.125/6.25/12.5GHz spacing";
             }
             enum "1549.19" {
               description "1549.19 nm/193.515625 THz 3.125GHz spacing";
             }
             enum "1549.16" {
               description "1549.16 nm/193.518750 THz 3.125/6.25GHz spacing";
             }
             enum "1549.14" {
               description "1549.14 nm/193.521875 THz 3.125GHz spacing";
             }
             enum "1549.11" {
               description "1549.11 nm/193.525000 THz 3.125/6.25/12.5GHz spacing";
             }
             enum "1549.09" {
               description "1549.09 nm/193.528125 THz 3.125GHz spacing";
             }
             enum "1549.06" {
               description "1549.06 nm/193.531250 THz 3.125/6.25GHz spacing";
             }
             enum "1549.04" {
               description "1549.04 nm/193.534375 THz 3.125GHz spacing";
             }
             enum "1549.01" {
               description "1549.01 nm/193.537500 THz 3.125/6.25/12.5GHz spacing";
             }
             enum "1548.99" {
               description "1548.99 nm/193.540625 THz 3.125GHz spacing";
             }
             enum "1548.96" {
               description "1548.96 nm/193.543750 THz 3.125/6.25GHz spacing";
             }
             enum "1548.94" {
               description "1548.94 nm/193.546875 THz 3.125GHz spacing";
             }
             enum "1548.91" {
               description "1548.91 nm/193.550000 THz 3.125/6.25/12.5/50GHz spacing";
             }
             enum "1548.89" {
               description "1548.89 nm/193.553125 THz 3.125GHz spacing";
             }
             enum "1548.86" {
               description "1548.86 nm/193.556250 THz 3.125/6.25GHz spacing";
             }
             enum "1548.84" {
               description "1548.84 nm/193.559375 THz 3.125GHz spacing";
             }
             enum "1548.81" {
               description "1548.81 nm/193.562500 THz 3.125/6.25/12.5GHz spacing";
             }
             enum "1548.79" {
               description "1548.79 nm/193.565625 THz 3.125GHz spacing";
             }
             enum "1548.76" {
               description "1548.76 nm/193.568750 THz 3.125/6.25GHz spacing";
             }
             enum "1548.74" {
               description "1548.74 nm/193.571875 THz 3.125GHz spacing";
             }
             enum "1548.71" {
               description "1548.71 nm/193.575000 THz 3.125/6.25/12.5/75GHz spacing";
             }
             enum "1548.69" {
               description "1548.69 nm/193.578125 THz 3.125GHz spacing";
             }
             enum "1548.66" {
               description "1548.66 nm/193.581250 THz 3.125/6.25GHz spacing";
             }
             enum "1548.64" {
               description "1548.64 nm/193.584375 THz 3.125GHz spacing";
             }
             enum "1548.61" {
               description "1548.61 nm/193.587500 THz 3.125/6.25/12.5GHz spacing";
             }
             enum "1548.59" {
               description "1548.59 nm/193.590625 THz 3.125GHz spacing";
             }
             enum "1548.56" {
               description "1548.56 nm/193.593750 THz 3.125/6.25GHz spacing";
             }
             enum "1548.54" {
               description "1548.54 nm/193.596875 THz 3.125GHz spacing";
             }
             enum "1548.51" {
               description "1548.51 nm/193.600000 THz 3.125/6.25/12.5/100GHz spacing";
             }
             enum "1548.49" {
               description "1548.49 nm/193.603125 THz 3.125GHz spacing";
             }
             enum "1548.46" {
               description "1548.46 nm/193.606250 THz 3.125/6.25GHz spacing";
             }
             enum "1548.44" {
               description "1548.44 nm/193.609375 THz 3.125GHz spacing";
             }
             enum "1548.41" {
               description "1548.41 nm/193.612500 THz 3.125/6.25/12.5GHz spacing";
             }
             enum "1548.39" {
               description "1548.39 nm/193.615625 THz 3.125GHz spacing";
             }
             enum "1548.36" {
               description "1548.36 nm/193.618750 THz 3.125/6.25GHz spacing";
             }
             enum "1548.34" {
               description "1548.34 nm/193.621875 THz 3.125GHz spacing";
             }
             enum "1548.31" {
               description "1548.31 nm/193.625000 THz 3.125/6.25/12.5GHz spacing";
             }
             enum "1548.29" {
               description "1548.29 nm/193.628125 THz 3.125GHz spacing";
             }
             enum "1548.26" {
               description "1548.26 nm/193.631250 THz 3.125/6.25GHz spacing";
             }
             enum "1548.24" {
               description "1548.24 nm/193.634375 THz 3.125GHz spacing";
             }
             enum "1548.21" {
               description "1548.21 nm/193.637500 THz 3.125/6.25/12.5GHz spacing";
             }
             enum "1548.19" {
               description "1548.19 nm/193.640625 THz 3.125GHz spacing";
             }
             enum "1548.16" {
               description "1548.16 nm/193.643750 THz 3.125/6.25GHz spacing";
             }
             enum "1548.14" {
               description "1548.14 nm/193.646875 THz 3.125GHz spacing";
             }
             enum "1548.11" {
               description "1548.11 nm/193.650000 THz 3.125/6.25/12.5/50/75GHz spacing";
             }
             enum "1548.09" {
               description "1548.09 nm/193.653125 THz 3.125GHz spacing";
             }
             enum "1548.06" {
               description "1548.06 nm/193.656250 THz 3.125/6.25GHz spacing";
             }
             enum "1548.04" {
               description "1548.04 nm/193.659375 THz 3.125GHz spacing";
             }
             enum "1548.02" {
               description "1548.02 nm/193.662500 THz 3.125/6.25/12.5GHz spacing";
             }
             enum "1547.99" {
               description "1547.99 nm/193.665625 THz 3.125GHz spacing";
             }
             enum "1547.97" {
               description "1547.97 nm/193.668750 THz 3.125/6.25GHz spacing";
             }
             enum "1547.94" {
               description "1547.94 nm/193.671875 THz 3.125GHz spacing";
             }
             enum "1547.92" {
               description "1547.92 nm/193.675000 THz 3.125/6.25/12.5GHz spacing";
             }
             enum "1547.89" {
               description "1547.89 nm/193.678125 THz 3.125GHz spacing";
             }
             enum "1547.87" {
               description "1547.87 nm/193.681250 THz 3.125/6.25GHz spacing";
             }
             enum "1547.84" {
               description "1547.84 nm/193.684375 THz 3.125GHz spacing";
             }
             enum "1547.82" {
               description "1547.82 nm/193.687500 THz 3.125/6.25/12.5GHz spacing";
             }
             enum "1547.79" {
               description "1547.79 nm/193.690625 THz 3.125GHz spacing";
             }
             enum "1547.77" {
               description "1547.77 nm/193.693750 THz 3.125/6.25GHz spacing";
             }
             enum "1547.74" {
               description "1547.74 nm/193.696875 THz 3.125GHz spacing";
             }
             enum "1547.72" {
               description "1547.72 nm/193.700000 THz 3.125/6.25/12.5/100GHz spacing";
             }
             enum "1547.69" {
               description "1547.69 nm/193.703125 THz 3.125GHz spacing";
             }
             enum "1547.67" {
               description "1547.67 nm/193.706250 THz 3.125/6.25GHz spacing";
             }
             enum "1547.64" {
               description "1547.64 nm/193.709375 THz 3.125GHz spacing";
             }
             enum "1547.62" {
               description "1547.62 nm/193.712500 THz 3.125/6.25/12.5GHz spacing";
             }
             enum "1547.59" {
               description "1547.59 nm/193.715625 THz 3.125GHz spacing";
             }
             enum "1547.57" {
               description "1547.57 nm/193.718750 THz 3.125/6.25GHz spacing";
             }
             enum "1547.54" {
               description "1547.54 nm/193.721875 THz 3.125GHz spacing";
             }
             enum "1547.52" {
               description "1547.52 nm/193.725000 THz 3.125/6.25/12.5/75GHz spacing";
             }
             enum "1547.49" {
               description "1547.49 nm/193.728125 THz 3.125GHz spacing";
             }
             enum "1547.47" {
               description "1547.47 nm/193.731250 THz 3.125/6.25GHz spacing";
             }
             enum "1547.44" {
               description "1547.44 nm/193.734375 THz 3.125GHz spacing";
             }
             enum "1547.42" {
               description "1547.42 nm/193.737500 THz 3.125/6.25/12.5GHz spacing";
             }
             enum "1547.39" {
               description "1547.39 nm/193.740625 THz 3.125GHz spacing";
             }
             enum "1547.37" {
               description "1547.37 nm/193.743750 THz 3.125/6.25GHz spacing";
             }
             enum "1547.34" {
               description "1547.34 nm/193.746875 THz 3.125GHz spacing";
             }
             enum "1547.32" {
               description "1547.32 nm/193.750000 THz 3.125/6.25/12.5/50GHz spacing";
             }
             enum "1547.29" {
               description "1547.29 nm/193.753125 THz 3.125GHz spacing";
             }
             enum "1547.27" {
               description "1547.27 nm/193.756250 THz 3.125/6.25GHz spacing";
             }
             enum "1547.24" {
               description "1547.24 nm/193.759375 THz 3.125GHz spacing";
             }
             enum "1547.22" {
               description "1547.22 nm/193.762500 THz 3.125/6.25/12.5GHz spacing";
             }
             enum "1547.19" {
               description "1547.19 nm/193.765625 THz 3.125GHz spacing";
             }
             enum "1547.17" {
               description "1547.17 nm/193.768750 THz 3.125/6.25GHz spacing";
             }
             enum "1547.14" {
               description "1547.14 nm/193.771875 THz 3.125GHz spacing";
             }
             enum "1547.12" {
               description "1547.12 nm/193.775000 THz 3.125/6.25/12.5GHz spacing";
             }
             enum "1547.09" {
               description "1547.09 nm/193.778125 THz 3.125GHz spacing";
             }
             enum "1547.07" {
               description "1547.07 nm/193.781250 THz 3.125/6.25GHz spacing";
             }
             enum "1547.04" {
               description "1547.04 nm/193.784375 THz 3.125GHz spacing";
             }
             enum "1547.02" {
               description "1547.02 nm/193.787500 THz 3.125/6.25/12.5GHz spacing";
             }
             enum "1546.99" {
               description "1546.99 nm/193.790625 THz 3.125GHz spacing";
             }
             enum "1546.97" {
               description "1546.97 nm/193.793750 THz 3.125/6.25GHz spacing";
             }
             enum "1546.94" {
               description "1546.94 nm/193.796875 THz 3.125GHz spacing";
             }
             enum "1546.92" {
               description "1546.92 nm/193.800000 THz 3.125/6.25/12.5/50/75/100GHz spacing";
             }
             enum "1546.89" {
               description "1546.89 nm/193.803125 THz 3.125GHz spacing";
             }
             enum "1546.87" {
               description "1546.87 nm/193.806250 THz 3.125/6.25GHz spacing";
             }
             enum "1546.84" {
               description "1546.84 nm/193.809375 THz 3.125GHz spacing";
             }
             enum "1546.82" {
               description "1546.82 nm/193.812500 THz 3.125/6.25/12.5GHz spacing";
             }
             enum "1546.79" {
               description "1546.79 nm/193.815625 THz 3.125GHz spacing";
             }
             enum "1546.77" {
               description "1546.77 nm/193.818750 THz 3.125/6.25GHz spacing";
             }
             enum "1546.74" {
               description "1546.74 nm/193.821875 THz 3.125GHz spacing";
             }
             enum "1546.72" {
               description "1546.72 nm/193.825000 THz 3.125/6.25/12.5GHz spacing";
             }
             enum "1546.69" {
               description "1546.69 nm/193.828125 THz 3.125GHz spacing";
             }
             enum "1546.67" {
               description "1546.67 nm/193.831250 THz 3.125/6.25GHz spacing";
             }
             enum "1546.64" {
               description "1546.64 nm/193.834375 THz 3.125GHz spacing";
             }
             enum "1546.62" {
               description "1546.62 nm/193.837500 THz 3.125/6.25/12.5GHz spacing";
             }
             enum "1546.59" {
               description "1546.59 nm/193.840625 THz 3.125GHz spacing";
             }
             enum "1546.57" {
               description "1546.57 nm/193.843750 THz 3.125/6.25GHz spacing";
             }
             enum "1546.54" {
               description "1546.54 nm/193.846875 THz 3.125GHz spacing";
             }
             enum "1546.52" {
               description "1546.52 nm/193.850000 THz 3.125/6.25/12.5/50GHz spacing";
             }
             enum "1546.49" {
               description "1546.49 nm/193.853125 THz 3.125GHz spacing";
             }
             enum "1546.47" {
               description "1546.47 nm/193.856250 THz 3.125/6.25GHz spacing";
             }
             enum "1546.44" {
               description "1546.44 nm/193.859375 THz 3.125GHz spacing";
             }
             enum "1546.42" {
               description "1546.42 nm/193.862500 THz 3.125/6.25/12.5GHz spacing";
             }
             enum "1546.39" {
               description "1546.39 nm/193.865625 THz 3.125GHz spacing";
             }
             enum "1546.37" {
               description "1546.37 nm/193.868750 THz 3.125/6.25GHz spacing";
             }
             enum "1546.34" {
               description "1546.34 nm/193.871875 THz 3.125GHz spacing";
             }
             enum "1546.32" {
               description "1546.32 nm/193.875000 THz 3.125/6.25/12.5/75GHz spacing";
             }
             enum "1546.29" {
               description "1546.29 nm/193.878125 THz 3.125GHz spacing";
             }
             enum "1546.27" {
               description "1546.27 nm/193.881250 THz 3.125/6.25GHz spacing";
             }
             enum "1546.24" {
               description "1546.24 nm/193.884375 THz 3.125GHz spacing";
             }
             enum "1546.22" {
               description "1546.22 nm/193.887500 THz 3.125/6.25/12.5GHz spacing";
             }
             enum "1546.19" {
               description "1546.19 nm/193.890625 THz 3.125GHz spacing";
             }
             enum "1546.17" {
               description "1546.17 nm/193.893750 THz 3.125/6.25GHz spacing";
             }
             enum "1546.14" {
               description "1546.14 nm/193.896875 THz 3.125GHz spacing";
             }
             enum "1546.12" {
               description "1546.12 nm/193.900000 THz 3.125/6.25/12.5/100GHz spacing";
             }
             enum "1546.09" {
               description "1546.09 nm/193.903125 THz 3.125GHz spacing";
             }
             enum "1546.07" {
               description "1546.07 nm/193.906250 THz 3.125/6.25GHz spacing";
             }
             enum "1546.04" {
               description "1546.04 nm/193.909375 THz 3.125GHz spacing";
             }
             enum "1546.02" {
               description "1546.02 nm/193.912500 THz 3.125/6.25/12.5GHz spacing";
             }
             enum "1545.99" {
               description "1545.99 nm/193.915625 THz 3.125GHz spacing";
             }
             enum "1545.97" {
               description "1545.97 nm/193.918750 THz 3.125/6.25GHz spacing";
             }
             enum "1545.94" {
               description "1545.94 nm/193.921875 THz 3.125GHz spacing";
             }
             enum "1545.92" {
               description "1545.92 nm/193.925000 THz 3.125/6.25/12.5GHz spacing";
             }
             enum "1545.89" {
               description "1545.89 nm/193.928125 THz 3.125GHz spacing";
             }
             enum "1545.87" {
               description "1545.87 nm/193.931250 THz 3.125/6.25GHz spacing";
             }
             enum "1545.84" {
               description "1545.84 nm/193.934375 THz 3.125GHz spacing";
             }
             enum "1545.82" {
               description "1545.82 nm/193.937500 THz 3.125/6.25/12.5GHz spacing";
             }
             enum "1545.80" {
               description "1545.80 nm/193.940625 THz 3.125GHz spacing";
             }
             enum "1545.77" {
               description "1545.77 nm/193.943750 THz 3.125/6.25GHz spacing";
             }
             enum "1545.75" {
               description "1545.75 nm/193.946875 THz 3.125GHz spacing";
             }
             enum "1545.72" {
               description "1545.72 nm/193.950000 THz 3.125/6.25/12.5/50/75GHz spacing";
             }
             enum "1545.70" {
               description "1545.70 nm/193.953125 THz 3.125GHz spacing";
             }
             enum "1545.67" {
               description "1545.67 nm/193.956250 THz 3.125/6.25GHz spacing";
             }
             enum "1545.65" {
               description "1545.65 nm/193.959375 THz 3.125GHz spacing";
             }
             enum "1545.62" {
               description "1545.62 nm/193.962500 THz 3.125/6.25/12.5GHz spacing";
             }
             enum "1545.60" {
               description "1545.60 nm/193.965625 THz 3.125GHz spacing";
             }
             enum "1545.57" {
               description "1545.57 nm/193.968750 THz 3.125/6.25GHz spacing";
             }
             enum "1545.55" {
               description "1545.55 nm/193.971875 THz 3.125GHz spacing";
             }
             enum "1545.52" {
               description "1545.52 nm/193.975000 THz 3.125/6.25/12.5GHz spacing";
             }
             enum "1545.50" {
               description "1545.50 nm/193.978125 THz 3.125GHz spacing";
             }
             enum "1545.47" {
               description "1545.47 nm/193.981250 THz 3.125/6.25GHz spacing";
             }
             enum "1545.45" {
               description "1545.45 nm/193.984375 THz 3.125GHz spacing";
             }
             enum "1545.42" {
               description "1545.42 nm/193.987500 THz 3.125/6.25/12.5GHz spacing";
             }
             enum "1545.40" {
               description "1545.40 nm/193.990625 THz 3.125GHz spacing";
             }
             enum "1545.37" {
               description "1545.37 nm/193.993750 THz 3.125/6.25GHz spacing";
             }
             enum "1545.35" {
               description "1545.35 nm/193.996875 THz 3.125GHz spacing";
             }
             enum "1545.32" {
               description "1545.32 nm/194.000000 THz 3.125/6.25/12.5/100GHz spacing";
             }
             enum "1545.30" {
               description "1545.30 nm/194.003125 THz 3.125GHz spacing";
             }
             enum "1545.27" {
               description "1545.27 nm/194.006250 THz 3.125/6.25GHz spacing";
             }
             enum "1545.25" {
               description "1545.25 nm/194.009375 THz 3.125GHz spacing";
             }
             enum "1545.22" {
               description "1545.22 nm/194.012500 THz 3.125/6.25/12.5GHz spacing";
             }
             enum "1545.20" {
               description "1545.20 nm/194.015625 THz 3.125GHz spacing";
             }
             enum "1545.17" {
               description "1545.17 nm/194.018750 THz 3.125/6.25GHz spacing";
             }
             enum "1545.15" {
               description "1545.15 nm/194.021875 THz 3.125GHz spacing";
             }
             enum "1545.12" {
               description "1545.12 nm/194.025000 THz 3.125/6.25/12.5/75GHz spacing";
             }
             enum "1545.10" {
               description "1545.10 nm/194.028125 THz 3.125GHz spacing";
             }
             enum "1545.07" {
               description "1545.07 nm/194.031250 THz 3.125/6.25GHz spacing";
             }
             enum "1545.05" {
               description "1545.05 nm/194.034375 THz 3.125GHz spacing";
             }
             enum "1545.02" {
               description "1545.02 nm/194.037500 THz 3.125/6.25/12.5GHz spacing";
             }
             enum "1545.00" {
               description "1545.00 nm/194.040625 THz 3.125GHz spacing";
             }
             enum "1544.97" {
               description "1544.97 nm/194.043750 THz 3.125/6.25GHz spacing";
             }
             enum "1544.95" {
               description "1544.95 nm/194.046875 THz 3.125GHz spacing";
             }
             enum "1544.92" {
               description "1544.92 nm/194.050000 THz 3.125/6.25/12.5/50GHz spacing";
             }
             enum "1544.90" {
               description "1544.90 nm/194.053125 THz 3.125GHz spacing";
             }
             enum "1544.87" {
               description "1544.87 nm/194.056250 THz 3.125/6.25GHz spacing";
             }
             enum "1544.85" {
               description "1544.85 nm/194.059375 THz 3.125GHz spacing";
             }
             enum "1544.82" {
               description "1544.82 nm/194.062500 THz 3.125/6.25/12.5GHz spacing";
             }
             enum "1544.80" {
               description "1544.80 nm/194.065625 THz 3.125GHz spacing";
             }
             enum "1544.77" {
               description "1544.77 nm/194.068750 THz 3.125/6.25GHz spacing";
             }
             enum "1544.75" {
               description "1544.75 nm/194.071875 THz 3.125GHz spacing";
             }
             enum "1544.72" {
               description "1544.72 nm/194.075000 THz 3.125/6.25/12.5GHz spacing";
             }
             enum "1544.70" {
               description "1544.70 nm/194.078125 THz 3.125GHz spacing";
             }
             enum "1544.68" {
               description "1544.68 nm/194.081250 THz 3.125/6.25GHz spacing";
             }
             enum "1544.65" {
               description "1544.65 nm/194.084375 THz 3.125GHz spacing";
             }
             enum "1544.63" {
               description "1544.63 nm/194.087500 THz 3.125/6.25/12.5GHz spacing";
             }
             enum "1544.60" {
               description "1544.60 nm/194.090625 THz 3.125GHz spacing";
             }
             enum "1544.58" {
               description "1544.58 nm/194.093750 THz 3.125/6.25GHz spacing";
             }
             enum "1544.55" {
               description "1544.55 nm/194.096875 THz 3.125GHz spacing";
             }
             enum "1544.53" {
               description "1544.53 nm/194.100000 THz 3.125/6.25/12.5/50/75/100GHz spacing";
             }
             enum "1544.50" {
               description "1544.50 nm/194.103125 THz 3.125GHz spacing";
             }
             enum "1544.48" {
               description "1544.48 nm/194.106250 THz 3.125/6.25GHz spacing";
             }
             enum "1544.45" {
               description "1544.45 nm/194.109375 THz 3.125GHz spacing";
             }
             enum "1544.43" {
               description "1544.43 nm/194.112500 THz 3.125/6.25/12.5GHz spacing";
             }
             enum "1544.40" {
               description "1544.40 nm/194.115625 THz 3.125GHz spacing";
             }
             enum "1544.38" {
               description "1544.38 nm/194.118750 THz 3.125/6.25GHz spacing";
             }
             enum "1544.35" {
               description "1544.35 nm/194.121875 THz 3.125GHz spacing";
             }
             enum "1544.33" {
               description "1544.33 nm/194.125000 THz 3.125/6.25/12.5GHz spacing";
             }
             enum "1544.30" {
               description "1544.30 nm/194.128125 THz 3.125GHz spacing";
             }
             enum "1544.28" {
               description "1544.28 nm/194.131250 THz 3.125/6.25GHz spacing";
             }
             enum "1544.25" {
               description "1544.25 nm/194.134375 THz 3.125GHz spacing";
             }
             enum "1544.23" {
               description "1544.23 nm/194.137500 THz 3.125/6.25/12.5GHz spacing";
             }
             enum "1544.20" {
               description "1544.20 nm/194.140625 THz 3.125GHz spacing";
             }
             enum "1544.18" {
               description "1544.18 nm/194.143750 THz 3.125/6.25GHz spacing";
             }
             enum "1544.15" {
               description "1544.15 nm/194.146875 THz 3.125GHz spacing";
             }
             enum "1544.13" {
               description "1544.13 nm/194.150000 THz 3.125/6.25/12.5/50GHz spacing";
             }
             enum "1544.10" {
               description "1544.10 nm/194.153125 THz 3.125GHz spacing";
             }
             enum "1544.08" {
               description "1544.08 nm/194.156250 THz 3.125/6.25GHz spacing";
             }
             enum "1544.05" {
               description "1544.05 nm/194.159375 THz 3.125GHz spacing";
             }
             enum "1544.03" {
               description "1544.03 nm/194.162500 THz 3.125/6.25/12.5GHz spacing";
             }
             enum "1544.00" {
               description "1544.00 nm/194.165625 THz 3.125GHz spacing";
             }
             enum "1543.98" {
               description "1543.98 nm/194.168750 THz 3.125/6.25GHz spacing";
             }
             enum "1543.95" {
               description "1543.95 nm/194.171875 THz 3.125GHz spacing";
             }
             enum "1543.93" {
               description "1543.93 nm/194.175000 THz 3.125/6.25/12.5/75GHz spacing";
             }
             enum "1543.90" {
               description "1543.90 nm/194.178125 THz 3.125GHz spacing";
             }
             enum "1543.88" {
               description "1543.88 nm/194.181250 THz 3.125/6.25GHz spacing";
             }
             enum "1543.85" {
               description "1543.85 nm/194.184375 THz 3.125GHz spacing";
             }
             enum "1543.83" {
               description "1543.83 nm/194.187500 THz 3.125/6.25/12.5GHz spacing";
             }
             enum "1543.81" {
               description "1543.81 nm/194.190625 THz 3.125GHz spacing";
             }
             enum "1543.78" {
               description "1543.78 nm/194.193750 THz 3.125/6.25GHz spacing";
             }
             enum "1543.76" {
               description "1543.76 nm/194.196875 THz 3.125GHz spacing";
             }
             enum "1543.73" {
               description "1543.73 nm/194.200000 THz 3.125/6.25/12.5/100GHz spacing";
             }
             enum "1543.71" {
               description "1543.71 nm/194.203125 THz 3.125GHz spacing";
             }
             enum "1543.68" {
               description "1543.68 nm/194.206250 THz 3.125/6.25GHz spacing";
             }
             enum "1543.66" {
               description "1543.66 nm/194.209375 THz 3.125GHz spacing";
             }
             enum "1543.63" {
               description "1543.63 nm/194.212500 THz 3.125/6.25/12.5GHz spacing";
             }
             enum "1543.61" {
               description "1543.61 nm/194.215625 THz 3.125GHz spacing";
             }
             enum "1543.58" {
               description "1543.58 nm/194.218750 THz 3.125/6.25GHz spacing";
             }
             enum "1543.56" {
               description "1543.56 nm/194.221875 THz 3.125GHz spacing";
             }
             enum "1543.53" {
               description "1543.53 nm/194.225000 THz 3.125/6.25/12.5GHz spacing";
             }
             enum "1543.51" {
               description "1543.51 nm/194.228125 THz 3.125GHz spacing";
             }
             enum "1543.48" {
               description "1543.48 nm/194.231250 THz 3.125/6.25GHz spacing";
             }
             enum "1543.46" {
               description "1543.46 nm/194.234375 THz 3.125GHz spacing";
             }
             enum "1543.43" {
               description "1543.43 nm/194.237500 THz 3.125/6.25/12.5GHz spacing";
             }
             enum "1543.41" {
               description "1543.41 nm/194.240625 THz 3.125GHz spacing";
             }
             enum "1543.38" {
               description "1543.38 nm/194.243750 THz 3.125/6.25GHz spacing";
             }
             enum "1543.36" {
               description "1543.36 nm/194.246875 THz 3.125GHz spacing";
             }
             enum "1543.33" {
               description "1543.33 nm/194.250000 THz 3.125/6.25/12.5/50/75GHz spacing";
             }
             enum "1543.31" {
               description "1543.31 nm/194.253125 THz 3.125GHz spacing";
             }
             enum "1543.28" {
               description "1543.28 nm/194.256250 THz 3.125/6.25GHz spacing";
             }
             enum "1543.26" {
               description "1543.26 nm/194.259375 THz 3.125GHz spacing";
             }
             enum "1543.23" {
               description "1543.23 nm/194.262500 THz 3.125/6.25/12.5GHz spacing";
             }
             enum "1543.21" {
               description "1543.21 nm/194.265625 THz 3.125GHz spacing";
             }
             enum "1543.18" {
               description "1543.18 nm/194.268750 THz 3.125/6.25GHz spacing";
             }
             enum "1543.16" {
               description "1543.16 nm/194.271875 THz 3.125GHz spacing";
             }
             enum "1543.13" {
               description "1543.13 nm/194.275000 THz 3.125/6.25/12.5GHz spacing";
             }
             enum "1543.11" {
               description "1543.11 nm/194.278125 THz 3.125GHz spacing";
             }
             enum "1543.08" {
               description "1543.08 nm/194.281250 THz 3.125/6.25GHz spacing";
             }
             enum "1543.06" {
               description "1543.06 nm/194.284375 THz 3.125GHz spacing";
             }
             enum "1543.04" {
               description "1543.04 nm/194.287500 THz 3.125/6.25/12.5GHz spacing";
             }
             enum "1543.01" {
               description "1543.01 nm/194.290625 THz 3.125GHz spacing";
             }
             enum "1542.99" {
               description "1542.99 nm/194.293750 THz 3.125/6.25GHz spacing";
             }
             enum "1542.96" {
               description "1542.96 nm/194.296875 THz 3.125GHz spacing";
             }
             enum "1542.94" {
               description "1542.94 nm/194.300000 THz 3.125/6.25/12.5/100GHz spacing";
             }
             enum "1542.91" {
               description "1542.91 nm/194.303125 THz 3.125GHz spacing";
             }
             enum "1542.89" {
               description "1542.89 nm/194.306250 THz 3.125/6.25GHz spacing";
             }
             enum "1542.86" {
               description "1542.86 nm/194.309375 THz 3.125GHz spacing";
             }
             enum "1542.84" {
               description "1542.84 nm/194.312500 THz 3.125/6.25/12.5GHz spacing";
             }
             enum "1542.81" {
               description "1542.81 nm/194.315625 THz 3.125GHz spacing";
             }
             enum "1542.79" {
               description "1542.79 nm/194.318750 THz 3.125/6.25GHz spacing";
             }
             enum "1542.76" {
               description "1542.76 nm/194.321875 THz 3.125GHz spacing";
             }
             enum "1542.74" {
               description "1542.74 nm/194.325000 THz 3.125/6.25/12.5/75GHz spacing";
             }
             enum "1542.71" {
               description "1542.71 nm/194.328125 THz 3.125GHz spacing";
             }
             enum "1542.69" {
               description "1542.69 nm/194.331250 THz 3.125/6.25GHz spacing";
             }
             enum "1542.66" {
               description "1542.66 nm/194.334375 THz 3.125GHz spacing";
             }
             enum "1542.64" {
               description "1542.64 nm/194.337500 THz 3.125/6.25/12.5GHz spacing";
             }
             enum "1542.61" {
               description "1542.61 nm/194.340625 THz 3.125GHz spacing";
             }
             enum "1542.59" {
               description "1542.59 nm/194.343750 THz 3.125/6.25GHz spacing";
             }
             enum "1542.56" {
               description "1542.56 nm/194.346875 THz 3.125GHz spacing";
             }
             enum "1542.54" {
               description "1542.54 nm/194.350000 THz 3.125/6.25/12.5/50GHz spacing";
             }
             enum "1542.51" {
               description "1542.51 nm/194.353125 THz 3.125GHz spacing";
             }
             enum "1542.49" {
               description "1542.49 nm/194.356250 THz 3.125/6.25GHz spacing";
             }
             enum "1542.46" {
               description "1542.46 nm/194.359375 THz 3.125GHz spacing";
             }
             enum "1542.44" {
               description "1542.44 nm/194.362500 THz 3.125/6.25/12.5GHz spacing";
             }
             enum "1542.42" {
               description "1542.42 nm/194.365625 THz 3.125GHz spacing";
             }
             enum "1542.39" {
               description "1542.39 nm/194.368750 THz 3.125/6.25GHz spacing";
             }
             enum "1542.37" {
               description "1542.37 nm/194.371875 THz 3.125GHz spacing";
             }
             enum "1542.34" {
               description "1542.34 nm/194.375000 THz 3.125/6.25/12.5GHz spacing";
             }
             enum "1542.32" {
               description "1542.32 nm/194.378125 THz 3.125GHz spacing";
             }
             enum "1542.29" {
               description "1542.29 nm/194.381250 THz 3.125/6.25GHz spacing";
             }
             enum "1542.27" {
               description "1542.27 nm/194.384375 THz 3.125GHz spacing";
             }
             enum "1542.24" {
               description "1542.24 nm/194.387500 THz 3.125/6.25/12.5GHz spacing";
             }
             enum "1542.22" {
               description "1542.22 nm/194.390625 THz 3.125GHz spacing";
             }
             enum "1542.19" {
               description "1542.19 nm/194.393750 THz 3.125/6.25GHz spacing";
             }
             enum "1542.17" {
               description "1542.17 nm/194.396875 THz 3.125GHz spacing";
             }
             enum "1542.14" {
               description "1542.14 nm/194.400000 THz 3.125/6.25/12.5/50/75/100GHz spacing";
             }
             enum "1542.12" {
               description "1542.12 nm/194.403125 THz 3.125GHz spacing";
             }
             enum "1542.09" {
               description "1542.09 nm/194.406250 THz 3.125/6.25GHz spacing";
             }
             enum "1542.07" {
               description "1542.07 nm/194.409375 THz 3.125GHz spacing";
             }
             enum "1542.04" {
               description "1542.04 nm/194.412500 THz 3.125/6.25/12.5GHz spacing";
             }
             enum "1542.02" {
               description "1542.02 nm/194.415625 THz 3.125GHz spacing";
             }
             enum "1541.99" {
               description "1541.99 nm/194.418750 THz 3.125/6.25GHz spacing";
             }
             enum "1541.97" {
               description "1541.97 nm/194.421875 THz 3.125GHz spacing";
             }
             enum "1541.94" {
               description "1541.94 nm/194.425000 THz 3.125/6.25/12.5GHz spacing";
             }
             enum "1541.92" {
               description "1541.92 nm/194.428125 THz 3.125GHz spacing";
             }
             enum "1541.89" {
               description "1541.89 nm/194.431250 THz 3.125/6.25GHz spacing";
             }
             enum "1541.87" {
               description "1541.87 nm/194.434375 THz 3.125GHz spacing";
             }
             enum "1541.84" {
               description "1541.84 nm/194.437500 THz 3.125/6.25/12.5GHz spacing";
             }
             enum "1541.82" {
               description "1541.82 nm/194.440625 THz 3.125GHz spacing";
             }
             enum "1541.80" {
               description "1541.80 nm/194.443750 THz 3.125/6.25GHz spacing";
             }
             enum "1541.77" {
               description "1541.77 nm/194.446875 THz 3.125GHz spacing";
             }
             enum "1541.75" {
               description "1541.75 nm/194.450000 THz 3.125/6.25/12.5/50GHz spacing";
             }
             enum "1541.72" {
               description "1541.72 nm/194.453125 THz 3.125GHz spacing";
             }
             enum "1541.70" {
               description "1541.70 nm/194.456250 THz 3.125/6.25GHz spacing";
             }
             enum "1541.67" {
               description "1541.67 nm/194.459375 THz 3.125GHz spacing";
             }
             enum "1541.65" {
               description "1541.65 nm/194.462500 THz 3.125/6.25/12.5GHz spacing";
             }
             enum "1541.62" {
               description "1541.62 nm/194.465625 THz 3.125GHz spacing";
             }
             enum "1541.60" {
               description "1541.60 nm/194.468750 THz 3.125/6.25GHz spacing";
             }
             enum "1541.57" {
               description "1541.57 nm/194.471875 THz 3.125GHz spacing";
             }
             enum "1541.55" {
               description "1541.55 nm/194.475000 THz 3.125/6.25/12.5/75GHz spacing";
             }
             enum "1541.52" {
               description "1541.52 nm/194.478125 THz 3.125GHz spacing";
             }
             enum "1541.50" {
               description "1541.50 nm/194.481250 THz 3.125/6.25GHz spacing";
             }
             enum "1541.47" {
               description "1541.47 nm/194.484375 THz 3.125GHz spacing";
             }
             enum "1541.45" {
               description "1541.45 nm/194.487500 THz 3.125/6.25/12.5GHz spacing";
             }
             enum "1541.42" {
               description "1541.42 nm/194.490625 THz 3.125GHz spacing";
             }
             enum "1541.40" {
               description "1541.40 nm/194.493750 THz 3.125/6.25GHz spacing";
             }
             enum "1541.37" {
               description "1541.37 nm/194.496875 THz 3.125GHz spacing";
             }
             enum "1541.35" {
               description "1541.35 nm/194.500000 THz 3.125/6.25/12.5/100GHz spacing";
             }
             enum "1541.32" {
               description "1541.32 nm/194.503125 THz 3.125GHz spacing";
             }
             enum "1541.30" {
               description "1541.30 nm/194.506250 THz 3.125/6.25GHz spacing";
             }
             enum "1541.28" {
               description "1541.28 nm/194.509375 THz 3.125GHz spacing";
             }
             enum "1541.25" {
               description "1541.25 nm/194.512500 THz 3.125/6.25/12.5GHz spacing";
             }
             enum "1541.23" {
               description "1541.23 nm/194.515625 THz 3.125GHz spacing";
             }
             enum "1541.20" {
               description "1541.20 nm/194.518750 THz 3.125/6.25GHz spacing";
             }
             enum "1541.18" {
               description "1541.18 nm/194.521875 THz 3.125GHz spacing";
             }
             enum "1541.15" {
               description "1541.15 nm/194.525000 THz 3.125/6.25/12.5GHz spacing";
             }
             enum "1541.13" {
               description "1541.13 nm/194.528125 THz 3.125GHz spacing";
             }
             enum "1541.10" {
               description "1541.10 nm/194.531250 THz 3.125/6.25GHz spacing";
             }
             enum "1541.08" {
               description "1541.08 nm/194.534375 THz 3.125GHz spacing";
             }
             enum "1541.05" {
               description "1541.05 nm/194.537500 THz 3.125/6.25/12.5GHz spacing";
             }
             enum "1541.03" {
               description "1541.03 nm/194.540625 THz 3.125GHz spacing";
             }
             enum "1541.00" {
               description "1541.00 nm/194.543750 THz 3.125/6.25GHz spacing";
             }
             enum "1540.98" {
               description "1540.98 nm/194.546875 THz 3.125GHz spacing";
             }
             enum "1540.95" {
               description "1540.95 nm/194.550000 THz 3.125/6.25/12.5/50/75GHz spacing";
             }
             enum "1540.93" {
               description "1540.93 nm/194.553125 THz 3.125GHz spacing";
             }
             enum "1540.90" {
               description "1540.90 nm/194.556250 THz 3.125/6.25GHz spacing";
             }
             enum "1540.88" {
               description "1540.88 nm/194.559375 THz 3.125GHz spacing";
             }
             enum "1540.85" {
               description "1540.85 nm/194.562500 THz 3.125/6.25/12.5GHz spacing";
             }
             enum "1540.83" {
               description "1540.83 nm/194.565625 THz 3.125GHz spacing";
             }
             enum "1540.80" {
               description "1540.80 nm/194.568750 THz 3.125/6.25GHz spacing";
             }
             enum "1540.78" {
               description "1540.78 nm/194.571875 THz 3.125GHz spacing";
             }
             enum "1540.76" {
               description "1540.76 nm/194.575000 THz 3.125/6.25/12.5GHz spacing";
             }
             enum "1540.73" {
               description "1540.73 nm/194.578125 THz 3.125GHz spacing";
             }
             enum "1540.71" {
               description "1540.71 nm/194.581250 THz 3.125/6.25GHz spacing";
             }
             enum "1540.68" {
               description "1540.68 nm/194.584375 THz 3.125GHz spacing";
             }
             enum "1540.66" {
               description "1540.66 nm/194.587500 THz 3.125/6.25/12.5GHz spacing";
             }
             enum "1540.63" {
               description "1540.63 nm/194.590625 THz 3.125GHz spacing";
             }
             enum "1540.61" {
               description "1540.61 nm/194.593750 THz 3.125/6.25GHz spacing";
             }
             enum "1540.58" {
               description "1540.58 nm/194.596875 THz 3.125GHz spacing";
             }
             enum "1540.56" {
               description "1540.56 nm/194.600000 THz 3.125/6.25/12.5/100GHz spacing";
             }
             enum "1540.53" {
               description "1540.53 nm/194.603125 THz 3.125GHz spacing";
             }
             enum "1540.51" {
               description "1540.51 nm/194.606250 THz 3.125/6.25GHz spacing";
             }
             enum "1540.48" {
               description "1540.48 nm/194.609375 THz 3.125GHz spacing";
             }
             enum "1540.46" {
               description "1540.46 nm/194.612500 THz 3.125/6.25/12.5GHz spacing";
             }
             enum "1540.43" {
               description "1540.43 nm/194.615625 THz 3.125GHz spacing";
             }
             enum "1540.41" {
               description "1540.41 nm/194.618750 THz 3.125/6.25GHz spacing";
             }
             enum "1540.38" {
               description "1540.38 nm/194.621875 THz 3.125GHz spacing";
             }
             enum "1540.36" {
               description "1540.36 nm/194.625000 THz 3.125/6.25/12.5/75GHz spacing";
             }
             enum "1540.33" {
               description "1540.33 nm/194.628125 THz 3.125GHz spacing";
             }
             enum "1540.31" {
               description "1540.31 nm/194.631250 THz 3.125/6.25GHz spacing";
             }
             enum "1540.29" {
               description "1540.29 nm/194.634375 THz 3.125GHz spacing";
             }
             enum "1540.26" {
               description "1540.26 nm/194.637500 THz 3.125/6.25/12.5GHz spacing";
             }
             enum "1540.24" {
               description "1540.24 nm/194.640625 THz 3.125GHz spacing";
             }
             enum "1540.21" {
               description "1540.21 nm/194.643750 THz 3.125/6.25GHz spacing";
             }
             enum "1540.19" {
               description "1540.19 nm/194.646875 THz 3.125GHz spacing";
             }
             enum "1540.16" {
               description "1540.16 nm/194.650000 THz 3.125/6.25/12.5/50GHz spacing";
             }
             enum "1540.14" {
               description "1540.14 nm/194.653125 THz 3.125GHz spacing";
             }
             enum "1540.11" {
               description "1540.11 nm/194.656250 THz 3.125/6.25GHz spacing";
             }
             enum "1540.09" {
               description "1540.09 nm/194.659375 THz 3.125GHz spacing";
             }
             enum "1540.06" {
               description "1540.06 nm/194.662500 THz 3.125/6.25/12.5GHz spacing";
             }
             enum "1540.04" {
               description "1540.04 nm/194.665625 THz 3.125GHz spacing";
             }
             enum "1540.01" {
               description "1540.01 nm/194.668750 THz 3.125/6.25GHz spacing";
             }
             enum "1539.99" {
               description "1539.99 nm/194.671875 THz 3.125GHz spacing";
             }
             enum "1539.96" {
               description "1539.96 nm/194.675000 THz 3.125/6.25/12.5/75GHz spacing";
             }
             enum "1539.94" {
               description "1539.94 nm/194.678125 THz 3.125GHz spacing";
             }
             enum "1539.91" {
               description "1539.91 nm/194.681250 THz 3.125/6.25GHz spacing";
             }
             enum "1539.89" {
               description "1539.89 nm/194.684375 THz 3.125GHz spacing";
             }
             enum "1539.86" {
               description "1539.86 nm/194.687500 THz 3.125/6.25/12.5GHz spacing";
             }
             enum "1539.84" {
               description "1539.84 nm/194.690625 THz 3.125GHz spacing";
             }
             enum "1539.82" {
               description "1539.82 nm/194.693750 THz 3.125/6.25GHz spacing";
             }
             enum "1539.79" {
               description "1539.79 nm/194.696875 THz 3.125GHz spacing";
             }
             enum "1539.77" {
               description "1539.77 nm/194.700000 THz 3.125/6.25/12.5/50/75/100GHz spacing";
             }
             enum "1539.74" {
               description "1539.74 nm/194.703125 THz 3.125GHz spacing";
             }
             enum "1539.72" {
               description "1539.72 nm/194.706250 THz 3.125/6.25GHz spacing";
             }
             enum "1539.69" {
               description "1539.69 nm/194.709375 THz 3.125GHz spacing";
             }
             enum "1539.67" {
               description "1539.67 nm/194.712500 THz 3.125/6.25/12.5GHz spacing";
             }
             enum "1539.64" {
               description "1539.64 nm/194.715625 THz 3.125GHz spacing";
             }
             enum "1539.62" {
               description "1539.62 nm/194.718750 THz 3.125/6.25GHz spacing";
             }
             enum "1539.59" {
               description "1539.59 nm/194.721875 THz 3.125GHz spacing";
             }
             enum "1539.57" {
               description "1539.57 nm/194.725000 THz 3.125/6.25/12.5GHz spacing";
             }
             enum "1539.54" {
               description "1539.54 nm/194.728125 THz 3.125GHz spacing";
             }
             enum "1539.52" {
               description "1539.52 nm/194.731250 THz 3.125/6.25GHz spacing";
             }
             enum "1539.49" {
               description "1539.49 nm/194.734375 THz 3.125GHz spacing";
             }
             enum "1539.47" {
               description "1539.47 nm/194.737500 THz 3.125/6.25/12.5GHz spacing";
             }
             enum "1539.44" {
               description "1539.44 nm/194.740625 THz 3.125GHz spacing";
             }
             enum "1539.42" {
               description "1539.42 nm/194.743750 THz 3.125/6.25GHz spacing";
             }
             enum "1539.40" {
               description "1539.40 nm/194.746875 THz 3.125GHz spacing";
             }
             enum "1539.37" {
               description "1539.37 nm/194.750000 THz 3.125/6.25/12.5/50GHz spacing";
             }
             enum "1539.35" {
               description "1539.35 nm/194.753125 THz 3.125GHz spacing";
             }
             enum "1539.32" {
               description "1539.32 nm/194.756250 THz 3.125/6.25GHz spacing";
             }
             enum "1539.30" {
               description "1539.30 nm/194.759375 THz 3.125GHz spacing";
             }
             enum "1539.27" {
               description "1539.27 nm/194.762500 THz 3.125/6.25/12.5GHz spacing";
             }
             enum "1539.25" {
               description "1539.25 nm/194.765625 THz 3.125GHz spacing";
             }
             enum "1539.22" {
               description "1539.22 nm/194.768750 THz 3.125/6.25GHz spacing";
             }
             enum "1539.20" {
               description "1539.20 nm/194.771875 THz 3.125GHz spacing";
             }
             enum "1539.17" {
               description "1539.17 nm/194.775000 THz 3.125/6.25/12.5/75GHz spacing";
             }
             enum "1539.15" {
               description "1539.15 nm/194.778125 THz 3.125GHz spacing";
             }
             enum "1539.12" {
               description "1539.12 nm/194.781250 THz 3.125/6.25GHz spacing";
             }
             enum "1539.10" {
               description "1539.10 nm/194.784375 THz 3.125GHz spacing";
             }
             enum "1539.07" {
               description "1539.07 nm/194.787500 THz 3.125/6.25/12.5GHz spacing";
             }
             enum "1539.05" {
               description "1539.05 nm/194.790625 THz 3.125GHz spacing";
             }
             enum "1539.03" {
               description "1539.03 nm/194.793750 THz 3.125/6.25GHz spacing";
             }
             enum "1539.00" {
               description "1539.00 nm/194.796875 THz 3.125GHz spacing";
             }
             enum "1538.98" {
               description "1538.98 nm/194.800000 THz 3.125/6.25/12.5/100GHz spacing";
             }
             enum "1538.95" {
               description "1538.95 nm/194.803125 THz 3.125GHz spacing";
             }
             enum "1538.93" {
               description "1538.93 nm/194.806250 THz 3.125/6.25GHz spacing";
             }
             enum "1538.90" {
               description "1538.90 nm/194.809375 THz 3.125GHz spacing";
             }
             enum "1538.88" {
               description "1538.88 nm/194.812500 THz 3.125/6.25/12.5GHz spacing";
             }
             enum "1538.85" {
               description "1538.85 nm/194.815625 THz 3.125GHz spacing";
             }
             enum "1538.83" {
               description "1538.83 nm/194.818750 THz 3.125/6.25GHz spacing";
             }
             enum "1538.80" {
               description "1538.80 nm/194.821875 THz 3.125GHz spacing";
             }
             enum "1538.78" {
               description "1538.78 nm/194.825000 THz 3.125/6.25/12.5GHz spacing";
             }
             enum "1538.75" {
               description "1538.75 nm/194.828125 THz 3.125GHz spacing";
             }
             enum "1538.73" {
               description "1538.73 nm/194.831250 THz 3.125/6.25GHz spacing";
             }
             enum "1538.70" {
               description "1538.70 nm/194.834375 THz 3.125GHz spacing";
             }
             enum "1538.68" {
               description "1538.68 nm/194.837500 THz 3.125/6.25/12.5GHz spacing";
             }
             enum "1538.65" {
               description "1538.65 nm/194.840625 THz 3.125GHz spacing";
             }
             enum "1538.63" {
               description "1538.63 nm/194.843750 THz 3.125/6.25GHz spacing";
             }
             enum "1538.61" {
               description "1538.61 nm/194.846875 THz 3.125GHz spacing";
             }
             enum "1538.58" {
               description "1538.58 nm/194.850000 THz 3.125/6.25/12.5/50/75GHz spacing";
             }
             enum "1538.56" {
               description "1538.56 nm/194.853125 THz 3.125GHz spacing";
             }
             enum "1538.53" {
               description "1538.53 nm/194.856250 THz 3.125/6.25GHz spacing";
             }
             enum "1538.51" {
               description "1538.51 nm/194.859375 THz 3.125GHz spacing";
             }
             enum "1538.48" {
               description "1538.48 nm/194.862500 THz 3.125/6.25/12.5GHz spacing";
             }
             enum "1538.46" {
               description "1538.46 nm/194.865625 THz 3.125GHz spacing";
             }
             enum "1538.43" {
               description "1538.43 nm/194.868750 THz 3.125/6.25GHz spacing";
             }
             enum "1538.41" {
               description "1538.41 nm/194.871875 THz 3.125GHz spacing";
             }
             enum "1538.38" {
               description "1538.38 nm/194.875000 THz 3.125/6.25/12.5GHz spacing";
             }
             enum "1538.36" {
               description "1538.36 nm/194.878125 THz 3.125GHz spacing";
             }
             enum "1538.33" {
               description "1538.33 nm/194.881250 THz 3.125/6.25GHz spacing";
             }
             enum "1538.31" {
               description "1538.31 nm/194.884375 THz 3.125GHz spacing";
             }
             enum "1538.28" {
               description "1538.28 nm/194.887500 THz 3.125/6.25/12.5GHz spacing";
             }
             enum "1538.26" {
               description "1538.26 nm/194.890625 THz 3.125GHz spacing";
             }
             enum "1538.24" {
               description "1538.24 nm/194.893750 THz 3.125/6.25GHz spacing";
             }
             enum "1538.21" {
               description "1538.21 nm/194.896875 THz 3.125GHz spacing";
             }
             enum "1538.19" {
               description "1538.19 nm/194.900000 THz 3.125/6.25/12.5/100GHz spacing";
             }
             enum "1538.16" {
               description "1538.16 nm/194.903125 THz 3.125GHz spacing";
             }
             enum "1538.14" {
               description "1538.14 nm/194.906250 THz 3.125/6.25GHz spacing";
             }
             enum "1538.11" {
               description "1538.11 nm/194.909375 THz 3.125GHz spacing";
             }
             enum "1538.09" {
               description "1538.09 nm/194.912500 THz 3.125/6.25/12.5GHz spacing";
             }
             enum "1538.06" {
               description "1538.06 nm/194.915625 THz 3.125GHz spacing";
             }
             enum "1538.04" {
               description "1538.04 nm/194.918750 THz 3.125/6.25GHz spacing";
             }
             enum "1538.01" {
               description "1538.01 nm/194.921875 THz 3.125GHz spacing";
             }
             enum "1537.99" {
               description "1537.99 nm/194.925000 THz 3.125/6.25/12.5/75GHz spacing";
             }
             enum "1537.96" {
               description "1537.96 nm/194.928125 THz 3.125GHz spacing";
             }
             enum "1537.94" {
               description "1537.94 nm/194.931250 THz 3.125/6.25GHz spacing";
             }
             enum "1537.91" {
               description "1537.91 nm/194.934375 THz 3.125GHz spacing";
             }
             enum "1537.89" {
               description "1537.89 nm/194.937500 THz 3.125/6.25/12.5GHz spacing";
             }
             enum "1537.87" {
               description "1537.87 nm/194.940625 THz 3.125GHz spacing";
             }
             enum "1537.84" {
               description "1537.84 nm/194.943750 THz 3.125/6.25GHz spacing";
             }
             enum "1537.82" {
               description "1537.82 nm/194.946875 THz 3.125GHz spacing";
             }
             enum "1537.79" {
               description "1537.79 nm/194.950000 THz 3.125/6.25/12.5/50GHz spacing";
             }
             enum "1537.77" {
               description "1537.77 nm/194.953125 THz 3.125GHz spacing";
             }
             enum "1537.74" {
               description "1537.74 nm/194.956250 THz 3.125/6.25GHz spacing";
             }
             enum "1537.72" {
               description "1537.72 nm/194.959375 THz 3.125GHz spacing";
             }
             enum "1537.69" {
               description "1537.69 nm/194.962500 THz 3.125/6.25/12.5GHz spacing";
             }
             enum "1537.67" {
               description "1537.67 nm/194.965625 THz 3.125GHz spacing";
             }
             enum "1537.64" {
               description "1537.64 nm/194.968750 THz 3.125/6.25GHz spacing";
             }
             enum "1537.62" {
               description "1537.62 nm/194.971875 THz 3.125GHz spacing";
             }
             enum "1537.59" {
               description "1537.59 nm/194.975000 THz 3.125/6.25/12.5GHz spacing";
             }
             enum "1537.57" {
               description "1537.57 nm/194.978125 THz 3.125GHz spacing";
             }
             enum "1537.55" {
               description "1537.55 nm/194.981250 THz 3.125/6.25GHz spacing";
             }
             enum "1537.52" {
               description "1537.52 nm/194.984375 THz 3.125GHz spacing";
             }
             enum "1537.50" {
               description "1537.50 nm/194.987500 THz 3.125/6.25/12.5GHz spacing";
             }
             enum "1537.47" {
               description "1537.47 nm/194.990625 THz 3.125GHz spacing";
             }
             enum "1537.45" {
               description "1537.45 nm/194.993750 THz 3.125/6.25GHz spacing";
             }
             enum "1537.42" {
               description "1537.42 nm/194.996875 THz 3.125GHz spacing";
             }
             enum "1537.40" {
               description "1537.40 nm/195.000000 THz 3.125/6.25/12.5/50/75/100GHz spacing";
             }
             enum "1537.37" {
               description "1537.37 nm/195.003125 THz 3.125GHz spacing";
             }
             enum "1537.35" {
               description "1537.35 nm/195.006250 THz 3.125/6.25GHz spacing";
             }
             enum "1537.32" {
               description "1537.32 nm/195.009375 THz 3.125GHz spacing";
             }
             enum "1537.30" {
               description "1537.30 nm/195.012500 THz 3.125/6.25/12.5GHz spacing";
             }
             enum "1537.27" {
               description "1537.27 nm/195.015625 THz 3.125GHz spacing";
             }
             enum "1537.25" {
               description "1537.25 nm/195.018750 THz 3.125/6.25GHz spacing";
             }
             enum "1537.22" {
               description "1537.22 nm/195.021875 THz 3.125GHz spacing";
             }
             enum "1537.20" {
               description "1537.20 nm/195.025000 THz 3.125/6.25/12.5GHz spacing";
             }
             enum "1537.18" {
               description "1537.18 nm/195.028125 THz 3.125GHz spacing";
             }
             enum "1537.15" {
               description "1537.15 nm/195.031250 THz 3.125/6.25GHz spacing";
             }
             enum "1537.13" {
               description "1537.13 nm/195.034375 THz 3.125GHz spacing";
             }
             enum "1537.10" {
               description "1537.10 nm/195.037500 THz 3.125/6.25/12.5GHz spacing";
             }
             enum "1537.08" {
               description "1537.08 nm/195.040625 THz 3.125GHz spacing";
             }
             enum "1537.05" {
               description "1537.05 nm/195.043750 THz 3.125/6.25GHz spacing";
             }
             enum "1537.03" {
               description "1537.03 nm/195.046875 THz 3.125GHz spacing";
             }
             enum "1537.00" {
               description "1537.00 nm/195.050000 THz 3.125/6.25/12.5/50GHz spacing";
             }
             enum "1536.98" {
               description "1536.98 nm/195.053125 THz 3.125GHz spacing";
             }
             enum "1536.95" {
               description "1536.95 nm/195.056250 THz 3.125/6.25GHz spacing";
             }
             enum "1536.93" {
               description "1536.93 nm/195.059375 THz 3.125GHz spacing";
             }
             enum "1536.90" {
               description "1536.90 nm/195.062500 THz 3.125/6.25/12.5GHz spacing";
             }
             enum "1536.88" {
               description "1536.88 nm/195.065625 THz 3.125GHz spacing";
             }
             enum "1536.86" {
               description "1536.86 nm/195.068750 THz 3.125/6.25GHz spacing";
             }
             enum "1536.83" {
               description "1536.83 nm/195.071875 THz 3.125GHz spacing";
             }
             enum "1536.81" {
               description "1536.81 nm/195.075000 THz 3.125/6.25/12.5/75GHz spacing";
             }
             enum "1536.78" {
               description "1536.78 nm/195.078125 THz 3.125GHz spacing";
             }
             enum "1536.76" {
               description "1536.76 nm/195.081250 THz 3.125/6.25GHz spacing";
             }
             enum "1536.73" {
               description "1536.73 nm/195.084375 THz 3.125GHz spacing";
             }
             enum "1536.71" {
               description "1536.71 nm/195.087500 THz 3.125/6.25/12.5GHz spacing";
             }
             enum "1536.68" {
               description "1536.68 nm/195.090625 THz 3.125GHz spacing";
             }
             enum "1536.66" {
               description "1536.66 nm/195.093750 THz 3.125/6.25GHz spacing";
             }
             enum "1536.63" {
               description "1536.63 nm/195.096875 THz 3.125GHz spacing";
             }
             enum "1536.61" {
               description "1536.61 nm/195.100000 THz 3.125/6.25/12.5/100GHz spacing";
             }
             enum "1536.58" {
               description "1536.58 nm/195.103125 THz 3.125GHz spacing";
             }
             enum "1536.56" {
               description "1536.56 nm/195.106250 THz 3.125/6.25GHz spacing";
             }
             enum "1536.54" {
               description "1536.54 nm/195.109375 THz 3.125GHz spacing";
             }
             enum "1536.51" {
               description "1536.51 nm/195.112500 THz 3.125/6.25/12.5GHz spacing";
             }
             enum "1536.49" {
               description "1536.49 nm/195.115625 THz 3.125GHz spacing";
             }
             enum "1536.46" {
               description "1536.46 nm/195.118750 THz 3.125/6.25GHz spacing";
             }
             enum "1536.44" {
               description "1536.44 nm/195.121875 THz 3.125GHz spacing";
             }
             enum "1536.41" {
               description "1536.41 nm/195.125000 THz 3.125/6.25/12.5GHz spacing";
             }
             enum "1536.39" {
               description "1536.39 nm/195.128125 THz 3.125GHz spacing";
             }
             enum "1536.36" {
               description "1536.36 nm/195.131250 THz 3.125/6.25GHz spacing";
             }
             enum "1536.34" {
               description "1536.34 nm/195.134375 THz 3.125GHz spacing";
             }
             enum "1536.31" {
               description "1536.31 nm/195.137500 THz 3.125/6.25/12.5GHz spacing";
             }
             enum "1536.29" {
               description "1536.29 nm/195.140625 THz 3.125GHz spacing";
             }
             enum "1536.26" {
               description "1536.26 nm/195.143750 THz 3.125/6.25GHz spacing";
             }
             enum "1536.24" {
               description "1536.24 nm/195.146875 THz 3.125GHz spacing";
             }
             enum "1536.22" {
               description "1536.22 nm/195.150000 THz 3.125/6.25/12.5/50/75GHz spacing";
             }
             enum "1536.19" {
               description "1536.19 nm/195.153125 THz 3.125GHz spacing";
             }
             enum "1536.17" {
               description "1536.17 nm/195.156250 THz 3.125/6.25GHz spacing";
             }
             enum "1536.14" {
               description "1536.14 nm/195.159375 THz 3.125GHz spacing";
             }
             enum "1536.12" {
               description "1536.12 nm/195.162500 THz 3.125/6.25/12.5GHz spacing";
             }
             enum "1536.09" {
               description "1536.09 nm/195.165625 THz 3.125GHz spacing";
             }
             enum "1536.07" {
               description "1536.07 nm/195.168750 THz 3.125/6.25GHz spacing";
             }
             enum "1536.04" {
               description "1536.04 nm/195.171875 THz 3.125GHz spacing";
             }
             enum "1536.02" {
               description "1536.02 nm/195.175000 THz 3.125/6.25/12.5GHz spacing";
             }
             enum "1535.99" {
               description "1535.99 nm/195.178125 THz 3.125GHz spacing";
             }
             enum "1535.97" {
               description "1535.97 nm/195.181250 THz 3.125/6.25GHz spacing";
             }
             enum "1535.94" {
               description "1535.94 nm/195.184375 THz 3.125GHz spacing";
             }
             enum "1535.92" {
               description "1535.92 nm/195.187500 THz 3.125/6.25/12.5GHz spacing";
             }
             enum "1535.90" {
               description "1535.90 nm/195.190625 THz 3.125GHz spacing";
             }
             enum "1535.87" {
               description "1535.87 nm/195.193750 THz 3.125/6.25GHz spacing";
             }
             enum "1535.85" {
               description "1535.85 nm/195.196875 THz 3.125GHz spacing";
             }
             enum "1535.82" {
               description "1535.82 nm/195.200000 THz 3.125/6.25/12.5/100GHz spacing";
             }
             enum "1535.80" {
               description "1535.80 nm/195.203125 THz 3.125GHz spacing";
             }
             enum "1535.77" {
               description "1535.77 nm/195.206250 THz 3.125/6.25GHz spacing";
             }
             enum "1535.75" {
               description "1535.75 nm/195.209375 THz 3.125GHz spacing";
             }
             enum "1535.72" {
               description "1535.72 nm/195.212500 THz 3.125/6.25/12.5GHz spacing";
             }
             enum "1535.70" {
               description "1535.70 nm/195.215625 THz 3.125GHz spacing";
             }
             enum "1535.67" {
               description "1535.67 nm/195.218750 THz 3.125/6.25GHz spacing";
             }
             enum "1535.65" {
               description "1535.65 nm/195.221875 THz 3.125GHz spacing";
             }
             enum "1535.63" {
               description "1535.63 nm/195.225000 THz 3.125/6.25/12.5/75GHz spacing";
             }
             enum "1535.60" {
               description "1535.60 nm/195.228125 THz 3.125GHz spacing";
             }
             enum "1535.58" {
               description "1535.58 nm/195.231250 THz 3.125/6.25GHz spacing";
             }
             enum "1535.55" {
               description "1535.55 nm/195.234375 THz 3.125GHz spacing";
             }
             enum "1535.53" {
               description "1535.53 nm/195.237500 THz 3.125/6.25/12.5GHz spacing";
             }
             enum "1535.50" {
               description "1535.50 nm/195.240625 THz 3.125GHz spacing";
             }
             enum "1535.48" {
               description "1535.48 nm/195.243750 THz 3.125/6.25GHz spacing";
             }
             enum "1535.45" {
               description "1535.45 nm/195.246875 THz 3.125GHz spacing";
             }
             enum "1535.43" {
               description "1535.43 nm/195.250000 THz 3.125/6.25/12.5/50GHz spacing";
             }
             enum "1535.40" {
               description "1535.40 nm/195.253125 THz 3.125GHz spacing";
             }
             enum "1535.38" {
               description "1535.38 nm/195.256250 THz 3.125/6.25GHz spacing";
             }
             enum "1535.36" {
               description "1535.36 nm/195.259375 THz 3.125GHz spacing";
             }
             enum "1535.33" {
               description "1535.33 nm/195.262500 THz 3.125/6.25/12.5GHz spacing";
             }
             enum "1535.31" {
               description "1535.31 nm/195.265625 THz 3.125GHz spacing";
             }
             enum "1535.28" {
               description "1535.28 nm/195.268750 THz 3.125/6.25GHz spacing";
             }
             enum "1535.26" {
               description "1535.26 nm/195.271875 THz 3.125GHz spacing";
             }
             enum "1535.23" {
               description "1535.23 nm/195.275000 THz 3.125/6.25/12.5GHz spacing";
             }
             enum "1535.21" {
               description "1535.21 nm/195.278125 THz 3.125GHz spacing";
             }
             enum "1535.18" {
               description "1535.18 nm/195.281250 THz 3.125/6.25GHz spacing";
             }
             enum "1535.16" {
               description "1535.16 nm/195.284375 THz 3.125GHz spacing";
             }
             enum "1535.13" {
               description "1535.13 nm/195.287500 THz 3.125/6.25/12.5GHz spacing";
             }
             enum "1535.11" {
               description "1535.11 nm/195.290625 THz 3.125GHz spacing";
             }
             enum "1535.08" {
               description "1535.08 nm/195.293750 THz 3.125/6.25GHz spacing";
             }
             enum "1535.06" {
               description "1535.06 nm/195.296875 THz 3.125GHz spacing";
             }
             enum "1535.04" {
               description "1535.04 nm/195.300000 THz 3.125/6.25/12.5/50/75/100GHz spacing";
             }
             enum "1535.01" {
               description "1535.01 nm/195.303125 THz 3.125GHz spacing";
             }
             enum "1534.99" {
               description "1534.99 nm/195.306250 THz 3.125/6.25GHz spacing";
             }
             enum "1534.96" {
               description "1534.96 nm/195.309375 THz 3.125GHz spacing";
             }
             enum "1534.94" {
               description "1534.94 nm/195.312500 THz 3.125/6.25/12.5GHz spacing";
             }
             enum "1534.91" {
               description "1534.91 nm/195.315625 THz 3.125GHz spacing";
             }
             enum "1534.89" {
               description "1534.89 nm/195.318750 THz 3.125/6.25GHz spacing";
             }
             enum "1534.86" {
               description "1534.86 nm/195.321875 THz 3.125GHz spacing";
             }
             enum "1534.84" {
               description "1534.84 nm/195.325000 THz 3.125/6.25/12.5GHz spacing";
             }
             enum "1534.81" {
               description "1534.81 nm/195.328125 THz 3.125GHz spacing";
             }
             enum "1534.79" {
               description "1534.79 nm/195.331250 THz 3.125/6.25GHz spacing";
             }
             enum "1534.77" {
               description "1534.77 nm/195.334375 THz 3.125GHz spacing";
             }
             enum "1534.74" {
               description "1534.74 nm/195.337500 THz 3.125/6.25/12.5GHz spacing";
             }
             enum "1534.72" {
               description "1534.72 nm/195.340625 THz 3.125GHz spacing";
             }
             enum "1534.69" {
               description "1534.69 nm/195.343750 THz 3.125/6.25GHz spacing";
             }
             enum "1534.67" {
               description "1534.67 nm/195.346875 THz 3.125GHz spacing";
             }
             enum "1534.64" {
               description "1534.64 nm/195.350000 THz 3.125/6.25/12.5/50GHz spacing";
             }
             enum "1534.62" {
               description "1534.62 nm/195.353125 THz 3.125GHz spacing";
             }
             enum "1534.59" {
               description "1534.59 nm/195.356250 THz 3.125/6.25GHz spacing";
             }
             enum "1534.57" {
               description "1534.57 nm/195.359375 THz 3.125GHz spacing";
             }
             enum "1534.54" {
               description "1534.54 nm/195.362500 THz 3.125/6.25/12.5GHz spacing";
             }
             enum "1534.52" {
               description "1534.52 nm/195.365625 THz 3.125GHz spacing";
             }
             enum "1534.50" {
               description "1534.50 nm/195.368750 THz 3.125/6.25GHz spacing";
             }
             enum "1534.47" {
               description "1534.47 nm/195.371875 THz 3.125GHz spacing";
             }
             enum "1534.45" {
               description "1534.45 nm/195.375000 THz 3.125/6.25/12.5/75GHz spacing";
             }
             enum "1534.42" {
               description "1534.42 nm/195.378125 THz 3.125GHz spacing";
             }
             enum "1534.40" {
               description "1534.40 nm/195.381250 THz 3.125/6.25GHz spacing";
             }
             enum "1534.37" {
               description "1534.37 nm/195.384375 THz 3.125GHz spacing";
             }
             enum "1534.35" {
               description "1534.35 nm/195.387500 THz 3.125/6.25/12.5GHz spacing";
             }
             enum "1534.32" {
               description "1534.32 nm/195.390625 THz 3.125GHz spacing";
             }
             enum "1534.30" {
               description "1534.30 nm/195.393750 THz 3.125/6.25GHz spacing";
             }
             enum "1534.27" {
               description "1534.27 nm/195.396875 THz 3.125GHz spacing";
             }
             enum "1534.25" {
               description "1534.25 nm/195.400000 THz 3.125/6.25/12.5/100GHz spacing";
             }
             enum "1534.23" {
               description "1534.23 nm/195.403125 THz 3.125GHz spacing";
             }
             enum "1534.20" {
               description "1534.20 nm/195.406250 THz 3.125/6.25GHz spacing";
             }
             enum "1534.18" {
               description "1534.18 nm/195.409375 THz 3.125GHz spacing";
             }
             enum "1534.15" {
               description "1534.15 nm/195.412500 THz 3.125/6.25/12.5GHz spacing";
             }
             enum "1534.13" {
               description "1534.13 nm/195.415625 THz 3.125GHz spacing";
             }
             enum "1534.10" {
               description "1534.10 nm/195.418750 THz 3.125/6.25GHz spacing";
             }
             enum "1534.08" {
               description "1534.08 nm/195.421875 THz 3.125GHz spacing";
             }
             enum "1534.05" {
               description "1534.05 nm/195.425000 THz 3.125/6.25/12.5GHz spacing";
             }
             enum "1534.03" {
               description "1534.03 nm/195.428125 THz 3.125GHz spacing";
             }
             enum "1534.00" {
               description "1534.00 nm/195.431250 THz 3.125/6.25GHz spacing";
             }
             enum "1533.98" {
               description "1533.98 nm/195.434375 THz 3.125GHz spacing";
             }
             enum "1533.96" {
               description "1533.96 nm/195.437500 THz 3.125/6.25/12.5GHz spacing";
             }
             enum "1533.93" {
               description "1533.93 nm/195.440625 THz 3.125GHz spacing";
             }
             enum "1533.91" {
               description "1533.91 nm/195.443750 THz 3.125/6.25GHz spacing";
             }
             enum "1533.88" {
               description "1533.88 nm/195.446875 THz 3.125GHz spacing";
             }
             enum "1533.86" {
               description "1533.86 nm/195.450000 THz 3.125/6.25/12.5/50/75GHz spacing";
             }
             enum "1533.83" {
               description "1533.83 nm/195.453125 THz 3.125GHz spacing";
             }
             enum "1533.81" {
               description "1533.81 nm/195.456250 THz 3.125/6.25GHz spacing";
             }
             enum "1533.78" {
               description "1533.78 nm/195.459375 THz 3.125GHz spacing";
             }
             enum "1533.76" {
               description "1533.76 nm/195.462500 THz 3.125/6.25/12.5GHz spacing";
             }
             enum "1533.73" {
               description "1533.73 nm/195.465625 THz 3.125GHz spacing";
             }
             enum "1533.71" {
               description "1533.71 nm/195.468750 THz 3.125/6.25GHz spacing";
             }
             enum "1533.69" {
               description "1533.69 nm/195.471875 THz 3.125GHz spacing";
             }
             enum "1533.66" {
               description "1533.66 nm/195.475000 THz 3.125/6.25/12.5GHz spacing";
             }
             enum "1533.64" {
               description "1533.64 nm/195.478125 THz 3.125GHz spacing";
             }
             enum "1533.61" {
               description "1533.61 nm/195.481250 THz 3.125/6.25GHz spacing";
             }
             enum "1533.59" {
               description "1533.59 nm/195.484375 THz 3.125GHz spacing";
             }
             enum "1533.56" {
               description "1533.56 nm/195.487500 THz 3.125/6.25/12.5GHz spacing";
             }
             enum "1533.54" {
               description "1533.54 nm/195.490625 THz 3.125GHz spacing";
             }
             enum "1533.51" {
               description "1533.51 nm/195.493750 THz 3.125/6.25GHz spacing";
             }
             enum "1533.49" {
               description "1533.49 nm/195.496875 THz 3.125GHz spacing";
             }
             enum "1533.47" {
               description "1533.47 nm/195.500000 THz 3.125/6.25/12.5/100GHz spacing";
             }
             enum "1533.44" {
               description "1533.44 nm/195.503125 THz 3.125GHz spacing";
             }
             enum "1533.42" {
               description "1533.42 nm/195.506250 THz 3.125/6.25GHz spacing";
             }
             enum "1533.39" {
               description "1533.39 nm/195.509375 THz 3.125GHz spacing";
             }
             enum "1533.37" {
               description "1533.37 nm/195.512500 THz 3.125/6.25/12.5GHz spacing";
             }
             enum "1533.34" {
               description "1533.34 nm/195.515625 THz 3.125GHz spacing";
             }
             enum "1533.32" {
               description "1533.32 nm/195.518750 THz 3.125/6.25GHz spacing";
             }
             enum "1533.29" {
               description "1533.29 nm/195.521875 THz 3.125GHz spacing";
             }
             enum "1533.27" {
               description "1533.27 nm/195.525000 THz 3.125/6.25/12.5/75GHz spacing";
             }
             enum "1533.24" {
               description "1533.24 nm/195.528125 THz 3.125GHz spacing";
             }
             enum "1533.22" {
               description "1533.22 nm/195.531250 THz 3.125/6.25GHz spacing";
             }
             enum "1533.20" {
               description "1533.20 nm/195.534375 THz 3.125GHz spacing";
             }
             enum "1533.17" {
               description "1533.17 nm/195.537500 THz 3.125/6.25/12.5GHz spacing";
             }
             enum "1533.15" {
               description "1533.15 nm/195.540625 THz 3.125GHz spacing";
             }
             enum "1533.12" {
               description "1533.12 nm/195.543750 THz 3.125/6.25GHz spacing";
             }
             enum "1533.10" {
               description "1533.10 nm/195.546875 THz 3.125GHz spacing";
             }
             enum "1533.07" {
               description "1533.07 nm/195.550000 THz 3.125/6.25/12.5/50GHz spacing";
             }
             enum "1533.05" {
               description "1533.05 nm/195.553125 THz 3.125GHz spacing";
             }
             enum "1533.02" {
               description "1533.02 nm/195.556250 THz 3.125/6.25GHz spacing";
             }
             enum "1533.00" {
               description "1533.00 nm/195.559375 THz 3.125GHz spacing";
             }
             enum "1532.98" {
               description "1532.98 nm/195.562500 THz 3.125/6.25/12.5GHz spacing";
             }
             enum "1532.95" {
               description "1532.95 nm/195.565625 THz 3.125GHz spacing";
             }
             enum "1532.93" {
               description "1532.93 nm/195.568750 THz 3.125/6.25GHz spacing";
             }
             enum "1532.90" {
               description "1532.90 nm/195.571875 THz 3.125GHz spacing";
             }
             enum "1532.88" {
               description "1532.88 nm/195.575000 THz 3.125/6.25/12.5GHz spacing";
             }
             enum "1532.85" {
               description "1532.85 nm/195.578125 THz 3.125GHz spacing";
             }
             enum "1532.83" {
               description "1532.83 nm/195.581250 THz 3.125/6.25GHz spacing";
             }
             enum "1532.80" {
               description "1532.80 nm/195.584375 THz 3.125GHz spacing";
             }
             enum "1532.78" {
               description "1532.78 nm/195.587500 THz 3.125/6.25/12.5GHz spacing";
             }
             enum "1532.75" {
               description "1532.75 nm/195.590625 THz 3.125GHz spacing";
             }
             enum "1532.73" {
               description "1532.73 nm/195.593750 THz 3.125/6.25GHz spacing";
             }
             enum "1532.71" {
               description "1532.71 nm/195.596875 THz 3.125GHz spacing";
             }
             enum "1532.68" {
               description "1532.68 nm/195.600000 THz 3.125/6.25/12.5/50/75/100GHz spacing";
             }
             enum "1532.66" {
               description "1532.66 nm/195.603125 THz 3.125GHz spacing";
             }
             enum "1532.63" {
               description "1532.63 nm/195.606250 THz 3.125/6.25GHz spacing";
             }
             enum "1532.61" {
               description "1532.61 nm/195.609375 THz 3.125GHz spacing";
             }
             enum "1532.58" {
               description "1532.58 nm/195.612500 THz 3.125/6.25/12.5GHz spacing";
             }
             enum "1532.56" {
               description "1532.56 nm/195.615625 THz 3.125GHz spacing";
             }
             enum "1532.53" {
               description "1532.53 nm/195.618750 THz 3.125/6.25GHz spacing";
             }
             enum "1532.51" {
               description "1532.51 nm/195.621875 THz 3.125GHz spacing";
             }
             enum "1532.49" {
               description "1532.49 nm/195.625000 THz 3.125/6.25/12.5GHz spacing";
             }
             enum "1532.46" {
               description "1532.46 nm/195.628125 THz 3.125GHz spacing";
             }
             enum "1532.44" {
               description "1532.44 nm/195.631250 THz 3.125/6.25GHz spacing";
             }
             enum "1532.41" {
               description "1532.41 nm/195.634375 THz 3.125GHz spacing";
             }
             enum "1532.39" {
               description "1532.39 nm/195.637500 THz 3.125/6.25/12.5GHz spacing";
             }
             enum "1532.36" {
               description "1532.36 nm/195.640625 THz 3.125GHz spacing";
             }
             enum "1532.34" {
               description "1532.34 nm/195.643750 THz 3.125/6.25GHz spacing";
             }
             enum "1532.31" {
               description "1532.31 nm/195.646875 THz 3.125GHz spacing";
             }
             enum "1532.29" {
               description "1532.29 nm/195.650000 THz 3.125/6.25/12.5/50GHz spacing";
             }
             enum "1532.27" {
               description "1532.27 nm/195.653125 THz 3.125GHz spacing";
             }
             enum "1532.24" {
               description "1532.24 nm/195.656250 THz 3.125/6.25GHz spacing";
             }
             enum "1532.22" {
               description "1532.22 nm/195.659375 THz 3.125GHz spacing";
             }
             enum "1532.19" {
               description "1532.19 nm/195.662500 THz 3.125/6.25/12.5GHz spacing";
             }
             enum "1532.17" {
               description "1532.17 nm/195.665625 THz 3.125GHz spacing";
             }
             enum "1532.14" {
               description "1532.14 nm/195.668750 THz 3.125/6.25GHz spacing";
             }
             enum "1532.12" {
               description "1532.12 nm/195.671875 THz 3.125GHz spacing";
             }
             enum "1532.09" {
               description "1532.09 nm/195.675000 THz 3.125/6.25/12.5/75GHz spacing";
             }
             enum "1532.07" {
               description "1532.07 nm/195.678125 THz 3.125GHz spacing";
             }
             enum "1532.04" {
               description "1532.04 nm/195.681250 THz 3.125/6.25GHz spacing";
             }
             enum "1532.02" {
               description "1532.02 nm/195.684375 THz 3.125GHz spacing";
             }
             enum "1532.00" {
               description "1532.00 nm/195.687500 THz 3.125/6.25/12.5GHz spacing";
             }
             enum "1531.97" {
               description "1531.97 nm/195.690625 THz 3.125GHz spacing";
             }
             enum "1531.95" {
               description "1531.95 nm/195.693750 THz 3.125/6.25GHz spacing";
             }
             enum "1531.92" {
               description "1531.92 nm/195.696875 THz 3.125GHz spacing";
             }
             enum "1531.90" {
               description "1531.90 nm/195.700000 THz 3.125/6.25/12.5/100GHz spacing";
             }
             enum "1531.87" {
               description "1531.87 nm/195.703125 THz 3.125GHz spacing";
             }
             enum "1531.85" {
               description "1531.85 nm/195.706250 THz 3.125/6.25GHz spacing";
             }
             enum "1531.82" {
               description "1531.82 nm/195.709375 THz 3.125GHz spacing";
             }
             enum "1531.80" {
               description "1531.80 nm/195.712500 THz 3.125/6.25/12.5GHz spacing";
             }
             enum "1531.78" {
               description "1531.78 nm/195.715625 THz 3.125GHz spacing";
             }
             enum "1531.75" {
               description "1531.75 nm/195.718750 THz 3.125/6.25GHz spacing";
             }
             enum "1531.73" {
               description "1531.73 nm/195.721875 THz 3.125GHz spacing";
             }
             enum "1531.70" {
               description "1531.70 nm/195.725000 THz 3.125/6.25/12.5GHz spacing";
             }
             enum "1531.68" {
               description "1531.68 nm/195.728125 THz 3.125GHz spacing";
             }
             enum "1531.65" {
               description "1531.65 nm/195.731250 THz 3.125/6.25GHz spacing";
             }
             enum "1531.63" {
               description "1531.63 nm/195.734375 THz 3.125GHz spacing";
             }
             enum "1531.60" {
               description "1531.60 nm/195.737500 THz 3.125/6.25/12.5GHz spacing";
             }
             enum "1531.58" {
               description "1531.58 nm/195.740625 THz 3.125GHz spacing";
             }
             enum "1531.56" {
               description "1531.56 nm/195.743750 THz 3.125/6.25GHz spacing";
             }
             enum "1531.53" {
               description "1531.53 nm/195.746875 THz 3.125GHz spacing";
             }
             enum "1531.51" {
               description "1531.51 nm/195.750000 THz 3.125/6.25/12.5/50/75GHz spacing";
             }
             enum "1531.48" {
               description "1531.48 nm/195.753125 THz 3.125GHz spacing";
             }
             enum "1531.46" {
               description "1531.46 nm/195.756250 THz 3.125/6.25GHz spacing";
             }
             enum "1531.43" {
               description "1531.43 nm/195.759375 THz 3.125GHz spacing";
             }
             enum "1531.41" {
               description "1531.41 nm/195.762500 THz 3.125/6.25/12.5GHz spacing";
             }
             enum "1531.38" {
               description "1531.38 nm/195.765625 THz 3.125GHz spacing";
             }
             enum "1531.36" {
               description "1531.36 nm/195.768750 THz 3.125/6.25GHz spacing";
             }
             enum "1531.34" {
               description "1531.34 nm/195.771875 THz 3.125GHz spacing";
             }
             enum "1531.31" {
               description "1531.31 nm/195.775000 THz 3.125/6.25/12.5GHz spacing";
             }
             enum "1531.29" {
               description "1531.29 nm/195.778125 THz 3.125GHz spacing";
             }
             enum "1531.26" {
               description "1531.26 nm/195.781250 THz 3.125/6.25GHz spacing";
             }
             enum "1531.24" {
               description "1531.24 nm/195.784375 THz 3.125GHz spacing";
             }
             enum "1531.21" {
               description "1531.21 nm/195.787500 THz 3.125/6.25/12.5GHz spacing";
             }
             enum "1531.19" {
               description "1531.19 nm/195.790625 THz 3.125GHz spacing";
             }
             enum "1531.16" {
               description "1531.16 nm/195.793750 THz 3.125/6.25GHz spacing";
             }
             enum "1531.14" {
               description "1531.14 nm/195.796875 THz 3.125GHz spacing";
             }
             enum "1531.12" {
               description "1531.12 nm/195.800000 THz 3.125/6.25/12.5/100GHz spacing";
             }
             enum "1531.09" {
               description "1531.09 nm/195.803125 THz 3.125GHz spacing";
             }
             enum "1531.07" {
               description "1531.07 nm/195.806250 THz 3.125/6.25GHz spacing";
             }
             enum "1531.04" {
               description "1531.04 nm/195.809375 THz 3.125GHz spacing";
             }
             enum "1531.02" {
               description "1531.02 nm/195.812500 THz 3.125/6.25/12.5GHz spacing";
             }
             enum "1530.99" {
               description "1530.99 nm/195.815625 THz 3.125GHz spacing";
             }
             enum "1530.97" {
               description "1530.97 nm/195.818750 THz 3.125/6.25GHz spacing";
             }
             enum "1530.94" {
               description "1530.94 nm/195.821875 THz 3.125GHz spacing";
             }
             enum "1530.92" {
               description "1530.92 nm/195.825000 THz 3.125/6.25/12.5/75GHz spacing";
             }
             enum "1530.90" {
               description "1530.90 nm/195.828125 THz 3.125GHz spacing";
             }
             enum "1530.87" {
               description "1530.87 nm/195.831250 THz 3.125/6.25GHz spacing";
             }
             enum "1530.85" {
               description "1530.85 nm/195.834375 THz 3.125GHz spacing";
             }
             enum "1530.82" {
               description "1530.82 nm/195.837500 THz 3.125/6.25/12.5GHz spacing";
             }
             enum "1530.80" {
               description "1530.80 nm/195.840625 THz 3.125GHz spacing";
             }
             enum "1530.77" {
               description "1530.77 nm/195.843750 THz 3.125/6.25GHz spacing";
             }
             enum "1530.75" {
               description "1530.75 nm/195.846875 THz 3.125GHz spacing";
             }
             enum "1530.72" {
               description "1530.72 nm/195.850000 THz 3.125/6.25/12.5/50GHz spacing";
             }
             enum "1530.70" {
               description "1530.70 nm/195.853125 THz 3.125GHz spacing";
             }
             enum "1530.68" {
               description "1530.68 nm/195.856250 THz 3.125/6.25GHz spacing";
             }
             enum "1530.65" {
               description "1530.65 nm/195.859375 THz 3.125GHz spacing";
             }
             enum "1530.63" {
               description "1530.63 nm/195.862500 THz 3.125/6.25/12.5GHz spacing";
             }
             enum "1530.60" {
               description "1530.60 nm/195.865625 THz 3.125GHz spacing";
             }
             enum "1530.58" {
               description "1530.58 nm/195.868750 THz 3.125/6.25GHz spacing";
             }
             enum "1530.55" {
               description "1530.55 nm/195.871875 THz 3.125GHz spacing";
             }
             enum "1530.53" {
               description "1530.53 nm/195.875000 THz 3.125/6.25/12.5GHz spacing";
             }
             enum "1530.51" {
               description "1530.51 nm/195.878125 THz 3.125GHz spacing";
             }
             enum "1530.48" {
               description "1530.48 nm/195.881250 THz 3.125/6.25GHz spacing";
             }
             enum "1530.46" {
               description "1530.46 nm/195.884375 THz 3.125GHz spacing";
             }
             enum "1530.43" {
               description "1530.43 nm/195.887500 THz 3.125/6.25/12.5GHz spacing";
             }
             enum "1530.41" {
               description "1530.41 nm/195.890625 THz 3.125GHz spacing";
             }
             enum "1530.38" {
               description "1530.38 nm/195.893750 THz 3.125/6.25GHz spacing";
             }
             enum "1530.36" {
               description "1530.36 nm/195.896875 THz 3.125GHz spacing";
             }
             enum "1530.33" {
               description "1530.33 nm/195.900000 THz 3.125/6.25/12.5/50/75/100GHz spacing";
             }
             enum "1530.31" {
               description "1530.31 nm/195.903125 THz 3.125GHz spacing";
             }
             enum "1530.29" {
               description "1530.29 nm/195.906250 THz 3.125/6.25GHz spacing";
             }
             enum "1530.26" {
               description "1530.26 nm/195.909375 THz 3.125GHz spacing";
             }
             enum "1530.24" {
               description "1530.24 nm/195.912500 THz 3.125/6.25/12.5GHz spacing";
             }
             enum "1530.21" {
               description "1530.21 nm/195.915625 THz 3.125GHz spacing";
             }
             enum "1530.19" {
               description "1530.19 nm/195.918750 THz 3.125/6.25GHz spacing";
             }
             enum "1530.16" {
               description "1530.16 nm/195.921875 THz 3.125GHz spacing";
             }
             enum "1530.14" {
               description "1530.14 nm/195.925000 THz 3.125/6.25/12.5GHz spacing";
             }
             enum "1530.11" {
               description "1530.11 nm/195.928125 THz 3.125GHz spacing";
             }
             enum "1530.09" {
               description "1530.09 nm/195.931250 THz 3.125/6.25GHz spacing";
             }
             enum "1530.07" {
               description "1530.07 nm/195.934375 THz 3.125GHz spacing";
             }
             enum "1530.04" {
               description "1530.04 nm/195.937500 THz 3.125/6.25/12.5GHz spacing";
             }
             enum "1530.02" {
               description "1530.02 nm/195.940625 THz 3.125GHz spacing";
             }
             enum "1529.99" {
               description "1529.99 nm/195.943750 THz 3.125/6.25GHz spacing";
             }
             enum "1529.97" {
               description "1529.97 nm/195.946875 THz 3.125GHz spacing";
             }
             enum "1529.94" {
               description "1529.94 nm/195.950000 THz 3.125/6.25/12.5/50GHz spacing";
             }
             enum "1529.92" {
               description "1529.92 nm/195.953125 THz 3.125GHz spacing";
             }
             enum "1529.89" {
               description "1529.89 nm/195.956250 THz 3.125/6.25GHz spacing";
             }
             enum "1529.87" {
               description "1529.87 nm/195.959375 THz 3.125GHz spacing";
             }
             enum "1529.85" {
               description "1529.85 nm/195.962500 THz 3.125/6.25/12.5GHz spacing";
             }
             enum "1529.82" {
               description "1529.82 nm/195.965625 THz 3.125GHz spacing";
             }
             enum "1529.80" {
               description "1529.80 nm/195.968750 THz 3.125/6.25GHz spacing";
             }
             enum "1529.77" {
               description "1529.77 nm/195.971875 THz 3.125GHz spacing";
             }
             enum "1529.75" {
               description "1529.75 nm/195.975000 THz 3.125/6.25/12.5/75GHz spacing";
             }
             enum "1529.72" {
               description "1529.72 nm/195.978125 THz 3.125GHz spacing";
             }
             enum "1529.70" {
               description "1529.70 nm/195.981250 THz 3.125/6.25GHz spacing";
             }
             enum "1529.68" {
               description "1529.68 nm/195.984375 THz 3.125GHz spacing";
             }
             enum "1529.65" {
               description "1529.65 nm/195.987500 THz 3.125/6.25/12.5GHz spacing";
             }
             enum "1529.63" {
               description "1529.63 nm/195.990625 THz 3.125GHz spacing";
             }
             enum "1529.60" {
               description "1529.60 nm/195.993750 THz 3.125/6.25GHz spacing";
             }
             enum "1529.58" {
               description "1529.58 nm/195.996875 THz 3.125GHz spacing";
             }
             enum "1529.55" {
               description "1529.55 nm/196.000000 THz 3.125/6.25/12.5/100GHz spacing";
             }
             enum "1529.53" {
               description "1529.53 nm/196.003125 THz 3.125GHz spacing";
             }
             enum "1529.50" {
               description "1529.50 nm/196.006250 THz 3.125/6.25GHz spacing";
             }
             enum "1529.48" {
               description "1529.48 nm/196.009375 THz 3.125GHz spacing";
             }
             enum "1529.46" {
               description "1529.46 nm/196.012500 THz 3.125/6.25/12.5GHz spacing";
             }
             enum "1529.43" {
               description "1529.43 nm/196.015625 THz 3.125GHz spacing";
             }
             enum "1529.41" {
               description "1529.41 nm/196.018750 THz 3.125/6.25GHz spacing";
             }
             enum "1529.38" {
               description "1529.38 nm/196.021875 THz 3.125GHz spacing";
             }
             enum "1529.36" {
               description "1529.36 nm/196.025000 THz 3.125/6.25/12.5GHz spacing";
             }
             enum "1529.33" {
               description "1529.33 nm/196.028125 THz 3.125GHz spacing";
             }
             enum "1529.31" {
               description "1529.31 nm/196.031250 THz 3.125/6.25GHz spacing";
             }
             enum "1529.29" {
               description "1529.29 nm/196.034375 THz 3.125GHz spacing";
             }
             enum "1529.26" {
               description "1529.26 nm/196.037500 THz 3.125/6.25/12.5GHz spacing";
             }
             enum "1529.24" {
               description "1529.24 nm/196.040625 THz 3.125GHz spacing";
             }
             enum "1529.21" {
               description "1529.21 nm/196.043750 THz 3.125/6.25GHz spacing";
             }
             enum "1529.19" {
               description "1529.19 nm/196.046875 THz 3.125GHz spacing";
             }
             enum "1529.16" {
               description "1529.16 nm/196.050000 THz 3.125/6.25/12.5/50/75GHz spacing";
             }
             enum "1529.14" {
               description "1529.14 nm/196.053125 THz 3.125GHz spacing";
             }
             enum "1529.11" {
               description "1529.11 nm/196.056250 THz 3.125/6.25GHz spacing";
             }
             enum "1529.09" {
               description "1529.09 nm/196.059375 THz 3.125GHz spacing";
             }
             enum "1529.07" {
               description "1529.07 nm/196.062500 THz 3.125/6.25/12.5GHz spacing";
             }
             enum "1529.04" {
               description "1529.04 nm/196.065625 THz 3.125GHz spacing";
             }
             enum "1529.02" {
               description "1529.02 nm/196.068750 THz 3.125/6.25GHz spacing";
             }
             enum "1528.99" {
               description "1528.99 nm/196.071875 THz 3.125GHz spacing";
             }
             enum "1528.97" {
               description "1528.97 nm/196.075000 THz 3.125/6.25/12.5GHz spacing";
             }
             enum "1528.94" {
               description "1528.94 nm/196.078125 THz 3.125GHz spacing";
             }
             enum "1528.92" {
               description "1528.92 nm/196.081250 THz 3.125/6.25GHz spacing";
             }
             enum "1528.90" {
               description "1528.90 nm/196.084375 THz 3.125GHz spacing";
             }
             enum "1528.87" {
               description "1528.87 nm/196.087500 THz 3.125/6.25/12.5GHz spacing";
             }
             enum "1528.85" {
               description "1528.85 nm/196.090625 THz 3.125GHz spacing";
             }
             enum "1528.82" {
               description "1528.82 nm/196.093750 THz 3.125/6.25GHz spacing";
             }
             enum "1528.80" {
               description "1528.80 nm/196.096875 THz 3.125GHz spacing";
             }
             enum "1528.77" {
               description "1528.77 nm/196.100000 THz 3.125/6.25/12.5/50/75/100GHz spacing";
             }
             enum "1528.75" {
               description "1528.75 nm/196.103125 THz 3.125GHz spacing";
             }
             enum "1528.72" {
               description "1528.72 nm/196.106250 THz 3.125/6.25GHz spacing";
             }
             enum "1528.70" {
               description "1528.70 nm/196.109375 THz 3.125GHz spacing";
             }
             enum "1528.68" {
               description "1528.68 nm/196.112500 THz 3.125/6.25/12.5GHz spacing";
             }
             enum "1528.65" {
               description "1528.65 nm/196.115625 THz 3.125GHz spacing";
             }
             enum "1528.63" {
               description "1528.63 nm/196.118750 THz 3.125/6.25GHz spacing";
             }
             enum "1528.60" {
               description "1528.60 nm/196.121875 THz 3.125GHz spacing";
             }
             enum "1528.58" {
               description "1528.58 nm/196.125000 THz 3.125/6.25/12.5/75GHz spacing";
             }
             enum "1528.55" {
               description "1528.55 nm/196.128125 THz 3.125GHz spacing";
             }
             enum "1528.53" {
               description "1528.53 nm/196.131250 THz 3.125/6.25GHz spacing";
             }
             enum "1528.51" {
               description "1528.51 nm/196.134375 THz 3.125GHz spacing";
             }
             enum "1528.48" {
               description "1528.48 nm/196.137500 THz 3.125/6.25/12.5GHz spacing";
             }
             enum "1528.46" {
               description "1528.46 nm/196.140625 THz 3.125GHz spacing";
             }
             enum "1528.43" {
               description "1528.43 nm/196.143750 THz 3.125/6.25GHz spacing";
             }
             enum "1528.41" {
               description "1528.41 nm/196.146875 THz 3.125GHz spacing";
             }
             enum "1528.38" {
               description "1528.38 nm/196.15040 THz 50Ghz spacing";
             }
           }
         }
       }
       case case_2 {
         leaf frequency {
           description "Optical channel frequency in terahertz";
           type enumeration {
             enum "191.1003" {
               description "191.1003 THz/1568.77 nm 50/100Ghz spacing";
             }
             enum "191.15000" {
               description "191.15000 THz/1568.36 nm 6.25/12.5/50GHz spacing";
             }
             enum "191.15625" {
               description "191.15625 THz/1568.31 nm 6.25GHz spacing";
             }
             enum "191.16250" {
               description "191.16250 THz/1568.26 nm 6.25/12.5GHz spacing";
             }
             enum "191.16875" {
               description "191.16875 THz/1568.21 nm 6.25GHz spacing";
             }
             enum "191.17500" {
               description "191.17500 THz/1568.16 nm 6.25/12.5GHz spacing";
             }
             enum "191.18125" {
               description "191.18125 THz/1568.11 nm 6.25GHz spacing";
             }
             enum "191.18750" {
               description "191.18750 THz/1568.05 nm 6.25/12.5GHz spacing";
             }
             enum "191.19375" {
               description "191.19375 THz/1568.00 nm 6.25GHz spacing";
             }
             enum "191.20000" {
               description "191.20000 THz/1567.95 nm 6.25/12.5/50/100GHz spacing";
             }
             enum "191.20625" {
               description "191.20625 THz/1567.90 nm 6.25GHz spacing";
             }
             enum "191.21250" {
               description "191.21250 THz/1567.85 nm 6.25/12.5GHz spacing";
             }
             enum "191.21875" {
               description "191.21875 THz/1567.80 nm 6.25GHz spacing";
             }
             enum "191.22500" {
               description "191.22500 THz/1567.75 nm 6.25/12.5GHz spacing";
             }
             enum "191.23125" {
               description "191.23125 THz/1567.70 nm 6.25GHz spacing";
             }
             enum "191.23750" {
               description "191.23750 THz/1567.64 nm 6.25/12.5GHz spacing";
             }
             enum "191.24375" {
               description "191.24375 THz/1567.59 nm 6.25GHz spacing";
             }
             enum "191.25000" {
               description "191.25000 THz/1567.54 nm 6.25/12.5/50GHz spacing";
             }
             enum "191.25625" {
               description "191.25625 THz/1567.49 nm 6.25GHz spacing";
             }
             enum "191.26250" {
               description "191.26250 THz/1567.44 nm 6.25/12.5GHz spacing";
             }
             enum "191.26875" {
               description "191.26875 THz/1567.39 nm 6.25GHz spacing";
             }
             enum "191.27500" {
               description "191.27500 THz/1567.34 nm 6.25/12.5GHz spacing";
             }
             enum "191.28125" {
               description "191.28125 THz/1567.29 nm 6.25GHz spacing";
             }
             enum "191.28750" {
               description "191.28750 THz/1567.23 nm 6.25/12.5GHz spacing";
             }
             enum "191.29375" {
               description "191.29375 THz/1567.18 nm 6.25GHz spacing";
             }
             enum "191.30000" {
               description "191.30000 THz/1567.13 nm 6.25/12.5/50/100GHz spacing";
             }
             enum "191.30625" {
               description "191.30625 THz/1567.08 nm 6.25GHz spacing";
             }
             enum "191.31250" {
               description "191.31250 THz/1567.03 nm 6.25/12.5GHz spacing";
             }
             enum "191.31875" {
               description "191.31875 THz/1566.98 nm 6.25GHz spacing";
             }
             enum "191.32500" {
               description "191.32500 THz/1566.93 nm 6.25/12.5GHz spacing";
             }
             enum "191.33125" {
               description "191.33125 THz/1566.88 nm 6.25GHz spacing";
             }
             enum "191.33750" {
               description "191.33750 THz/1566.83 nm 6.25/12.5GHz spacing";
             }
             enum "191.34375" {
               description "191.34375 THz/1566.77 nm 6.25GHz spacing";
             }
             enum "191.35000" {
               description "191.35000 THz/1566.72 nm 6.25/12.5/50GHz spacing";
             }
             enum "191.35625" {
               description "191.35625 THz/1566.67 nm 6.25GHz spacing";
             }
             enum "191.36250" {
               description "191.36250 THz/1566.62 nm 6.25/12.5GHz spacing";
             }
             enum "191.36875" {
               description "191.36875 THz/1566.57 nm 6.25GHz spacing";
             }
             enum "191.37500" {
               description "191.37500 THz/1566.52 nm 6.25/12.5/75GHz spacing";
             }
             enum "191.38125" {
               description "191.38125 THz/1566.47 nm 6.25GHz spacing";
             }
             enum "191.38750" {
               description "191.38750 THz/1566.42 nm 6.25/12.5GHz spacing";
             }
             enum "191.39375" {
               description "191.39375 THz/1566.36 nm 6.25GHz spacing";
             }
             enum "191.40000" {
               description "191.40000 THz/1566.31 nm 6.25/12.5/50/100GHz spacing";
             }
             enum "191.40625" {
               description "191.40625 THz/1566.26 nm 6.25GHz spacing";
             }
             enum "191.41250" {
               description "191.41250 THz/1566.21 nm 6.25/12.5GHz spacing";
             }
             enum "191.41875" {
               description "191.41875 THz/1566.16 nm 6.25GHz spacing";
             }
             enum "191.42500" {
               description "191.42500 THz/1566.11 nm 6.25/12.5GHz spacing";
             }
             enum "191.43125" {
               description "191.43125 THz/1566.06 nm 6.25GHz spacing";
             }
             enum "191.43750" {
               description "191.43750 THz/1566.01 nm 6.25/12.5GHz spacing";
             }
             enum "191.44375" {
               description "191.44375 THz/1565.96 nm 6.25GHz spacing";
             }
             enum "191.45000" {
               description "191.45000 THz/1565.90 nm 6.25/12.5/50/75GHz spacing";
             }
             enum "191.45625" {
               description "191.45625 THz/1565.85 nm 6.25GHz spacing";
             }
             enum "191.46250" {
               description "191.46250 THz/1565.80 nm 6.25/12.5GHz spacing";
             }
             enum "191.46875" {
               description "191.46875 THz/1565.75 nm 6.25GHz spacing";
             }
             enum "191.47500" {
               description "191.47500 THz/1565.70 nm 6.25/12.5GHz spacing";
             }
             enum "191.48125" {
               description "191.48125 THz/1565.65 nm 6.25GHz spacing";
             }
             enum "191.48750" {
               description "191.48750 THz/1565.60 nm 6.25/12.5GHz spacing";
             }
             enum "191.49375" {
               description "191.49375 THz/1565.55 nm 6.25GHz spacing";
             }
             enum "191.50000" {
               description "191.50000 THz/1565.50 nm 6.25/12.5/50/100GHz spacing";
             }
             enum "191.50625" {
               description "191.50625 THz/1565.44 nm 6.25GHz spacing";
             }
             enum "191.51250" {
               description "191.51250 THz/1565.39 nm 6.25/12.5GHz spacing";
             }
             enum "191.51875" {
               description "191.51875 THz/1565.34 nm 6.25GHz spacing";
             }
             enum "191.52500" {
               description "191.52500 THz/1565.29 nm 6.25/12.5/75GHz spacing";
             }
             enum "191.53125" {
               description "191.53125 THz/1565.24 nm 6.25GHz spacing";
             }
             enum "191.53750" {
               description "191.53750 THz/1565.19 nm 6.25/12.5GHz spacing";
             }
             enum "191.54375" {
               description "191.54375 THz/1565.14 nm 6.25GHz spacing";
             }
             enum "191.55000" {
               description "191.55000 THz/1565.09 nm 6.25/12.5/50GHz spacing";
             }
             enum "191.55625" {
               description "191.55625 THz/1565.04 nm 6.25GHz spacing";
             }
             enum "191.56250" {
               description "191.56250 THz/1564.99 nm 6.25/12.5GHz spacing";
             }
             enum "191.56875" {
               description "191.56875 THz/1564.93 nm 6.25GHz spacing";
             }
             enum "191.57500" {
               description "191.57500 THz/1564.88 nm 6.25/12.5GHz spacing";
             }
             enum "191.58125" {
               description "191.58125 THz/1564.83 nm 6.25GHz spacing";
             }
             enum "191.58750" {
               description "191.58750 THz/1564.78 nm 6.25/12.5GHz spacing";
             }
             enum "191.59375" {
               description "191.59375 THz/1564.73 nm 6.25GHz spacing";
             }
             enum "191.60000" {
               description "191.60000 THz/1564.68 nm 6.25/12.5/50/75/100GHz spacing";
             }
             enum "191.60625" {
               description "191.60625 THz/1564.63 nm 6.25GHz spacing";
             }
             enum "191.61250" {
               description "191.61250 THz/1564.58 nm 6.25/12.5GHz spacing";
             }
             enum "191.61875" {
               description "191.61875 THz/1564.53 nm 6.25GHz spacing";
             }
             enum "191.62500" {
               description "191.62500 THz/1564.47 nm 6.25/12.5GHz spacing";
             }
             enum "191.63125" {
               description "191.63125 THz/1564.42 nm 6.25GHz spacing";
             }
             enum "191.63750" {
               description "191.63750 THz/1564.37 nm 6.25/12.5GHz spacing";
             }
             enum "191.64375" {
               description "191.64375 THz/1564.32 nm 6.25GHz spacing";
             }
             enum "191.65000" {
               description "191.65000 THz/1564.27 nm 6.25/12.5/50GHz spacing";
             }
             enum "191.65625" {
               description "191.65625 THz/1564.22 nm 6.25GHz spacing";
             }
             enum "191.66250" {
               description "191.66250 THz/1564.17 nm 6.25/12.5GHz spacing";
             }
             enum "191.66875" {
               description "191.66875 THz/1564.12 nm 6.25GHz spacing";
             }
             enum "191.67500" {
               description "191.67500 THz/1564.07 nm 6.25/12.5/75GHz spacing";
             }
             enum "191.68125" {
               description "191.68125 THz/1564.02 nm 6.25GHz spacing";
             }
             enum "191.68750" {
               description "191.68750 THz/1563.96 nm 6.25/12.5GHz spacing";
             }
             enum "191.69375" {
               description "191.69375 THz/1563.91 nm 6.25GHz spacing";
             }
             enum "191.70000" {
               description "191.70000 THz/1563.86 nm 6.25/12.5/50/100GHz spacing";
             }
             enum "191.70625" {
               description "191.70625 THz/1563.81 nm 6.25GHz spacing";
             }
             enum "191.71250" {
               description "191.71250 THz/1563.76 nm 6.25/12.5GHz spacing";
             }
             enum "191.71875" {
               description "191.71875 THz/1563.71 nm 6.25GHz spacing";
             }
             enum "191.72500" {
               description "191.72500 THz/1563.66 nm 6.25/12.5GHz spacing";
             }
             enum "191.73125" {
               description "191.73125 THz/1563.61 nm 6.25GHz spacing";
             }
             enum "191.73750" {
               description "191.73750 THz/1563.56 nm 6.25/12.5GHz spacing";
             }
             enum "191.74375" {
               description "191.74375 THz/1563.51 nm 6.25GHz spacing";
             }
             enum "191.75000" {
               description "191.75000 THz/1563.45 nm 6.25/12.5/50/75GHz spacing";
             }
             enum "191.75625" {
               description "191.75625 THz/1563.40 nm 6.25GHz spacing";
             }
             enum "191.76250" {
               description "191.76250 THz/1563.35 nm 6.25/12.5GHz spacing";
             }
             enum "191.76875" {
               description "191.76875 THz/1563.30 nm 6.25GHz spacing";
             }
             enum "191.77500" {
               description "191.77500 THz/1563.25 nm 6.25/12.5GHz spacing";
             }
             enum "191.78125" {
               description "191.78125 THz/1563.20 nm 6.25GHz spacing";
             }
             enum "191.78750" {
               description "191.78750 THz/1563.15 nm 6.25/12.5GHz spacing";
             }
             enum "191.79375" {
               description "191.79375 THz/1563.10 nm 6.25GHz spacing";
             }
             enum "191.80000" {
               description "191.80000 THz/1563.05 nm 6.25/12.5/50/100GHz spacing";
             }
             enum "191.80625" {
               description "191.80625 THz/1563.00 nm 6.25GHz spacing";
             }
             enum "191.81250" {
               description "191.81250 THz/1562.95 nm 6.25/12.5GHz spacing";
             }
             enum "191.81875" {
               description "191.81875 THz/1562.89 nm 6.25GHz spacing";
             }
             enum "191.82500" {
               description "191.82500 THz/1562.84 nm 6.25/12.5/75GHz spacing";
             }
             enum "191.83125" {
               description "191.83125 THz/1562.79 nm 6.25GHz spacing";
             }
             enum "191.83750" {
               description "191.83750 THz/1562.74 nm 6.25/12.5GHz spacing";
             }
             enum "191.84375" {
               description "191.84375 THz/1562.69 nm 6.25GHz spacing";
             }
             enum "191.85000" {
               description "191.85000 THz/1562.64 nm 6.25/12.5/50GHz spacing";
             }
             enum "191.85625" {
               description "191.85625 THz/1562.59 nm 6.25GHz spacing";
             }
             enum "191.86250" {
               description "191.86250 THz/1562.54 nm 6.25/12.5GHz spacing";
             }
             enum "191.86875" {
               description "191.86875 THz/1562.49 nm 6.25GHz spacing";
             }
             enum "191.87500" {
               description "191.87500 THz/1562.44 nm 6.25/12.5GHz spacing";
             }
             enum "191.88125" {
               description "191.88125 THz/1562.39 nm 6.25GHz spacing";
             }
             enum "191.88750" {
               description "191.88750 THz/1562.33 nm 6.25/12.5GHz spacing";
             }
             enum "191.89375" {
               description "191.89375 THz/1562.28 nm 6.25GHz spacing";
             }
             enum "191.90000" {
               description "191.90000 THz/1562.23 nm 6.25/12.5/50/75/100GHz spacing";
             }
             enum "191.90625" {
               description "191.90625 THz/1562.18 nm 6.25GHz spacing";
             }
             enum "191.91250" {
               description "191.91250 THz/1562.13 nm 6.25/12.5GHz spacing";
             }
             enum "191.91875" {
               description "191.91875 THz/1562.08 nm 6.25GHz spacing";
             }
             enum "191.92500" {
               description "191.92500 THz/1562.03 nm 6.25/12.5GHz spacing";
             }
             enum "191.93125" {
               description "191.93125 THz/1561.98 nm 6.25GHz spacing";
             }
             enum "191.93750" {
               description "191.93750 THz/1561.93 nm 6.25/12.5GHz spacing";
             }
             enum "191.94375" {
               description "191.94375 THz/1561.88 nm 6.25GHz spacing";
             }
             enum "191.95000" {
               description "191.95000 THz/1561.83 nm 6.25/12.5/50GHz spacing";
             }
             enum "191.95625" {
               description "191.95625 THz/1561.77 nm 6.25GHz spacing";
             }
             enum "191.96250" {
               description "191.96250 THz/1561.72 nm 6.25/12.5GHz spacing";
             }
             enum "191.96875" {
               description "191.96875 THz/1561.67 nm 6.25GHz spacing";
             }
             enum "191.97500" {
               description "191.97500 THz/1561.62 nm 6.25/12.5/75GHz spacing";
             }
             enum "191.98125" {
               description "191.98125 THz/1561.57 nm 6.25GHz spacing";
             }
             enum "191.98750" {
               description "191.98750 THz/1561.52 nm 6.25/12.5GHz spacing";
             }
             enum "191.99375" {
               description "191.99375 THz/1561.47 nm 6.25GHz spacing";
             }
             enum "192.00000" {
               description "192.00000 THz/1561.42 nm 6.25/12.5/50/100GHz spacing";
             }
             enum "192.00625" {
               description "192.00625 THz/1561.37 nm 6.25GHz spacing";
             }
             enum "192.01250" {
               description "192.01250 THz/1561.32 nm 6.25/12.5GHz spacing";
             }
             enum "192.01875" {
               description "192.01875 THz/1561.27 nm 6.25GHz spacing";
             }
             enum "192.02500" {
               description "192.02500 THz/1561.22 nm 6.25/12.5GHz spacing";
             }
             enum "192.03125" {
               description "192.03125 THz/1561.16 nm 6.25GHz spacing";
             }
             enum "192.03750" {
               description "192.03750 THz/1561.11 nm 6.25/12.5GHz spacing";
             }
             enum "192.04375" {
               description "192.04375 THz/1561.06 nm 6.25GHz spacing";
             }
             enum "192.05000" {
               description "192.05000 THz/1561.01 nm 6.25/12.5/50/75GHz spacing";
             }
             enum "192.05625" {
               description "192.05625 THz/1560.96 nm 6.25GHz spacing";
             }
             enum "192.06250" {
               description "192.06250 THz/1560.91 nm 6.25/12.5GHz spacing";
             }
             enum "192.06875" {
               description "192.06875 THz/1560.86 nm 6.25GHz spacing";
             }
             enum "192.07500" {
               description "192.07500 THz/1560.81 nm 6.25/12.5GHz spacing";
             }
             enum "192.08125" {
               description "192.08125 THz/1560.76 nm 6.25GHz spacing";
             }
             enum "192.08750" {
               description "192.08750 THz/1560.71 nm 6.25/12.5GHz spacing";
             }
             enum "192.09375" {
               description "192.09375 THz/1560.66 nm 6.25GHz spacing";
             }
             enum "192.10000" {
               description "192.10000 THz/1560.61 nm 6.25/12.5/50/100GHz spacing";
             }
             enum "192.10625" {
               description "192.10625 THz/1560.56 nm 6.25GHz spacing";
             }
             enum "192.11250" {
               description "192.11250 THz/1560.50 nm 6.25/12.5GHz spacing";
             }
             enum "192.11875" {
               description "192.11875 THz/1560.45 nm 6.25GHz spacing";
             }
             enum "192.12500" {
               description "192.12500 THz/1560.40 nm 6.25/12.5/75GHz spacing";
             }
             enum "192.13125" {
               description "192.13125 THz/1560.35 nm 6.25GHz spacing";
             }
             enum "192.13750" {
               description "192.13750 THz/1560.30 nm 6.25/12.5GHz spacing";
             }
             enum "192.14375" {
               description "192.14375 THz/1560.25 nm 6.25GHz spacing";
             }
             enum "192.15000" {
               description "192.15000 THz/1560.20 nm 6.25/12.5/50GHz spacing";
             }
             enum "192.15625" {
               description "192.15625 THz/1560.15 nm 6.25GHz spacing";
             }
             enum "192.16250" {
               description "192.16250 THz/1560.10 nm 6.25/12.5GHz spacing";
             }
             enum "192.16875" {
               description "192.16875 THz/1560.05 nm 6.25GHz spacing";
             }
             enum "192.17500" {
               description "192.17500 THz/1560.00 nm 6.25/12.5GHz spacing";
             }
             enum "192.18125" {
               description "192.18125 THz/1559.95 nm 6.25GHz spacing";
             }
             enum "192.18750" {
               description "192.18750 THz/1559.90 nm 6.25/12.5GHz spacing";
             }
             enum "192.19375" {
               description "192.19375 THz/1559.84 nm 6.25GHz spacing";
             }
             enum "192.20000" {
               description "192.20000 THz/1559.79 nm 6.25/12.5/50/75/100GHz spacing";
             }
             enum "192.20625" {
               description "192.20625 THz/1559.74 nm 6.25GHz spacing";
             }
             enum "192.21250" {
               description "192.21250 THz/1559.69 nm 6.25/12.5GHz spacing";
             }
             enum "192.21875" {
               description "192.21875 THz/1559.64 nm 6.25GHz spacing";
             }
             enum "192.22500" {
               description "192.22500 THz/1559.59 nm 6.25/12.5GHz spacing";
             }
             enum "192.23125" {
               description "192.23125 THz/1559.54 nm 6.25GHz spacing";
             }
             enum "192.23750" {
               description "192.23750 THz/1559.49 nm 6.25/12.5GHz spacing";
             }
             enum "192.24375" {
               description "192.24375 THz/1559.44 nm 6.25GHz spacing";
             }
             enum "192.25000" {
               description "192.25000 THz/1559.39 nm 6.25/12.5/50GHz spacing";
             }
             enum "192.25625" {
               description "192.25625 THz/1559.34 nm 6.25GHz spacing";
             }
             enum "192.26250" {
               description "192.26250 THz/1559.29 nm 6.25/12.5GHz spacing";
             }
             enum "192.26875" {
               description "192.26875 THz/1559.24 nm 6.25GHz spacing";
             }
             enum "192.27500" {
               description "192.27500 THz/1559.19 nm 6.25/12.5GHz spacing";
             }
             enum "192.28125" {
               description "192.28125 THz/1559.14 nm 6.25GHz spacing";
             }
             enum "192.28750" {
               description "192.28750 THz/1559.08 nm 6.25/12.5GHz spacing";
             }
             enum "192.29375" {
               description "192.29375 THz/1559.03 nm 6.25GHz spacing";
             }
             enum "192.30000" {
               description "192.30000 THz/1558.98 nm 6.25/12.5/50/100GHz spacing";
             }
             enum "192.30625" {
               description "192.30625 THz/1558.93 nm 6.25GHz spacing";
             }
             enum "192.31250" {
               description "192.31250 THz/1558.88 nm 6.25/12.5GHz spacing";
             }
             enum "192.31875" {
               description "192.31875 THz/1558.83 nm 6.25GHz spacing";
             }
             enum "192.32500" {
               description "192.32500 THz/1558.78 nm 6.25/12.5GHz spacing";
             }
             enum "192.33125" {
               description "192.33125 THz/1558.73 nm 6.25GHz spacing";
             }
             enum "192.33750" {
               description "192.33750 THz/1558.68 nm 6.25/12.5GHz spacing";
             }
             enum "192.34375" {
               description "192.34375 THz/1558.63 nm 6.25GHz spacing";
             }
             enum "192.35000" {
               description "192.35000 THz/1558.58 nm 6.25/12.5/50/75GHz spacing";
             }
             enum "192.35625" {
               description "192.35625 THz/1558.53 nm 6.25GHz spacing";
             }
             enum "192.36250" {
               description "192.36250 THz/1558.48 nm 6.25/12.5GHz spacing";
             }
             enum "192.36875" {
               description "192.36875 THz/1558.43 nm 6.25GHz spacing";
             }
             enum "192.37500" {
               description "192.37500 THz/1558.38 nm 6.25/12.5GHz spacing";
             }
             enum "192.38125" {
               description "192.38125 THz/1558.32 nm 6.25GHz spacing";
             }
             enum "192.38750" {
               description "192.38750 THz/1558.27 nm 6.25/12.5GHz spacing";
             }
             enum "192.39375" {
               description "192.39375 THz/1558.22 nm 6.25GHz spacing";
             }
             enum "192.40000" {
               description "192.40000 THz/1558.17 nm 6.25/12.5/50/100GHz spacing";
             }
             enum "192.40625" {
               description "192.40625 THz/1558.12 nm 6.25GHz spacing";
             }
             enum "192.41250" {
               description "192.41250 THz/1558.07 nm 6.25/12.5GHz spacing";
             }
             enum "192.41875" {
               description "192.41875 THz/1558.02 nm 6.25GHz spacing";
             }
             enum "192.42500" {
               description "192.42500 THz/1557.97 nm 6.25/12.5/75GHz spacing";
             }
             enum "192.43125" {
               description "192.43125 THz/1557.92 nm 6.25GHz spacing";
             }
             enum "192.43750" {
               description "192.43750 THz/1557.87 nm 6.25/12.5GHz spacing";
             }
             enum "192.44375" {
               description "192.44375 THz/1557.82 nm 6.25GHz spacing";
             }
             enum "192.45000" {
               description "192.45000 THz/1557.77 nm 6.25/12.5/50GHz spacing";
             }
             enum "192.45625" {
               description "192.45625 THz/1557.72 nm 6.25GHz spacing";
             }
             enum "192.46250" {
               description "192.46250 THz/1557.67 nm 6.25/12.5GHz spacing";
             }
             enum "192.46875" {
               description "192.46875 THz/1557.62 nm 6.25GHz spacing";
             }
             enum "192.47500" {
               description "192.47500 THz/1557.57 nm 6.25/12.5GHz spacing";
             }
             enum "192.48125" {
               description "192.48125 THz/1557.52 nm 6.25GHz spacing";
             }
             enum "192.48750" {
               description "192.48750 THz/1557.46 nm 6.25/12.5GHz spacing";
             }
             enum "192.49375" {
               description "192.49375 THz/1557.41 nm 6.25GHz spacing";
             }
             enum "192.50000" {
               description "192.50000 THz/1557.36 nm 6.25/12.5/50/75/100GHz spacing";
             }
             enum "192.50625" {
               description "192.50625 THz/1557.31 nm 6.25GHz spacing";
             }
             enum "192.51250" {
               description "192.51250 THz/1557.26 nm 6.25/12.5GHz spacing";
             }
             enum "192.51875" {
               description "192.51875 THz/1557.21 nm 6.25GHz spacing";
             }
             enum "192.52500" {
               description "192.52500 THz/1557.16 nm 6.25/12.5GHz spacing";
             }
             enum "192.53125" {
               description "192.53125 THz/1557.11 nm 6.25GHz spacing";
             }
             enum "192.53750" {
               description "192.53750 THz/1557.06 nm 6.25/12.5GHz spacing";
             }
             enum "192.54375" {
               description "192.54375 THz/1557.01 nm 6.25GHz spacing";
             }
             enum "192.55000" {
               description "192.55000 THz/1556.96 nm 6.25/12.5/50GHz spacing";
             }
             enum "192.55625" {
               description "192.55625 THz/1556.91 nm 6.25GHz spacing";
             }
             enum "192.56250" {
               description "192.56250 THz/1556.86 nm 6.25/12.5GHz spacing";
             }
             enum "192.56875" {
               description "192.56875 THz/1556.81 nm 6.25GHz spacing";
             }
             enum "192.57500" {
               description "192.57500 THz/1556.76 nm 6.25/12.5/75GHz spacing";
             }
             enum "192.58125" {
               description "192.58125 THz/1556.71 nm 6.25GHz spacing";
             }
             enum "192.58750" {
               description "192.58750 THz/1556.66 nm 6.25/12.5GHz spacing";
             }
             enum "192.59375" {
               description "192.59375 THz/1556.61 nm 6.25GHz spacing";
             }
             enum "192.60000" {
               description "192.60000 THz/1556.55 nm 6.25/12.5/50/100GHz spacing";
             }
             enum "192.60625" {
               description "192.60625 THz/1556.50 nm 6.25GHz spacing";
             }
             enum "192.61250" {
               description "192.61250 THz/1556.45 nm 6.25/12.5GHz spacing";
             }
             enum "192.61875" {
               description "192.61875 THz/1556.40 nm 6.25GHz spacing";
             }
             enum "192.62500" {
               description "192.62500 THz/1556.35 nm 6.25/12.5GHz spacing";
             }
             enum "192.63125" {
               description "192.63125 THz/1556.30 nm 6.25GHz spacing";
             }
             enum "192.63750" {
               description "192.63750 THz/1556.25 nm 6.25/12.5GHz spacing";
             }
             enum "192.64375" {
               description "192.64375 THz/1556.20 nm 6.25GHz spacing";
             }
             enum "192.65000" {
               description "192.65000 THz/1556.15 nm 6.25/12.5/50/75GHz spacing";
             }
             enum "192.65625" {
               description "192.65625 THz/1556.10 nm 6.25GHz spacing";
             }
             enum "192.66250" {
               description "192.66250 THz/1556.05 nm 6.25/12.5GHz spacing";
             }
             enum "192.66875" {
               description "192.66875 THz/1556.00 nm 6.25GHz spacing";
             }
             enum "192.67500" {
               description "192.67500 THz/1555.95 nm 6.25/12.5GHz spacing";
             }
             enum "192.68125" {
               description "192.68125 THz/1555.90 nm 6.25GHz spacing";
             }
             enum "192.68750" {
               description "192.68750 THz/1555.85 nm 6.25/12.5GHz spacing";
             }
             enum "192.69375" {
               description "192.69375 THz/1555.80 nm 6.25GHz spacing";
             }
             enum "192.70000" {
               description "192.70000 THz/1555.75 nm 6.25/12.5/50/100GHz spacing";
             }
             enum "192.70625" {
               description "192.70625 THz/1555.70 nm 6.25GHz spacing";
             }
             enum "192.71250" {
               description "192.71250 THz/1555.65 nm 6.25/12.5GHz spacing";
             }
             enum "192.71875" {
               description "192.71875 THz/1555.60 nm 6.25GHz spacing";
             }
             enum "192.72500" {
               description "192.72500 THz/1555.55 nm 6.25/12.5/75GHz spacing";
             }
             enum "192.73125" {
               description "192.73125 THz/1555.49 nm 6.25GHz spacing";
             }
             enum "192.73750" {
               description "192.73750 THz/1555.44 nm 6.25/12.5GHz spacing";
             }
             enum "192.74375" {
               description "192.74375 THz/1555.39 nm 6.25GHz spacing";
             }
             enum "192.75000" {
               description "192.75000 THz/1555.34 nm 6.25/12.5/50GHz spacing";
             }
             enum "192.75625" {
               description "192.75625 THz/1555.29 nm 6.25GHz spacing";
             }
             enum "192.76250" {
               description "192.76250 THz/1555.24 nm 6.25/12.5GHz spacing";
             }
             enum "192.76875" {
               description "192.76875 THz/1555.19 nm 6.25GHz spacing";
             }
             enum "192.77500" {
               description "192.77500 THz/1555.14 nm 6.25/12.5GHz spacing";
             }
             enum "192.78125" {
               description "192.78125 THz/1555.09 nm 6.25GHz spacing";
             }
             enum "192.78750" {
               description "192.78750 THz/1555.04 nm 6.25/12.5GHz spacing";
             }
             enum "192.79375" {
               description "192.79375 THz/1554.99 nm 6.25GHz spacing";
             }
             enum "192.80000" {
               description "192.80000 THz/1554.94 nm 6.25/12.5/50/75/100GHz spacing";
             }
             enum "192.80625" {
               description "192.80625 THz/1554.89 nm 6.25GHz spacing";
             }
             enum "192.81250" {
               description "192.81250 THz/1554.84 nm 6.25/12.5GHz spacing";
             }
             enum "192.81875" {
               description "192.81875 THz/1554.79 nm 6.25GHz spacing";
             }
             enum "192.82500" {
               description "192.82500 THz/1554.74 nm 6.25/12.5GHz spacing";
             }
             enum "192.83125" {
               description "192.83125 THz/1554.69 nm 6.25GHz spacing";
             }
             enum "192.83750" {
               description "192.83750 THz/1554.64 nm 6.25/12.5GHz spacing";
             }
             enum "192.84375" {
               description "192.84375 THz/1554.59 nm 6.25GHz spacing";
             }
             enum "192.85000" {
               description "192.85000 THz/1554.54 nm 6.25/12.5/50GHz spacing";
             }
             enum "192.85625" {
               description "192.85625 THz/1554.49 nm 6.25GHz spacing";
             }
             enum "192.86250" {
               description "192.86250 THz/1554.44 nm 6.25/12.5GHz spacing";
             }
             enum "192.86875" {
               description "192.86875 THz/1554.39 nm 6.25GHz spacing";
             }
             enum "192.87500" {
               description "192.87500 THz/1554.34 nm 6.25/12.5/75GHz spacing";
             }
             enum "192.88125" {
               description "192.88125 THz/1554.29 nm 6.25GHz spacing";
             }
             enum "192.88750" {
               description "192.88750 THz/1554.23 nm 6.25/12.5GHz spacing";
             }
             enum "192.89375" {
               description "192.89375 THz/1554.18 nm 6.25GHz spacing";
             }
             enum "192.90000" {
               description "192.90000 THz/1554.13 nm 6.25/12.5/50/100GHz spacing";
             }
             enum "192.90625" {
               description "192.90625 THz/1554.08 nm 6.25GHz spacing";
             }
             enum "192.91250" {
               description "192.91250 THz/1554.03 nm 6.25/12.5GHz spacing";
             }
             enum "192.91875" {
               description "192.91875 THz/1553.98 nm 6.25GHz spacing";
             }
             enum "192.92500" {
               description "192.92500 THz/1553.93 nm 6.25/12.5GHz spacing";
             }
             enum "192.93125" {
               description "192.93125 THz/1553.88 nm 6.25GHz spacing";
             }
             enum "192.93750" {
               description "192.93750 THz/1553.83 nm 6.25/12.5GHz spacing";
             }
             enum "192.94375" {
               description "192.94375 THz/1553.78 nm 6.25GHz spacing";
             }
             enum "192.95000" {
               description "192.95000 THz/1553.73 nm 6.25/12.5/50/75GHz spacing";
             }
             enum "192.95625" {
               description "192.95625 THz/1553.68 nm 6.25GHz spacing";
             }
             enum "192.96250" {
               description "192.96250 THz/1553.63 nm 6.25/12.5GHz spacing";
             }
             enum "192.96875" {
               description "192.96875 THz/1553.58 nm 6.25GHz spacing";
             }
             enum "192.97500" {
               description "192.97500 THz/1553.53 nm 6.25/12.5GHz spacing";
             }
             enum "192.98125" {
               description "192.98125 THz/1553.48 nm 6.25GHz spacing";
             }
             enum "192.98750" {
               description "192.98750 THz/1553.43 nm 6.25/12.5GHz spacing";
             }
             enum "192.99375" {
               description "192.99375 THz/1553.38 nm 6.25GHz spacing";
             }
             enum "193.00000" {
               description "193.00000 THz/1553.33 nm 6.25/12.5/50/100GHz spacing";
             }
             enum "193.00625" {
               description "193.00625 THz/1553.28 nm 6.25GHz spacing";
             }
             enum "193.01250" {
               description "193.01250 THz/1553.23 nm 6.25/12.5GHz spacing";
             }
             enum "193.01875" {
               description "193.01875 THz/1553.18 nm 6.25GHz spacing";
             }
             enum "193.02500" {
               description "193.02500 THz/1553.13 nm 6.25/12.5/75GHz spacing";
             }
             enum "193.03125" {
               description "193.03125 THz/1553.08 nm 6.25GHz spacing";
             }
             enum "193.03750" {
               description "193.03750 THz/1553.03 nm 6.25/12.5GHz spacing";
             }
             enum "193.04375" {
               description "193.04375 THz/1552.98 nm 6.25GHz spacing";
             }
             enum "193.05000" {
               description "193.05000 THz/1552.93 nm 6.25/12.5/50GHz spacing";
             }
             enum "193.05625" {
               description "193.05625 THz/1552.88 nm 6.25GHz spacing";
             }
             enum "193.06250" {
               description "193.06250 THz/1552.83 nm 6.25/12.5GHz spacing";
             }
             enum "193.06875" {
               description "193.06875 THz/1552.78 nm 6.25GHz spacing";
             }
             enum "193.07500" {
               description "193.07500 THz/1552.73 nm 6.25/12.5GHz spacing";
             }
             enum "193.08125" {
               description "193.08125 THz/1552.68 nm 6.25GHz spacing";
             }
             enum "193.08750" {
               description "193.08750 THz/1552.62 nm 6.25/12.5GHz spacing";
             }
             enum "193.09375" {
               description "193.09375 THz/1552.57 nm 6.25GHz spacing";
             }
             enum "193.10000" {
               description "193.10000 THz/1552.52 nm 6.25/12.5/50/75/100GHz spacing";
             }
             enum "193.10625" {
               description "193.10625 THz/1552.47 nm 6.25GHz spacing";
             }
             enum "193.11250" {
               description "193.11250 THz/1552.42 nm 6.25/12.5GHz spacing";
             }
             enum "193.11875" {
               description "193.11875 THz/1552.37 nm 6.25GHz spacing";
             }
             enum "193.12500" {
               description "193.12500 THz/1552.32 nm 6.25/12.5GHz spacing";
             }
             enum "193.13125" {
               description "193.13125 THz/1552.27 nm 6.25GHz spacing";
             }
             enum "193.13750" {
               description "193.13750 THz/1552.22 nm 6.25/12.5GHz spacing";
             }
             enum "193.14375" {
               description "193.14375 THz/1552.17 nm 6.25GHz spacing";
             }
             enum "193.15000" {
               description "193.15000 THz/1552.12 nm 6.25/12.5/50GHz spacing";
             }
             enum "193.15625" {
               description "193.15625 THz/1552.07 nm 6.25GHz spacing";
             }
             enum "193.16250" {
               description "193.16250 THz/1552.02 nm 6.25/12.5GHz spacing";
             }
             enum "193.16875" {
               description "193.16875 THz/1551.97 nm 6.25GHz spacing";
             }
             enum "193.17500" {
               description "193.17500 THz/1551.92 nm 6.25/12.5/75GHz spacing";
             }
             enum "193.18125" {
               description "193.18125 THz/1551.87 nm 6.25GHz spacing";
             }
             enum "193.18750" {
               description "193.18750 THz/1551.82 nm 6.25/12.5GHz spacing";
             }
             enum "193.19375" {
               description "193.19375 THz/1551.77 nm 6.25GHz spacing";
             }
             enum "193.20000" {
               description "193.20000 THz/1551.72 nm 6.25/12.5/50/100GHz spacing";
             }
             enum "193.20625" {
               description "193.20625 THz/1551.67 nm 6.25GHz spacing";
             }
             enum "193.21250" {
               description "193.21250 THz/1551.62 nm 6.25/12.5GHz spacing";
             }
             enum "193.21875" {
               description "193.21875 THz/1551.57 nm 6.25GHz spacing";
             }
             enum "193.22500" {
               description "193.22500 THz/1551.52 nm 6.25/12.5GHz spacing";
             }
             enum "193.23125" {
               description "193.23125 THz/1551.47 nm 6.25GHz spacing";
             }
             enum "193.23750" {
               description "193.23750 THz/1551.42 nm 6.25/12.5GHz spacing";
             }
             enum "193.24375" {
               description "193.24375 THz/1551.37 nm 6.25GHz spacing";
             }
             enum "193.25000" {
               description "193.25000 THz/1551.32 nm 6.25/12.5/50/75GHz spacing";
             }
             enum "193.25625" {
               description "193.25625 THz/1551.27 nm 6.25GHz spacing";
             }
             enum "193.26250" {
               description "193.26250 THz/1551.22 nm 6.25/12.5GHz spacing";
             }
             enum "193.26875" {
               description "193.26875 THz/1551.17 nm 6.25GHz spacing";
             }
             enum "193.27500" {
               description "193.27500 THz/1551.12 nm 6.25/12.5GHz spacing";
             }
             enum "193.28125" {
               description "193.28125 THz/1551.07 nm 6.25GHz spacing";
             }
             enum "193.28750" {
               description "193.28750 THz/1551.02 nm 6.25/12.5GHz spacing";
             }
             enum "193.29375" {
               description "193.29375 THz/1550.97 nm 6.25GHz spacing";
             }
             enum "193.30000" {
               description "193.30000 THz/1550.92 nm 6.25/12.5/50/100GHz spacing";
             }
             enum "193.30625" {
               description "193.30625 THz/1550.87 nm 6.25GHz spacing";
             }
             enum "193.31250" {
               description "193.31250 THz/1550.82 nm 6.25/12.5GHz spacing";
             }
             enum "193.31875" {
               description "193.31875 THz/1550.77 nm 6.25GHz spacing";
             }
             enum "193.32500" {
               description "193.32500 THz/1550.72 nm 6.25/12.5/75GHz spacing";
             }
             enum "193.33125" {
               description "193.33125 THz/1550.67 nm 6.25GHz spacing";
             }
             enum "193.33750" {
               description "193.33750 THz/1550.62 nm 6.25/12.5GHz spacing";
             }
             enum "193.34375" {
               description "193.34375 THz/1550.57 nm 6.25GHz spacing";
             }
             enum "193.35000" {
               description "193.35000 THz/1550.52 nm 6.25/12.5/50GHz spacing";
             }
             enum "193.35625" {
               description "193.35625 THz/1550.47 nm 6.25GHz spacing";
             }
             enum "193.36250" {
               description "193.36250 THz/1550.42 nm 6.25/12.5GHz spacing";
             }
             enum "193.36875" {
               description "193.36875 THz/1550.37 nm 6.25GHz spacing";
             }
             enum "193.37500" {
               description "193.37500 THz/1550.32 nm 6.25/12.5GHz spacing";
             }
             enum "193.38125" {
               description "193.38125 THz/1550.27 nm 6.25GHz spacing";
             }
             enum "193.38750" {
               description "193.38750 THz/1550.22 nm 6.25/12.5GHz spacing";
             }
             enum "193.39375" {
               description "193.39375 THz/1550.17 nm 6.25GHz spacing";
             }
             enum "193.40000" {
               description "193.40000 THz/1550.12 nm 6.25/12.5/50/75/100GHz spacing";
             }
             enum "193.40625" {
               description "193.40625 THz/1550.07 nm 6.25GHz spacing";
             }
             enum "193.41250" {
               description "193.41250 THz/1550.02 nm 6.25/12.5GHz spacing";
             }
             enum "193.41875" {
               description "193.41875 THz/1549.97 nm 6.25GHz spacing";
             }
             enum "193.42500" {
               description "193.42500 THz/1549.92 nm 6.25/12.5GHz spacing";
             }
             enum "193.43125" {
               description "193.43125 THz/1549.87 nm 6.25GHz spacing";
             }
             enum "193.43750" {
               description "193.43750 THz/1549.82 nm 6.25/12.5GHz spacing";
             }
             enum "193.44375" {
               description "193.44375 THz/1549.77 nm 6.25GHz spacing";
             }
             enum "193.45000" {
               description "193.45000 THz/1549.72 nm 6.25/12.5/50GHz spacing";
             }
             enum "193.45625" {
               description "193.45625 THz/1549.67 nm 6.25GHz spacing";
             }
             enum "193.46250" {
               description "193.46250 THz/1549.62 nm 6.25/12.5GHz spacing";
             }
             enum "193.46875" {
               description "193.46875 THz/1549.57 nm 6.25GHz spacing";
             }
             enum "193.47500" {
               description "193.47500 THz/1549.52 nm 6.25/12.5/75GHz spacing";
             }
             enum "193.48125" {
               description "193.48125 THz/1549.47 nm 6.25GHz spacing";
             }
             enum "193.48750" {
               description "193.48750 THz/1549.42 nm 6.25/12.5GHz spacing";
             }
             enum "193.49375" {
               description "193.49375 THz/1549.37 nm 6.25GHz spacing";
             }
             enum "193.50000" {
               description "193.50000 THz/1549.32 nm 6.25/12.5/50/100GHz spacing";
             }
             enum "193.50625" {
               description "193.50625 THz/1549.26 nm 6.25GHz spacing";
             }
             enum "193.51250" {
               description "193.51250 THz/1549.21 nm 6.25/12.5GHz spacing";
             }
             enum "193.51875" {
               description "193.51875 THz/1549.16 nm 6.25GHz spacing";
             }
             enum "193.52500" {
               description "193.52500 THz/1549.11 nm 6.25/12.5GHz spacing";
             }
             enum "193.53125" {
               description "193.53125 THz/1549.06 nm 6.25GHz spacing";
             }
             enum "193.53750" {
               description "193.53750 THz/1549.01 nm 6.25/12.5GHz spacing";
             }
             enum "193.54375" {
               description "193.54375 THz/1548.96 nm 6.25GHz spacing";
             }
             enum "193.55000" {
               description "193.55000 THz/1548.91 nm 6.25/12.5/50/75GHz spacing";
             }
             enum "193.55625" {
               description "193.55625 THz/1548.86 nm 6.25GHz spacing";
             }
             enum "193.56250" {
               description "193.56250 THz/1548.81 nm 6.25/12.5GHz spacing";
             }
             enum "193.56875" {
               description "193.56875 THz/1548.76 nm 6.25GHz spacing";
             }
             enum "193.57500" {
               description "193.57500 THz/1548.71 nm 6.25/12.5GHz spacing";
             }
             enum "193.58125" {
               description "193.58125 THz/1548.66 nm 6.25GHz spacing";
             }
             enum "193.58750" {
               description "193.58750 THz/1548.61 nm 6.25/12.5GHz spacing";
             }
             enum "193.59375" {
               description "193.59375 THz/1548.56 nm 6.25GHz spacing";
             }
             enum "193.60000" {
               description "193.60000 THz/1548.51 nm 6.25/12.5/50/100GHz spacing";
             }
             enum "193.60625" {
               description "193.60625 THz/1548.46 nm 6.25GHz spacing";
             }
             enum "193.61250" {
               description "193.61250 THz/1548.41 nm 6.25/12.5GHz spacing";
             }
             enum "193.61875" {
               description "193.61875 THz/1548.36 nm 6.25GHz spacing";
             }
             enum "193.62500" {
               description "193.62500 THz/1548.31 nm 6.25/12.5/75GHz spacing";
             }
             enum "193.63125" {
               description "193.63125 THz/1548.26 nm 6.25GHz spacing";
             }
             enum "193.63750" {
               description "193.63750 THz/1548.21 nm 6.25/12.5GHz spacing";
             }
             enum "193.64375" {
               description "193.64375 THz/1548.16 nm 6.25GHz spacing";
             }
             enum "193.65000" {
               description "193.65000 THz/1548.11 nm 6.25/12.5/50GHz spacing";
             }
             enum "193.65625" {
               description "193.65625 THz/1548.06 nm 6.25GHz spacing";
             }
             enum "193.66250" {
               description "193.66250 THz/1548.02 nm 6.25/12.5GHz spacing";
             }
             enum "193.66875" {
               description "193.66875 THz/1547.97 nm 6.25GHz spacing";
             }
             enum "193.67500" {
               description "193.67500 THz/1547.92 nm 6.25/12.5GHz spacing";
             }
             enum "193.68125" {
               description "193.68125 THz/1547.87 nm 6.25GHz spacing";
             }
             enum "193.68750" {
               description "193.68750 THz/1547.82 nm 6.25/12.5GHz spacing";
             }
             enum "193.69375" {
               description "193.69375 THz/1547.77 nm 6.25GHz spacing";
             }
             enum "193.70000" {
               description "193.70000 THz/1547.72 nm 6.25/12.5/50/100/75GHz spacing";
             }
             enum "193.70625" {
               description "193.70625 THz/1547.67 nm 6.25GHz spacing";
             }
             enum "193.71250" {
               description "193.71250 THz/1547.62 nm 6.25/12.5GHz spacing";
             }
             enum "193.71875" {
               description "193.71875 THz/1547.57 nm 6.25GHz spacing";
             }
             enum "193.72500" {
               description "193.72500 THz/1547.52 nm 6.25/12.5GHz spacing";
             }
             enum "193.73125" {
               description "193.73125 THz/1547.47 nm 6.25GHz spacing";
             }
             enum "193.73750" {
               description "193.73750 THz/1547.42 nm 6.25/12.5GHz spacing";
             }
             enum "193.74375" {
               description "193.74375 THz/1547.37 nm 6.25GHz spacing";
             }
             enum "193.75000" {
               description "193.75000 THz/1547.32 nm 6.25/12.5/50GHz spacing";
             }
             enum "193.75625" {
               description "193.75625 THz/1547.27 nm 6.25GHz spacing";
             }
             enum "193.76250" {
               description "193.76250 THz/1547.22 nm 6.25/12.5GHz spacing";
             }
             enum "193.76875" {
               description "193.76875 THz/1547.17 nm 6.25GHz spacing";
             }
             enum "193.77500" {
               description "193.77500 THz/1547.12 nm 6.25/12.5/75GHz spacing";
             }
             enum "193.78125" {
               description "193.78125 THz/1547.07 nm 6.25GHz spacing";
             }
             enum "193.78750" {
               description "193.78750 THz/1547.02 nm 6.25/12.5GHz spacing";
             }
             enum "193.79375" {
               description "193.79375 THz/1546.97 nm 6.25GHz spacing";
             }
             enum "193.80000" {
               description "193.80000 THz/1546.92 nm 6.25/12.5/50/100GHz spacing";
             }
             enum "193.80625" {
               description "193.80625 THz/1546.87 nm 6.25GHz spacing";
             }
             enum "193.81250" {
               description "193.81250 THz/1546.82 nm 6.25/12.5GHz spacing";
             }
             enum "193.81875" {
               description "193.81875 THz/1546.77 nm 6.25GHz spacing";
             }
             enum "193.82500" {
               description "193.82500 THz/1546.72 nm 6.25/12.5GHz spacing";
             }
             enum "193.83125" {
               description "193.83125 THz/1546.67 nm 6.25GHz spacing";
             }
             enum "193.83750" {
               description "193.83750 THz/1546.62 nm 6.25/12.5GHz spacing";
             }
             enum "193.84375" {
               description "193.84375 THz/1546.57 nm 6.25GHz spacing";
             }
             enum "193.85000" {
               description "193.85000 THz/1546.52 nm 6.25/12.5/50/75GHz spacing";
             }
             enum "193.85625" {
               description "193.85625 THz/1546.47 nm 6.25GHz spacing";
             }
             enum "193.86250" {
               description "193.86250 THz/1546.42 nm 6.25/12.5GHz spacing";
             }
             enum "193.86875" {
               description "193.86875 THz/1546.37 nm 6.25GHz spacing";
             }
             enum "193.87500" {
               description "193.87500 THz/1546.32 nm 6.25/12.5GHz spacing";
             }
             enum "193.88125" {
               description "193.88125 THz/1546.27 nm 6.25GHz spacing";
             }
             enum "193.88750" {
               description "193.88750 THz/1546.22 nm 6.25/12.5GHz spacing";
             }
             enum "193.89375" {
               description "193.89375 THz/1546.17 nm 6.25GHz spacing";
             }
             enum "193.90000" {
               description "193.90000 THz/1546.12 nm 6.25/12.5/50/100GHz spacing";
             }
             enum "193.90625" {
               description "193.90625 THz/1546.07 nm 6.25GHz spacing";
             }
             enum "193.91250" {
               description "193.91250 THz/1546.02 nm 6.25/12.5GHz spacing";
             }
             enum "193.91875" {
               description "193.91875 THz/1545.97 nm 6.25GHz spacing";
             }
             enum "193.92500" {
               description "193.92500 THz/1545.92 nm 6.25/12.5/75GHz spacing";
             }
             enum "193.93125" {
               description "193.93125 THz/1545.87 nm 6.25GHz spacing";
             }
             enum "193.93750" {
               description "193.93750 THz/1545.82 nm 6.25/12.5GHz spacing";
             }
             enum "193.94375" {
               description "193.94375 THz/1545.77 nm 6.25GHz spacing";
             }
             enum "193.95000" {
               description "193.95000 THz/1545.72 nm 6.25/12.5/50GHz spacing";
             }
             enum "193.95625" {
               description "193.95625 THz/1545.67 nm 6.25GHz spacing";
             }
             enum "193.96250" {
               description "193.96250 THz/1545.62 nm 6.25/12.5GHz spacing";
             }
             enum "193.96875" {
               description "193.96875 THz/1545.57 nm 6.25GHz spacing";
             }
             enum "193.97500" {
               description "193.97500 THz/1545.52 nm 6.25/12.5GHz spacing";
             }
             enum "193.98125" {
               description "193.98125 THz/1545.47 nm 6.25GHz spacing";
             }
             enum "193.98750" {
               description "193.98750 THz/1545.42 nm 6.25/12.5GHz spacing";
             }
             enum "193.99375" {
               description "193.99375 THz/1545.37 nm 6.25GHz spacing";
             }
             enum "194.00000" {
               description "194.00000 THz/1545.32 nm 6.25/12.5/50/75/100GHz spacing";
             }
             enum "194.00625" {
               description "194.00625 THz/1545.27 nm 6.25GHz spacing";
             }
             enum "194.01250" {
               description "194.01250 THz/1545.22 nm 6.25/12.5GHz spacing";
             }
             enum "194.01875" {
               description "194.01875 THz/1545.17 nm 6.25GHz spacing";
             }
             enum "194.02500" {
               description "194.02500 THz/1545.12 nm 6.25/12.5GHz spacing";
             }
             enum "194.03125" {
               description "194.03125 THz/1545.07 nm 6.25GHz spacing";
             }
             enum "194.03750" {
               description "194.03750 THz/1545.02 nm 6.25/12.5GHz spacing";
             }
             enum "194.04375" {
               description "194.04375 THz/1544.97 nm 6.25GHz spacing";
             }
             enum "194.05000" {
               description "194.05000 THz/1544.92 nm 6.25/12.5/50GHz spacing";
             }
             enum "194.05625" {
               description "194.05625 THz/1544.87 nm 6.25GHz spacing";
             }
             enum "194.06250" {
               description "194.06250 THz/1544.82 nm 6.25/12.5GHz spacing";
             }
             enum "194.06875" {
               description "194.06875 THz/1544.77 nm 6.25GHz spacing";
             }
             enum "194.07500" {
               description "194.07500 THz/1544.72 nm 6.25/12.5/75GHz spacing";
             }
             enum "194.08125" {
               description "194.08125 THz/1544.68 nm 6.25GHz spacing";
             }
             enum "194.08750" {
               description "194.08750 THz/1544.63 nm 6.25/12.5GHz spacing";
             }
             enum "194.09375" {
               description "194.09375 THz/1544.58 nm 6.25GHz spacing";
             }
             enum "194.10000" {
               description "194.10000 THz/1544.53 nm 6.25/12.5/50/100GHz spacing";
             }
             enum "194.10625" {
               description "194.10625 THz/1544.48 nm 6.25GHz spacing";
             }
             enum "194.11250" {
               description "194.11250 THz/1544.43 nm 6.25/12.5GHz spacing";
             }
             enum "194.11875" {
               description "194.11875 THz/1544.38 nm 6.25GHz spacing";
             }
             enum "194.12500" {
               description "194.12500 THz/1544.33 nm 6.25/12.5GHz spacing";
             }
             enum "194.13125" {
               description "194.13125 THz/1544.28 nm 6.25GHz spacing";
             }
             enum "194.13750" {
               description "194.13750 THz/1544.23 nm 6.25/12.5GHz spacing";
             }
             enum "194.14375" {
               description "194.14375 THz/1544.18 nm 6.25GHz spacing";
             }
             enum "194.15000" {
               description "194.15000 THz/1544.13 nm 6.25/12.5/50/75GHz spacing";
             }
             enum "194.15625" {
               description "194.15625 THz/1544.08 nm 6.25GHz spacing";
             }
             enum "194.16250" {
               description "194.16250 THz/1544.03 nm 6.25/12.5GHz spacing";
             }
             enum "194.16875" {
               description "194.16875 THz/1543.98 nm 6.25GHz spacing";
             }
             enum "194.17500" {
               description "194.17500 THz/1543.93 nm 6.25/12.5GHz spacing";
             }
             enum "194.18125" {
               description "194.18125 THz/1543.88 nm 6.25GHz spacing";
             }
             enum "194.18750" {
               description "194.18750 THz/1543.83 nm 6.25/12.5GHz spacing";
             }
             enum "194.19375" {
               description "194.19375 THz/1543.78 nm 6.25GHz spacing";
             }
             enum "194.20000" {
               description "194.20000 THz/1543.73 nm 6.25/12.5/50/100GHz spacing";
             }
             enum "194.20625" {
               description "194.20625 THz/1543.68 nm 6.25GHz spacing";
             }
             enum "194.21250" {
               description "194.21250 THz/1543.63 nm 6.25/12.5GHz spacing";
             }
             enum "194.21875" {
               description "194.21875 THz/1543.58 nm 6.25GHz spacing";
             }
             enum "194.22500" {
               description "194.22500 THz/1543.53 nm 6.25/12.5/75GHz spacing";
             }
             enum "194.23125" {
               description "194.23125 THz/1543.48 nm 6.25GHz spacing";
             }
             enum "194.23750" {
               description "194.23750 THz/1543.43 nm 6.25/12.5GHz spacing";
             }
             enum "194.24375" {
               description "194.24375 THz/1543.38 nm 6.25GHz spacing";
             }
             enum "194.25000" {
               description "194.25000 THz/1543.33 nm 6.25/12.5/50/75GHz spacing";
             }
             enum "194.25625" {
               description "194.25625 THz/1543.28 nm 6.25GHz spacing";
             }
             enum "194.26250" {
               description "194.26250 THz/1543.23 nm 6.25/12.5GHz spacing";
             }
             enum "194.26875" {
               description "194.26875 THz/1543.18 nm 6.25GHz spacing";
             }
             enum "194.27500" {
               description "194.27500 THz/1543.13 nm 6.25/12.5GHz spacing";
             }
             enum "194.28125" {
               description "194.28125 THz/1543.08 nm 6.25GHz spacing";
             }
             enum "194.28750" {
               description "194.28750 THz/1543.04 nm 6.25/12.5GHz spacing";
             }
             enum "194.29375" {
               description "194.29375 THz/1542.99 nm 6.25GHz spacing";
             }
             enum "194.30000" {
               description "194.30000 THz/1542.94 nm 6.25/12.5/50/75/100GHz spacing";
             }
             enum "194.30625" {
               description "194.30625 THz/1542.89 nm 6.25GHz spacing";
             }
             enum "194.31250" {
               description "194.31250 THz/1542.84 nm 6.25/12.5GHz spacing";
             }
             enum "194.31875" {
               description "194.31875 THz/1542.79 nm 6.25GHz spacing";
             }
             enum "194.32500" {
               description "194.32500 THz/1542.74 nm 6.25/12.5GHz spacing";
             }
             enum "194.33125" {
               description "194.33125 THz/1542.69 nm 6.25GHz spacing";
             }
             enum "194.33750" {
               description "194.33750 THz/1542.64 nm 6.25/12.5GHz spacing";
             }
             enum "194.34375" {
               description "194.34375 THz/1542.59 nm 6.25GHz spacing";
             }
             enum "194.35000" {
               description "194.35000 THz/1542.54 nm 6.25/12.5/50GHz spacing";
             }
             enum "194.35625" {
               description "194.35625 THz/1542.49 nm 6.25GHz spacing";
             }
             enum "194.36250" {
               description "194.36250 THz/1542.44 nm 6.25/12.5GHz spacing";
             }
             enum "194.36875" {
               description "194.36875 THz/1542.39 nm 6.25GHz spacing";
             }
             enum "194.37500" {
               description "194.37500 THz/1542.34 nm 6.25/12.5/75GHz spacing";
             }
             enum "194.38125" {
               description "194.38125 THz/1542.29 nm 6.25GHz spacing";
             }
             enum "194.38750" {
               description "194.38750 THz/1542.24 nm 6.25/12.5GHz spacing";
             }
             enum "194.39375" {
               description "194.39375 THz/1542.19 nm 6.25GHz spacing";
             }
             enum "194.40000" {
               description "194.40000 THz/1542.14 nm 6.25/12.5/50/100GHz spacing";
             }
             enum "194.40625" {
               description "194.40625 THz/1542.09 nm 6.25GHz spacing";
             }
             enum "194.41250" {
               description "194.41250 THz/1542.04 nm 6.25/12.5GHz spacing";
             }
             enum "194.41875" {
               description "194.41875 THz/1541.99 nm 6.25GHz spacing";
             }
             enum "194.42500" {
               description "194.42500 THz/1541.94 nm 6.25/12.5GHz spacing";
             }
             enum "194.43125" {
               description "194.43125 THz/1541.89 nm 6.25GHz spacing";
             }
             enum "194.43750" {
               description "194.43750 THz/1541.84 nm 6.25/12.5GHz spacing";
             }
             enum "194.44375" {
               description "194.44375 THz/1541.80 nm 6.25GHz spacing";
             }
             enum "194.45000" {
               description "194.45000 THz/1541.75 nm 6.25/12.5/50/75GHz spacing";
             }
             enum "194.45625" {
               description "194.45625 THz/1541.70 nm 6.25GHz spacing";
             }
             enum "194.46250" {
               description "194.46250 THz/1541.65 nm 6.25/12.5GHz spacing";
             }
             enum "194.46875" {
               description "194.46875 THz/1541.60 nm 6.25GHz spacing";
             }
             enum "194.47500" {
               description "194.47500 THz/1541.55 nm 6.25/12.5GHz spacing";
             }
             enum "194.48125" {
               description "194.48125 THz/1541.50 nm 6.25GHz spacing";
             }
             enum "194.48750" {
               description "194.48750 THz/1541.45 nm 6.25/12.5GHz spacing";
             }
             enum "194.49375" {
               description "194.49375 THz/1541.40 nm 6.25GHz spacing";
             }
             enum "194.50000" {
               description "194.50000 THz/1541.35 nm 6.25/12.5/50/100GHz spacing";
             }
             enum "194.50625" {
               description "194.50625 THz/1541.30 nm 6.25GHz spacing";
             }
             enum "194.51250" {
               description "194.51250 THz/1541.25 nm 6.25/12.5GHz spacing";
             }
             enum "194.51875" {
               description "194.51875 THz/1541.20 nm 6.25GHz spacing";
             }
             enum "194.52500" {
               description "194.52500 THz/1541.15 nm 6.25/12.5/75GHz spacing";
             }
             enum "194.53125" {
               description "194.53125 THz/1541.10 nm 6.25GHz spacing";
             }
             enum "194.53750" {
               description "194.53750 THz/1541.05 nm 6.25/12.5GHz spacing";
             }
             enum "194.54375" {
               description "194.54375 THz/1541.00 nm 6.25GHz spacing";
             }
             enum "194.55000" {
               description "194.55000 THz/1540.95 nm 6.25/12.5/50GHz spacing";
             }
             enum "194.55625" {
               description "194.55625 THz/1540.90 nm 6.25GHz spacing";
             }
             enum "194.56250" {
               description "194.56250 THz/1540.85 nm 6.25/12.5GHz spacing";
             }
             enum "194.56875" {
               description "194.56875 THz/1540.80 nm 6.25GHz spacing";
             }
             enum "194.57500" {
               description "194.57500 THz/1540.76 nm 6.25/12.5GHz spacing";
             }
             enum "194.58125" {
               description "194.58125 THz/1540.71 nm 6.25GHz spacing";
             }
             enum "194.58750" {
               description "194.58750 THz/1540.66 nm 6.25/12.5GHz spacing";
             }
             enum "194.59375" {
               description "194.59375 THz/1540.61 nm 6.25GHz spacing";
             }
             enum "194.60000" {
               description "194.60000 THz/1540.56 nm 6.25/12.5/50/75/100GHz spacing";
             }
             enum "194.60625" {
               description "194.60625 THz/1540.51 nm 6.25GHz spacing";
             }
             enum "194.61250" {
               description "194.61250 THz/1540.46 nm 6.25/12.5GHz spacing";
             }
             enum "194.61875" {
               description "194.61875 THz/1540.41 nm 6.25GHz spacing";
             }
             enum "194.62500" {
               description "194.62500 THz/1540.36 nm 6.25/12.5GHz spacing";
             }
             enum "194.63125" {
               description "194.63125 THz/1540.31 nm 6.25GHz spacing";
             }
             enum "194.63750" {
               description "194.63750 THz/1540.26 nm 6.25/12.5GHz spacing";
             }
             enum "194.64375" {
               description "194.64375 THz/1540.21 nm 6.25GHz spacing";
             }
             enum "194.65000" {
               description "194.65000 THz/1540.16 nm 6.25/12.5/50GHz spacing";
             }
             enum "194.65625" {
               description "194.65625 THz/1540.11 nm 6.25GHz spacing";
             }
             enum "194.66250" {
               description "194.66250 THz/1540.06 nm 6.25/12.5GHz spacing";
             }
             enum "194.66875" {
               description "194.66875 THz/1540.01 nm 6.25GHz spacing";
             }
             enum "194.67500" {
               description "194.67500 THz/1539.96 nm 6.25/12.5/75GHz spacing";
             }
             enum "194.68125" {
               description "194.68125 THz/1539.91 nm 6.25GHz spacing";
             }
             enum "194.68750" {
               description "194.68750 THz/1539.86 nm 6.25/12.5GHz spacing";
             }
             enum "194.69375" {
               description "194.69375 THz/1539.82 nm 6.25GHz spacing";
             }
             enum "194.70000" {
               description "194.70000 THz/1539.77 nm 6.25/12.5/50/100GHz spacing";
             }
             enum "194.70625" {
               description "194.70625 THz/1539.72 nm 6.25GHz spacing";
             }
             enum "194.71250" {
               description "194.71250 THz/1539.67 nm 6.25/12.5GHz spacing";
             }
             enum "194.71875" {
               description "194.71875 THz/1539.62 nm 6.25GHz spacing";
             }
             enum "194.72500" {
               description "194.72500 THz/1539.57 nm 6.25/12.5GHz spacing";
             }
             enum "194.73125" {
               description "194.73125 THz/1539.52 nm 6.25GHz spacing";
             }
             enum "194.73750" {
               description "194.73750 THz/1539.47 nm 6.25/12.5GHz spacing";
             }
             enum "194.74375" {
               description "194.74375 THz/1539.42 nm 6.25GHz spacing";
             }
             enum "194.75000" {
               description "194.75000 THz/1539.37 nm 6.25/12.5/50/75GHz spacing";
             }
             enum "194.75625" {
               description "194.75625 THz/1539.32 nm 6.25GHz spacing";
             }
             enum "194.76250" {
               description "194.76250 THz/1539.27 nm 6.25/12.5GHz spacing";
             }
             enum "194.76875" {
               description "194.76875 THz/1539.22 nm 6.25GHz spacing";
             }
             enum "194.77500" {
               description "194.77500 THz/1539.17 nm 6.25/12.5GHz spacing";
             }
             enum "194.78125" {
               description "194.78125 THz/1539.12 nm 6.25GHz spacing";
             }
             enum "194.78750" {
               description "194.78750 THz/1539.07 nm 6.25/12.5GHz spacing";
             }
             enum "194.79375" {
               description "194.79375 THz/1539.03 nm 6.25GHz spacing";
             }
             enum "194.80000" {
               description "194.80000 THz/1538.98 nm 6.25/12.5/50/100GHz spacing";
             }
             enum "194.80625" {
               description "194.80625 THz/1538.93 nm 6.25GHz spacing";
             }
             enum "194.81250" {
               description "194.81250 THz/1538.88 nm 6.25/12.5GHz spacing";
             }
             enum "194.81875" {
               description "194.81875 THz/1538.83 nm 6.25GHz spacing";
             }
             enum "194.82500" {
               description "194.82500 THz/1538.78 nm 6.25/12.5/75GHz spacing";
             }
             enum "194.83125" {
               description "194.83125 THz/1538.73 nm 6.25GHz spacing";
             }
             enum "194.83750" {
               description "194.83750 THz/1538.68 nm 6.25/12.5GHz spacing";
             }
             enum "194.84375" {
               description "194.84375 THz/1538.63 nm 6.25GHz spacing";
             }
             enum "194.85000" {
               description "194.85000 THz/1538.58 nm 6.25/12.5/50GHz spacing";
             }
             enum "194.85625" {
               description "194.85625 THz/1538.53 nm 6.25GHz spacing";
             }
             enum "194.86250" {
               description "194.86250 THz/1538.48 nm 6.25/12.5GHz spacing";
             }
             enum "194.86875" {
               description "194.86875 THz/1538.43 nm 6.25GHz spacing";
             }
             enum "194.87500" {
               description "194.87500 THz/1538.38 nm 6.25/12.5GHz spacing";
             }
             enum "194.88125" {
               description "194.88125 THz/1538.33 nm 6.25GHz spacing";
             }
             enum "194.88750" {
               description "194.88750 THz/1538.28 nm 6.25/12.5GHz spacing";
             }
             enum "194.89375" {
               description "194.89375 THz/1538.24 nm 6.25GHz spacing";
             }
             enum "194.90000" {
               description "194.90000 THz/1538.19 nm 6.25/12.5/50/75/100GHz spacing";
             }
             enum "194.90625" {
               description "194.90625 THz/1538.14 nm 6.25GHz spacing";
             }
             enum "194.91250" {
               description "194.91250 THz/1538.09 nm 6.25/12.5GHz spacing";
             }
             enum "194.91875" {
               description "194.91875 THz/1538.04 nm 6.25GHz spacing";
             }
             enum "194.92500" {
               description "194.92500 THz/1537.99 nm 6.25/12.5GHz spacing";
             }
             enum "194.93125" {
               description "194.93125 THz/1537.94 nm 6.25GHz spacing";
             }
             enum "194.93750" {
               description "194.93750 THz/1537.89 nm 6.25/12.5GHz spacing";
             }
             enum "194.94375" {
               description "194.94375 THz/1537.84 nm 6.25GHz spacing";
             }
             enum "194.95000" {
               description "194.95000 THz/1537.79 nm 6.25/12.5/50GHz spacing";
             }
             enum "194.95625" {
               description "194.95625 THz/1537.74 nm 6.25GHz spacing";
             }
             enum "194.96250" {
               description "194.96250 THz/1537.69 nm 6.25/12.5GHz spacing";
             }
             enum "194.96875" {
               description "194.96875 THz/1537.64 nm 6.25GHz spacing";
             }
             enum "194.97500" {
               description "194.97500 THz/1537.59 nm 6.25/12.5/75GHz spacing";
             }
             enum "194.98125" {
               description "194.98125 THz/1537.55 nm 6.25GHz spacing";
             }
             enum "194.98750" {
               description "194.98750 THz/1537.50 nm 6.25/12.5GHz spacing";
             }
             enum "194.99375" {
               description "194.99375 THz/1537.45 nm 6.25GHz spacing";
             }
             enum "195.00000" {
               description "195.00000 THz/1537.40 nm 6.25/12.5/50/100GHz spacing";
             }
             enum "195.00625" {
               description "195.00625 THz/1537.35 nm 6.25GHz spacing";
             }
             enum "195.01250" {
               description "195.01250 THz/1537.30 nm 6.25/12.5GHz spacing";
             }
             enum "195.01875" {
               description "195.01875 THz/1537.25 nm 6.25GHz spacing";
             }
             enum "195.02500" {
               description "195.02500 THz/1537.20 nm 6.25/12.5GHz spacing";
             }
             enum "195.03125" {
               description "195.03125 THz/1537.15 nm 6.25GHz spacing";
             }
             enum "195.03750" {
               description "195.03750 THz/1537.10 nm 6.25/12.5GHz spacing";
             }
             enum "195.04375" {
               description "195.04375 THz/1537.05 nm 6.25GHz spacing";
             }
             enum "195.05000" {
               description "195.05000 THz/1537.00 nm 6.25/12.5/50/75GHz spacing";
             }
             enum "195.05625" {
               description "195.05625 THz/1536.95 nm 6.25GHz spacing";
             }
             enum "195.06250" {
               description "195.06250 THz/1536.90 nm 6.25/12.5GHz spacing";
             }
             enum "195.06875" {
               description "195.06875 THz/1536.86 nm 6.25GHz spacing";
             }
             enum "195.07500" {
               description "195.07500 THz/1536.81 nm 6.25/12.5GHz spacing";
             }
             enum "195.08125" {
               description "195.08125 THz/1536.76 nm 6.25GHz spacing";
             }
             enum "195.08750" {
               description "195.08750 THz/1536.71 nm 6.25/12.5GHz spacing";
             }
             enum "195.09375" {
               description "195.09375 THz/1536.66 nm 6.25GHz spacing";
             }
             enum "195.10000" {
               description "195.10000 THz/1536.61 nm 6.25/12.5/50/100GHz spacing";
             }
             enum "195.10625" {
               description "195.10625 THz/1536.56 nm 6.25GHz spacing";
             }
             enum "195.11250" {
               description "195.11250 THz/1536.51 nm 6.25/12.5GHz spacing";
             }
             enum "195.11875" {
               description "195.11875 THz/1536.46 nm 6.25GHz spacing";
             }
             enum "195.12500" {
               description "195.12500 THz/1536.41 nm 6.25/12.5/75GHz spacing";
             }
             enum "195.13125" {
               description "195.13125 THz/1536.36 nm 6.25GHz spacing";
             }
             enum "195.13750" {
               description "195.13750 THz/1536.31 nm 6.25/12.5GHz spacing";
             }
             enum "195.14375" {
               description "195.14375 THz/1536.26 nm 6.25GHz spacing";
             }
             enum "195.15000" {
               description "195.15000 THz/1536.22 nm 6.25/12.5/50GHz spacing";
             }
             enum "195.15625" {
               description "195.15625 THz/1536.17 nm 6.25GHz spacing";
             }
             enum "195.16250" {
               description "195.16250 THz/1536.12 nm 6.25/12.5GHz spacing";
             }
             enum "195.16875" {
               description "195.16875 THz/1536.07 nm 6.25GHz spacing";
             }
             enum "195.17500" {
               description "195.17500 THz/1536.02 nm 6.25/12.5GHz spacing";
             }
             enum "195.18125" {
               description "195.18125 THz/1535.97 nm 6.25GHz spacing";
             }
             enum "195.18750" {
               description "195.18750 THz/1535.92 nm 6.25/12.5GHz spacing";
             }
             enum "195.19375" {
               description "195.19375 THz/1535.87 nm 6.25GHz spacing";
             }
             enum "195.20000" {
               description "195.20000 THz/1535.82 nm 6.25/12.5/50/75/100GHz spacing";
             }
             enum "195.20625" {
               description "195.20625 THz/1535.77 nm 6.25GHz spacing";
             }
             enum "195.21250" {
               description "195.21250 THz/1535.72 nm 6.25/12.5GHz spacing";
             }
             enum "195.21875" {
               description "195.21875 THz/1535.67 nm 6.25GHz spacing";
             }
             enum "195.22500" {
               description "195.22500 THz/1535.63 nm 6.25/12.5GHz spacing";
             }
             enum "195.23125" {
               description "195.23125 THz/1535.58 nm 6.25GHz spacing";
             }
             enum "195.23750" {
               description "195.23750 THz/1535.53 nm 6.25/12.5GHz spacing";
             }
             enum "195.24375" {
               description "195.24375 THz/1535.48 nm 6.25GHz spacing";
             }
             enum "195.25000" {
               description "195.25000 THz/1535.43 nm 6.25/12.5/50GHz spacing";
             }
             enum "195.25625" {
               description "195.25625 THz/1535.38 nm 6.25GHz spacing";
             }
             enum "195.26250" {
               description "195.26250 THz/1535.33 nm 6.25/12.5GHz spacing";
             }
             enum "195.26875" {
               description "195.26875 THz/1535.28 nm 6.25GHz spacing";
             }
             enum "195.27500" {
               description "195.27500 THz/1535.23 nm 6.25/12.5/75GHz spacing";
             }
             enum "195.28125" {
               description "195.28125 THz/1535.18 nm 6.25GHz spacing";
             }
             enum "195.28750" {
               description "195.28750 THz/1535.13 nm 6.25/12.5GHz spacing";
             }
             enum "195.29375" {
               description "195.29375 THz/1535.08 nm 6.25GHz spacing";
             }
             enum "195.30000" {
               description "195.30000 THz/1535.04 nm 6.25/12.5/50/100GHz spacing";
             }
             enum "195.30625" {
               description "195.30625 THz/1534.99 nm 6.25GHz spacing";
             }
             enum "195.31250" {
               description "195.31250 THz/1534.94 nm 6.25/12.5GHz spacing";
             }
             enum "195.31875" {
               description "195.31875 THz/1534.89 nm 6.25GHz spacing";
             }
             enum "195.32500" {
               description "195.32500 THz/1534.84 nm 6.25/12.5GHz spacing";
             }
             enum "195.33125" {
               description "195.33125 THz/1534.79 nm 6.25GHz spacing";
             }
             enum "195.33750" {
               description "195.33750 THz/1534.74 nm 6.25/12.5GHz spacing";
             }
             enum "195.34375" {
               description "195.34375 THz/1534.69 nm 6.25GHz spacing";
             }
             enum "195.35000" {
               description "195.35000 THz/1534.64 nm 6.25/12.5/50/75GHz spacing";
             }
             enum "195.35625" {
               description "195.35625 THz/1534.59 nm 6.25GHz spacing";
             }
             enum "195.36250" {
               description "195.36250 THz/1534.54 nm 6.25/12.5GHz spacing";
             }
             enum "195.36875" {
               description "195.36875 THz/1534.50 nm 6.25GHz spacing";
             }
             enum "195.37500" {
               description "195.37500 THz/1534.45 nm 6.25/12.5GHz spacing";
             }
             enum "195.38125" {
               description "195.38125 THz/1534.40 nm 6.25GHz spacing";
             }
             enum "195.38750" {
               description "195.38750 THz/1534.35 nm 6.25/12.5GHz spacing";
             }
             enum "195.39375" {
               description "195.39375 THz/1534.30 nm 6.25GHz spacing";
             }
             enum "195.40000" {
               description "195.40000 THz/1534.25 nm 6.25/12.5/50/100GHz spacing";
             }
             enum "195.40625" {
               description "195.40625 THz/1534.20 nm 6.25GHz spacing";
             }
             enum "195.41250" {
               description "195.41250 THz/1534.15 nm 6.25/12.5GHz spacing";
             }
             enum "195.41875" {
               description "195.41875 THz/1534.10 nm 6.25GHz spacing";
             }
             enum "195.42500" {
               description "195.42500 THz/1534.05 nm 6.25/12.5/75GHz spacing";
             }
             enum "195.43125" {
               description "195.43125 THz/1534.00 nm 6.25GHz spacing";
             }
             enum "195.43750" {
               description "195.43750 THz/1533.96 nm 6.25/12.5GHz spacing";
             }
             enum "195.44375" {
               description "195.44375 THz/1533.91 nm 6.25GHz spacing";
             }
             enum "195.45000" {
               description "195.45000 THz/1533.86 nm 6.25/12.5/50GHz spacing";
             }
             enum "195.45625" {
               description "195.45625 THz/1533.81 nm 6.25GHz spacing";
             }
             enum "195.46250" {
               description "195.46250 THz/1533.76 nm 6.25/12.5GHz spacing";
             }
             enum "195.46875" {
               description "195.46875 THz/1533.71 nm 6.25GHz spacing";
             }
             enum "195.47500" {
               description "195.47500 THz/1533.66 nm 6.25/12.5GHz spacing";
             }
             enum "195.48125" {
               description "195.48125 THz/1533.61 nm 6.25GHz spacing";
             }
             enum "195.48750" {
               description "195.48750 THz/1533.56 nm 6.25/12.5GHz spacing";
             }
             enum "195.49375" {
               description "195.49375 THz/1533.51 nm 6.25GHz spacing";
             }
             enum "195.50000" {
               description "195.50000 THz/1533.47 nm 6.25/12.5/50/75/100GHz spacing";
             }
             enum "195.50625" {
               description "195.50625 THz/1533.42 nm 6.25GHz spacing";
             }
             enum "195.51250" {
               description "195.51250 THz/1533.37 nm 6.25/12.5GHz spacing";
             }
             enum "195.51875" {
               description "195.51875 THz/1533.32 nm 6.25GHz spacing";
             }
             enum "195.52500" {
               description "195.52500 THz/1533.27 nm 6.25/12.5GHz spacing";
             }
             enum "195.53125" {
               description "195.53125 THz/1533.22 nm 6.25GHz spacing";
             }
             enum "195.53750" {
               description "195.53750 THz/1533.17 nm 6.25/12.5GHz spacing";
             }
             enum "195.54375" {
               description "195.54375 THz/1533.12 nm 6.25GHz spacing";
             }
             enum "195.55000" {
               description "195.55000 THz/1533.07 nm 6.25/12.5/50GHz spacing";
             }
             enum "195.55625" {
               description "195.55625 THz/1533.02 nm 6.25GHz spacing";
             }
             enum "195.56250" {
               description "195.56250 THz/1532.98 nm 6.25/12.5GHz spacing";
             }
             enum "195.56875" {
               description "195.56875 THz/1532.93 nm 6.25GHz spacing";
             }
             enum "195.57500" {
               description "195.57500 THz/1532.88 nm 6.25/12.5/75GHz spacing";
             }
             enum "195.58125" {
               description "195.58125 THz/1532.83 nm 6.25GHz spacing";
             }
             enum "195.58750" {
               description "195.58750 THz/1532.78 nm 6.25/12.5GHz spacing";
             }
             enum "195.59375" {
               description "195.59375 THz/1532.73 nm 6.25GHz spacing";
             }
             enum "195.60000" {
               description "195.60000 THz/1532.68 nm 6.25/12.5/50/100GHz spacing";
             }
             enum "195.60625" {
               description "195.60625 THz/1532.63 nm 6.25GHz spacing";
             }
             enum "195.61250" {
               description "195.61250 THz/1532.58 nm 6.25/12.5GHz spacing";
             }
             enum "195.61875" {
               description "195.61875 THz/1532.53 nm 6.25GHz spacing";
             }
             enum "195.62500" {
               description "195.62500 THz/1532.49 nm 6.25/12.5GHz spacing";
             }
             enum "195.63125" {
               description "195.63125 THz/1532.44 nm 6.25GHz spacing";
             }
             enum "195.63750" {
               description "195.63750 THz/1532.39 nm 6.25/12.5GHz spacing";
             }
             enum "195.64375" {
               description "195.64375 THz/1532.34 nm 6.25GHz spacing";
             }
             enum "195.65000" {
               description "195.65000 THz/1532.29 nm 6.25/12.5/50/75GHz spacing";
             }
             enum "195.65625" {
               description "195.65625 THz/1532.24 nm 6.25GHz spacing";
             }
             enum "195.66250" {
               description "195.66250 THz/1532.19 nm 6.25/12.5GHz spacing";
             }
             enum "195.66875" {
               description "195.66875 THz/1532.14 nm 6.25GHz spacing";
             }
             enum "195.67500" {
               description "195.67500 THz/1532.09 nm 6.25/12.5GHz spacing";
             }
             enum "195.68125" {
               description "195.68125 THz/1532.04 nm 6.25GHz spacing";
             }
             enum "195.68750" {
               description "195.68750 THz/1532.00 nm 6.25/12.5GHz spacing";
             }
             enum "195.69375" {
               description "195.69375 THz/1531.95 nm 6.25GHz spacing";
             }
             enum "195.70000" {
               description "195.70000 THz/1531.90 nm 6.25/12.5/50/100GHz spacing";
             }
             enum "195.70625" {
               description "195.70625 THz/1531.85 nm 6.25GHz spacing";
             }
             enum "195.71250" {
               description "195.71250 THz/1531.80 nm 6.25/12.5GHz spacing";
             }
             enum "195.71875" {
               description "195.71875 THz/1531.75 nm 6.25GHz spacing";
             }
             enum "195.72500" {
               description "195.72500 THz/1531.70 nm 6.25/12.5/75GHz spacing";
             }
             enum "195.73125" {
               description "195.73125 THz/1531.65 nm 6.25GHz spacing";
             }
             enum "195.73750" {
               description "195.73750 THz/1531.60 nm 6.25/12.5GHz spacing";
             }
             enum "195.74375" {
               description "195.74375 THz/1531.56 nm 6.25GHz spacing";
             }
             enum "195.75000" {
               description "195.75000 THz/1531.51 nm 6.25/12.5/50GHz spacing";
             }
             enum "195.75625" {
               description "195.75625 THz/1531.46 nm 6.25GHz spacing";
             }
             enum "195.76250" {
               description "195.76250 THz/1531.41 nm 6.25/12.5GHz spacing";
             }
             enum "195.76875" {
               description "195.76875 THz/1531.36 nm 6.25GHz spacing";
             }
             enum "195.77500" {
               description "195.77500 THz/1531.31 nm 6.25/12.5GHz spacing";
             }
             enum "195.78125" {
               description "195.78125 THz/1531.26 nm 6.25GHz spacing";
             }
             enum "195.78750" {
               description "195.78750 THz/1531.21 nm 6.25/12.5GHz spacing";
             }
             enum "195.79375" {
               description "195.79375 THz/1531.16 nm 6.25GHz spacing";
             }
             enum "195.80000" {
               description "195.80000 THz/1531.12 nm 6.25/12.5/50/75/100GHz spacing";
             }
             enum "195.80625" {
               description "195.80625 THz/1531.07 nm 6.25GHz spacing";
             }
             enum "195.81250" {
               description "195.81250 THz/1531.02 nm 6.25/12.5GHz spacing";
             }
             enum "195.81875" {
               description "195.81875 THz/1530.97 nm 6.25GHz spacing";
             }
             enum "195.82500" {
               description "195.82500 THz/1530.92 nm 6.25/12.5GHz spacing";
             }
             enum "195.83125" {
               description "195.83125 THz/1530.87 nm 6.25GHz spacing";
             }
             enum "195.83750" {
               description "195.83750 THz/1530.82 nm 6.25/12.5GHz spacing";
             }
             enum "195.84375" {
               description "195.84375 THz/1530.77 nm 6.25GHz spacing";
             }
             enum "195.85000" {
               description "195.85000 THz/1530.72 nm 6.25/12.5/50GHz spacing";
             }
             enum "195.85625" {
               description "195.85625 THz/1530.68 nm 6.25GHz spacing";
             }
             enum "195.86250" {
               description "195.86250 THz/1530.63 nm 6.25/12.5GHz spacing";
             }
             enum "195.86875" {
               description "195.86875 THz/1530.58 nm 6.25GHz spacing";
             }
             enum "195.87500" {
               description "195.87500 THz/1530.53 nm 6.25/12.5/75GHz spacing";
             }
             enum "195.88125" {
               description "195.88125 THz/1530.48 nm 6.25GHz spacing";
             }
             enum "195.88750" {
               description "195.88750 THz/1530.43 nm 6.25/12.5GHz spacing";
             }
             enum "195.89375" {
               description "195.89375 THz/1530.38 nm 6.25GHz spacing";
             }
             enum "195.90000" {
               description "195.90000 THz/1530.33 nm 6.25/12.5/50/100GHz spacing";
             }
             enum "195.90625" {
               description "195.90625 THz/1530.29 nm 6.25GHz spacing";
             }
             enum "195.91250" {
               description "195.91250 THz/1530.24 nm 6.25/12.5GHz spacing";
             }
             enum "195.91875" {
               description "195.91875 THz/1530.19 nm 6.25GHz spacing";
             }
             enum "195.92500" {
               description "195.92500 THz/1530.14 nm 6.25/12.5GHz spacing";
             }
             enum "195.93125" {
               description "195.93125 THz/1530.09 nm 6.25GHz spacing";
             }
             enum "195.93750" {
               description "195.93750 THz/1530.04 nm 6.25/12.5GHz spacing";
             }
             enum "195.94375" {
               description "195.94375 THz/1529.99 nm 6.25GHz spacing";
             }
             enum "195.95000" {
               description "195.95000 THz/1529.94 nm 6.25/12.5/50/75GHz spacing";
             }
             enum "195.95625" {
               description "195.95625 THz/1529.89 nm 6.25GHz spacing";
             }
             enum "195.96250" {
               description "195.96250 THz/1529.85 nm 6.25/12.5GHz spacing";
             }
             enum "195.96875" {
               description "195.96875 THz/1529.80 nm 6.25GHz spacing";
             }
             enum "195.97500" {
               description "195.97500 THz/1529.75 nm 6.25/12.5GHz spacing";
             }
             enum "195.98125" {
               description "195.98125 THz/1529.70 nm 6.25GHz spacing";
             }
             enum "195.98750" {
               description "195.98750 THz/1529.65 nm 6.25/12.5GHz spacing";
             }
             enum "195.99375" {
               description "195.99375 THz/1529.60 nm 6.25GHz spacing";
             }
             enum "196.00000" {
               description "196.00000 THz/1529.55 nm 6.25/12.5/50/100GHz spacing";
             }
             enum "196.00625" {
               description "196.00625 THz/1529.50 nm 6.25GHz spacing";
             }
             enum "196.01250" {
               description "196.01250 THz/1529.46 nm 6.25/12.5GHz spacing";
             }
             enum "196.01875" {
               description "196.01875 THz/1529.41 nm 6.25GHz spacing";
             }
             enum "196.02500" {
               description "196.02500 THz/1529.36 nm 6.25/12.5/75GHz spacing";
             }
             enum "196.03125" {
               description "196.03125 THz/1529.31 nm 6.25GHz spacing";
             }
             enum "196.03750" {
               description "196.03750 THz/1529.26 nm 6.25/12.5GHz spacing";
             }
             enum "196.04375" {
               description "196.04375 THz/1529.21 nm 6.25GHz spacing";
             }
             enum "196.05000" {
               description "196.05000 THz/1529.16 nm 6.25/12.5/50GHz spacing";
             }
             enum "196.05625" {
               description "196.05625 THz/1529.11 nm 6.25GHz spacing";
             }
             enum "196.06250" {
               description "196.06250 THz/1529.07 nm 6.25/12.5GHz spacing";
             }
             enum "196.06875" {
               description "196.06875 THz/1529.02 nm 6.25GHz spacing";
             }
             enum "196.07500" {
               description "196.07500 THz/1528.97 nm 6.25/12.5GHz spacing";
             }
             enum "196.08125" {
               description "196.08125 THz/1528.92 nm 6.25GHz spacing";
             }
             enum "196.08750" {
               description "196.08750 THz/1528.87 nm 6.25/12.5GHz spacing";
             }
             enum "196.09375" {
               description "196.09375 THz/1528.82 nm 6.25GHz spacing";
             }
             enum "196.10000" {
               description "196.10000 THz/1528.77 nm 6.25/12.5/50/75/100GHz spacing";
             }
             enum "196.15040" {
               description "196.15040 THz/1528.38 nm 50Ghz spacing";
             }
           }
         }
       }
     }
     leaf tx-power {
       description "Transmit laser output power";
       units "dBm";
       type string {
         junos:posix-pattern "^([+-]?[1-9]?[0-9](.[0-9][0-9]?)?)$";
         junos:pattern-message "Signed value with up to 2 decimal places";
       }
     }
     choice laser-enable-choice {
       leaf laser-enable {
         description "Enable transmit laser";
         type empty;
       }
       leaf no-laser-enable {
         description "Don't enable transmit laser";
         type empty;
       }
     }
   }
   grouping odu-attributes {
     description "Optical Data Unit configuration attributes";
     uses apply-advanced;
     leaf rate {
       description "Specific type of ODU, according to data rate";
       type enumeration {
         enum "odu4" {
           description "ODU4 for 100 Gbps";
         }
       }
     }
     choice is-ma-choice {
       leaf is-ma {
         description "Link is enabled for maintenance tasks, alarms are masked";
         type empty;
       }
       leaf no-is-ma {
         description "Don't link is enabled for maintenance tasks, alarms are masked";
         type empty;
       }
     }
     container tti {
       description "Configuration of OTU trail trace identifier";
       presence "enable tti";
       uses otn-tti-attributes;
     }
     container degrade {
       description "Configuration of OTU degrade defect detection";
       presence "enable degrade";
       uses otn-degrade;
     }
     leaf exp-payload-type {
       description "Expected OPU payload type";
       type union {
         type uint8;
         type string {
           pattern "<.*>|$.*";
         }
       }
     }
     container prbs {
       description "Configuration of framed pseudorandom binary sequence test signal";
       presence "enable prbs";
       uses prbs-config;
     }
   }
   grouping otn-degrade {
     description "Configuration of degrade defect detection";
     uses apply-advanced;
     leaf degm {
       description "Number of consecutive intervals error rate above threshold";
       type union {
         type string {
           pattern "<.*>|$.*";
         }
         type uint16 {
           range "2 .. 10";
         }
       }
     }
     leaf degthr {
       description "Threshold - percentage errored blocks, ex. 1.23 = 1.23%";
       type string {
         junos:posix-pattern "^((100(.00?)?)|(([1-9])?[0-9](.[0-9][0-9]?)?))$";
         junos:pattern-message "Percentage value up to 2 decimal places";
       }
     }
   }
   grouping otn-tti-attributes {
     description "Configuration of OTN trail trace identifier";
     uses apply-advanced;
     leaf sapi {
       description "Transmitted source access point identifier field";
       type string {
         length "0 .. 15";
       }
     }
     leaf dapi {
       description "Transmitted destination access point identifier field";
       type string {
         length "0 .. 15";
       }
     }
     leaf operator {
       description "Transmitted operator field";
       type string {
         length "0 .. 32";
       }
     }
     leaf exp-sapi {
       description "Expected received source access point identifier field";
       type string {
         length "0 .. 15";
       }
     }
     leaf exp-dapi {
       description "Expected received destination access point identifier field";
       type string {
         length "0 .. 15";
       }
     }
     leaf tim-detect-mode {
       description "Trace input mismatch defect detection mode";
       type enumeration {
         enum "disabled" {
           description "Detection of trace input mismatch defect disabled";
         }
         enum "sapi-only" {
           description "Detection of trace input mismatch defect on SAPI field only";
         }
         enum "dapi-only" {
           description "Detection of trace input mismatch defect on DAPI field only";
         }
         enum "sapi-and-dapi" {
           description "Detection of trace input mismatch defect on both SAPI and DAPI fields";
         }
       }
     }
     choice tim-act-enable-choice {
       leaf tim-act-enable {
         description "Enable trace input mismatch consequential actions";
         type empty;
       }
       leaf no-tim-act-enable {
         description "Don't enable trace input mismatch consequential actions";
         type empty;
       }
     }
   }
   grouping otn_options_type {
     uses apply-advanced;
     choice laser-enable-choice {
       leaf laser-enable {
         description "Enable Laser";
         type empty;
       }
       leaf no-laser-enable {
         description "Don't enable Laser";
         type empty;
       }
     }
     choice is-ma-choice {
       leaf is-ma {
         description "Link is enabled with alarms masked";
         type empty;
       }
       leaf no-is-ma {
         description "Don't link is enabled with alarms masked";
         type empty;
       }
     }
     choice line-loopback-choice {
       leaf line-loopback {
         description "Enable line loopback";
         type empty;
       }
       leaf no-line-loopback {
         description "Don't enable line loopback";
         type empty;
       }
     }
     choice local-loopback-choice {
       leaf local-loopback {
         description "Enable local host loopback";
         type empty;
       }
       leaf no-local-loopback {
         description "Don't enable local host loopback";
         type empty;
       }
     }
     choice prbs-choice {
       leaf prbs {
         description "Enable otn payload prbs";
         type empty;
       }
       leaf no-prbs {
         description "Don't enable otn payload prbs";
         type empty;
       }
     }
     choice odu-ttim-action-enable-choice {
       leaf odu-ttim-action-enable {
         description "Enable consequent action for ODU TTIM";
         type empty;
       }
       leaf no-odu-ttim-action-enable {
         description "Don't enable consequent action for ODU TTIM";
         type empty;
       }
     }
     choice otu-ttim-action-enable-choice {
       leaf otu-ttim-action-enable {
         description "Enable consequent action for OTU TTIM";
         type empty;
       }
       leaf no-otu-ttim-action-enable {
         description "Don't enable consequent action for OTU TTIM";
         type empty;
       }
     }
     choice transport-monitoring-choice {
       leaf transport-monitoring {
         description "Enable transport monitoring";
         type empty;
       }
       leaf no-transport-monitoring {
         description "Don't enable transport monitoring";
         type empty;
       }
     }
     container odu-delay-management {
       description "Set odu delay management";
       uses apply-advanced;
       choice monitor-end-point-choice {
         leaf monitor-end-point {
           description "Originate connection monitor end point";
           type empty;
         }
         leaf no-monitor-end-point {
           description "Don't originate connection monitor end point";
           type empty;
         }
       }
       choice start-measurement-choice {
         leaf start-measurement {
           description "Enable to start a dm measurement";
           type empty;
         }
         leaf no-start-measurement {
           description "Don't enable to start a dm measurement";
           type empty;
         }
       }
       choice bypass-choice {
         leaf bypass {
           description "Act as tandem passing dm value through node";
           type empty;
         }
         leaf no-bypass {
           description "Don't act as tandem passing dm value through node";
           type empty;
         }
       }
       leaf number-of-frames {
         description "Number of consequent frames to declare dm done";
         type union {
           type string {
             pattern "<.*>|$.*";
           }
           type uint32 {
             range "0 .. 255";
           }
         }
       }
       choice remote-loop-enable-choice {
         leaf remote-loop-enable {
           description "Enable remote DM loop on remote end";
           type empty;
         }
         leaf no-remote-loop-enable {
           description "Don't enable remote DM loop on remote end";
           type empty;
         }
       }
     }
     container signal-degrade {
       description "Signal degrade thresholds";
       uses apply-advanced;
       leaf interval {
         description "Time interval";
         default "10";
         units "milliseconds";
         type union {
           type string {
             pattern "<.*>|$.*";
           }
           type uint32 {
             range "1 .. 1000";
           }
         }
       }
       leaf ber-threshold-clear {
         description "Ber threshold for signal degrade clear (format: xe-n, example: 4.5e-3)";
         type string {
           junos:posix-pattern "^[0-9]+(.[0-9]+)?e-[0-9]$";
           junos:pattern-message "Ber threshold value in format: xe-n, x is an integer or decimal number, n = 0..9";
         }
       }
       leaf ber-threshold-signal-degrade {
         description "Ber threshold for signal-degrade (format: xe-n, example: 4.5e-3)";
         type string {
           junos:posix-pattern "^[0-9]+(.[0-9]+)?e-[0-9]$";
           junos:pattern-message "Ber threshold value in format: xe-n, x is an integer or decimal number, n = 0..9";
         }
       }
       leaf q-threshold-signal-degrade-clear {
         description "Q threshold for signal-degrade clear (e.g. 14.26)";
         units "dB";
         type string;
       }
       leaf q-threshold-signal-degrade {
         description "Q threshold for signal-degrade (e.g. 9.26)";
         units "dB";
         type string;
       }
     }
     container odu-signal-degrade {
       description "Signal degrade thresholds for ODU";
       uses apply-advanced;
       leaf interval {
         description "Time interval";
         default "10";
         units "milliseconds";
         type union {
           type string {
             pattern "<.*>|$.*";
           }
           type uint32 {
             range "1 .. 1000";
           }
         }
       }
       leaf ber-threshold-clear {
         description "Ber th for sd clear (format: xe-n, example: 4.5e-3)";
         default "1.0e-9";
         type string {
           junos:posix-pattern "^[0-9]+(.[0-9]+)?e-[0-9]$";
           junos:pattern-message "Ber threshold value in format: xe-n, x is an integer or decimal number, n = 0..9";
         }
       }
       leaf ber-threshold-signal-degrade {
         description "Ber th for sd (format: xe-n, example: 4.5e-3)";
         default "1.0e-6";
         type string {
           junos:posix-pattern "^[0-9]+(.[0-9]+)?e-[0-9]$";
           junos:pattern-message "Ber threshold value in format: xe-n, x is an integer or decimal number, n = 0..9";
         }
       }
     }
     container preemptive-fast-reroute {
       description "Preemptive fast reroute";
       uses apply-advanced;
       choice odu-signal-degrade-monitor-enable-choice {
         leaf odu-signal-degrade-monitor-enable {
           description "Enable ODU signal degrade monitoring";
           type empty;
         }
         leaf no-odu-signal-degrade-monitor-enable {
           description "Don't enable ODU signal degrade monitoring";
           type empty;
         }
       }
       choice odu-backward-frr-enable-choice {
         leaf odu-backward-frr-enable {
           description "Enable ODU backward frr insertion";
           type empty;
         }
         leaf no-odu-backward-frr-enable {
           description "Don't enable ODU backward frr insertion";
           type empty;
         }
       }
       choice signal-degrade-monitor-enable-choice {
         leaf signal-degrade-monitor-enable {
           description "Enable signal degrade monitoring";
           type empty;
         }
         leaf no-signal-degrade-monitor-enable {
           description "Don't enable signal degrade monitoring";
           type empty;
         }
       }
       choice backward-frr-enable-choice {
         leaf backward-frr-enable {
           description "Enable backward frr insertion";
           type empty;
         }
         leaf no-backward-frr-enable {
           description "Don't enable backward frr insertion";
           type empty;
         }
       }
     }
     leaf fec {
       description "Forward Error Correction mode";
       type enumeration {
         enum "none" {
           description "GFEC all 0's";
         }
         enum "gfec" {
           description "GFEC-Generic Forward Error Correction";
         }
         enum "efec" {
           description "EFEC-Enhanced Forward Error Correction";
         }
         enum "gfec-sdfec" {
           description "Both gfec and sdfec";
         }
         enum "ufec" {
           description "UFEC-Ultra Forward Error Correction";
         }
         enum "sdfec" {
           description "SDFEC-Soft Decision Forward Error Correction";
         }
         enum "hgfec" {
           description "HGFEC-High Gain Forward Error Correction";
         }
         enum "sdfec15" {
           description "SDFEC with 15 percent overhead - non-differential";
         }
       }
     }
     choice insert-odu-oci-choice {
       leaf insert-odu-oci {
         description "Force odu open connection indication";
         type empty;
       }
       leaf no-insert-odu-oci {
         description "Don't force odu open connection indication";
         type empty;
       }
     }
     choice insert-odu-lck-choice {
       leaf insert-odu-lck {
         description "Force odu locked maintenance signal";
         type empty;
       }
       leaf no-insert-odu-lck {
         description "Don't force odu locked maintenance signal";
         type empty;
       }
     }
     leaf rate {
       description "Optical Transmission Network mode";
       type enumeration {
         enum "pass-thru" {
           description "Pass through mode - No OTN framing";
         }
         enum "fixed-stuff-bytes" {
           description "Fixed Stuff Bytes 11.0957Gbps";
         }
         enum "no-fixed-stuff-bytes" {
           description "No Fixed Stuff Bytes 11.0491Gbps";
         }
         enum "oc192" {
           description "OTU2 for OC192 10.7Gbps";
         }
         enum "otu3" {
           description "OTU3 for 40Gbps";
         }
         enum "otu4" {
           description "OTU4/OTU4v for 100Gbps-127Gbps";
         }
       }
     }
     container bytes {
       description "Set OTN header bytes";
       uses apply-advanced;
       leaf transmit-payload-type {
         description "Transmit payload type";
         type union {
           type string {
             pattern "<.*>|$.*";
           }
           type uint32 {
             range "0 .. 255";
           }
         }
       }
     }
     container tti {
       description "Trace Identifier";
       uses apply-advanced;
       leaf otu-dapi {
         description "OTU Destination Access Point Identifier";
         type string;
       }
       leaf otu-sapi {
         description "OTU Source Access Point Identifier";
         type string;
       }
       leaf otu-expected-receive-dapi {
         description "OTU Expected Receive Destination Access Point Identifier";
         type string;
       }
       leaf otu-expected-receive-sapi {
         description "OTU Expected Receive Source Access Point Identifier";
         type string;
       }
       leaf odu-dapi {
         description "ODU Destination Access Point Identifier";
         type string;
       }
       leaf odu-sapi {
         description "ODU Source Access Point Identifier";
         type string;
       }
       leaf odu-expected-receive-dapi {
         description "ODU Expected Receive Destination Access Point Identifier";
         type string;
       }
       leaf odu-expected-receive-sapi {
         description "ODU Expected Receive Source Access Point Identifier";
         type string;
       }
       choice otu-dapi-first-byte-nul-choice {
         leaf otu-dapi-first-byte-nul {
           description "Insert all-0s to first byte";
           type empty;
         }
         leaf no-otu-dapi-first-byte-nul {
           description "Don't insert all-0s to first byte";
           type empty;
         }
       }
       choice otu-sapi-first-byte-nul-choice {
         leaf otu-sapi-first-byte-nul {
           description "Insert all-0s to first byte";
           type empty;
         }
         leaf no-otu-sapi-first-byte-nul {
           description "Don't insert all-0s to first byte";
           type empty;
         }
       }
       choice otu-expected-receive-dapi-first-byte-nul-choice {
         leaf otu-expected-receive-dapi-first-byte-nul {
           description "Insert all-0s to first byte";
           type empty;
         }
         leaf no-otu-expected-receive-dapi-first-byte-nul {
           description "Don't insert all-0s to first byte";
           type empty;
         }
       }
       choice otu-expected-receive-sapi-first-byte-nul-choice {
         leaf otu-expected-receive-sapi-first-byte-nul {
           description "Insert all-0s to first byte";
           type empty;
         }
         leaf no-otu-expected-receive-sapi-first-byte-nul {
           description "Don't insert all-0s to first byte";
           type empty;
         }
       }
       choice odu-dapi-first-byte-nul-choice {
         leaf odu-dapi-first-byte-nul {
           description "Insert all-0s to first byte";
           type empty;
         }
         leaf no-odu-dapi-first-byte-nul {
           description "Don't insert all-0s to first byte";
           type empty;
         }
       }
       choice odu-sapi-first-byte-nul-choice {
         leaf odu-sapi-first-byte-nul {
           description "Insert all-0s to first byte";
           type empty;
         }
         leaf no-odu-sapi-first-byte-nul {
           description "Don't insert all-0s to first byte";
           type empty;
         }
       }
       choice odu-expected-receive-dapi-first-byte-nul-choice {
         leaf odu-expected-receive-dapi-first-byte-nul {
           description "Insert all-0s to first byte";
           type empty;
         }
         leaf no-odu-expected-receive-dapi-first-byte-nul {
           description "Don't insert all-0s to first byte";
           type empty;
         }
       }
       choice odu-expected-receive-sapi-first-byte-nul-choice {
         leaf odu-expected-receive-sapi-first-byte-nul {
           description "Insert all-0s to first byte";
           type empty;
         }
         leaf no-odu-expected-receive-sapi-first-byte-nul {
           description "Don't insert all-0s to first byte";
           type empty;
         }
       }
     }
     container trigger {
       description "Defect triggers";
       uses apply-advanced;
       container oc-los {
         junos:cli-feature "oneliner";
         description "OC Loss Of Signal defect trigger";
         choice oc_los_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-lof {
         junos:cli-feature "oneliner";
         description "OC Loss Of Frame defect trigger";
         choice oc_lof_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-lom {
         junos:cli-feature "oneliner";
         description "OC Loss Of Multiframe defect trigger";
         choice oc_lom_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-wavelength-lock {
         junos:cli-feature "oneliner";
         description "OC Wavelength Lock defect trigger";
         choice oc_wavelength_lock_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-tsf {
         junos:cli-feature "oneliner";
         description "Oc tsf defect trigger";
         choice oc-tsf-choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-ais {
         junos:cli-feature "oneliner";
         description "OTU Alarm Indication Signal defect trigger";
         choice otu_ais_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-bdi {
         junos:cli-feature "oneliner";
         description "OTU Backward Defect Indication defect trigger";
         choice otu_bdi_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-iae {
         junos:cli-feature "oneliner";
         description "OTU Incoming Alignment defect trigger";
         choice otu_iae_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-ttim {
         junos:cli-feature "oneliner";
         description "OTU Trail Trace Identifier Mismatch defect trigger";
         choice otu_ttim_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-sd {
         junos:cli-feature "oneliner";
         description "OTU Signal Degrade defect trigger";
         choice otu_sd_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-fec-deg {
         junos:cli-feature "oneliner";
         description "OTU FEC Degrade defect trigger";
         choice otu_fec_deg_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-fec-exe {
         junos:cli-feature "oneliner";
         description "OTU FEC Excessive Error defect trigger";
         choice otu_fec_exe_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-ais {
         junos:cli-feature "oneliner";
         description "ODU Alarm Indication Signal defect trigger";
         choice odu_ais_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-bdi {
         junos:cli-feature "oneliner";
         description "ODU Backward Defect Indication defect trigger";
         choice odu_bdi_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-iae {
         junos:cli-feature "oneliner";
         description "Odu iae defect trigger";
         choice odu-iae-choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-bei {
         junos:cli-feature "oneliner";
         description "Odu backward error indication defect trigger";
         choice odu_bei_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-oci {
         junos:cli-feature "oneliner";
         description "ODU Open Connection Indication defect trigger";
         choice odu_oci_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-lck {
         junos:cli-feature "oneliner";
         description "ODU Locked defect trigger";
         choice odu_lck_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-ttim {
         junos:cli-feature "oneliner";
         description "ODU Trail Trace Identifier Mismatch defect trigger";
         choice odu_ttim_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-sd {
         junos:cli-feature "oneliner";
         description "ODU Signal Degrade defect trigger";
         choice odu_sd_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container opu-ptim {
         junos:cli-feature "oneliner";
         description "Payload Type Mismatch defect trigger";
         choice opu_ptm_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
     }
     container tca {
       description "TCA - threshold crossing alerts";
       uses apply-advanced;
       container otu-tca-es {
         junos:cli-feature "oneliner";
         description "OTU Errored Seconds Threshold crossing defect trigger";
         choice enable-tca-choice {
           leaf enable-tca {
             description "Enable the OTU errored seconds threshold crossing alert";
             type empty;
           }
           leaf no-enable-tca {
             description "Don't enable the OTU errored seconds threshold crossing alert";
             type empty;
           }
         }
         leaf threshold {
           description "TCA threshold for OTU errored seconds in 15 minutes";
           default "135";
           type union {
             type string {
               pattern "<.*>|$.*";
             }
             type uint32 {
               range "1 .. 900";
             }
           }
         }
         leaf threshold-24hrs {
           description "TCA threshold for OTU errored seconds in 24 hours";
           default "162";
           type union {
             type string {
               pattern "<.*>|$.*";
             }
             type uint32 {
               range "1 .. 86400";
             }
           }
         }
       }
       container otu-tca-ses {
         junos:cli-feature "oneliner";
         description "OTU Severely Errored Seconds Threshold crossing defect trigger";
         choice enable-tca-choice {
           leaf enable-tca {
             description "Enable the OTU severely errored seconds threshold crossing alert";
             type empty;
           }
           leaf no-enable-tca {
             description "Don't enable the OTU severely errored seconds threshold crossing alert";
             type empty;
           }
         }
         leaf threshold {
           description "TCA threshold for OTU severely errored seconds in 15 minutes";
           default "90";
           type union {
             type string {
               pattern "<.*>|$.*";
             }
             type uint32 {
               range "1 .. 900";
             }
           }
         }
         leaf threshold-24hrs {
           description "TCA threshold for OTU severely errored seconds in 24 hours";
           default "108";
           type union {
             type string {
               pattern "<.*>|$.*";
             }
             type uint32 {
               range "1 .. 86400";
             }
           }
         }
       }
       container otu-tca-uas {
         junos:cli-feature "oneliner";
         description "OTU Unavailable Seconds Threshold crossing defect trigger";
         choice enable-tca-choice {
           leaf enable-tca {
             description "Enable the OTU unavailable seconds threshold crossing alert";
             type empty;
           }
           leaf no-enable-tca {
             description "Don't enable the OTU unavailable seconds threshold crossing alert";
             type empty;
           }
         }
         leaf threshold {
           description "TCA threshold for OTU unavailable seconds in 15 minutes";
           default "90";
           type union {
             type string {
               pattern "<.*>|$.*";
             }
             type uint32 {
               range "10 .. 900";
             }
           }
         }
         leaf threshold-24hrs {
           description "TCA threshold for OTU unavailable seconds in 24 hours";
           default "108";
           type union {
             type string {
               pattern "<.*>|$.*";
             }
             type uint32 {
               range "10 .. 86400";
             }
           }
         }
       }
       container otu-tca-bbe {
         junos:cli-feature "oneliner";
         description "OTU Background Block Error Threshold crossing defect trigger";
         choice enable-tca-choice {
           leaf enable-tca {
             description "Enable the OTU BBE threshold crossing alert";
             type empty;
           }
           leaf no-enable-tca {
             description "Don't enable the OTU BBE threshold crossing alert";
             type empty;
           }
         }
         leaf threshold {
           description "TCA threshold for OTU BBE in 15 minutes";
           default "800";
           type union {
             type string {
               pattern "<.*>|$.*";
             }
             type uint32 {
               range "1 .. 771000000";
             }
           }
         }
         leaf threshold-24hrs {
           description "TCA threshold for OTU BBE in 24 hours";
           default "960";
           type union {
             type string {
               pattern "<.*>|$.*";
             }
             type uint32 {
               range "1 .. 771000000";
             }
           }
         }
       }
       container otu-tca-es-fe {
         junos:cli-feature "oneliner";
         description "OTU far-end Errored Seconds Threshold crossing defect trigger";
         choice enable-tca-choice {
           leaf enable-tca {
             description "Enable the OTU far-end errored seconds threshold crossing alert";
             type empty;
           }
           leaf no-enable-tca {
             description "Don't enable the OTU far-end errored seconds threshold crossing alert";
             type empty;
           }
         }
         leaf threshold {
           description "TCA threshold for OTU far-end errored seconds in 15 minutes";
           default "135";
           type union {
             type string {
               pattern "<.*>|$.*";
             }
             type uint32 {
               range "1 .. 900";
             }
           }
         }
         leaf threshold-24hrs {
           description "TCA threshold for OTU far-end errored seconds in 24 hours";
           default "162";
           type union {
             type string {
               pattern "<.*>|$.*";
             }
             type uint32 {
               range "1 .. 86400";
             }
           }
         }
       }
       container otu-tca-ses-fe {
         junos:cli-feature "oneliner";
         description "OTU far-end Severely Errored Seconds Threshold crossing defect trigger";
         choice enable-tca-choice {
           leaf enable-tca {
             description "Enable the OTU far-end Unavailable Seconds threshold crossing alert";
             type empty;
           }
           leaf no-enable-tca {
             description "Don't enable the OTU far-end Unavailable Seconds threshold crossing alert";
             type empty;
           }
         }
         leaf threshold {
           description "TCA threshold for OTU far-end severely errored seconds in 15 minutes";
           default "90";
           type union {
             type string {
               pattern "<.*>|$.*";
             }
             type uint32 {
               range "1 .. 900";
             }
           }
         }
         leaf threshold-24hrs {
           description "TCA threshold for OTU far-end severely errored seconds in 24 hours";
           default "108";
           type union {
             type string {
               pattern "<.*>|$.*";
             }
             type uint32 {
               range "1 .. 86400";
             }
           }
         }
       }
       container otu-tca-uas-fe {
         junos:cli-feature "oneliner";
         description "OTU far-end Unavailable Seconds Threshold crossing defect trigger";
         choice enable-tca-choice {
           leaf enable-tca {
             description "Enable the OTU far end unavailabe second threshold crossing alert";
             type empty;
           }
           leaf no-enable-tca {
             description "Don't enable the OTU far end unavailabe second threshold crossing alert";
             type empty;
           }
         }
         leaf threshold {
           description "TCA threshold for OTU far-end unavailable seconds in 15 minutes";
           default "90";
           type union {
             type string {
               pattern "<.*>|$.*";
             }
             type uint32 {
               range "10 .. 900";
             }
           }
         }
         leaf threshold-24hrs {
           description "TCA threshold for OTU far-end unavailable seconds in 24 hours";
           default "108";
           type union {
             type string {
               pattern "<.*>|$.*";
             }
             type uint32 {
               range "10 .. 86400";
             }
           }
         }
       }
       container otu-tca-bbe-fe {
         junos:cli-feature "oneliner";
         description "OTU far-end Background Block Error (BEI) Threshold crossing defect trigger";
         choice enable-tca-choice {
           leaf enable-tca {
             description "Enable the OTU BBE (BEI) threshold crossing alert";
             type empty;
           }
           leaf no-enable-tca {
             description "Don't enable the OTU BBE (BEI) threshold crossing alert";
             type empty;
           }
         }
         leaf threshold {
           description "TCA threshold for OTU far-end BBE (BEI) in 15 minutes";
           default "800";
           type union {
             type string {
               pattern "<.*>|$.*";
             }
             type uint32 {
               range "1 .. 771000000";
             }
           }
         }
         leaf threshold-24hrs {
           description "TCA threshold for OTU far-end BBE (BEI) in 24 hours";
           default "960";
           type union {
             type string {
               pattern "<.*>|$.*";
             }
             type uint32 {
               range "1 .. 771000000";
             }
           }
         }
       }
       container odu-tca-es {
         junos:cli-feature "oneliner";
         description "ODU Errored Seconds Threshold crossing defect trigger";
         choice enable-tca-choice {
           leaf enable-tca {
             description "Enable the ODU errored seconds threshold crossing alert";
             type empty;
           }
           leaf no-enable-tca {
             description "Don't enable the ODU errored seconds threshold crossing alert";
             type empty;
           }
         }
         leaf threshold {
           description "TCA threshold for ODU errored seconds in 15 minutes";
           default "135";
           type union {
             type string {
               pattern "<.*>|$.*";
             }
             type uint32 {
               range "1 .. 900";
             }
           }
         }
         leaf threshold-24hrs {
           description "TCA threshold for ODU errored seconds in 24 hours";
           default "162";
           type union {
             type string {
               pattern "<.*>|$.*";
             }
             type uint32 {
               range "1 .. 86400";
             }
           }
         }
       }
       container odu-tca-ses {
         junos:cli-feature "oneliner";
         description "ODU Severely Errored Seconds Threshold crossing defect trigger";
         choice enable-tca-choice {
           leaf enable-tca {
             description "Enable the ODU severely errored seconds threshold crossing alert";
             type empty;
           }
           leaf no-enable-tca {
             description "Don't enable the ODU severely errored seconds threshold crossing alert";
             type empty;
           }
         }
         leaf threshold {
           description "TCA threshold for ODU severely errored seconds in 15 minutes";
           default "90";
           type union {
             type string {
               pattern "<.*>|$.*";
             }
             type uint32 {
               range "1 .. 900";
             }
           }
         }
         leaf threshold-24hrs {
           description "TCA threshold for ODU severely-errored seconds in 24 hours";
           default "108";
           type union {
             type string {
               pattern "<.*>|$.*";
             }
             type uint32 {
               range "1 .. 86400";
             }
           }
         }
       }
       container odu-tca-uas {
         junos:cli-feature "oneliner";
         description "ODU Unavailable Seconds Threshold crossing defect trigger";
         choice enable-tca-choice {
           leaf enable-tca {
             description "Enable the ODU unavailable seconds threshold crossing alert";
             type empty;
           }
           leaf no-enable-tca {
             description "Don't enable the ODU unavailable seconds threshold crossing alert";
             type empty;
           }
         }
         leaf threshold {
           description "TCA threshold for ODU unavailable seconds in 15 minutes";
           default "90";
           type union {
             type string {
               pattern "<.*>|$.*";
             }
             type uint32 {
               range "10 .. 900";
             }
           }
         }
         leaf threshold-24hrs {
           description "TCA threshold for ODU unavailable seconds in 24 hours";
           default "108";
           type union {
             type string {
               pattern "<.*>|$.*";
             }
             type uint32 {
               range "10 .. 86400";
             }
           }
         }
       }
       container odu-tca-bbe {
         junos:cli-feature "oneliner";
         description "ODU Background Block Error Threshold crossing defect trigger";
         choice enable-tca-choice {
           leaf enable-tca {
             description "Enable the ODU BBE threshold crossing alert";
             type empty;
           }
           leaf no-enable-tca {
             description "Don't enable the ODU BBE threshold crossing alert";
             type empty;
           }
         }
         leaf threshold {
           description "TCA threshold for ODU BBE in 15 minutes";
           default "800";
           type union {
             type string {
               pattern "<.*>|$.*";
             }
             type uint32 {
               range "1 .. 771000000";
             }
           }
         }
         leaf threshold-24hrs {
           description "TCA threshold for ODU backgrand block error in 24 hours";
           default "960";
           type union {
             type string {
               pattern "<.*>|$.*";
             }
             type uint32 {
               range "1 .. 771000000";
             }
           }
         }
       }
       container odu-tca-es-fe {
         junos:cli-feature "oneliner";
         description "ODU far-end Errored Seconds Threshold crossing defect trigger";
         choice enable-tca-choice {
           leaf enable-tca {
             description "Enable the ODU far-end errored seconds threshold crossing alert";
             type empty;
           }
           leaf no-enable-tca {
             description "Don't enable the ODU far-end errored seconds threshold crossing alert";
             type empty;
           }
         }
         leaf threshold {
           description "TCA threshold for ODU far-end errored seconds in 15 minutes";
           default "135";
           type union {
             type string {
               pattern "<.*>|$.*";
             }
             type uint32 {
               range "1 .. 900";
             }
           }
         }
         leaf threshold-24hrs {
           description "TCA threshold for ODU far-end errored seconds in 24 hours";
           default "162";
           type union {
             type string {
               pattern "<.*>|$.*";
             }
             type uint32 {
               range "1 .. 86400";
             }
           }
         }
       }
       container odu-tca-ses-fe {
         junos:cli-feature "oneliner";
         description "ODU far-end Severely Errored Seconds Threshold crossing defect trigger";
         choice enable-tca-choice {
           leaf enable-tca {
             description "Enable the ODU far-end Unavailable Seconds threshold crossing alert";
             type empty;
           }
           leaf no-enable-tca {
             description "Don't enable the ODU far-end Unavailable Seconds threshold crossing alert";
             type empty;
           }
         }
         leaf threshold {
           description "TCA threshold for ODU far-end severely errored seconds in 15 minutes";
           default "90";
           type union {
             type string {
               pattern "<.*>|$.*";
             }
             type uint32 {
               range "1 .. 900";
             }
           }
         }
         leaf threshold-24hrs {
           description "TCA threshold for ODU severely-errored seconds in 24 hours";
           default "108";
           type union {
             type string {
               pattern "<.*>|$.*";
             }
             type uint32 {
               range "1 .. 86400";
             }
           }
         }
       }
       container odu-tca-uas-fe {
         junos:cli-feature "oneliner";
         description "ODU far-end Unavailable Seconds Threshold crossing defect trigger";
         choice enable-tca-choice {
           leaf enable-tca {
             description "Enable the ODU far end unavailabe second threshold crossing alert";
             type empty;
           }
           leaf no-enable-tca {
             description "Don't enable the ODU far end unavailabe second threshold crossing alert";
             type empty;
           }
         }
         leaf threshold {
           description "TCA threshold for ODU far-end unavailable seconds in 15 minutes";
           default "90";
           type union {
             type string {
               pattern "<.*>|$.*";
             }
             type uint32 {
               range "10 .. 900";
             }
           }
         }
         leaf threshold-24hrs {
           description "TCA threshold for ODU far-end unavailable seconds in 24 hours";
           default "108";
           type union {
             type string {
               pattern "<.*>|$.*";
             }
             type uint32 {
               range "10 .. 86400";
             }
           }
         }
       }
       container odu-tca-bbe-fe {
         junos:cli-feature "oneliner";
         description "ODU far-end Background Block Error (BEI) Threshold crossing defect trigger";
         choice enable-tca-choice {
           leaf enable-tca {
             description "Enable the ODU BBE (BEI) threshold crossing alert";
             type empty;
           }
           leaf no-enable-tca {
             description "Don't enable the ODU BBE (BEI) threshold crossing alert";
             type empty;
           }
         }
         leaf threshold {
           description "TCA threshold for ODU far-end BBE (BEI) in 15 minutes";
           default "800";
           type union {
             type string {
               pattern "<.*>|$.*";
             }
             type uint32 {
               range "1 .. 771000000";
             }
           }
         }
         leaf threshold-24hrs {
           description "TCA threshold for ODU far-end backgrand block error in 24 hours";
           default "960";
           type union {
             type string {
               pattern "<.*>|$.*";
             }
             type uint32 {
               range "1 .. 771000000";
             }
           }
         }
       }
       container otu-tca-fec-ber {
         junos:cli-feature "oneliner";
         description "OTU Errored Seconds Threshold crossing defect trigger";
         choice enable-tca-choice {
           leaf enable-tca {
             description "Enable the OTU errored seconds threshold crossing alert";
             type empty;
           }
           leaf no-enable-tca {
             description "Don't enable the OTU errored seconds threshold crossing alert";
             type empty;
           }
         }
         leaf threshold {
           description "TCA threshold for BER value in format: xe-n, x is an integer or decimal number, n = 0..9";
           default "10e-3";
           type string {
             junos:posix-pattern "^[0-9]+(.[0-9]+)?e-[0-9]$";
             junos:pattern-message "FEC BER threshold value in format: xe-n, x is an integer or decimal number, n = 0..9";
           }
         }
         leaf threshold-24hrs {
           description "TCA threshold for BER value in format: xe-n, x is an integer or decimal number, n = 0..9";
           default "10e-3";
           type string {
             junos:posix-pattern "^[0-9]+(.[0-9]+)?e-[0-9]$";
             junos:pattern-message "FEC BER threshold value in format: xe-n, x is an integer or decimal number, n = 0..9";
           }
         }
       }
     }
   }
   grouping otu-attributes {
     description "Optical transmission unit configuration attributes";
     uses apply-advanced;
     leaf rate {
       description "Specific type of OTU, according to data rate";
       type enumeration {
         enum "otu4" {
           description "OTU4 for 100 Gbps";
         }
       }
     }
     choice is-ma-choice {
       leaf is-ma {
         description "Link is enabled for maintenance tasks, alarms are masked";
         type empty;
       }
       leaf no-is-ma {
         description "Don't link is enabled for maintenance tasks, alarms are masked";
         type empty;
       }
     }
     leaf fec {
       description "Forward error correction type";
       type enumeration {
         enum "none" {
           description "No forward error correction applied";
         }
         enum "gfec" {
           description "ITU-T G.709 standard forward error correction";
         }
         enum "hgfec" {
           description "High gain FEC";
         }
       }
     }
     leaf loopback {
       description "Enabled loopback mode";
       type enumeration {
         enum "none" {
           description "No loopback mode active";
         }
         enum "local" {
           description "Local loopback (host side)";
         }
         enum "line" {
           description "Line loopback (network side)";
         }
       }
     }
     container tti {
       description "Configuration of OTU trail trace identifier";
       presence "enable tti";
       uses otn-tti-attributes;
     }
     container degrade {
       description "Configuration of OTU degrade defect detection";
       presence "enable degrade";
       uses otn-degrade;
     }
   }
   grouping p2mp_ldp_lsp_nh_obj {
     uses apply-advanced;
     list root-address {
       key name;
       description "Configure the root address of P2MP LSP";
       leaf name {
         description "Root address of the P2MP LSP";
         junos:cli-feature "nokeyword";
         type jt:ipaddr;
       }
       uses apply-advanced;
       leaf lsp-id {
         description "Configure the generic LSP identifier";
         type union {
           type string {
             pattern "<.*>|$.*";
           }
           type uint32 {
             range "1 .. 65535";
           }
         }
       }
       list group-address {
         key name;
         description "IPv4/Ipv6 group address for mLDP LSP";
         leaf name {
           description "IPv4/Ipv6 group address";
           junos:cli-feature "nokeyword";
           type jt:ipaddr;
         }
         uses apply-advanced;
         list source-address {
           key name;
           description "IPv4/Ipv6 source address";
           leaf name {
             description "IPv4/Ipv6 source address for mLDP LSP";
             junos:cli-feature "nokeyword";
             type jt:ipaddr;
           }
           uses apply-advanced;
         }
       }
     }
   }
   grouping pim_bootstrap_options_type {
     uses apply-advanced;
     leaf priority {
       description "Eligibility to be the bootstrap router";
       type union {
         type string {
           pattern "<.*>|$.*";
         }
         type uint32 {
           range "0 .. 255";
         }
       }
     }
     leaf-list import {
       ordered-by user;
       description "Bootstrap import policy";
       type jt:policy-algebra;
     }
     leaf-list export {
       ordered-by user;
       description "Bootstrap export policy";
       type jt:policy-algebra;
     }
   }
   grouping pim_filter_obj {
     junos:cli-feature "oneliner";
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping pim_rp_group_range_type {
     junos:cli-feature "homogeneous";
     leaf name {
       junos:cli-feature "nokeyword";
       type jt:ipprefix;
     }
     uses apply-advanced;
     leaf nexthop-hold-time {
       description "Nexthop hold time in milliseconds";
       units "milliseconds";
       type union {
         type string {
           pattern "<.*>|$.*";
         }
         type uint32 {
           range "1 .. 1000";
         }
       }
     }
   }
   grouping ppp_options_type {
     uses apply-advanced;
     leaf dynamic-profile {
       description "Dynamic profile name";
       junos:must "(\"dynamic-profiles $$\")";
       junos:must-message "referenced dynamic-profile must be defined";
       junos:must "(any \".. .. .. unit <*>\")";
       junos:must-message "dynamic-profile statement can be configured only on logical interfaces";
       type string;
     }
     container chap {
       presence "enable chap";
       description "Challenge Handshake Authentication Protocol options";
       uses apply-advanced;
       choice access-data {
         case case_1 {
           leaf access-profile {
             description "Profile containing client list and access parameters";
             junos:must "(\"access profile $$\")";
             junos:must-message "referenced access profile must be defined";
             type string {
               length "1 .. 63";
             }
           }
         }
         case case_2 {
           leaf default-chap-secret {
             description "Default CHAP secret to be used when no matching access profile exists";
             type jt:unreadable;
           }
         }
       }
       leaf local-name {
         description "Name sent in CHAP-Challenge and CHAP-Response";
         type string;
       }
       leaf no-rfc2486 {
         description "RFC2486 compliance is not enforced";
         type empty;
       }
       leaf passive {
         description "Handle incoming CHAP requests only";
         type empty;
       }
     }
     container pap {
       presence "enable pap";
       description "Password Authentication Protocol options";
       uses apply-advanced;
       choice access-data {
         case case_1 {
           leaf access-profile {
             description "Profile containing client list and access parameters";
             junos:must "(\"access profile $$\")";
             junos:must-message "referenced access profile must be defined";
             type string {
               length "1 .. 63";
             }
           }
         }
         case case_2 {
           leaf default-password {
             description "Default PAP password used in the absence of matching profile";
             type jt:unreadable;
           }
         }
       }
       leaf local-name {
         description "Name sent in PAP request packet";
         type string;
       }
       leaf no-rfc2486 {
         description "RFC2486 compliance is not enforced";
         type empty;
       }
       leaf local-password {
         description "Password sent in PAP request packet";
         type jt:unreadable;
       }
       leaf passive {
         description "Do not handle PAP authentication requests";
         junos:must "(\".. local-password\")";
         junos:must-message "local-password MUST be set if passive is used with PAP";
         type empty;
       }
     }
     container compression {
       junos:cli-feature "oneliner";
       description "Set compression options";
       leaf acfc {
         description "Negotiate Address/Control field compression";
         junos:must "(!(\".. .. .. encapsulation frame-relay-ppp\"))";
         junos:must-message "compression acfc is not supported on encapsulation frame-relay-ppp";
         type empty;
       }
       leaf pfc {
         description "Negotiate Protocol field compression";
         type empty;
       }
     }
     leaf lcp-restart-timer {
       description "LCP restart timer";
       units "milliseconds";
       junos:must "(any \".. .. .. unit <*>\")";
       junos:must-message "lcp-restart-timer statement can be configured only on logical interfaces";
       type union {
         type string {
           pattern "<.*>|$.*";
         }
         type uint16 {
           range "20 .. 10000";
         }
       }
     }
     leaf ncp-restart-timer {
       description "NCP restart timer";
       units "milliseconds";
       junos:must "(any \".. .. .. unit <*>\")";
       junos:must-message "ncp-restart-timer statement can be configured only on logical interfaces";
       type union {
         type string {
           pattern "<.*>|$.*";
         }
         type uint16 {
           range "500 .. 10000";
         }
       }
     }
     leaf no-termination-request {
       description "Don't send PPP termination requests";
       type empty;
     }
     leaf loopback-clear-timer {
       description "Loopback clear timer";
       units "seconds";
       junos:must "(any \".. .. .. unit <*>\")";
       junos:must-message "loopback-clear-timer statement can be configured only on logical interfaces";
       type union {
         type string {
           pattern "<.*>|$.*";
         }
         type uint8 {
           range "1 .. 60";
         }
       }
     }
     leaf lcp-max-conf-req {
       description "Maximum LCP Conf-Req to be sent, 0 means infinite";
       junos:must "(any \".. .. .. unit <*>\")";
       junos:must-message "lcp-max-conf-req statement can be configured only on logical interfaces";
       type union {
         type string {
           pattern "<.*>|$.*";
         }
         type uint32 {
           range "0 .. 65535";
         }
       }
     }
     leaf ncp-max-conf-req {
       description "Maximum NCP Conf-Req to be sent, 0 means infinite";
       junos:must "(any \".. .. .. unit <*>\")";
       junos:must-message "ncp-max-conf-req statement can be configured only on logical interfaces";
       type union {
         type string {
           pattern "<.*>|$.*";
         }
         type uint32 {
           range "0 .. 65535";
         }
       }
     }
     leaf on-demand-ip-address {
       description "Enable On-Demand IPv4 address allocation and de-allocation";
       junos:must "(any \".. .. .. unit <*>\")";
       junos:must-message "on-demand-ip-address statement can be configured only on logical interfaces";
       type empty;
     }
     leaf aaa-options {
       description "Attach AAA options name to dynamic-profile";
       junos:must "(\"access aaa-options $$\")";
       junos:must-message "referenced aaa-options name must be defined";
       type string {
         length "1 .. 63";
       }
     }
     leaf service-profile {
       description "Default service profile";
       type string {
         length "1 .. 128";
       }
     }
     container initiate-ncp {
       junos:must "(any \".. .. .. unit <*>\")";
       junos:must-message "initiate-ncp statement can be configured only on logical interfaces";
       description "Enable server initiated NCP";
       uses apply-advanced;
       leaf ip {
         description "Enable server initiated IPNCP";
         type empty;
       }
       leaf ipv6 {
         description "Enable server initiated IPv6NCP";
         type empty;
       }
       leaf dual-stack-passive {
         description "Disable server initiated IPNCP/IPv6NCP for dual-stack client";
         type empty;
       }
     }
     leaf mtu {
       description "The Maximum Transfer Unit size in bytes";
       junos:must "(any \".. .. .. unit <*>\")";
       junos:must-message "mtu statement can be configured only on logical interfaces";
       type string;
     }
     leaf peer-ip-address-optional {
       description "Set Peer IP Address Optional in IP NCP Negotiations";
       type empty;
     }
     leaf ipcp-suggest-dns-option {
       description "Suggest peer to negotiate with DNS Addresses options";
       type empty;
     }
     leaf ignore-magic-number-mismatch {
       description "Ignore magic-number validation failure in LCP keepalive";
       type empty;
     }
     container local-authentication {
       description "Local Authentication Protocol options";
       uses local_auth_type;
     }
     leaf lcp-connection-update {
       description "Enable LCP connection update request to peer";
       type empty;
     }
   }
   grouping local_auth_type {
     description "Local authentication";
     uses apply-advanced;
     leaf password {
       description "Username password";
       type string {
         length "1 .. 64";
       }
     }
     container username-include {
       description "Add username options";
       uses apply-advanced;
       leaf mac-address {
         description "Include MAC address";
         type empty;
       }
       leaf circuit-id {
         description "Include circuit-id ";
         type empty;
       }
       leaf remote-id {
         description "Include remote-id ";
         type empty;
       }
       leaf domain-name {
         description "Domain name";
         type string {
           length "1 .. 64";
         }
       }
       leaf delimiter {
         description "Delimiter/separator character";
         type string {
           length 1;
         }
       }
     }
   }
   grouping pppoe_options_type {
     uses apply-advanced;
     leaf underlying-interface {
       description "Underlying interface name";
       junos:must "((!(\"interfaces $$-IFL pppoe-underlying-options dynamic-profile\") && !(\"interfaces $$-IFL family pppoe dynamic-profile\")))";
       junos:must-message "Underlying interface cannot be used for both static and dynamic PPPoE interfaces";
       junos:must "((\"interfaces $$-IFL encapsulation ppp-over-ether\" || (\"interfaces $$-IFL encapsulation ppp-over-ether-over-atm-llc\" || \"interfaces $$-IFL family pppoe\")))";
       junos:must-message "Underlying interface must be configured";
       type string;
     }
     leaf idle-timeout {
       description "Time for which session can be idle (0 = forever)";
       units "seconds";
       type union {
         type string {
           pattern "<.*>|$.*";
         }
         type uint32 {
           range "0 .. 4294967295";
         }
       }
     }
     leaf access-concentrator {
       description "Name of the access concentrator (PPPoE server)";
       type string;
     }
     leaf service-name {
       description "Service to be requested (from PPPoE server)";
       type string;
     }
     leaf auto-reconnect {
       description "Time to reconnect after session terminates (0 = never)";
       units "seconds";
       type union {
         type string {
           pattern "<.*>|$.*";
         }
         type uint32 {
           range "0 .. 4294967295";
         }
       }
     }
     choice pppoe-mode {
       case case_1 {
         leaf server {
           description "PPPoE operates in server mode";
           type empty;
         }
       }
       case case_2 {
         leaf client {
           description "PPPoE operates in client mode";
           type empty;
         }
       }
     }
     leaf ppp-max-payload {
       description "Specify the value of ppp-max-payload tag";
       type union {
         type string {
           pattern "<.*>|$.*";
         }
         type uint32 {
           range "1492 .. 9192";
         }
       }
     }
   }
   grouping prbs-config {
     description "Configuration of pseudorandom binary sequence test signal";
     uses apply-advanced;
     choice enable-prbs-choice {
       leaf enable-prbs {
         description "Enable PRBS test pattern generation and monitoring";
         type empty;
       }
       leaf no-enable-prbs {
         description "Don't enable PRBS test pattern generation and monitoring";
         type empty;
       }
     }
     leaf direction {
       description "Direction of generated and received PRBS test signal";
       default "line";
       type enumeration {
         enum "local" {
           description "Test signal generated towards and received from host-side";
         }
         enum "line" {
           description "Test signal generated towards and received from network-side";
         }
       }
     }
     leaf pattern {
       description "Pattern to use for PRBS test signal";
       default "prbs-31";
       type enumeration {
         enum "prbs-31" {
           description "2^31 polynomial PRBS test signal, as per G.709";
         }
         enum "prbs-23" {
           description "2^23 polynomial PRBS test signal, SONET/SDH framed";
         }
         enum "prbs-15" {
           description "2^15 polynomial PRBS test signal";
         }
         enum "prbs-7" {
           description "2^7 polynomial PRBS test signal";
         }
       }
     }
     choice invert-choice {
       leaf invert {
         description "Invert the test pattern";
         type empty;
       }
       leaf no-invert {
         description "Don't invert the test pattern";
         type empty;
       }
     }
   }
   grouping prefix_action {
     leaf name {
       description "Prefix action name";
       junos:cli-feature "nokeyword";
       type string {
         junos:posix-pattern "!^((__.*)|(.{65,}))$";
         junos:pattern-message "Must be a non-reserved string of 64 characters or less";
       }
     }
     uses apply-advanced;
     leaf policer {
       description "Police the packet using a set of named policer";
       type string {
         junos:posix-pattern "!^((__.*)|(.{65,}))$";
         junos:pattern-message "Must be a non-reserved string of 64 characters or less";
       }
     }
     leaf count {
       description "Enable counters";
       type empty;
     }
     leaf filter-specific {
       description "Filter specific, else term specific";
       type empty;
     }
     leaf subnet-prefix-length {
       description "Prefix length for the total address range";
       type union {
         type string {
           pattern "<.*>|$.*";
         }
         type uint32 {
           range "0 .. 32";
         }
       }
     }
     choice source_or_dest {
       case case_1 {
         leaf source-prefix-length {
           description "Source prefix range";
           type union {
             type string {
               pattern "<.*>|$.*";
             }
             type uint32 {
               range "0 .. 32";
             }
           }
         }
       }
       case case_2 {
         leaf destination-prefix-length {
           description "Destination prefix range";
           type union {
             type string {
               pattern "<.*>|$.*";
             }
             type uint32 {
               range "0 .. 32";
             }
           }
         }
       }
     }
   }
   grouping prefix_list_items {
     junos:cli-feature "nokeyword";
     junos:cli-feature "homogeneous";
     leaf name {
       description "Address prefix";
       junos:cli-feature "nokeyword";
       type jt:ipprefix-only;
     }
     uses apply-advanced;
   }
   grouping qualified_nh_obj {
     leaf name {
       description "Next hop to destination";
       junos:cli-feature "nokeyword";
       type union {
         type jt:ipaddr-or-interface;
         type string {
           pattern "<.*>|$.*";
         }
       }
     }
     uses apply-advanced;
     leaf preference {
       description "Preference of qualified next hop";
       type union {
         type uint32;
         type string {
           pattern "<.*>|$.*";
         }
       }
     }
     leaf metric {
       description "Metric of qualified next hop";
       type union {
         type uint32;
         type string {
           pattern "<.*>|$.*";
         }
       }
     }
     leaf interface {
       description "Interface of qualified next hop";
       type union {
         type jt:interface-name;
         type string {
           pattern "<.*>|$.*";
         }
       }
     }
     leaf mac-address {
       description "Next-hop Mac Address";
       type jt:mac-unicast;
     }
     leaf order {
       description "Order of qualified next hop";
       type union {
         type string {
           pattern "<.*>|$.*";
         }
         type uint16 {
           range "1 .. 65535";
         }
       }
     }
     leaf tag {
       description "Tag string";
       type union {
         type uint32;
         type string {
           pattern "<.*>|$.*";
         }
       }
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       leaf inline-disable {
         description "Disable inline mode for this BFD session";
         type empty;
       }
       leaf pdu-size {
         description "BFD transport protocol payload size";
         default "24";
         type union {
           type string {
             pattern "<.*>|$.*";
           }
           type uint32 {
             range "24 .. 16000";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           junos:must "(\".. algorithm\")";
           junos:must-message "May not be configured without algorithm";
           junos:must "(\"security authentication-key-chains key-chain $$\")";
           junos:must-message "Referenced key-chain must be defined";
           type string;
         }
         leaf algorithm {
           description "Algorithm name";
           junos:must "(\".. key-chain\")";
           junos:must-message "May not be configured without key-chain";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       container echo {
         junos:must "(!(\".. echo-lite\"))";
         junos:must-message "'echo-lite' and 'echo' mode cannot be configured at the same time";
         description "Echo mode parameters";
         uses apply-advanced;
         leaf minimum-interval {
           description "Minimum transmit and receive interval";
           units "milliseconds";
           type union {
             type string {
               pattern "<.*>|$.*";
             }
             type uint32 {
               range "100 .. 255000";
             }
           }
         }
       }
       container echo-lite {
         junos:must "(!(\".. echo\"))";
         junos:must-message "'echo-lite' and 'echo' mode cannot be configured at the same time";
         description "Echo-lite more parameters";
         uses apply-advanced;
         leaf minimum-interval {
           description "Minimum transmit and receive interval";
           units "milliseconds";
           type union {
             type string {
               pattern "<.*>|$.*";
             }
             type uint32 {
               range "1 .. 255000";
             }
           }
         }
       }
       leaf neighbor {
         description "BFD neighbor address";
         type jt:ipaddr;
       }
       leaf local-address {
         description "BFD local address (for multihop only)";
         type jt:ipaddr;
       }
       leaf holddown-interval {
         description "Time to hold the session-UP notification to the client";
         units "milliseconds";
         type union {
           type string {
             pattern "<.*>|$.*";
           }
           type uint32 {
             range "0 .. 255000";
           }
         }
       }
       leaf minimum-receive-ttl {
         description "Minimum receive TTL below which to drop";
         type union {
           type string {
             pattern "<.*>|$.*";
           }
           type uint8 {
             range "1 .. 255";
           }
         }
       }
     }
   }
   grouping rib_aggregate_type {
     uses apply-advanced;
     container defaults {
       description "Global route options";
       uses apply-advanced;
       container metric {
         description "Metric value";
         presence "enable metric";
         junos:cli-feature "oneliner";
         uses rib_static_metric_type;
       }
       container metric2 {
         description "Metric value 2";
         presence "enable metric2";
         junos:cli-feature "oneliner";
         uses rib_static_metric_type;
       }
       container metric3 {
         description "Metric value 3";
         presence "enable metric3";
         junos:cli-feature "oneliner";
         uses rib_static_metric_type;
       }
       container metric4 {
         description "Metric value 4";
         presence "enable metric4";
         junos:cli-feature "oneliner";
         uses rib_static_metric_type;
       }
       container tag {
         description "Tag string";
         presence "enable tag";
         junos:cli-feature "oneliner";
         uses rib_static_metric_type;
       }
       container tag2 {
         description "Tag string 2";
         presence "enable tag2";
         junos:cli-feature "oneliner";
         uses rib_static_metric_type;
       }
       container preference {
         description "Preference value";
         presence "enable preference";
         junos:cli-feature "oneliner";
         uses rib_static_metric_type;
       }
       container preference2 {
         description "Preference value 2";
         presence "enable preference2";
         junos:cli-feature "oneliner";
         uses rib_static_metric_type;
       }
       container color {
         description "Color (preference) value";
         presence "enable color";
         junos:cli-feature "oneliner";
         uses rib_static_metric_type;
       }
       container color2 {
         description "Color (preference) value 2";
         presence "enable color2";
         junos:cli-feature "oneliner";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           junos:cli-feature "nokeyword";
           type string {
             junos:posix-pattern "^[0-9]+(.[0-9]+)?$";
             junos:pattern-message "Use format \'x\' or \'x.y\' to specify number \'x\' (Range 1 .. 4294967295) or number with higher 2 bytes \'x\' (Range 0 .. 65535) and lower 2 bytes \'y\' (Range 0 .. 65535) respectively";
           }
         }
         leaf address {
           description "Address of BGP system that formed the route";
           junos:cli-feature "nokeyword";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
       container algorithm {
         junos:cli-feature "oneliner";
         description "Algorithm number";
         leaf number {
           description "Algorithm number";
           junos:cli-feature "nokeyword";
           type union {
             type string {
               pattern "<.*>|$.*";
             }
             type uint32 {
               range "0 .. 255";
             }
           }
         }
       }
     }
     leaf protocol-instance-name {
       description "Name of protocol instance under routing instance";
       type string;
     }
     list route {
       key name;
       junos:cli-feature "oneliner-plus";
       description "Individual route options";
       leaf name {
         description "Destination prefix";
         junos:cli-feature "nokeyword";
         type jt:ipprefix;
       }
       uses apply-advanced;
       leaf description {
         description "Description for aggregate routes";
         type string {
           junos:posix-pattern "^.{1,255}$";
           junos:pattern-message "Must be a string of 255 characters or less";
         }
       }
       leaf-list policy {
         ordered-by user;
         description "Policy filter";
         type jt:policy-algebra;
       }
       container metric {
         description "Metric value";
         presence "enable metric";
         junos:cli-feature "oneliner";
         uses rib_static_metric_type;
       }
       container metric2 {
         description "Metric value 2";
         presence "enable metric2";
         junos:cli-feature "oneliner";
         uses rib_static_metric_type;
       }
       container metric3 {
         description "Metric value 3";
         presence "enable metric3";
         junos:cli-feature "oneliner";
         uses rib_static_metric_type;
       }
       container metric4 {
         description "Metric value 4";
         presence "enable metric4";
         junos:cli-feature "oneliner";
         uses rib_static_metric_type;
       }
       container tag {
         description "Tag string";
         presence "enable tag";
         junos:cli-feature "oneliner";
         uses rib_static_metric_type;
       }
       container tag2 {
         description "Tag string 2";
         presence "enable tag2";
         junos:cli-feature "oneliner";
         uses rib_static_metric_type;
       }
       container preference {
         description "Preference value";
         presence "enable preference";
         junos:cli-feature "oneliner";
         uses rib_static_metric_type;
       }
       container preference2 {
         description "Preference value 2";
         presence "enable preference2";
         junos:cli-feature "oneliner";
         uses rib_static_metric_type;
       }
       container color {
         description "Color (preference) value";
         presence "enable color";
         junos:cli-feature "oneliner";
         uses rib_static_metric_type;
       }
       container color2 {
         description "Color (preference) value 2";
         presence "enable color2";
         junos:cli-feature "oneliner";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           junos:cli-feature "nokeyword";
           type string {
             junos:posix-pattern "^[0-9]+(.[0-9]+)?$";
             junos:pattern-message "Use format \'x\' or \'x.y\' to specify number \'x\' (Range 1 .. 4294967295) or number with higher 2 bytes \'x\' (Range 0 .. 65535) and lower 2 bytes \'y\' (Range 0 .. 65535) respectively";
           }
         }
         leaf address {
           description "Address of BGP system that formed the route";
           junos:cli-feature "nokeyword";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
       container algorithm {
         junos:cli-feature "oneliner";
         description "Algorithm number";
         leaf number {
           description "Algorithm number";
           junos:cli-feature "nokeyword";
           type union {
             type string {
               pattern "<.*>|$.*";
             }
             type uint32 {
               range "0 .. 255";
             }
           }
         }
       }
     }
   }
   grouping rib_group_type {
     junos:cli-feature "oneliner-plus";
     uses apply-advanced;
     leaf inet-old-style {
       description "Name of the IPv4 routing table group";
       status deprecated;
       junos:cli-feature "nokeyword";
       type string;
     }
     leaf inet {
       description "Name of the IPv4 routing table group";
       type string;
     }
     leaf inet3 {
       description "Name of the IPv4 inet.3 routing table group";
       type string;
     }
     leaf inet6 {
       description "Name of the IPv6 routing table group";
       type string;
     }
     leaf inet63 {
       description "Name of the IPv6 inet6.3 routing table group";
       type string;
     }
   }
   grouping rib_static_metric_type {
     junos:cli-feature "oneliner";
     leaf metric-value {
       description "Metric value";
       junos:cli-feature "nokeyword";
       type union {
         type uint32;
         type string {
           pattern "<.*>|$.*";
         }
       }
     }
     leaf type {
       description "Metric type";
       type union {
         type string {
           pattern "<.*>|$.*";
         }
         type uint32 {
           range "1 .. 16";
         }
       }
     }
   }
   grouping sonet_options_type {
     uses apply-advanced;
     leaf vtmapping {
       description "VT mapping mode";
       type enumeration {
         enum "klm" {
           description "KLM mode";
         }
         enum "itu-t" {
           description "ITU-T mode";
         }
       }
     }
     leaf fcs {
       description "Frame checksum";
       type enumeration {
         enum "32" {
           description "32-bit mode";
         }
         enum "16" {
           description "16-bit mode";
         }
       }
     }
     leaf path-trace {
       description "Path trace string";
       type string;
     }
     leaf loopback {
       description "Loopback mode";
       type enumeration {
         enum "local" {
           description "Local loopback";
         }
         enum "remote" {
           description "Remote loopback";
         }
       }
     }
     container trigger {
       description "Defect triggers";
       uses apply-advanced;
       container lol {
         junos:cli-feature "oneliner";
         description "LOL defect trigger";
         choice lol_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container pll {
         junos:cli-feature "oneliner";
         description "PLL defect trigger";
         choice pll_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lof {
         junos:cli-feature "oneliner";
         description "LOF defect trigger";
         choice lof_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container los {
         junos:cli-feature "oneliner";
         description "LOS defect trigger";
         choice los_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ais-l {
         junos:cli-feature "oneliner";
         description "AIS-L defect trigger";
         choice ais_l_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container rfi-l {
         junos:cli-feature "oneliner";
         description "RFI-L defect trigger";
         choice rfi_l_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ber-sd {
         description "BER-SD defect trigger";
         uses apply-advanced;
         choice ber_sd_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ber-sf {
         description "BER-SF defect trigger";
         uses apply-advanced;
         choice ber_sf_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ais-p {
         junos:cli-feature "oneliner";
         description "AIS-P defect trigger";
         choice ais_p_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lop-p {
         junos:cli-feature "oneliner";
         description "LOP-P defect trigger";
         choice lop_p_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container rfi-p {
         junos:cli-feature "oneliner";
         description "RFI-P defect trigger";
         choice rfi_p_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container uneq-p {
         junos:cli-feature "oneliner";
         description "UNEQ-P defect trigger";
         choice uneq_p_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container plm-p {
         junos:cli-feature "oneliner";
         description "PLM-P defect trigger";
         choice plm_p_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container locd {
         junos:cli-feature "oneliner";
         description "LOCD defect trigger (ATM only)";
         choice locd_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lcdp {
         junos:cli-feature "oneliner";
         description "LCD-P defect trigger (Ethernet WAN only)";
         choice lcdp_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
     }
     container aps {
       description "Automatic Protection Switching";
       uses aps_type;
     }
     choice payload_scrambler_choices {
       case case_1 {
         container payload-scrambler {
           presence "enable payload-scrambler";
           junos:cli-feature "oneliner";
           description "Enable payload scrambling";
           choice payload-choice {
           }
         }
       }
       case case_2 {
         leaf no-payload-scrambler {
           description "Do not enable payload scrambling";
           type empty;
         }
       }
     }
     choice z0-increment-choice {
       leaf z0-increment {
         description "Increment Z0 in SDH mode";
         type empty;
       }
       leaf no-z0-increment {
         description "Don't increment Z0 in SDH mode";
         type empty;
       }
     }
     choice loop-timing-choice {
       leaf loop-timing {
         description "Set loop timing for STM-1";
         type empty;
       }
       leaf no-loop-timing {
         description "Don't set loop timing for STM-1";
         type empty;
       }
     }
     container bytes {
       description "Set SONET header bytes";
       uses apply-advanced;
       leaf e1-quiet {
         description "E1-quiet value";
         type union {
           type string {
             pattern "<.*>|$.*";
           }
           type uint32 {
             range "0 .. 255";
           }
         }
       }
       leaf f1 {
         description "F1 user value";
         type union {
           type string {
             pattern "<.*>|$.*";
           }
           type uint32 {
             range "0 .. 255";
           }
         }
       }
       leaf f2 {
         description "F2 user value";
         type union {
           type string {
             pattern "<.*>|$.*";
           }
           type uint32 {
             range "0 .. 255";
           }
         }
       }
       leaf s1 {
         description "S1/Z1 value (stratum clock by convention)";
         type union {
           type string {
             pattern "<.*>|$.*";
           }
           type uint32 {
             range "0 .. 255";
           }
         }
       }
       leaf z3 {
         description "Z3 user value";
         type union {
           type string {
             pattern "<.*>|$.*";
           }
           type uint32 {
             range "0 .. 255";
           }
         }
       }
       leaf z4 {
         description "Z4 user value";
         type union {
           type string {
             pattern "<.*>|$.*";
           }
           type uint32 {
             range "0 .. 255";
           }
         }
       }
       leaf c2 {
         description "C2 user value";
         type union {
           type string {
             pattern "<.*>|$.*";
           }
           type uint32 {
             range "0 .. 255";
           }
         }
       }
     }
     leaf rfc-2615 {
       description "RFC 2615 compliance";
       type empty;
     }
     leaf aggregate {
       description "Join a SONET aggregate";
       type union {
         type jt:interface-device;
         type string {
           pattern "<.*>|$.*";
         }
       }
     }
     container mpls {
       description "MPLS options";
       uses mpls_ifd_options;
     }
   }
   grouping springte_lsp_nh_obj {
     uses apply-advanced;
     leaf nexthop {
       description "SPRING-TE LSP to use to reach destination";
       junos:cli-feature "nokeyword";
       type string {
         length "1 .. 128";
       }
     }
     container lsp-source {
       description "Source of tunnel creation";
       uses apply-advanced;
       choice lsp-src-choice {
         case case_1 {
           leaf pcep {
             description "Path computation element protocol";
             type empty;
           }
         }
         case case_2 {
           leaf static {
             description "Static configuration";
             type empty;
           }
         }
         case case_3 {
           leaf dtm {
             description "Dynamic tunnel module";
             type empty;
           }
         }
         case case_4 {
           leaf bgp {
             description "BGP SRTE";
             type empty;
           }
         }
       }
     }
   }
   grouping three-color-policer-type {
     description "Three-color policer";
     leaf name {
       description "Policer name";
       junos:cli-feature "nokeyword";
       type string {
         junos:posix-pattern "!^((__.*)|(.{65,}))$";
         junos:pattern-message "Must be a non-reserved string of 64 characters or less";
       }
     }
     uses apply-advanced;
     leaf filter-specific {
       description "Three color policer is filter-specific";
       junos:must "(!(\".. loss-priority\"))";
       junos:must-message "cannot support three-color-policer action if loss-priority is configured";
       type empty;
     }
     leaf logical-interface-policer {
       description "Policer is logical interface policer";
       junos:must "(!(\".. loss-priority\"))";
       junos:must-message "cannot support three-color-policer action if loss-priority is configured";
       type empty;
     }
     leaf physical-interface-policer {
       description "Policer is physical interface policer";
       type empty;
     }
     container action {
       junos:must "(!(\".. loss-priority\"))";
       junos:must-message "cannot support three-color-policer action if loss-priority is configured";
       description "Action for three-color policer";
       uses apply-advanced;
       list loss-priority {
         key name;
         ordered-by user;
         description "Loss priority for packet";
         uses three-color-policer-action;
         junos:cli-feature "oneliner";
       }
     }
     choice rate-type-choice {
       case case_1 {
         container single-rate {
           description "Single-rate policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-rate {
             description "Bandwidth allowed for committed traffic";
             units "bits per second";
             type string;
           }
           leaf committed-burst-size {
             description "Burst size allowed for committed traffic";
             units "bytes";
             type string;
           }
           leaf excess-burst-size {
             description "Burst size allowed for excess traffic";
             units "bytes";
             type string;
           }
         }
       }
       case case_2 {
         container single-packet-rate {
           presence "enable single-packet-rate";
           description "Single-rate packet policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-pps {
             description "PPS allowed for committed traffic";
             units "packets per second";
             type string;
           }
           leaf committed-packet-burst {
             description "Packet burst allowed for committed traffic";
             units "packets";
             type string;
           }
           leaf excess-packet-burst {
             description "Packet burst allowed for excess traffic";
             units "packets";
             type string;
           }
         }
       }
       case case_3 {
         container two-rate {
           presence "enable two-rate";
           description "Two-rate policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-rate {
             description "Bandwidth allowed for committed traffic";
             units "bits per second";
             type string;
           }
           leaf committed-burst-size {
             description "Burst size allowed for committed traffic  ";
             units "bytes";
             type string;
           }
           leaf peak-information-rate {
             description "Bandwidth allowed for peak traffic";
             units "bits per second";
             type string;
           }
           leaf peak-burst-size {
             description "Burst size allowed for peak traffic  ";
             units "bytes";
             type string;
           }
           container aggregate-policing {
             presence "enable aggregate-policing";
             description "Configure Aggregate Policer";
             uses apply-advanced;
             list policer {
               key name;
               ordered-by user;
               description "Two-color policer to be used as aggregate";
               max-elements 1;
               leaf name {
                 description "Name of two-color policer to use to aggregate police";
                 junos:cli-feature "nokeyword";
                 junos:must "(\"firewall policer $$\")";
                 junos:must-message "Referenced aggregate policer is not defined";
                 type string;
               }
               uses apply-advanced;
               leaf aggregate-sharing-mode {
                 description "Hierarchical Metering model";
                 type enumeration {
                   enum "hybrid" {
                     description "Child policer CIR rates are guaranteed rates and PIR rate are peak rates for member flow";
                   }
                 }
               }
             }
           }
         }
       }
       case case_4 {
         container two-packet-rate {
           presence "enable two-packet-rate";
           description "Two-rate packet policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-pps {
             description "PPS allowed for committed traffic";
             units "packets per second";
             type string;
           }
           leaf committed-packet-burst {
             description "Packet burst allowed for committed traffic  ";
             units "packets";
             type string;
           }
           leaf peak-information-pps {
             description "PPS allowed for peak traffic";
             units "packets per second";
             type string;
           }
           leaf peak-packet-burst {
             description "Packet burst allowed for peak traffic  ";
             units "packets";
             type string;
           }
         }
       }
     }
   }
   grouping three-color-policer-action {
     junos:cli-feature "oneliner";
     description "Action for three-color policer";
     leaf name {
       description "Loss priority for packet";
       junos:cli-feature "nokeyword";
       type enumeration {
         enum "high" {
           description "High loss priority";
         }
       }
     }
     uses apply-advanced;
     container then {
       junos:cli-feature "oneliner-plus";
       description "Action to take if the rate limits are exceeded";
       uses apply-advanced;
       leaf discard {
         description "Discard the packet";
         type empty;
       }
     }
   }
   grouping to_fabric_object {
     description "Match traffic going to fabric";
     uses apply-advanced;
     leaf except {
       description "Match traffic switched locally and not going to fabric";
       type empty;
     }
   }
   grouping tunnel_end_point {
     description "Define a tunnel end point";
     leaf name {
       description "Tunnel end-point identifier (ASCII string)";
       junos:cli-feature "nokeyword";
       type string {
         junos:posix-pattern "!^((__.*)|(.{65,}))$";
         junos:pattern-message "Must be a non-reserved string of 64 characters or less";
       }
     }
     uses apply-advanced;
     choice l3-protocol {
       case case_1 {
         container ipv6 {
           presence "enable ipv6";
           description "Enter an IPv6 tunnel";
           uses apply-advanced;
           leaf source-address {
             description "Tunnel source address";
             type jt:ipv6addr;
           }
           leaf destination-address {
             description "Tunnel destination address";
             type jt:ipv6prefix;
           }
         }
       }
       case case_2 {
         container ipv4 {
           presence "enable ipv4";
           description "Enter an IPv4 tunnel";
           uses apply-advanced;
           leaf source-address {
             description "Tunnel source address";
             type jt:ipv4addr;
           }
           leaf destination-address {
             description "Tunnel destination address";
             type jt:ipv4prefix;
           }
         }
       }
     }
     choice tunnel-protocol {
       case case_1 {
         container gre {
           presence "enable gre";
           description "Tunnel is GRE";
           uses apply-advanced;
           leaf key {
             description "Key for authentication";
             type union {
               type uint32;
               type string {
                 pattern "<.*>|$.*";
               }
             }
           }
         }
       }
       case case_2 {
         container gre-in-udp {
           presence "enable gre-in-udp";
           description "Tunnel is GRE-in-UDP";
           uses apply-advanced;
           leaf source-port {
             description "UDP source port";
             type union {
               type string {
                 pattern "<.*>|$.*";
               }
               type uint32 {
                 range "0 .. 65535";
               }
             }
           }
           leaf destination-port {
             description "UDP destination port";
             type union {
               type string {
                 pattern "<.*>|$.*";
               }
               type uint32 {
                 range "0 .. 65535";
               }
             }
           }
           leaf key {
             description "GRE key for authentication";
             type union {
               type uint32;
               type string {
                 pattern "<.*>|$.*";
               }
             }
           }
         }
       }
     }
   }
   grouping vlan_map {
     junos:cli-feature "oneliner-plus";
     description "IEEE 802.1q Virtual LAN (VLAN) Tag mapping";
     uses apply-advanced;
     choice operation_choices {
       case case_1 {
         leaf push {
           description "Push a VLAN tag";
           type empty;
         }
       }
       case case_2 {
         leaf swap {
           description "Swap a VLAN tag";
           type empty;
         }
       }
       case case_3 {
         leaf pop {
           description "Pop a VLAN tag";
           type empty;
         }
       }
       case case_4 {
         leaf push-push {
           description "Push two VLAN tags";
           type empty;
         }
       }
       case case_5 {
         leaf swap-push {
           description "Swap VLAN tag and push a new VLAN tag";
           type empty;
         }
       }
       case case_6 {
         leaf swap-swap {
           description "Swap both outer and inner VLAN tags";
           type empty;
         }
       }
       case case_7 {
         leaf pop-swap {
           description "Pop outer VLAN tag and swap inner VLAN tag";
           type empty;
         }
       }
       case case_8 {
         leaf pop-pop {
           description "Pop both outer and inner VLAN tags";
           type empty;
         }
       }
     }
     leaf tag-protocol-id {
       description "IEEE 802.1q Tag Protocol Identifier to rewrite";
       type string;
     }
     leaf inner-tag-protocol-id {
       description "IEEE 802.1q Tag Protocol ID to rewrite for inner tag";
       type string;
     }
     leaf vlan-id {
       description "VLAN ID to rewrite";
       type string;
     }
     leaf inner-vlan-id {
       description "VLAN ID to rewrite for inner tag";
       type string;
     }
   }
   grouping vpls_filter {
     description "Define an VPLS firewall filter";
     leaf name {
       description "Filter name";
       junos:cli-feature "nokeyword";
       type string {
         junos:posix-pattern "!^((__.*)|(.{65,}))$";
         junos:pattern-message "Must be a non-reserved string of 64 characters or less";
       }
     }
     uses apply-advanced;
     leaf-list accounting-profile {
       ordered-by user;
       description "Accounting profile name";
       junos:must "(\"accounting-options filter-profile\")";
       junos:must-message "referenced accounting profile must be defined";
       type string;
     }
     leaf interface-specific {
       description "Defined counters are interface specific";
       type empty;
     }
     leaf transient-filter {
       description "Transient filter to be used for filter modification";
       type string;
     }
     leaf physical-interface-filter {
       description "Filter is physical interface filter";
       type empty;
     }
     list term {
       key name;
       ordered-by user;
       description "Define a firewall term";
       leaf name {
         description "Term name";
         junos:cli-feature "nokeyword";
         type string {
           junos:posix-pattern "!^((__.*)|(.{65,}))$";
           junos:pattern-message "Must be a non-reserved string of 64 characters or less";
         }
       }
       uses apply-advanced;
       leaf filter {
         description "Filter to include";
         junos:must "(\"firewall family vpls filter $$\")";
         junos:must-message "Referenced filter is not defined";
         junos:must "((!(\".. from\") && !(\".. then\")))";
         junos:must-message "Not compatible with 'from or then'";
         type string {
           junos:posix-pattern "!^((__.*)|(.{65,}))$";
           junos:pattern-message "Must be a non-reserved string of 64 characters or less";
         }
       }
       container from {
         description "Define match criteria";
         uses apply-advanced;
         choice interface-group_choice {
           case case_1 {
             leaf-list interface-group {
               ordered-by user;
               description "Range of values";
               type string;
             }
           }
           case case_2 {
           }
         }
         choice ether-type_choice {
           case case_1 {
             leaf-list ether-type {
               ordered-by user;
               type string;
             }
           }
           case case_2 {
             leaf-list ether-type-except {
               ordered-by user;
               type string;
             }
           }
         }
         choice vlan-ether-type_choice {
           case case_1 {
             leaf-list vlan-ether-type {
               ordered-by user;
               type string;
             }
           }
           case case_2 {
           }
         }
         list destination-mac-address {
           key name;
           ordered-by user;
           description "Destination MAC address";
           uses firewall_mac_addr_object;
           junos:cli-feature "homogeneous";
           junos:cli-feature "oneliner";
         }
         list source-mac-address {
           key name;
           ordered-by user;
           description "Source MAC address";
           uses firewall_mac_addr_object;
           junos:cli-feature "homogeneous";
           junos:cli-feature "oneliner";
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice loss-priority_choice {
           case case_1 {
           }
           case case_2 {
           }
         }
         choice learn-vlan-id_choice {
           case case_1 {
             leaf-list learn-vlan-id {
               ordered-by user;
               description "Learn-vlan-id range (0..4095)";
               type string {
                 junos:posix-pattern "^([0-9]{1,3}|[1-3][0-9][0-9][0-9]|40[0-8][0-9]|409[0-5])(-([0-9]{1,3}|[1-3][0-9][0-9][0-9]|40[0-8][0-9]|409[0-5]))?$";
                 junos:pattern-message "Must be a numerical value or range between 0-4095";
               }
             }
           }
           case case_2 {
             leaf-list learn-vlan-id-except {
               ordered-by user;
               description "Learn-vlan-id range (0..4095)";
               type string {
                 junos:posix-pattern "^([0-9]{1,3}|[1-3][0-9][0-9][0-9]|40[0-8][0-9]|409[0-5])(-([0-9]{1,3}|[1-3][0-9][0-9][0-9]|40[0-8][0-9]|409[0-5]))?$";
                 junos:pattern-message "Must be a numerical value or range between 0-4095";
               }
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice user-vlan-id_choice {
           case case_1 {
             leaf-list user-vlan-id {
               ordered-by user;
               description "User-vlan-id range (0..4095)";
               type string {
                 junos:posix-pattern "^([0-9]{1,3}|[1-3][0-9][0-9][0-9]|40[0-8][0-9]|409[0-5])(-([0-9]{1,3}|[1-3][0-9][0-9][0-9]|40[0-8][0-9]|409[0-5]))?$";
                 junos:pattern-message "Must be a numerical value or range between 0-4095";
               }
             }
           }
           case case_2 {
             leaf-list user-vlan-id-except {
               ordered-by user;
               description "User-vlan-id range (0..4095)";
               type string {
                 junos:posix-pattern "^([0-9]{1,3}|[1-3][0-9][0-9][0-9]|40[0-8][0-9]|409[0-5])(-([0-9]{1,3}|[1-3][0-9][0-9][0-9]|40[0-8][0-9]|409[0-5]))?$";
                 junos:pattern-message "Must be a numerical value or range between 0-4095";
               }
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         choice learn-vlan-dei_choice {
           case case_1 {
             leaf-list learn-vlan-dei {
               ordered-by user;
               description "DEI value 0-1";
               type union {
                 type string {
                   pattern "<.*>|$.*";
                 }
                 type uint32 {
                   range "0 .. 1";
                 }
               }
             }
           }
           case case_2 {
             leaf-list learn-vlan-dei-except {
               ordered-by user;
               description "DEI value 0-1";
               type union {
                 type string {
                   pattern "<.*>|$.*";
                 }
                 type uint32 {
                   range "0 .. 1";
                 }
               }
             }
           }
         }
         choice traffic-type_choice {
           case case_1 {
           }
           case case_2 {
           }
         }
         list ip-source-address {
           key name;
           ordered-by user;
           description "Match IP source address";
           uses firewall_addr_object;
           junos:cli-feature "homogeneous";
           junos:cli-feature "oneliner";
         }
         list ip-destination-address {
           key name;
           ordered-by user;
           description "Match IP destination address";
           uses firewall_addr_object;
           junos:cli-feature "homogeneous";
           junos:cli-feature "oneliner";
         }
         choice ip-protocol_choice {
           case case_1 {
             leaf-list ip-protocol {
               ordered-by user;
               type string;
             }
           }
           case case_2 {
             leaf-list ip-protocol-except {
               ordered-by user;
               type string;
             }
           }
         }
         choice dscp_choice {
           case case_1 {
             leaf-list dscp {
               ordered-by user;
               type string;
             }
           }
           case case_2 {
             leaf-list dscp-except {
               ordered-by user;
               type string;
             }
           }
         }
         choice ip-precedence_choice {
           case case_1 {
             leaf-list ip-precedence {
               ordered-by user;
               type string;
             }
           }
           case case_2 {
             leaf-list ip-precedence-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
           }
           case case_2 {
           }
         }
         choice icmp-code_choice {
           case case_1 {
             leaf-list icmp-code {
               ordered-by user;
               type string;
             }
           }
           case case_2 {
             leaf-list icmp-code-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         list interface {
           key name;
           ordered-by user;
           description "Match interface name";
           uses match_interface_object;
           junos:cli-feature "oneliner";
         }
         list interface-set {
           key name;
           ordered-by user;
           description "Match interface in set";
           uses match_interface_set_object;
           junos:cli-feature "oneliner";
         }
         list source-prefix-list {
           key name;
           ordered-by user;
           description "Match IP source prefixes in named list";
           uses firewall_prefix_list;
           junos:cli-feature "homogeneous";
           junos:cli-feature "oneliner";
         }
         list destination-prefix-list {
           key name;
           ordered-by user;
           description "Match IP destination prefixes in named list";
           uses firewall_prefix_list;
           junos:cli-feature "homogeneous";
           junos:cli-feature "oneliner";
         }
         list prefix-list {
           key name;
           ordered-by user;
           description "Match IP source or destination prefixes in named list";
           uses firewall_prefix_list;
           junos:cli-feature "homogeneous";
           junos:cli-feature "oneliner";
         }
         choice ipv6-next-header_choice {
           case case_1 {
           }
           case case_2 {
           }
         }
         choice ipv6-payload-protocol_choice {
           case case_1 {
           }
           case case_2 {
           }
         }
         choice ipv6-traffic-class_choice {
           case case_1 {
           }
           case case_2 {
           }
         }
         choice flex-mask_choice {
           case case_1 {
             container flexible-match-mask {
               description "Match flexible mask";
               presence "enable flexible-match-mask";
               uses match_L2_flexible_mask;
             }
           }
         }
         choice flex-range_choice {
           case case_1 {
             container flexible-match-range {
               description "Match flexible range";
               presence "enable flexible-match-range";
               junos:must "(!(\".. flexible-match-ranges\"))";
               junos:must-message "'flexible-match-range' and 'flexible-match-ranges' are mutually exclusive";
               uses match_L2_flexible_range;
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
       }
       container then {
         junos:cli-feature "oneliner-plus";
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               junos:must "(!(\".. loss-priority\"))";
               junos:must-message "cannot support three-color-policer action if loss-priority is configured";
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
           }
           case case_4 {
           }
           case case_5 {
             leaf policer-charge {
               description "Name of policer-charge used to charge the policer";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         leaf count {
           description "Count the packet in the named counter";
           type string {
             junos:posix-pattern "!^((__.*)|(.{65,}))$";
             junos:pattern-message "Must be a non-reserved string of 64 characters or less";
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
             junos:posix-pattern "^.{1,64}$";
             junos:pattern-message "Must be string of 64 characters or less";
           }
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           junos:must "(\"forwarding-options port-mirroring\")";
           junos:must-message "Configure 'port-mirroring' under 'forwarding-options'";
           type empty;
         }
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf log {
           description "Log the packet";
           type empty;
         }
         leaf syslog {
           description "System log (syslog) information about the packet";
           type empty;
         }
       }
     }
   }
   grouping vrrp-group {
     description "Virtual Router Redundancy Protocol group";
     leaf name {
       description "Identifier for VRRP group";
       junos:cli-feature "nokeyword";
       type union {
         type string {
           pattern "<.*>|$.*";
         }
         type uint32 {
           range "0 .. 255";
         }
       }
     }
     uses apply-advanced;
     choice address {
       case case_1 {
         leaf-list virtual-address {
           ordered-by user;
           description "One or more virtual IPv4 addresses";
           type jt:ipv4addr;
         }
       }
       case case_2 {
         leaf-list virtual-inet6-address {
           ordered-by user;
           description "One or more virtual inet6 addresses";
           type jt:ipv6addr;
         }
       }
     }
     leaf virtual-link-local-address {
       description "Virtual link-local addresses";
       junos:must "(\".. .. vrrp-inet6-group\")";
       junos:must-message "'virtual-link-local-address' statement can be included only for interfaces of type 'family inet6'";
       type jt:ipv6addr;
     }
     leaf priority {
       description "Virtual router election priority";
       type union {
         type string {
           pattern "<.*>|$.*";
         }
         type uint32 {
           range "0 .. 255";
         }
       }
     }
     leaf preferred {
       description "Preferred group on subnet";
       type empty;
     }
     choice advertisement_type {
       case case_1 {
         leaf advertise-interval {
           description "Advertisement interval";
           units "seconds";
           type union {
             type string {
               pattern "<.*>|$.*";
             }
             type uint32 {
               range "1 .. 255";
             }
           }
         }
       }
       case case_2 {
         leaf fast-interval {
           description "Fast advertisement interval";
           units "milliseconds";
           type union {
             type string {
               pattern "<.*>|$.*";
             }
             type uint32 {
               range "10 .. 40950";
             }
           }
         }
       }
       case case_3 {
         leaf inet6-advertise-interval {
           description "Inet6 advertisement interval";
           units "milliseconds";
           type union {
             type string {
               pattern "<.*>|$.*";
             }
             type uint32 {
               range "100 .. 40000";
             }
           }
         }
       }
     }
     choice preempt_type {
       case case_1 {
         container preempt {
           presence "enable preempt";
           description "Allow preemption";
           uses apply-advanced;
           leaf hold-time {
             description "Preemption hold time";
             units "seconds";
             type union {
               type string {
                 pattern "<.*>|$.*";
               }
               type uint32 {
                 range "0 .. 3600";
               }
             }
           }
         }
       }
       case case_2 {
         leaf no-preempt {
           description "Don't allow preemption";
           type empty;
         }
       }
     }
     choice accept_type {
       case case_1 {
         leaf accept-data {
           description "Accept packets destined for virtual IP address";
           type empty;
         }
       }
       case case_2 {
         leaf no-accept-data {
           description "Don't accept packets destined for virtual IP address";
           type empty;
         }
       }
     }
     leaf authentication-type {
       description "Authentication type";
       junos:must "(\".. .. vrrp-group\")";
       junos:must-message "'authentication-type' statement can be included only for interfaces of type 'family inet'";
       type enumeration {
         enum "md5" {
           description "HMAC-MD5-96";
         }
         enum "simple" {
           description "Simple password";
         }
       }
     }
     leaf authentication-key {
       description "Authentication key";
       junos:must "(\".. .. vrrp-group\")";
       junos:must-message "'authentication-key' statement can be included only for interfaces of type 'family inet'";
       type jt:unreadable;
     }
     container track {
       description "Interfaces to track for VRRP group";
       uses apply-advanced;
       leaf priority-hold-time {
         description "Priority hold time";
         units "seconds";
         type union {
           type string {
             pattern "<.*>|$.*";
           }
           type uint32 {
             range "0 .. 3600";
           }
         }
       }
       list interface {
         key name;
         ordered-by user;
         description "Interface to track in VRRP group";
         leaf name {
           description "Name of interface";
           junos:cli-feature "nokeyword";
           type union {
             type jt:interface-unit;
             type string {
               pattern "<.*>|$.*";
             }
           }
         }
         uses apply-advanced;
         list bandwidth-threshold {
           key name;
           junos:cli-feature "oneliner";
           description "Track bandwidth of interface";
           leaf name {
             description "Interface speed below which priority cost is incurred";
             junos:cli-feature "nokeyword";
             units "bits per second";
             type string;
           }
           leaf priority-cost {
             description "Value subtracted from priority when bandwidth is below threshold";
             type union {
               type string {
                 pattern "<.*>|$.*";
               }
               type uint32 {
                 range "1 .. 254";
               }
             }
           }
         }
         leaf priority-cost {
           description "Value to subtract from priority when interface is down";
           type union {
             type string {
               pattern "<.*>|$.*";
             }
             type uint32 {
               range "1 .. 254";
             }
           }
         }
       }
       list route {
         key "route_address routing-instance";
         ordered-by user;
         junos:cli-feature "oneliner";
         description "Route to track in VRRP group";
         leaf route_address {
           description "Route address";
           junos:cli-feature "nokeyword";
           type jt:ipprefix-mandatory;
         }
         leaf routing-instance {
           description "Routing instance to which route belongs, or 'default'";
           type string {
             junos:posix-pattern "!^((__.*__)|(all)|(.*[ ].*)|(\"\")|(.{129,}))$";
             junos:pattern-message "Must be a non-reserved string of 128 characters or less with no spaces.";
           }
         }
         leaf priority-cost {
           description "Value to subtract from priority when route is down";
           type union {
             type string {
               pattern "<.*>|$.*";
             }
             type uint32 {
               range "1 .. 254";
             }
           }
         }
       }
     }
     container vrrp-inherit-from {
       description "VRRP group to follow for this VRRP group";
       uses apply-advanced;
       leaf active-interface {
         description "Interface name of VRRP active group";
         type union {
           type jt:interface-unit;
           type string {
             pattern "<.*>|$.*";
           }
         }
       }
       leaf active-group {
         description "Identifier for VRRP active group";
         type union {
           type string {
             pattern "<.*>|$.*";
           }
           type uint32 {
             range "0 .. 255";
           }
         }
       }
     }
     leaf advertisements-threshold {
       description "Number of vrrp advertisements missed before declaring master down";
       type union {
         type string {
           pattern "<.*>|$.*";
         }
         type uint32 {
           range "1 .. 15";
         }
       }
     }
   }
 }
