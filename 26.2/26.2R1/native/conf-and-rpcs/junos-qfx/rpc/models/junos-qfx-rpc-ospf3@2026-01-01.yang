/*
 * Copyright (c) 2026 Juniper Networks, Inc.
 * All rights reserved.
 */
 module junos-qfx-rpc-ospf3 {
   namespace "http://yang.juniper.net/junos-qfx/rpc/ospf3";

   prefix ospf3;

   import junos-common-types {
     prefix jt;
     revision-date 2026-01-01;
   }

   organization "Juniper Networks, Inc.";

   contact "yang-support@juniper.net";

   description "Junos RPC YANG module for ospf3 command(s)";

   revision 2026-01-01 {
     description "Junos: 26.2R1.7";
   }

   rpc get-ospf3-overview-information {
     description "Show overview of OSPFv3 information";
     input {
       choice daemon-select {
         case logical-system {
           leaf logical-system {
             description "Name of logical system, or 'all'";
             type string {
             }
           }
         }
       }
       leaf verbosity_level {
         default "brief";
         type enumeration {
           enum "brief" {
             description "Display brief output (default)";
           }
           enum "extensive" {
             description "Display extensive output";
           }
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output-tags {
         case actual-tag {
           container ospf3-overview-information {
             uses ospf3-overview-information-block;
           }
         }
         case multichassis-tag {
           container multi-routing-engine-results {
             list multi-routing-engine-item {
               leaf re-name {
                 type string;
               }
               choice output-tags {
                 case actual-tag {
                   container ospf3-overview-information {
                     uses ospf3-overview-information-block;
                   }
                 }
               }
             }
           }
         }
       }
     }
   }
   rpc get-ospf3-database-information {
     description "Show OSPFv3 link-state database";
     input {
       choice daemon-select {
         case logical-system {
           leaf logical-system {
             description "Name of logical system, or 'all'";
             type string {
             }
           }
         }
       }
       leaf level {
         default "brief";
         type enumeration {
           enum "brief" {
             description "Display brief output (default)";
           }
           enum "detail" {
             description "Display detailed output";
           }
           enum "extensive" {
             description "Display extensive output";
           }
           enum "summary" {
             description "Display summary output";
           }
         }
       }
       leaf lsa-type {
         type enumeration {
           enum "router" {
             description "Router LSAs";
           }
           enum "network" {
             description "Network LSAs";
           }
           enum "inter-area-prefix" {
             description "Inter-area-prefix LSAs";
           }
           enum "inter-area-router" {
             description "Inter-area-router LSAs";
           }
           enum "external" {
             description "External LSAs";
           }
           enum "nssa" {
             description "NSSA LSAs";
           }
           enum "link" {
             description "Link LSAs";
           }
           enum "link-local" {
             description "Link-local LSAs";
           }
           enum "intra-area-prefix" {
             description "Intra-area-prefix LSAs";
           }
         }
       }
       leaf area {
         description "Area ID of OSPFv3 area";
         default "all";
         type string;
       }
       leaf lsa-id {
         description "ID of link-state advertisement";
         default "all";
         type string;
       }
       leaf advertising-router {
         description "Router ID of advertising router";
         type string;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output-tags {
         case actual-tag {
           container ospf3-database-information {
             uses ospf3-database-information-block;
           }
         }
         case multichassis-tag {
           container multi-routing-engine-results {
             list multi-routing-engine-item {
               leaf re-name {
                 type string;
               }
               choice output-tags {
                 case actual-tag {
                   container ospf3-database-information {
                     uses ospf3-database-information-block;
                   }
                 }
               }
             }
           }
         }
       }
     }
   }
   rpc get-ospf3-backup-spf-information {
     description "Show OSPFv3 backup SPF calculations information";
     input {
       choice daemon-select {
         case logical-system {
           leaf logical-system {
             description "Name of logical system, or 'all'";
             type string {
             }
           }
         }
       }
       leaf instance {
         description "Name of OSPF instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
       leaf area {
         description "OSPF area ID";
         type jt:areaid;
       }
       leaf no-coverage {
         description "Entries with no backup coverage";
         type empty;
       }
       leaf node-id {
         description "Display nodes matching the node-id";
         type string;
       }
       leaf verbosity_level {
         default "brief";
         type enumeration {
           enum "brief" {
             description "Display brief output (default)";
           }
           enum "detail" {
             description "Display detailed output";
           }
         }
       }
     }
     output {
       choice output-tags {
         case actual-tag {
           container ospf3-backup-spf-information {
             uses ospf3-backup-spf-information-block;
           }
         }
         case multichassis-tag {
           container multi-routing-engine-results {
             list multi-routing-engine-item {
               leaf re-name {
                 type string;
               }
               choice output-tags {
                 case actual-tag {
                   container ospf3-backup-spf-information {
                     uses ospf3-backup-spf-information-block;
                   }
                 }
               }
             }
           }
         }
       }
     }
   }
   rpc get-ospf3-backup-coverage-information {
     description "Show OSPFv3 backup coverage";
     input {
       choice daemon-select {
         case logical-system {
           leaf logical-system {
             description "Name of logical system, or 'all'";
             type string {
             }
           }
         }
       }
       leaf instance {
         description "Name of OSPF instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output-tags {
         case actual-tag {
           container ospf3-backup-coverage-information {
             uses ospf3-backup-coverage-information-block;
           }
         }
         case multichassis-tag {
           container multi-routing-engine-results {
             list multi-routing-engine-item {
               leaf re-name {
                 type string;
               }
               choice output-tags {
                 case actual-tag {
                   container ospf3-backup-coverage-information {
                     uses ospf3-backup-coverage-information-block;
                   }
                 }
               }
             }
           }
         }
       }
     }
   }
   rpc get-ospf3-backup-neighbor-information {
     description "Show OSPFv3 backup neighbors";
     input {
       choice daemon-select {
         case logical-system {
           leaf logical-system {
             description "Name of logical system, or 'all'";
             type string {
             }
           }
         }
       }
       leaf instance {
         description "Name of OSPF instance";
         type string;
       }
       leaf area {
         description "OSPF area ID";
         type jt:areaid;
       }
     }
     output {
       choice output-tags {
         case actual-tag {
           container ospf3-backup-neighbor-information {
             uses ospf3-backup-neighbor-information-block;
           }
         }
         case multichassis-tag {
           container multi-routing-engine-results {
             list multi-routing-engine-item {
               leaf re-name {
                 type string;
               }
               choice output-tags {
                 case actual-tag {
                   container ospf3-backup-neighbor-information {
                     uses ospf3-backup-neighbor-information-block;
                   }
                 }
               }
             }
           }
         }
       }
     }
   }
   rpc get-ospf3-backup-lsp-information {
     description "Show OSPFv3 MPLS backup LSP information";
     input {
       choice daemon-select {
         case logical-system {
           leaf logical-system {
             description "Name of logical system, or 'all'";
             type string {
             }
           }
         }
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output-tags {
         case actual-tag {
           container ospf3-backup-mplsp-information {
             uses ospf3-backup-mplsp-information-block;
           }
         }
         case multichassis-tag {
           container multi-routing-engine-results {
             list multi-routing-engine-item {
               leaf re-name {
                 type string;
               }
               choice output-tags {
                 case actual-tag {
                   container ospf3-backup-mplsp-information {
                     uses ospf3-backup-mplsp-information-block;
                   }
                 }
               }
             }
           }
         }
       }
     }
   }
   rpc get-ospf3-interface-information {
     description "Show OSPFv3 interface status";
     input {
       choice daemon-select {
         case logical-system {
           leaf logical-system {
             description "Name of logical system, or 'all'";
             type string {
             }
           }
         }
       }
       leaf verbosity_level {
         default "brief";
         type enumeration {
           enum "brief" {
             description "Display brief output (default)";
           }
           enum "detail" {
             description "Display detailed output";
           }
           enum "extensive" {
             description "Display extensive output";
           }
         }
       }
       leaf interface-name {
         description "Name of logical interface";
         type string;
       }
       leaf area {
         description "OSPF area ID";
         type jt:areaid;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output-tags {
         case actual-tag {
           container ospf3-interface-information {
             uses ospf3-interface-information-block;
           }
         }
         case multichassis-tag {
           container multi-routing-engine-results {
             list multi-routing-engine-item {
               leaf re-name {
                 type string;
               }
               choice output-tags {
                 case actual-tag {
                   container ospf3-interface-information {
                     uses ospf3-interface-information-block;
                   }
                 }
               }
             }
           }
         }
       }
     }
   }
   rpc get-ospf3-neighbor-information {
     description "Show OSPFv3 neighbor status";
     input {
       choice daemon-select {
         case logical-system {
           leaf logical-system {
             description "Name of logical system, or 'all'";
             type string {
             }
           }
         }
       }
       leaf verbosity_level {
         default "brief";
         type enumeration {
           enum "brief" {
             description "Display brief output (default)";
           }
           enum "detail" {
             description "Display detailed output";
           }
           enum "extensive" {
             description "Display extensive output";
           }
         }
       }
       leaf interface {
         description "Name of logical interface";
         type string;
       }
       leaf area {
         description "OSPF area ID";
         type jt:areaid;
       }
       leaf neighbor {
         description "IP address or ID of neighbor";
         type string;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output-tags {
         case actual-tag-1 {
           container ospf-neighbor-information-logical-system-all {
             uses ospf-neighbor-information-logical-system-all-block;
           }
         }
         case actual-tag-2 {
           container ospf3-neighbor-information-all {
             uses ospf3-neighbor-information-all-block;
           }
         }
         case actual-tag-3 {
           container ospf3-neighbor-information {
             uses ospf3-neighbor-information-block;
           }
         }
         case multichassis-tag {
           container multi-routing-engine-results {
             list multi-routing-engine-item {
               leaf re-name {
                 type string;
               }
               choice output-tags {
                 case actual-tag-1 {
                   container ospf-neighbor-information-logical-system-all {
                     uses ospf-neighbor-information-logical-system-all-block;
                   }
                 }
                 case actual-tag-2 {
                   container ospf3-neighbor-information-all {
                     uses ospf3-neighbor-information-all-block;
                   }
                 }
                 case actual-tag-3 {
                   container ospf3-neighbor-information {
                     uses ospf3-neighbor-information-block;
                   }
                 }
               }
             }
           }
         }
       }
     }
   }
   rpc get-ospf3-route-information {
     description "Show the OSPFv3 routing table";
     input {
       choice daemon-select {
         case logical-system {
           leaf logical-system {
             description "Name of logical system, or 'all'";
             type string {
             }
           }
         }
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
       leaf path-type {
         description "OSPF path type";
         type enumeration {
           enum "intra" {
             description "Display intra-area routes";
           }
           enum "inter" {
             description "Display inter-area routes";
           }
           enum "extern" {
             description "Display external routes";
           }
         }
       }
       leaf route-type {
         description "OSPF route type";
         type enumeration {
           enum "router" {
             description "Display routes to all routers";
           }
           enum "abr" {
             description "Display routes to area border routers";
           }
           enum "asbr" {
             description "Display routes to AS border routers";
           }
           enum "transit" {
             description "Display routes to pseudonodes";
           }
           enum "network" {
             description "Display routes to networks";
           }
         }
       }
       leaf no-backup-coverage {
         description "Display routes with no backup coverage";
         type empty;
       }
       leaf destination {
         description "Address and optional prefix length of destination";
         type jt:ipprefix;
       }
       leaf verbosity_level {
         default "brief";
         type enumeration {
           enum "brief" {
             description "Display brief output (default)";
           }
           enum "detail" {
             description "Display detailed output";
           }
           enum "extensive" {
             description "Display extensive output";
           }
         }
       }
       leaf instance {
         description "Name of OSPFv3 instance";
         type string;
       }
     }
     output {
       choice output-tags {
         case actual-tag {
           container ospf3-route-information {
             uses ospf3-route-information-block;
           }
         }
         case multichassis-tag {
           container multi-routing-engine-results {
             list multi-routing-engine-item {
               leaf re-name {
                 type string;
               }
               choice output-tags {
                 case actual-tag {
                   container ospf3-route-information {
                     uses ospf3-route-information-block;
                   }
                 }
               }
             }
           }
         }
       }
     }
   }
   rpc get-ospf3-statistics-information {
     description "Show OSPFv3 statistics";
     input {
       choice daemon-select {
         case logical-system {
           leaf logical-system {
             description "Name of logical system, or 'all'";
             type string {
             }
           }
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output-tags {
         case actual-tag {
           container ospf3-statistics-information {
             uses ospf3-statistics-information-block;
           }
         }
         case multichassis-tag {
           container multi-routing-engine-results {
             list multi-routing-engine-item {
               leaf re-name {
                 type string;
               }
               choice output-tags {
                 case actual-tag {
                   container ospf3-statistics-information {
                     uses ospf3-statistics-information-block;
                   }
                 }
               }
             }
           }
         }
       }
     }
   }
   rpc get-ospf3-intf-statistics-information {
     description "OSPFv3 interface statistics information";
     input {
       choice daemon-select {
         case logical-system {
           leaf logical-system {
             description "Name of logical system, or 'all'";
             type string {
             }
           }
         }
       }
       leaf instance {
         description "Name of OSPFv3 routing instance";
         type string;
       }
       leaf interface-name {
         description "Name of interface";
         type string;
       }
     }
     output {
       choice output-tags {
         case actual-tag {
           container ospf3-intf-statistics-information {
             uses ospf3-intf-statistics-information-block;
           }
         }
         case multichassis-tag {
           container multi-routing-engine-results {
             list multi-routing-engine-item {
               leaf re-name {
                 type string;
               }
               choice output-tags {
                 case actual-tag {
                   container ospf3-intf-statistics-information {
                     uses ospf3-intf-statistics-information-block;
                   }
                 }
               }
             }
           }
         }
       }
     }
   }
   rpc get-ospf3-io-statistics-information {
     description "Show OSPFv3 I/O statistics";
     input {
       choice daemon-select {
         case logical-system {
           leaf logical-system {
             description "Name of logical system, or 'all'";
             type string {
             }
           }
         }
       }
     }
     output {
       choice output-tags {
         case actual-tag {
           container ospf3-io-statistics-information {
             uses ospf3-io-statistics-information-block;
           }
         }
         case multichassis-tag {
           container multi-routing-engine-results {
             list multi-routing-engine-item {
               leaf re-name {
                 type string;
               }
               choice output-tags {
                 case actual-tag {
                   container ospf3-io-statistics-information {
                     uses ospf3-io-statistics-information-block;
                   }
                 }
               }
             }
           }
         }
       }
     }
   }
   rpc get-ospf3-log-information {
     description "Show OSPFv3 SPF log";
     input {
       choice daemon-select {
         case logical-system {
           leaf logical-system {
             description "Name of logical system, or 'all'";
             type string {
             }
           }
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output-tags {
         case actual-tag {
           container ospf3-log-information {
             uses ospf3-log-information-block;
           }
         }
         case multichassis-tag {
           container multi-routing-engine-results {
             list multi-routing-engine-item {
               leaf re-name {
                 type string;
               }
               choice output-tags {
                 case actual-tag {
                   container ospf3-log-information {
                     uses ospf3-log-information-block;
                   }
                 }
               }
             }
           }
         }
       }
     }
   }
   rpc get-ospf3-bgporr-information {
     description "Show BGP optimal route-reflection groups";
     input {
       choice daemon-select {
         case logical-system {
           leaf logical-system {
             description "Name of logical system, or 'all'";
             type string {
             }
           }
         }
       }
       leaf group {
         description "BGP optimal route-reflection peer group name";
         type string;
       }
       leaf topology {
         description "Name of topology";
         type string;
       }
       leaf path-type {
         description "OSPF path type";
         type enumeration {
           enum "intra" {
             description "Display intra-area routes";
           }
           enum "inter" {
             description "Display inter-area routes";
           }
           enum "extern" {
             description "Display external routes";
           }
         }
       }
       leaf route-type {
         description "OSPF route type";
         type enumeration {
           enum "router" {
             description "Display routes to all routers";
           }
           enum "abr" {
             description "Display routes to area border routers";
           }
           enum "asbr" {
             description "Display routes to AS border routers";
           }
           enum "transit" {
             description "Display routes to pseudonodes";
           }
           enum "network" {
             description "Display routes to networks";
           }
         }
       }
       leaf destination {
         description "Address and optional prefix length of destination";
         type jt:ipprefix;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
       leaf instance {
         description "Name of OSPF instance";
         type string;
       }
       leaf verbosity_level {
         default "brief";
         type enumeration {
           enum "brief" {
             description "Display brief output (default)";
           }
           enum "detail" {
             description "Display detailed output";
           }
           enum "extensive" {
             description "Display extensive output";
           }
         }
       }
     }
     output {
       choice output-tags {
         case actual-tag {
           container ospf3-bgporr-route-information {
             uses ospf3-bgporr-route-information-block;
           }
         }
         case multichassis-tag {
           container multi-routing-engine-results {
             list multi-routing-engine-item {
               leaf re-name {
                 type string;
               }
               choice output-tags {
                 case actual-tag {
                   container ospf3-bgporr-route-information {
                     uses ospf3-bgporr-route-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ospf3-overview-information-block {
     container ospf-overview {
       description
         "Overview information for an OSPF instance";
       leaf instance-name {
         type string;
       }
       leaf ospf-router-id {
         type jt:ipaddr;
         description
           "OSPF router ID";
       }
       leaf ospf-route-table-index {
         type uint32;
         description
           "Route table index";
       }
       leaf ospf-configured-overload {
         type empty;
         description
           "Instance is configured to be in overload";
       }
       leaf ospf-configured-overload-remaining-time {
         type string;
         description
           "Time remaining on configured overload timeout";
       }
       leaf ospf-abr {
         type empty;
         description
           "Router is an area border router";
       }
       leaf ospf-asbr {
         type empty;
         description
           "Router is an autonomous system boundary router";
       }
       leaf ospf-nssa-router {
         type empty;
         description
           "Router is a not-so-stubby area router";
       }
       leaf no-rfc-1583 {
         type empty;
         description
           "RFC1583 compatibility is disabled";
       }
       leaf forwarding-address-to-broadcast {
         type empty;
         description
           "Set forwarding address in Type 5 LSA in broadcast network";
       }
       leaf ospf-lsa-refresh-time {
         type uint32;
         description
           "Refresh period for link-state advertisement (in minutes)";
       }
       leaf ospf-traffic-engineering {
         type empty;
         description
           "Traffic engineering is enabled";
       }
       leaf ospf-dna-uncapable {
         type empty;
         description
           "Not safe to generate DoNotAge LSAs";
       }
       leaf ospf-as-dc-bit-clear-count {
         type uint32;
         description
           "Number of AS scope link-state advertisements received with DC 
           bit clear";
       }
       leaf ospf-area-dc-bit-clear-count {
         type uint32;
         description
           "Number of area scope link-state advertisements received with DC 
           bit clear";
       }
       leaf ospf-area-indications-count {
         type uint32;
         description
           "Number of indication link-state advertisements received";
       }
       leaf ospf-link-dc-bit-clear-count {
         type uint32;
         description
           "Number of link local scope link-state advertisements received 
           with no DC bit clear";
       }
       container ospf-restart {
         description
           "OSPF restart parameters";
         leaf ospf-restart-enabled {
           type string;
           description
             "OSPF restart mode";
         }
         leaf ospf-restart-duration {
           type uint32;
           description
             "Duration of OSPF restart (seconds)";
         }
         leaf ospf-restart-grace-period {
           type uint32;
           description
             "Grace period for OSPF restart (seconds)";
         }
         leaf ospf-standard-graceful-restart-helper-mode {
           type string;
           description
             "OSPF graceful restart (RFC3623) helper mode";
         }
         leaf ospf-restart-signaling-helper-mode {
           type string;
           description
             "OSPF restart-signaling helper mode";
         }
       }
       container ospf-db-protection-overview {
         description
           "OSPF database protection overview information";
         leaf ospf-db-protection-state {
           type string;
           description
             "Database protection state";
         }
         leaf ospf-db-protection-remaining-time {
           type uint32;
           description
             "Time remaining in the current state";
         }
         leaf ospf-db-protection-warning-threshold {
           type uint32;
           description
             "Warning threshold as percentage";
         }
         leaf ospf-db-protection-warning-only {
           type empty;
           description
             "Configured to generate warning only";
         }
         leaf ospf-db-protection-lsa-current {
           type uint32;
           description
             "Current number of non self-generated LSAs";
         }
         leaf ospf-db-protection-lsa-warning {
           type uint32;
           description
             "Warning number of non self-generated LSAs";
         }
         leaf ospf-db-protection-lsa-maximum {
           type uint32;
           description
             "Allowed number of non self-generated LSAs";
         }
         leaf ospf-db-protection-ignore-time {
           type uint32;
           description
             "Configured value of ignore time";
         }
         leaf ospf-db-protection-reset-time {
           type uint32;
           description
             "Configured value of reset time";
         }
         leaf ospf-db-protection-ignore-current {
           type uint32;
           description
             "Current number of transitions to Ignore state";
         }
         leaf ospf-db-protection-ignore-maximum {
           type uint32;
           description
             "Allowed number of transitions to Ignore state";
         }
       }
       list ospf-area-overview {
         key "ospf-area";
         description
           "Overview information for an OSPF area";
         leaf ospf-area {
           type string;
           description
             "Area ID";
         }
         leaf ospf-stub-type {
           type string;
           description
             "Stub type of area";
         }
         leaf ospf-stub-cost {
           type uint32;
           description
             "Cost of default route in stub area";
         }
         leaf ospf-virtual-transit {
           type empty;
           description
             "Area is transit for virtual links";
         }
         leaf authentication-type {
           type string;
           description
             "Type of authentication";
         }
         leaf ospf-abr-count {
           type uint32;
           description
             "Number of area border routers";
         }
         leaf ospf-asbr-count {
           type uint32;
           description
             "Number of autonomous system boundary routers";
         }
         leaf ospf-dna-uncapable {
           type empty;
           description
             "Not safe to generate DoNotAge LSAs";
         }
         leaf ospf-area-dc-bit-clear-count {
           type uint32;
           description
             "Number of area scope link-state advertisements received with 
             DC bit clear";
         }
         leaf ospf-area-indications-count {
           type uint32;
           description
             "Number of indication link-state advertisements received";
         }
         leaf ospf-area-self-indicating {
           type empty;
           description
             "Router generated an indication link-state advertisement";
         }
         leaf ospf-link-dc-bit-clear-count {
           type uint32;
           description
             "Number of link local scope link-state advertisements received 
             with no DC bit clear";
         }
         container ospf-nbr-overview {
           leaf ospf-nbr-up-count {
             type uint32;
             description
               "Number of neighbors in full state";
           }
         }
       }
       list ospf-topology-overview {
         key "ospf-topology-name";
         description
           "OSPF topology specific overview information";
         leaf ospf-topology-name {
           type string;
           description
             "OSPF topology name";
         }
         leaf ospf-topology-id {
           type int32;
           description
             "OSPF topology id";
         }
         leaf ospf-topology-configured-overload {
           type empty;
           description
             "Topology is configured to be in overload";
         }
         leaf ospf-topology-dynamic-overload {
           type empty;
           description
             "Topology is in dynamic overload i.e. prefix limit was exceeded";
         }
         leaf ospf-prefix-export-count {
           type uint32;
           description
             "Number of prefixes exported into the topology";
         }
         leaf ospf-prefix-export-limit {
           type uint32;
           description
             "Number of prefixes we are allowed to exported into the 
             topology";
         }
         leaf ospf-full-spf-count {
           type uint32;
           description
             "Number of full SPF calculations";
         }
         leaf ospf-spf-delay {
           type string;
           description
             "Delay before performing consecutive SPF calculations";
         }
         leaf ospf-spf-holddown {
           type string;
           description
             "Time to hold down before running an SPF";
         }
         leaf ospf-spf-rapid-runs {
           type string;
           description
             "Number of rapid SPF runs before SPF holddown";
         }
         leaf ospf-backup-spf-status {
           type string;
           description
             "Backup SPF status";
         }
         leaf ospf-backup-spf-remote-backup-calculation {
           type empty;
           description
             "Remote-LFA backup calculations enabled";
         }
         leaf ospf-backup-spf-downstream-only {
           type empty;
           description
             "Topology is configured to use only downstream backup paths";
         }
         leaf ospf-backup-spf-node-link-degradation {
           type empty;
           description
             "Topology is configured to use node link degradation";
         }
         leaf ospf-te-shortcuts {
           type empty;
           description
             "IP Traffic engineering shortcuts are enabled";
         }
         leaf ospf-te-shortcuts-mpls {
           type empty;
           description
             "MPLS Traffic engineering shortcuts are enabled";
         }
         leaf ospf-topo-sessid-count {
           type uint32;
           description
             "Number of Session IDs associated with routes in this toplogy";
         }
       }
       container ospf-spring-overview {
         description
           "OSPF spring parameters";
         leaf ospf-spring-enabled {
           type string;
           description
             "OSPF SPRING";
         }
         leaf ospf-srgb-allocation {
           type string;
           description
             "SRGB Block Allocation";
         }
         leaf ospf-node-segment-enabled {
           type string;
           description
             "OSPF node segments";
         }
         container ospf-srgb-config {
           description
             "SRGB block configuration related information";
           leaf ospf-srgb-config-block-header {
             type string;
             description
               "SRGB Config Block";
           }
           leaf ospf-srgb-start-label {
             type int32;
             description
               "Configuration of SRGB start label";
           }
           leaf ospf-srgb-index-range {
             type int32;
             description
               "Configuration of SRGB index range";
           }
         }
         container ospf-srgb-block {
           description
             "SRGB block related information";
           leaf ospf-srgb-start-index {
             type int32;
             description
               "Starting Index for SRGB Block";
           }
           leaf ospf-srgb-size {
             type int32;
             description
               "Size of the specific SRGB Block";
           }
           leaf ospf-srgb-first-label {
             type int32;
             description
               "First label allocated for SRGB Block";
           }
           leaf ospf-srgb-last-label {
             type int32;
             description
               "Last label allocated for SRGB Block";
           }
         }
         container ospf-node-segment {
           description
             "Node segments related information";
           leaf ospf-node-segment-ipv4-index {
             type int32;
             description
               "Ipv4 node segment index for this device";
           }
           leaf ospf-node-segment-index-range {
             type int32;
             description
               "Range of node segment indices configured";
           }
           leaf ospf-node-segment-block-header {
             type empty;
             description
               "Node segment blocks";
           }
           list ospf-node-segment-block {
             key "ospf-node-segment-block-start-index";
             description
               "Node segment blocks related information";
             leaf ospf-node-segment-block-start-index {
               type int32;
               description
                 "Starting index for the specific node segment block";
             }
             leaf ospf-node-segment-block-size {
               type int32;
               description
                 "Size of the specific node segment block";
             }
             leaf ospf-node-segment-block-first-label {
               type int32;
               description
                 "First label allocated for the specific node segment block";
             }
             leaf ospf-node-segment-block-last-label {
               type int32;
               description
                 "Last label allocated for the specific node segment block";
             }
           }
         }
       }
       container ospf-tilfa-overview {
         description
           "OSPF Post Convergence Backup parameters";
         leaf ospf-tilfa-enabled {
           type string;
           description
             "Post Convergence Backup";
         }
         leaf ospf-tilfa-max-labels {
           type int32;
           description
             "Max labels";
         }
         leaf ospf-tilfa-max-spf {
           type int32;
           description
             "Max spf";
         }
         leaf ospf-tilfa-ecmp-backup {
           type int32;
           description
             "Post Convergence Max Ecmp Backup";
         }
       }
     }
   }
   grouping ospf3-database-information-block {
     container ospf3-area-header {
       leaf ospf-area {
         type string;
         description
           "Area ID";
       }
     }
     container ospf3-intf-header {
       leaf ospf-intf {
         type string;
         description
           "Name of interface";
       }
       leaf ospf-area {
         type string;
         description
           "Area ID";
       }
     }
     list ospf3-database {
       leaf-list ospf3-database.external-heading {
         type string;
       }
       leaf-list ospf3-database.heading {
         type string;
       }
       leaf lsa-type {
         type string;
       }
       leaf our-entry {
         type empty;
       }
       leaf lsa-id {
         type string;
       }
       leaf advertising-router {
         type jt:ipaddr;
       }
       leaf sequence-number {
         type int64;
         description
           "History event number";
       }
       leaf age {
         type string;
       }
       leaf ospf-do-not-age {
         type empty;
         description
           "DoNotAge bit is set on the link-state advertisement received";
       }
       leaf checksum {
         type int32;
       }
       leaf lsa-length {
         type int32;
       }
       container ospf3-router-lsa {
         leaf bits {
           type int32;
         }
         leaf ospf3-options {
           type int32;
         }
         list ospf3-link {
           leaf link-type-name {
             type string;
             description
               "OSPF LSA link type";
           }
           leaf link-type-value {
             type int32;
           }
           leaf link-metric {
             type int32;
           }
           leaf link-intf-id {
             type int32;
           }
           leaf nbr-intf-id {
             type int32;
           }
           leaf nbr-rtr-id {
             type string;
           }
         }
         list ospf3-lsa-topology {
           description
             "OSPFv3 topology information for a LSA";
           leaf ospf-topology-name {
             type string;
             description
               "OSPF topology name";
           }
           leaf ospf-topology-id {
             type int32;
             description
               "OSPF topology id";
           }
           list ospf3-lsa-topology-link {
             description
               "OSPFv3 topology information for a set of links to a LSA";
             leaf link-type-name {
               type string;
               description
                 "OSPF LSA link type";
             }
             leaf ospf-lsa-topology-link-node-id {
               type string;
               description
                 "LSA ID of the node representing the remote LSA";
             }
             leaf ospf-lsa-topology-link-metric {
               type int32;
               description
                 "Minimum metric of the set of links";
             }
             leaf ospf-lsa-topology-link-state {
               type string;
               description
                 "State of the set of links";
             }
           }
         }
       }
       container ospf3-network-lsa {
         leaf ospf3-options {
           type int32;
         }
         leaf-list attached-router {
           type jt:ipaddr;
         }
         list ospf3-lsa-topology {
           description
             "OSPFv3 topology information for a LSA";
           leaf ospf-topology-name {
             type string;
             description
               "OSPF topology name";
           }
           leaf ospf-topology-id {
             type int32;
             description
               "OSPF topology id";
           }
           list ospf3-lsa-topology-link {
             description
               "OSPFv3 topology information for a set of links to a LSA";
             leaf link-type-name {
               type string;
               description
                 "OSPF LSA link type";
             }
             leaf ospf-lsa-topology-link-node-id {
               type string;
               description
                 "LSA ID of the node representing the remote LSA";
             }
             leaf ospf-lsa-topology-link-metric {
               type int32;
               description
                 "Minimum metric of the set of links";
             }
             leaf ospf-lsa-topology-link-state {
               type string;
               description
                 "State of the set of links";
             }
           }
         }
       }
       container ospf3-inter-area-prefix-lsa {
         leaf ospf3-prefix {
           type string;
         }
         leaf ospf3-prefix-options {
           type int32;
         }
         leaf metric {
           type int32;
         }
       }
       container ospf3-inter-area-router-lsa {
         leaf destination-router-id {
           type string;
         }
         leaf ospf3-options {
           type int32;
         }
         leaf metric {
           type int32;
         }
       }
       container ospf3-external-lsa {
         leaf ospf3-prefix {
           type string;
         }
         leaf ospf3-prefix-options {
           type int32;
         }
         leaf metric {
           type int32;
         }
         leaf type-value {
           type int32;
         }
         leaf forward-address {
           type jt:ipaddr;
         }
         leaf tag {
           type jt:ipaddr;
         }
       }
       container ospf3-link-lsa {
         leaf linklocal-address {
           type string;
         }
         leaf ospf3-options {
           type int32;
         }
         leaf router-priority {
           type int32;
           description
             "Router priority used in DR election on broadcast or NBMA 
             interface";
         }
         leaf prefix-count {
           type int32;
           description
             "Number of prefixes accepted before action is taken";
         }
         leaf ospf3-prefix {
           type string;
         }
         leaf ospf3-prefix-options {
           type int32;
         }
       }
       container ospf3-intra-area-prefix-lsa {
         leaf reference-lsa-type {
           type string;
         }
         leaf reference-lsa-id {
           type string;
         }
         leaf reference-lsa-router-id {
           type string;
         }
         leaf prefix-count {
           type int32;
           description
             "Number of prefixes accepted before action is taken";
         }
         leaf ospf3-prefix {
           type string;
         }
         leaf ospf3-prefix-options {
           type int32;
         }
         leaf ospf3-prefix-metric {
           type int32;
         }
       }
       container ospf-database-extensive {
         leaf generation-timer {
           type string;
         }
         leaf aging-timer {
           type string;
         }
         leaf installation-time {
           type string;
         }
         leaf expiration-time {
           type string;
         }
         leaf send-time {
           type string;
         }
         leaf lsa-changed-time {
           type string;
           description
             "Time elapsed since the link-state advertisement changed";
         }
         leaf lsa-change-count {
           type int32;
           description
             "Number of times link-state advertisement changed";
         }
         leaf indication-lsa {
           type empty;
           description
             "Indication link-state advertisement";
         }
         leaf database-entry-state {
           type string;
         }
         leaf database-telink-id {
           type int32;
         }
         leaf standby-flood-status {
           type string;
           description
             "Flooding status to standby Routing Engine";
         }
       }
       list ospf-opaque-link-local-lsa {
         container ospf-link-local-grace-lsa {
           leaf tlv-grace-type-name {
             type string;
           }
           leaf tlv-grace-value {
             type string;
           }
         }
         container ospf-link-local-te-lsa {
           container ospf-link-local-te-tlv {
             leaf link-local-te-tlv-type-name {
               type string;
             }
             leaf tlv-type-value {
               type int32;
             }
             leaf tlv-length {
               type int32;
             }
             leaf bytes-left {
               type int32;
             }
             leaf-list formatted-tlv-data {
               type string;
             }
           }
           container ospf-link-local-te-subtlv {
             leaf link-local-te-tlv-type-name {
               type string;
             }
             leaf tlv-type-value {
               type int32;
             }
             leaf tlv-length {
               type int32;
             }
             leaf bytes-left {
               type int32;
             }
             leaf-list formatted-tlv-data {
               type string;
             }
           }
         }
       }
     }
     container ospf3-database-summary {
       leaf ospf-area {
         type string;
         description
           "Area ID";
       }
       leaf ospf-intf {
         type string;
         description
           "Name of interface";
       }
       leaf ospf3-database-summary.external-heading {
         type string;
       }
       leaf ospf-lsa-count {
         type int32;
       }
       leaf ospf-lsa-type {
         type string;
       }
     }
   }
   grouping ospf3-backup-spf-information-block {
     list ospf3-topology-backup-spf {
       description
         "OSPFv3 topology specific backup SPF results";
       leaf ospf-topology-name {
         type string;
         description
           "OSPF topology name";
       }
       list ospf3-topology-area-backup-spf {
         description
           "OSPFv3 topology area specific backup SPF results";
         leaf ospf-area {
           type string;
           description
             "Area ID";
         }
         list ospf3-backup-spf-node {
           description
             "OSPFv3 node specific backup SPF information";
           leaf lsa-id {
             type string;
           }
           leaf ospf-node-metric {
             type int32;
             description
               "Self to destination metric";
           }
           container ospf-node-id {
             description
               "OSPF node ID";
             leaf advertising-router {
               type jt:ipaddr;
             }
             leaf lsa-id {
               type string;
             }
             leaf ospf-node-metric {
               type int32;
               description
                 "Self to destination metric";
             }
           }
           list ospf-parent-node-id {
             description
               "OSPF parent node ID";
             leaf ospf-parent-advertising-router {
               type jt:ipaddr;
               description
                 "Advertising router for the parent node";
             }
             leaf ospf-parent-lsa-id {
               type string;
               description
                 "LSA ID for the parent node";
             }
           }
           list ospf-next-hop {
             container next-hop-name {
               leaf interface-name {
                 type string;
                 description
                   "Name of interface";
               }
             }
             container next-hop-address {
               leaf interface-address {
                 type jt:ipaddr;
               }
             }
           }
           container ospf-backup-next-hop {
             leaf ospf-backup-next-hop-interface {
               type string;
             }
             leaf ospf-backup-next-hop-address {
               type string;
             }
             leaf ospf-backup-next-hop-lsp {
               type string;
             }
             leaf ospf-backup-next-hop-lsp-out-if {
               type string;
             }
             leaf ospf-backup-next-hop-type {
               type string;
             }
           }
           list ospf3-backup-spf-result {
             description
               "OSPFv3 backup SPF result";
             leaf ospf-backup-neighbor {
               type jt:ipaddr;
               description
                 "Backup neighbor router-id";
             }
             leaf ospf-backup-neighbor-via {
               type string;
               description
                 "Backup neighbor via direct/RSVP/LDP";
             }
             leaf ospf-backup-neighbor-is-lsp-endpoint {
               type empty;
               description
                 "Backup neighbor is an LSP endpoint";
             }
             leaf ospf-backup-metric {
               type int32;
               description
                 "Backup neighbor to destination metric";
             }
             leaf ospf-backup-neighbor-from-metric {
               type int32;
               description
                 "Backup neighbor to self metric";
             }
             leaf ospf-backup-neighbor-to-metric {
               type int32;
               description
                 "Self to backup neighbor metric";
             }
             leaf ospf-backup-preference {
               type int32;
               description
                 "Backup neighbor preference";
             }
             leaf-list ospf-track-item {
               type string;
               description
                 "Backup SPF result track item";
             }
             leaf-list ospf-rev-track-item {
               type string;
               description
                 "Backup RSPF result track item";
             }
             leaf ospf-backup-result-status {
               type string;
               description
                 "Backup SPF result status";
             }
             leaf ospf-backup-result-no-coverage-reason {
               type string;
               description
                 "Backup SPF result no coverage reason";
             }
             leaf ospf-backup-spf-result-path {
               type empty;
               description
                 "Path to the neighbour from backup root";
             }
             leaf ospf-backup-result-path-nodes {
               type string;
               description
                 "Backup node in the path";
             }
           }
         }
       }
     }
   }
   grouping ospf3-backup-coverage-information-block {
     list ospf3-topology-backup-coverage {
       key "ospf-topology-name";
       leaf ospf-topology-name {
         type string;
         description
           "OSPF topology name";
       }
       container ospf3-backup-node-coverage {
         leaf ospf-area {
           type string;
           description
             "Area ID";
         }
         leaf ospf-covered-nodes {
           type int32;
           description
             "Number of nodes covered by backup nexthops";
         }
         leaf ospf-total-nodes {
           type int32;
           description
             "Total number of nodes in the area";
         }
         leaf ospf-node-coverage {
           type string;
           description
             "Percent of nodes covered by backup nexthops";
         }
       }
       list ospf3-backup-route-coverage {
         key "ospf-path-type";
         leaf ospf-path-type {
           type string;
           description
             "Route path type";
         }
         leaf ospf-covered-routes {
           type int32;
           description
             "Number of routes covered by backup nexthops";
         }
         leaf ospf-total-routes {
           type int32;
           description
             "Total number of routes in the area";
         }
         leaf ospf-route-coverage {
           type string;
           description
             "Percent of routes covered by backup nexthops";
         }
       }
     }
   }
   grouping ospf3-backup-neighbor-information-block {
     list ospf3-topology-backup-neighbor {
       description
         "OSPFv3 topology specific backup neighbors";
       leaf ospf-topology-name {
         type string;
         description
           "OSPF topology name";
       }
       list ospf3-topology-area-backup-neighbor {
         description
           "OSPFv3 topology area specific backup neighbors";
         leaf ospf-area {
           type string;
           description
             "Area ID";
         }
         list ospf3-backup-neighbor-node {
           description
             "OSPFv3 backup neighbor node";
           leaf ospf-backup-neighbor {
             type jt:ipaddr;
             description
               "Backup neighbor router-id";
           }
           leaf ospf-backup-neighbor-is-lsp-endpoint {
             type empty;
             description
               "Backup neighbor is an LSP endpoint";
           }
           leaf ospf-backup-neighbor-from-metric {
             type int32;
             description
               "Backup neighbor to self metric";
           }
           leaf ospf-backup-neighbor-to-metric {
             type int32;
             description
               "Self to backup neighbor metric";
           }
           container ospf-backup-next-hop {
             leaf ospf-backup-next-hop-interface {
               type string;
             }
             leaf ospf-backup-next-hop-address {
               type string;
             }
             leaf ospf-backup-next-hop-lsp {
               type string;
             }
             leaf ospf-backup-next-hop-lsp-out-if {
               type string;
             }
             leaf ospf-backup-next-hop-type {
               type string;
             }
           }
         }
       }
     }
   }
   grouping ospf3-backup-mplsp-information-block {
     list ospf3-backup-mplsp {
       key "lsp-name";
       leaf lsp-name {
         type string;
         description
           "Tunneled into an RSVP LSP";
       }
       leaf lsp-addr {
         type jt:ipaddr;
         description
           "LSP destination address";
       }
       leaf lsp-status {
         type string;
         description
           "LSP status";
       }
       leaf lsp-last-change {
         type string;
         description
           "Time of last LSP change";
       }
       leaf te-metric {
         type int32;
         description
           "LSP TE metric";
       }
       leaf metric {
         type int32;
       }
     }
   }
   grouping ospf3-interface-information-block {
     list ospf3-interface {
       key "interface-name ospf-area";
       leaf interface-name {
         type string;
         description
           "Name of interface";
       }
       leaf ospf-interface-state {
         type string;
       }
       leaf ospf-area {
         type string;
         description
           "Area ID";
       }
       leaf dr-id {
         type jt:ipaddr;
       }
       leaf bdr-id {
         type jt:ipaddr;
       }
       leaf neighbor-count {
         type int32;
         description
           "Number of neighbors on PIM interface";
       }
       leaf interface-address {
         type jt:ipaddr;
       }
       leaf prefix-length {
         type int32;
       }
       leaf virtual-link-transit-area {
         type jt:ipaddr;
         description
           "Virtual link transit area";
       }
       leaf virtual-link-destination {
         type string;
         description
           "Virtual link destination address";
       }
       leaf ospf3-interface-index {
         type int32;
       }
       leaf interface-type {
         type string;
       }
       leaf mtu {
         type int32;
         description
           "MTU along an interface";
       }
       leaf interface-cost {
         type int32;
         description
           "Cost associated with this interface";
       }
       leaf router-priority {
         type int32;
         description
           "Router priority used in DR election on broadcast or NBMA 
           interface";
       }
       leaf adj-count {
         type int32;
         description
           "Count of fully adjacent neighbors";
       }
       leaf ospf3-router-lsa-id {
         type int32;
       }
       leaf interface-secondary {
         type empty;
         description
           "OSPF interface is secondary";
       }
       leaf interface-flood-reduction {
         type empty;
         description
           "Flood reduction is enabled";
       }
       leaf passive {
         type string;
       }
       leaf dr-address {
         type jt:ipaddr;
         description
           "IP address of DR";
       }
       leaf bdr-address {
         type jt:ipaddr;
         description
           "IP address of BDR";
       }
       leaf hello-interval {
         type int32;
         description
           "Interval between two successive hellos";
       }
       leaf poll-interval {
         type int32;
       }
       leaf dead-interval {
         type int32;
       }
       leaf retransmit-interval {
         type int32;
       }
       leaf ospf-stub-type {
         type string;
         description
           "Stub type of area";
       }
       leaf ipsec-sa {
         type string;
       }
       leaf ospf-interface-protection-type {
         type string;
       }
       leaf ospf-interface-no-eligible-backup {
         type empty;
       }
       leaf igp-ldp-sync-state {
         type string;
         description
           "State of synchronization between Label Distribution Protocol 
           (LDP) and the interior gateway protocol (IGP)";
       }
       leaf igp-ldp-sync-last-change {
         type string;
         description
           "Time since the state of synchronization between Label 
           Distribution Protocol (LDP) and the interior gateway protocol 
           (IGP) last changed";
       }
       leaf igp-ldp-sync-reason {
         type string;
         description
           "Reason for the change in the state of synchronization between 
           Label Distribution Protocol (LDP) and the interior gateway 
           protocol (IGP)";
       }
       leaf igp-ldp-sync-holdtime {
         type string;
         description
           "Length of time during which the maximum metric is advertised for
           an interface that is in the hold-down state because 
           synchronization was lost between Label Distribution Protocol 
           (LDP) and the interior gateway protocol (IGP)";
       }
       leaf igp-ldp-sync-timeleft {
         type int32;
         description
           "Remaining amount of time the interface will remain in the 
           hold-down state because synchronization was lost between Label 
           Distribution Protocol (LDP) and the interior gateway protocol 
           (IGP)";
       }
       leaf lsa-list {
         type string;
       }
       leaf interface-flood-list-count {
         type int32;
       }
       leaf flood-list-count {
         type int32;
       }
       leaf interface-description-list {
         type string;
       }
     }
   }
   grouping ospf-neighbor-information-logical-system-all-block {
     list logical-system {
       key "name";
       leaf name {
         type string;
       }
       container route-prefix-length-distribution {
         list route-table {
           key "table-name";
           leaf table-name {
             type string;
             description
               "Unicast routing table";
           }
           list protocols {
             key "protocol-name";
             leaf protocol-name {
               type string;
             }
             leaf protocol-route-count {
               type int32;
               description
                 "Total protocol routes";
             }
             leaf active-route-count {
               type int32;
               description
                 "Active routes";
             }
           }
           list rt-prefix-dist {
             key "rt-prefix-length";
             leaf rt-prefix-length {
               type string;
             }
             leaf rt-prefix-count {
               type int32;
             }
           }
           list rt {
             key "rt-destination";
             leaf rt-destination {
               type string;
               description
                 "Route prefixes awaiting ACK";
             }
             leaf rt-prefix-length {
               type string;
             }
             list rt-entry {
               leaf active-tag {
                 type string;
                 description
                   "Visual indication of active state of this route entry";
               }
               leaf validation-state {
                 type string;
                 description
                   "Validation-state of a route";
               }
               leaf protocol-name {
                 type string;
               }
               leaf preference {
                 type int32;
                 description
                   "Preference for the route";
               }
               leaf metric {
                 type int32;
               }
               leaf metric2 {
                 type int32;
               }
               leaf nh-type {
                 type string;
                 description
                   "Special next hop: Reject, Blackhole, Receive, Multicast,
                   Local, or Unused";
               }
               leaf as-path {
                 type string;
                 description
                   "Name of AS path regular expression (BGP only)";
               }
               leaf last-active {
                 type empty;
                 description
                   "This route entry was the last active route entry";
               }
               leaf current-active {
                 type empty;
                 description
                   "This route entry is currently active";
               }
               leaf bgp-rt-mult-nh-idx {
                 type uint32;
                 description
                   "BGP multipath nexthop index";
               }
               leaf deleted {
                 type empty;
               }
               leaf nh-erc-btid-id {
                 type string;
                 description
                   "ERC Backtrace ID";
               }
               leaf nh-erc-btid-op {
                 type string;
                 description
                   "ERC BTID Operation";
               }
               leaf nh-erc-btid-nreference {
                 type int32;
                 description
                   "ERC Number of BTID References";
               }
               leaf nh-erc-btid-bt {
                 type string;
                 description
                   "ERC BTID Backtrace ";
               }
               container route-record {
                 leaf rt-recorded {
                   type string;
                 }
                 leaf nh-address {
                   type string;
                   description
                     "Address of next hop";
                 }
                 leaf as-index {
                   type int32;
                 }
                 leaf as-recorded {
                   type string;
                 }
                 leaf com-index {
                   type int32;
                 }
                 leaf com-recorded {
                   type string;
                 }
               }
               list route-data-dcf {
                 key "trunk-id snmp-idx";
                 leaf trunk-id {
                   type int32;
                   description
                     "Trunk Identifier associated with the LAG port";
                 }
                 leaf snmp-idx {
                   type int32;
                   description
                     "IFD SNMP index";
                 }
                 leaf ts {
                   type int32;
                   description
                     "Timestamp associated with the route";
                 }
                 leaf class-id {
                   type int32;
                   description
                     "Class identifier associated with the route";
                 }
                 leaf rt-flags {
                   type string;
                   description
                     "Flags associated with the route";
                 }
                 leaf rt-type {
                   type string;
                   description
                     "Route type associated with the route";
                 }
                 leaf rt-proto {
                   type string;
                   description
                     "Protocol associated with the route";
                 }
                 leaf rt-l2domain {
                   type int32;
                   description
                     "L2domain associated with the route";
                 }
                 leaf rt-mac-addr {
                   type jt:mac-addr;
                   description
                     "Mac address associated with the route";
                 }
                 list snpa {
                   key "snpa-type";
                   leaf snpa-type {
                     type string;
                     description
                       "Type of SNPA";
                   }
                   list pfe-port-snpa {
                     key "pfe-id";
                     description
                       "PFE Port SNPA";
                     leaf pfe-id {
                       type int32;
                     }
                     leaf port-id {
                       type int32;
                     }
                   }
                   container network-element-port-snpa {
                     description
                       "Network Element Port SNPA";
                     leaf port-id {
                       type int32;
                     }
                   }
                   container mstp-root-snpa {
                     description
                       "Multiple Spanning Tree Protocol Root SNPA";
                     leaf mstp-root-id {
                       type int32;
                     }
                   }
                   list gateway-snpa {
                     key "gateway-addr";
                     description
                       "Gateway SNPA";
                     leaf gateway-addr {
                       type jt:ipaddr;
                     }
                   }
                   container layer2-domain-port-snpa {
                     description
                       "Layer-2 Domain Port SNPA";
                     leaf port-id {
                       type int32;
                     }
                   }
                   container replication-block-snpa {
                     description
                       "Replication Block SNPA";
                     leaf replication-block-id {
                       type int32;
                     }
                   }
                   container replication-route-snpa {
                     description
                       "Replication Route SNPA";
                     leaf network-element-id {
                       type jt:ipaddr;
                     }
                   }
                   container layer2-multicast-port-snpa {
                     description
                       "Layer-2 Multicast Port SNPA";
                     leaf layer2-multicast-port-id {
                       type int32;
                     }
                   }
                   container inh-snpa {
                     description
                       "Indirection SNPA";
                     leaf inh-id {
                       type int32;
                     }
                   }
                 }
                 leaf snpa-count {
                   type int32;
                   description
                     "Number of SNPAs in this route";
                 }
                 leaf snpa-length {
                   type int32;
                   description
                     "Total length of the SNPAs, in bytes";
                 }
                 container multicast-member-map-data {
                   description
                     "Multicast member map";
                   leaf multicast-root-hash {
                     type int32;
                   }
                   leaf multicast-core-hash {
                     type int32;
                   }
                   leaf multicast-edge-hash {
                     type int32;
                   }
                   leaf multicast-member-map {
                     type string;
                   }
                 }
                 container layer3-multicast-data {
                   description
                     "Layer3 multicast core key";
                   leaf layer3-multicast-corekey {
                     type int32;
                   }
                 }
                 container multicast-vsg-corekey-data {
                   description
                     "Vsg multicast core key";
                   leaf multicast-vsg-corekey-key {
                     type int32;
                   }
                   leaf multicast-vsg-corekey-len {
                     type int32;
                   }
                 }
               }
               container rtd-flow-dep {
                 leaf flow-dep-state {
                   type string;
                 }
                 leaf flow-origin {
                   type jt:ipaddr;
                   description
                     "Originator of the flow information";
                 }
                 leaf flow-next-as {
                   type uint32;
                   description
                     "Neighbor AS of the flow information";
                 }
                 container flow-ucast-rt {
                   description
                     "Unicast route used for resolution";
                   leaf flow-rtn-dest {
                     type jt:ipaddr;
                     description
                       "Destination address";
                   }
                   leaf flow-rtn-plen {
                     type int32;
                     description
                       "Prefix length";
                   }
                   leaf flow-rtn-state {
                     type string;
                     description
                       "Validation entry state";
                   }
                 }
               }
               container bgp-path-attributes {
                 container attr-as-path {
                   description
                     "AS Path Attribute";
                   leaf attr-length {
                     type string;
                   }
                   leaf flags {
                     type string;
                     description
                       "Enabled trace flags";
                   }
                   leaf path-length {
                     type string;
                   }
                   leaf attr-value {
                     type string;
                   }
                 }
                 container attr-as4-path {
                   description
                     "4-byte AS Path Attribute";
                   leaf attr-length {
                     type string;
                   }
                   leaf path-length {
                     type string;
                   }
                   leaf flags {
                     type string;
                     description
                       "Enabled trace flags";
                   }
                   leaf attr-value {
                     type string;
                   }
                 }
                 container attr-as-path-effective {
                   description
                     "Effective AS-Path Attribute";
                   leaf attr-length {
                     type string;
                   }
                   leaf aspath-effective-string {
                     type string;
                   }
                   leaf path-length {
                     type string;
                   }
                   leaf attr-value {
                     type string;
                   }
                   leaf flags {
                     type string;
                     description
                       "Enabled trace flags";
                   }
                 }
                 container attr-aggregator {
                   description
                     "Aggregator Attribute";
                   leaf attr-length {
                     type string;
                   }
                   leaf flags {
                     type string;
                     description
                       "Enabled trace flags";
                   }
                   leaf aggr-as-number {
                     type string;
                   }
                   leaf aggr-router-id {
                     type string;
                   }
                 }
                 container attr-aggregator4 {
                   description
                     "Aggregator4 Attribute";
                   leaf attr-length {
                     type string;
                   }
                   leaf flags {
                     type string;
                     description
                       "Enabled trace flags";
                   }
                   leaf aggr-as-number {
                     type string;
                   }
                   leaf aggr-router-id {
                     type string;
                   }
                 }
                 container attr-cluster-list {
                   description
                     "Cluster List Attribute";
                   leaf attr-length {
                     type string;
                   }
                   leaf attr-value {
                     type string;
                   }
                 }
                 container attr-originator-id {
                   description
                     "Originator Attribute";
                   leaf attr-length {
                     type string;
                   }
                   leaf attr-value {
                     type string;
                   }
                 }
                 leaf domain-path {
                   type string;
                 }
                 leaf attr-otc {
                   type int32;
                   description
                     "Only-to-customer attribute";
                 }
                 container attr-unrecognized {
                   description
                     "Unrecognized attributes";
                   leaf attr-length {
                     type string;
                   }
                   leaf attr-flags {
                     type string;
                   }
                   leaf attr-code {
                     type string;
                   }
                   leaf attr-value {
                     type string;
                   }
                 }
               }
               container communities {
                 leaf-list community {
                   type string;
                   description
                     "Basic community";
                 }
                 leaf-list extended-community {
                   type string;
                   description
                     "Extended community";
                 }
                 leaf-list ipv6-extended-community {
                   type string;
                   description
                     "IPv6 extended community";
                 }
               }
               list bgp-tunnel-attribute {
                 key "tunnel-attribute-type";
                 description
                   "Tunne encap attribute information";
                 leaf tunnel-attribute-type {
                   type string;
                 }
                 leaf tunnel-attribute-rpf {
                   type empty;
                 }
                 leaf tunnel-attribute-color {
                   type uint32;
                 }
                 leaf tunnel-attribute-destination {
                   type jt:ipaddr;
                 }
               }
               container attrset {
                 container bgp-prefix-sid-attr {
                   description
                     "BGP Prefix SID Attribute";
                   container bgp-prefix-sid-attr-label-idx-tlv {
                     leaf bgp-prefix-sid-label-idx-index {
                       type int32;
                     }
                     leaf bgp-prefix-sid-attr-status {
                       type string;
                     }
                   }
                   container bgp-prefix-sid-attr-srgb-tlv {
                     list bgp-prefix-sid-srgb-block {
                       key "bgp-prefix-sid-srgb-block-start-label";
                       leaf bgp-prefix-sid-srgb-block-start-label {
                         type int32;
                       }
                       leaf bgp-prefix-sid-srgb-block-range {
                         type int32;
                       }
                     }
                   }
                   container bgp-prefix-sid-attr-service-tlv {
                     leaf bgp-prefix-sid-srv6-sid-value {
                       type jt:ipaddr;
                     }
                     leaf bgp-prefix-sid-attr-service-tlv-type {
                       type uint32;
                     }
                     leaf bgp-prefix-sid-attr-tlv-type {
                       type uint32;
                     }
                     leaf bgp-prefix-sid-srv6-sid-bh {
                       type uint32;
                     }
                     leaf bgp-prefix-sid-srv6-sid-bl {
                       type uint32;
                     }
                     leaf bgp-prefix-sid-srv6-sid-nl {
                       type uint32;
                     }
                     leaf bgp-prefix-sid-srv6-sid-fl {
                       type uint32;
                     }
                     leaf bgp-prefix-sid-srv6-sid-al {
                       type uint32;
                     }
                     leaf bgp-prefix-sid-srv6-sid-tl {
                       type uint32;
                     }
                     leaf bgp-prefix-sid-srv6-sid-to {
                       type uint32;
                     }
                   }
                   container bgp-prefix-sid-attr-unknown-tlvs {
                     list bgp-prefix-sid-attr-unknown-tlv {
                       key "bgp-prefix-sid-unknown-tlv-type";
                       leaf bgp-prefix-sid-unknown-tlv-type {
                         type uint32;
                       }
                       leaf bgp-prefix-sid-unknown-tlv-len {
                         type uint32;
                       }
                     }
                   }
                 }
                 leaf attrset-as {
                   type int32;
                   description
                     "Originator AS";
                 }
                 leaf med {
                   type int32;
                   description
                     "Multiple exit discriminator";
                 }
                 leaf local-preference {
                   type int32;
                 }
                 leaf as-path {
                   type string;
                   description
                     "Name of AS path regular expression (BGP only)";
                 }
                 leaf pmsi {
                   type string;
                   description
                     "P-multicast service interface";
                 }
                 leaf cluster-id {
                   type string;
                 }
                 leaf originator {
                   type string;
                 }
                 leaf connector {
                   type string;
                 }
                 container communities {
                   leaf-list community {
                     type string;
                     description
                       "Basic community";
                   }
                   leaf-list extended-community {
                     type string;
                     description
                       "Extended community";
                   }
                   leaf-list ipv6-extended-community {
                     type string;
                     description
                       "IPv6 extended community";
                   }
                 }
                 list bgp-tunnel-attribute {
                   key "tunnel-attribute-type";
                   description
                     "Tunne encap attribute information";
                   leaf tunnel-attribute-type {
                     type string;
                   }
                   leaf tunnel-attribute-rpf {
                     type empty;
                   }
                   leaf tunnel-attribute-color {
                     type uint32;
                   }
                   leaf tunnel-attribute-destination {
                     type jt:ipaddr;
                   }
                 }
               }
               container link-state-information {
                 container link-state-link {
                   leaf link-name {
                     type string;
                   }
                   leaf color {
                     type int32;
                   }
                   leaf metric {
                     type int32;
                   }
                   leaf te-metric {
                     type int32;
                     description
                       "LSP TE metric";
                   }
                   leaf link-avg-delay {
                     type uint32;
                   }
                   leaf link-min-delay {
                     type uint32;
                   }
                   leaf link-max-delay {
                     type uint32;
                   }
                   leaf link-avg-delay-var {
                     type uint32;
                   }
                   leaf ldp-support {
                     type string;
                   }
                   leaf rsvpte-support {
                     type string;
                   }
                   leaf maximum-bw {
                     type uint64;
                   }
                   leaf reservable-bw {
                     type uint64;
                   }
                   container protections {
                     leaf-list protection-type {
                       type string;
                       description
                         "LSP protection desired";
                     }
                   }
                   container link-srlgs {
                     leaf-list link-srlg {
                       type string;
                     }
                   }
                   container unreserved-bws {
                     list unreserved-bw {
                       key "unreserved-bw-priority";
                       leaf unreserved-bw-priority {
                         type uint32;
                       }
                       leaf unreserved-bw-value {
                         type string;
                       }
                     }
                   }
                   container link-state-link-opaque-attrs {
                     leaf link-state-link-opaque-attrs-length {
                       type uint32;
                     }
                     leaf link-state-link-opaque-attrs-bytes {
                       type string;
                     }
                   }
                   container link-adj-sids {
                     list link-lan-adj-sid {
                       key "link-lan-adj-sid-label";
                       leaf link-lan-adj-sid-af {
                         type string;
                       }
                       leaf link-lan-adj-sid-label {
                         type uint32;
                       }
                       leaf link-lan-adj-sid-flags {
                         type string;
                       }
                       leaf link-lan-adj-sid-weight {
                         type uint32;
                       }
                       leaf link-lan-adj-sid-neighbor {
                         type string;
                       }
                     }
                     list link-p2p-adj-sid {
                       key "link-p2p-adj-sid-label";
                       leaf link-p2p-adj-sid-af {
                         type string;
                       }
                       leaf link-p2p-adj-sid-label {
                         type uint32;
                       }
                       leaf link-p2p-adj-sid-flags {
                         type string;
                       }
                       leaf link-p2p-adj-sid-weight {
                         type uint32;
                       }
                     }
                   }
                   container link-bgp-peer-sids {
                     list link-bgp-peer-sid {
                       key "link-bgp-peer-sid-label";
                       leaf link-bgp-peer-sid-label {
                         type uint32;
                       }
                       leaf link-bgp-peer-sid-flags {
                         type string;
                       }
                       leaf link-bgp-peer-sid-weight {
                         type uint32;
                       }
                     }
                   }
                   container link-srv6-end-x-sids {
                     list link-srv6-end-x-sid {
                       key "link-srv6-end-x-sid-val";
                       leaf link-srv6-end-x-sid-type {
                         type string;
                       }
                       leaf link-srv6-end-x-sid-val {
                         type jt:ipv6addr;
                       }
                       leaf link-srv6-end-x-sid-flags {
                         type string;
                       }
                       leaf link-srv6-end-x-sid-weight {
                         type int32;
                       }
                       leaf link-srv6-end-x-sid-algo {
                         type int32;
                       }
                       leaf link-srv6-end-x-sid-func {
                         type string;
                       }
                       leaf link-srv6-end-x-sid-lan-neighbor-id {
                         type string;
                       }
                       container link-srv6-end-x-sid-sstlv {
                         leaf link-srv6-end-x-sid-sstlv-header {
                           type empty;
                         }
                         leaf link-srv6-end-x-sid-sstlv-blen {
                           type uint32;
                         }
                         leaf link-srv6-end-x-sid-sstlv-nlen {
                           type uint32;
                         }
                         leaf link-srv6-end-x-sid-sstlv-flen {
                           type uint32;
                         }
                         leaf link-srv6-end-x-sid-sstlv-alen {
                           type uint32;
                         }
                       }
                     }
                   }
                   container link-msd-types {
                     list link-msd-entry {
                       key "link-msd-type";
                       leaf link-msd-type {
                         type uint32;
                       }
                       leaf link-msd-value {
                         type uint32;
                       }
                     }
                   }
                 }
                 container link-state-node {
                   leaf node-name {
                     type string;
                   }
                   leaf area-border-router {
                     type string;
                   }
                   leaf external-router {
                     type string;
                   }
                   leaf attached {
                     type string;
                   }
                   leaf overload {
                     type string;
                   }
                   container node-areas {
                     leaf-list node-area {
                       type string;
                     }
                   }
                   container node-ipv4-router-ids {
                     leaf-list node-ipv4-router-id {
                       type jt:ipaddr;
                     }
                   }
                   container node-ipv6-router-ids {
                     leaf-list node-ipv6-router-id {
                       type jt:ipaddr;
                     }
                   }
                   container node-topologies {
                     list node-topology {
                       key "id";
                       leaf id {
                         type uint32;
                       }
                     }
                   }
                   container link-state-node-opaque-attrs {
                     leaf link-state-node-opaque-attrs-length {
                       type uint32;
                     }
                     leaf link-state-node-opaque-attrs-bytes {
                       type string;
                     }
                   }
                   container node-spring-capability {
                     list node-spring-srgb-block {
                       key "node-spring-srgb-block-start node-spring-srgb-block-range";
                       leaf node-spring-srgb-block-start {
                         type uint32;
                       }
                       leaf node-spring-srgb-block-range {
                         type uint32;
                       }
                       leaf node-spring-srgb-block-flags {
                         type string;
                       }
                     }
                   }
                   container node-msd-types {
                     list node-msd-entry {
                       key "node-msd-type";
                       leaf node-msd-type {
                         type uint32;
                       }
                       leaf node-msd-value {
                         type uint32;
                       }
                     }
                   }
                   container node-srv6-capability {
                     leaf node-srv6-capability-flag {
                       type uint32;
                     }
                   }
                   container node-spring-algorithms {
                     list node-spring-algorithm {
                       key "node-spring-algorithm-type";
                       leaf node-spring-algorithm-type {
                         type uint32;
                       }
                     }
                   }
                   container node-spring-falgo-defs {
                     list node-spring-falgo-def {
                       key "node-spring-falgo-def-algo";
                       leaf node-spring-falgo-def-algo {
                         type uint32;
                       }
                       leaf node-spring-falgo-def-metric-type {
                         type uint32;
                       }
                       leaf node-spring-falgo-def-calculation-type {
                         type uint32;
                       }
                       leaf node-spring-falgo-def-priority {
                         type uint32;
                       }
                       leaf node-spring-falgo-def-flags {
                         type string;
                       }
                       leaf node-spring-falgo-def-include-any {
                         type string;
                       }
                       leaf node-spring-falgo-def-exclude {
                         type string;
                       }
                       leaf node-spring-falgo-def-include-all {
                         type string;
                       }
                     }
                   }
                 }
                 list link-state-te-policy-cp-segment {
                 }
                 container link-state-te-policy-cp {
                   leaf link-state-te-policy-cp-name {
                     type string;
                   }
                   leaf link-state-te-policy-cp-flags {
                     type string;
                   }
                   leaf link-state-te-policy-cp-preference {
                     type uint32;
                   }
                   leaf link-state-te-policy-cp-priority {
                     type uint32;
                   }
                   leaf link-state-te-policy-cp-constraint-header {
                     type empty;
                   }
                   leaf link-state-te-policy-cp-constraint-flags {
                     type string;
                   }
                   leaf link-state-te-policy-cp-mtid {
                     type uint32;
                   }
                   leaf link-state-te-policy-cp-algo {
                     type uint32;
                   }
                   leaf link-state-te-policy-cp-exclude-any {
                     type string;
                   }
                   leaf link-state-te-policy-cp-include-any {
                     type string;
                   }
                   leaf link-state-te-policy-cp-include-all {
                     type string;
                   }
                   leaf link-state-te-policy-cp-bandwidth {
                     type uint32;
                   }
                   leaf link-state-te-policy-cp-bsid-flags {
                     type string;
                   }
                   leaf link-state-te-policy-cp-mpls-bsid {
                     type uint32;
                   }
                   leaf link-state-te-policy-cp-mpls-spec-bsid {
                     type uint32;
                   }
                   leaf link-state-te-policy-cp-segment-list-count {
                     type int32;
                   }
                   container link-state-te-policy-cp-srv6-bsid-info {
                     leaf link-state-te-policy-cp-srv6-bsid-flags {
                       type string;
                       description
                         "SRv6 BSID flags";
                     }
                     leaf link-state-te-policy-cp-srv6-bsid {
                       type jt:ipv6addr;
                       description
                         "SRv6 BSID";
                     }
                     leaf link-state-te-policy-cp-srv6-spec-bsid {
                       type jt:ipv6addr;
                       description
                         "Specified SRv6 BSID";
                     }
                     leaf link-state-te-policy-cp-srv6-bsid-ep-bhv {
                       type uint32;
                       description
                         "SRv6 BSID endpoint behavior";
                     }
                     leaf link-state-te-policy-cp-srv6-bsid-ep-bhv-flags {
                       type string;
                       description
                         "SRv6 BSID endpoint behavior flags";
                     }
                     leaf link-state-te-policy-cp-srv6-bsid-ep-bhv-algo {
                       type uint32;
                       description
                         "SRv6 BSID endpoint behavior algo";
                     }
                     leaf link-state-te-policy-cp-srv6-bsid-sstlv {
                       type string;
                       description
                         "SRv6 BSID endpoint behavior SSTLV";
                     }
                   }
                   list link-state-te-policy-cp-segment-list {
                     key "link-state-te-policy-cp-segment-list-index";
                     leaf link-state-te-policy-cp-segment-list-index {
                       type int32;
                     }
                     leaf link-state-te-policy-cp-segment-list-flags {
                       type string;
                     }
                     leaf link-state-te-policy-cp-segment-list-mtid {
                       type uint32;
                     }
                     leaf link-state-te-policy-cp-segment-list-weight {
                       type uint32;
                     }
                     leaf link-state-te-policy-cp-segment-list-algo {
                       type uint32;
                     }
                     leaf link-state-te-policy-cp-segment-list-metric-type {
                       type string;
                     }
                     leaf link-state-te-policy-cp-segment-list-metric-value {
                       type uint32;
                     }
                     leaf link-state-te-policy-cp-segment-count {
                       type int32;
                     }
                     leaf link-state-te-policy-cp-segment-header {
                       type empty;
                     }
                     list link-state-te-policy-cp-segment {
                       leaf link-state-te-policy-cp-mpls-segment-id {
                         type uint32;
                       }
                       leaf link-state-te-policy-cp-srv6-segment-id {
                         type jt:ipv6addr;
                       }
                       leaf link-state-te-policy-cp-segment-descriptor {
                         type jt:ipaddr;
                       }
                       leaf link-state-te-policy-cp-segment-flags {
                         type string;
                       }
                       leaf link-state-te-policy-cp-segment-ep-bhv {
                         type string;
                       }
                       leaf link-state-te-policy-cp-segment-ep-bhv-flags {
                         type uint32;
                       }
                       leaf link-state-te-policy-cp-segment-ep-bhv-algo {
                         type uint32;
                       }
                       container link-state-te-policy-cp-segment-sstlv {
                         leaf link-state-te-policy-cp-segment-sstlv-header {
                           type empty;
                         }
                         leaf link-state-te-policy-cp-segment-sstlv-blen {
                           type uint32;
                         }
                         leaf link-state-te-policy-cp-segment-sstlv-nlen {
                           type uint32;
                         }
                         leaf link-state-te-policy-cp-segment-sstlv-flen {
                           type uint32;
                         }
                         leaf link-state-te-policy-cp-segment-sstlv-alen {
                           type uint32;
                         }
                       }
                     }
                   }
                 }
                 container link-state-prefix {
                   leaf link-state-prefix-attr-flags {
                     type string;
                   }
                   leaf link-state-prefix-metric {
                     type uint32;
                   }
                   list link-state-prefix-sid {
                     key "link-state-prefix-sid-index link-state-prefix-sid-flags link-state-prefix-sid-algo";
                     leaf link-state-prefix-sid-index {
                       type uint32;
                     }
                     leaf link-state-prefix-sid-flags {
                       type string;
                     }
                     leaf link-state-prefix-sid-algo {
                       type string;
                     }
                   }
                   container link-state-prefix-srv6-locator {
                     leaf link-state-prefix-srv6-locator-flags {
                       type string;
                     }
                     leaf link-state-prefix-srv6-locator-algo {
                       type string;
                     }
                     leaf link-state-prefix-srv6-locator-metric {
                       type string;
                     }
                   }
                   list link-state-prefix-fapm {
                     key "link-state-prefix-fapm-algo";
                     leaf link-state-prefix-fapm-algo {
                       type uint32;
                     }
                     leaf link-state-prefix-fapm-metric {
                       type uint32;
                     }
                   }
                 }
                 container link-state-srv6-endsid {
                   container link-state-srv6-endsid-info {
                     leaf link-state-srv6-endsid-epb {
                       type string;
                     }
                     leaf link-state-srv6-endsid-flags {
                       type string;
                     }
                     leaf link-state-srv6-endsid-algo {
                       type string;
                     }
                     container link-state-srv6-endsid-sstlv {
                       leaf link-state-srv6-endsid-sstlv-header {
                         type empty;
                       }
                       leaf link-state-srv6-endsid-sstlv-blen {
                         type uint32;
                       }
                       leaf link-state-srv6-endsid-sstlv-nlen {
                         type uint32;
                       }
                       leaf link-state-srv6-endsid-sstlv-flen {
                         type uint32;
                       }
                       leaf link-state-srv6-endsid-sstlv-alen {
                         type uint32;
                       }
                     }
                   }
                 }
                 container link-state-unknown-tlvs {
                   list link-state-unknown-tlv {
                     key "unknown-type";
                     leaf unknown-type {
                       type uint32;
                     }
                     leaf unknown-length {
                       type uint32;
                     }
                     leaf unknown-bytes {
                       type string;
                     }
                   }
                 }
               }
               container aggregate {
                 leaf aggregate-truncate {
                   type string;
                 }
                 container aggregate-as-path {
                   container bgp-path-attributes {
                     container attr-as-path {
                       description
                         "AS Path Attribute";
                       leaf attr-length {
                         type string;
                       }
                       leaf flags {
                         type string;
                         description
                           "Enabled trace flags";
                       }
                     }
                     container attr-as4-path {
                       description
                         "4-byte AS Path Attribute";
                       leaf attr-length {
                         type string;
                       }
                     }
                     container attr-as-path-effective {
                       description
                         "Effective AS-Path Attribute";
                       leaf attr-length {
                         type string;
                       }
                     }
                     container attr-aggregator {
                       description
                         "Aggregator Attribute";
                       leaf attr-length {
                         type string;
                       }
                     }
                     container attr-aggregator4 {
                       description
                         "Aggregator4 Attribute";
                       leaf attr-length {
                         type string;
                       }
                     }
                     container attr-cluster-list {
                       description
                         "Cluster List Attribute";
                       leaf attr-length {
                         type string;
                       }
                     }
                     container attr-originator-id {
                       description
                         "Originator Attribute";
                       leaf attr-length {
                         type string;
                       }
                     }
                   }
                   leaf as-path {
                     type string;
                     description
                       "Name of AS path regular expression (BGP only)";
                   }
                   leaf reference-count {
                     type int32;
                     description
                       "Reference count";
                   }
                   leaf as-path-length {
                     type int32;
                   }
                   leaf aggregate-truncate {
                     type string;
                   }
                 }
                 leaf aggregate-flags {
                   type string;
                   description
                     "Flags on this aggregate route entry";
                 }
                 leaf aggregate-depth {
                   type int32;
                   description
                     "Depth of this aggregate";
                 }
                 leaf aggregate-active {
                   type empty;
                   description
                     "Present if this aggregate is active";
                 }
                 leaf aggregate-algo {
                   type uint32;
                   description
                     "Algorithm number";
                 }
                 leaf contributing-route-count {
                   type int32;
                   description
                     "Number of contributing routes in this aggregate";
                 }
                 leaf aggregate-policy-name {
                   type string;
                 }
                 list aggregated-route {
                   key "destination-prefix";
                   leaf destination-prefix {
                     type string;
                     description
                       "Destination prefix and mask";
                   }
                   leaf protocol-name {
                     type string;
                   }
                 }
               }
               list kern-nhexpand {
                 description
                   "Next-hop gateway information";
                 container srv6-info {
                   leaf srv6-info-srh-sid-mode {
                     type string;
                     description
                       "Reduced/non-reduced mode for SRH";
                   }
                   leaf srv6-info-packet-mode {
                     type string;
                     description
                       "Packet mode for SRV6-Tunnel";
                   }
                   leaf srv6-info-srh-last-sid {
                     type string;
                     description
                       "Remove last sid for ACX";
                   }
                   leaf srv6-info-dyn-tunnel {
                     type string;
                     description
                       "SRv6 tunnel created dynamically";
                   }
                   leaf srv6-cos-propagation {
                     type string;
                     description
                       "SRv6 CoS propagation";
                   }
                   leaf srv6-ttl-propagation {
                     type string;
                     description
                       "SRv6 TTL propagation";
                   }
                   leaf srv6-source {
                     type jt:ipaddr;
                     description
                       "Source IPv6 address";
                   }
                   leaf srv6-destination {
                     type jt:ipaddr;
                     description
                       "Destination IPv6 address";
                   }
                   list srv6-segment-list {
                     key "srv6-segment-list-index";
                     description
                       "SRH Segment list";
                     leaf srv6-segment-list-index {
                       type uint32;
                       description
                         "SRH segment list index";
                     }
                     leaf srv6-segment-list-addr {
                       type jt:ipaddr;
                       description
                         "SRH segment address";
                     }
                   }
                 }
               }
               container kern-nh-platform-layer-input {
                 list kern-nhexpand {
                   description
                     "Next-hop gateway information";
                   container srv6-info {
                     leaf srv6-info-srh-sid-mode {
                       type string;
                       description
                         "Reduced/non-reduced mode for SRH";
                     }
                     leaf srv6-info-packet-mode {
                       type string;
                       description
                         "Packet mode for SRV6-Tunnel";
                     }
                     leaf srv6-info-srh-last-sid {
                       type string;
                       description
                         "Remove last sid for ACX";
                     }
                     leaf srv6-info-dyn-tunnel {
                       type string;
                       description
                         "SRv6 tunnel created dynamically";
                     }
                     leaf srv6-cos-propagation {
                       type string;
                       description
                         "SRv6 CoS propagation";
                     }
                     leaf srv6-ttl-propagation {
                       type string;
                       description
                         "SRv6 TTL propagation";
                     }
                     leaf srv6-source {
                       type jt:ipaddr;
                       description
                         "Source IPv6 address";
                     }
                     leaf srv6-destination {
                       type jt:ipaddr;
                       description
                         "Destination IPv6 address";
                     }
                     list srv6-segment-list {
                       key "srv6-segment-list-index";
                       description
                         "SRH Segment list";
                       leaf srv6-segment-list-index {
                         type uint32;
                         description
                           "SRH segment list index";
                       }
                       leaf srv6-segment-list-addr {
                         type jt:ipaddr;
                         description
                           "SRH segment address";
                       }
                     }
                   }
                 }
               }
               container kern-nh-platform-layer-output {
                 list kern-nhexpand {
                   description
                     "Next-hop gateway information";
                   container srv6-info {
                     leaf srv6-info-srh-sid-mode {
                       type string;
                       description
                         "Reduced/non-reduced mode for SRH";
                     }
                     leaf srv6-info-packet-mode {
                       type string;
                       description
                         "Packet mode for SRV6-Tunnel";
                     }
                     leaf srv6-info-srh-last-sid {
                       type string;
                       description
                         "Remove last sid for ACX";
                     }
                     leaf srv6-info-dyn-tunnel {
                       type string;
                       description
                         "SRv6 tunnel created dynamically";
                     }
                     leaf srv6-cos-propagation {
                       type string;
                       description
                         "SRv6 CoS propagation";
                     }
                     leaf srv6-ttl-propagation {
                       type string;
                       description
                         "SRv6 TTL propagation";
                     }
                     leaf srv6-source {
                       type jt:ipaddr;
                       description
                         "Source IPv6 address";
                     }
                     leaf srv6-destination {
                       type jt:ipaddr;
                       description
                         "Destination IPv6 address";
                     }
                     list srv6-segment-list {
                       key "srv6-segment-list-index";
                       description
                         "SRH Segment list";
                       leaf srv6-segment-list-index {
                         type uint32;
                         description
                           "SRH segment list index";
                       }
                       leaf srv6-segment-list-addr {
                         type jt:ipaddr;
                         description
                           "SRH segment address";
                       }
                     }
                   }
                 }
               }
               list nh {
                 description
                   "Next-hop gateway information";
                 leaf selected-next-hop {
                   type empty;
                   description
                     "Present if this next hop is selected";
                 }
                 leaf to {
                   type string;
                   description
                     "Neighbor address to which to send (next-hop address)";
                 }
                 leaf nh-indirect-fnh-type {
                   type string;
                   description
                     "Indirect pointing to a well-known nexthop";
                 }
                 leaf via {
                   type string;
                   description
                     "Reachable via a local interface";
                 }
                 container vxlan-header-rewrite {
                   description
                     "VXLAN tunnel rewrite information";
                   leaf vxlan-header-rewrite-mtu {
                     type int32;
                     description
                       "VXLAN tunnel MTU";
                   }
                   leaf vxlan-header-rewrite-flags {
                     type int32;
                     description
                       "VXLAN tunnel flags";
                   }
                   leaf vxlan-header-rewrite-encap-rtb-id {
                     type int32;
                     description
                       "VXLAN tunnel encapsulation table ID";
                   }
                   leaf vxlan-header-rewrite-decap-rtb-id {
                     type int32;
                     description
                       "VXLAN tunnel decapsulation table ID";
                   }
                   leaf vxlan-header-rewrite-encap-vnid {
                     type int32;
                     description
                       "VXLAN tunnel encapsulation VNI";
                   }
                   leaf vxlan-header-rewrite-decap-vnid {
                     type int32;
                     description
                       "VXLAN tunnel decapsulation VNI";
                   }
                   leaf vxlan-header-rewrite-svtep {
                     type jt:ipaddr;
                     description
                       "Source VTEP address";
                   }
                   leaf vxlan-header-rewrite-dvtep {
                     type jt:ipaddr;
                     description
                       "Destination VTEP address";
                   }
                   leaf vxlan-header-rewrite-smac {
                     type string;
                     description
                       "Source MAC address";
                   }
                   leaf vxlan-header-rewrite-dmac {
                     type string;
                     description
                       "Destination MAC address";
                   }
                 }
                 container srv6-info {
                   leaf srv6-info-srh-sid-mode {
                     type string;
                     description
                       "Reduced/non-reduced mode for SRH";
                   }
                   leaf srv6-info-packet-mode {
                     type string;
                     description
                       "Packet mode for SRV6-Tunnel";
                   }
                   leaf srv6-info-srh-last-sid {
                     type string;
                     description
                       "Remove last sid for ACX";
                   }
                   leaf srv6-info-dyn-tunnel {
                     type string;
                     description
                       "SRv6 tunnel created dynamically";
                   }
                   leaf srv6-cos-propagation {
                     type string;
                     description
                       "SRv6 CoS propagation";
                   }
                   leaf srv6-ttl-propagation {
                     type string;
                     description
                       "SRv6 TTL propagation";
                   }
                   leaf srv6-source {
                     type jt:ipaddr;
                     description
                       "Source IPv6 address";
                   }
                   leaf srv6-destination {
                     type jt:ipaddr;
                     description
                       "Destination IPv6 address";
                   }
                   list srv6-segment-list {
                     key "srv6-segment-list-index";
                     description
                       "SRH Segment list";
                     leaf srv6-segment-list-index {
                       type uint32;
                       description
                         "SRH segment list index";
                     }
                     leaf srv6-segment-list-addr {
                       type jt:ipaddr;
                       description
                         "SRH segment address";
                     }
                   }
                 }
                 leaf nh-string {
                   type string;
                 }
                 leaf nh-table-receive {
                   type string;
                   description
                     "Destination is a local address";
                 }
                 leaf nh-table {
                   type string;
                   description
                     "Indirect pointing to another table";
                 }
                 leaf nh-table-localized {
                   type string;
                   description
                     "Indirect pointing to a localized table";
                 }
                 leaf nh-localized-ifl {
                   type string;
                   description
                     "Indirect pointing to a localized ifl";
                 }
                 leaf lsp-name {
                   type string;
                   description
                     "Tunneled into an RSVP LSP";
                 }
                 leaf mpls-label {
                   type string;
                   description
                     "Label of MPLS packet";
                 }
                 leaf nh-local-interface {
                   type string;
                   description
                     "Destination is a local interface";
                 }
                 leaf nh-service {
                   type string;
                   description
                     "Next-hop service";
                 }
                 leaf nh-private-comp {
                   type string;
                   description
                     "Private Composite Next-hop";
                 }
                 leaf srv6-prefix-sid {
                   type jt:ipaddr;
                   description
                     "SRv6 prefixe sid value";
                 }
                 leaf srv6-encap-brief {
                   type string;
                   description
                     "IPV6 SR-header encapsulation";
                 }
                 leaf elnh-address {
                   type string;
                   description
                     "Address of Element Next-hop";
                 }
                 leaf localized-table {
                   type string;
                   description
                     "Name of localized table";
                 }
                 leaf ae-member-interface {
                   type string;
                   description
                     "AE Member interface";
                 }
                 leaf weight {
                   type int32;
                   description
                     "Next-hop weight";
                 }
                 leaf balance {
                   type int32;
                   description
                     "Next-hop balance";
                 }
                 leaf uflags {
                   type string;
                   description
                     "Next-hop uflags";
                 }
                 leaf filter {
                   type string;
                   description
                     "Next-hop firewall filter";
                 }
                 leaf session {
                   type string;
                   description
                     "Session ID Associated with this NH";
                 }
                 leaf statistics-id-group-terse {
                   type string;
                   description
                     "Statistics ID Group Associated with this NH";
                 }
                 leaf app-specific-opaque {
                   type string;
                   description
                     "Application specific opaque data dump";
                 }
                 leaf gw-opaque {
                   type string;
                   description
                     "Nexthops gateway opaque data handle";
                 }
                 leaf statistics-pkts-count {
                   type int32;
                   description
                     "Statistics packet count Associated with this NH";
                 }
                 leaf statistics-bytes-count {
                   type int32;
                   description
                     "Statistics bytes count Associated with this NH";
                 }
                 leaf ext-int-type {
                   type string;
                   description
                     "Next-hop type of equal-external-internal multipath";
                 }
                 leaf fc {
                   type int32;
                   description
                     "Forwarding-class";
                 }
                 leaf label-ttl-action {
                   type string;
                   description
                     "TTL action associated with labels";
                 }
                 leaf load-balance-label {
                   type string;
                   description
                     "Load balance action associated with labels";
                 }
                 leaf label-element {
                   type string;
                   description
                     "Pointer to the tag label element";
                 }
                 leaf label-element-parent {
                   type string;
                   description
                     "Pointer to the tag label element parent";
                 }
                 leaf label-element-refcount {
                   type string;
                   description
                     "Number of references to the tag label element";
                 }
                 leaf label-element-childcount {
                   type string;
                   description
                     "Number of child references to the tag label element";
                 }
                 leaf label-element-lspid {
                   type string;
                   description
                     "LSP ID of the tag label element";
                 }
                 leaf nh-service-pkt-dist {
                   type string;
                   description
                     "Multi services packet distribution type";
                 }
                 leaf nh-service-app-data {
                   type string;
                   description
                     "Multi services application specific data";
                 }
                 leaf nh-index {
                   type uint32;
                   description
                     "Next-hop index";
                 }
                 leaf nh-address {
                   type string;
                   description
                     "Address of next hop";
                 }
                 leaf nh-reference-count {
                   type int32;
                   description
                     "Number of references to this next hop";
                 }
                 leaf tunnel-composite-attr-type {
                   type string;
                   description
                     "Tunnel-Type for tunnel-composite-nexthop";
                 }
                 leaf tunnel-composite-attr-subtype {
                   type string;
                   description
                     "Tunnel-Subtype for tunnel-composite-nexthop";
                 }
                 leaf tunnel-composite-attr-reference-count {
                   type int32;
                   description
                     "Tunnel-reference-count for tunnel-composite-nexthop";
                 }
                 leaf tunnel-composite-attr-nh-id {
                   type int32;
                   description
                     "Tunnel-NextHop-Id for tunnel-composite-nexthop";
                 }
                 leaf tunnel-composite-attr-dest {
                   type jt:ipaddr;
                   description
                     "Tunnel-Destination for tunnel-composite-nexthop";
                 }
                 leaf tunnel-composite-attr-src {
                   type jt:ipaddr;
                   description
                     "Tunnel-Source for tunnel-composite-nexthop";
                 }
                 leaf tunnel-composite-attr-tunnel-endpoint {
                   type jt:ipaddr;
                   description
                     "Tunnel-Endpoint for tunnel-composite-nexthop";
                 }
                 leaf tunnel-composite-anchor-pfe {
                   type string;
                   description
                     "Anchor PFE name, if tunnel nexthop is localized";
                 }
                 leaf tunnel-composite-encap-rtb-id {
                   type int32;
                   description
                     "Tunnel encap routing table index";
                 }
                 leaf tunnel-composite-decap-rtb-id {
                   type int32;
                   description
                     "Tunnel decap routing table index";
                 }
                 leaf tunnel-composite-attr-ttl {
                   type int32;
                   description
                     "Tunnel-TTL for tunnel-composite-nexthop";
                 }
                 leaf tunnel-composite-attr-udp-port {
                   type int32;
                   description
                     "Tunnel-UDP-Destination port for 
                     tunnel-composite-nexthop";
                 }
                 leaf tunnel-composite-attr-fc-id {
                   type int32;
                   description
                     "Tunnel-Forwarding-Class-ID for 
                     tunnel-composite-nexthop";
                 }
                 leaf tunnel-composite-attr-tid {
                   type int32;
                   description
                     "Tunnel-Id for tunnel-composite-nexthop";
                 }
                 leaf tunnel-composite-attr-label {
                   type string;
                   description
                     "Tunnel-VPN-Label for tunnel-composite-nexthop";
                 }
                 leaf tunnel-composite-attr-label-ttl {
                   type string;
                   description
                     "Tunnel-VPN-Label-TTL for tunnel-composite-nexthop";
                 }
                 leaf tunnel-composite-attr-gre-key {
                   type int32;
                   description
                     "GRE key for tunnel-composite-nexthop";
                 }
                 leaf-list tunnel-composite-attr-segment-addr {
                   type jt:ipaddr;
                   description
                     "IPv6 segment-address";
                 }
                 leaf-list tunnel-composite-attr-sid {
                   type int32;
                   description
                     "IPv6 segment-sid";
                 }
                 leaf tunnel-composite-attr-vni {
                   type int32;
                   description
                     "Tunnel-VNI for tunnel-composite-nexthop in VxLAN";
                 }
                 leaf tunnel-composite-attr-dest-mac {
                   type string;
                   description
                     "Tunnel-Dest-Mac for tunnel-composite-nexthop in VxLAN";
                 }
                 leaf translate-composite-attr-type {
                   type string;
                   description
                     "Translation type for translate-composite-nexthop";
                 }
                 leaf translate-composite-attr-flags {
                   type string;
                   description
                     "Flags for translate-composite-nexthop";
                 }
                 leaf translate-composite-attr-reference-count {
                   type int32;
                   description
                     "Reference count for translate-composite-nexthop";
                 }
                 leaf translate-composite-attr-nh-id {
                   type int32;
                   description
                     "NextHop id for translate-composite-nexthop";
                 }
                 leaf translate-composite-attr-dest {
                   type jt:ipaddr;
                   description
                     "Translation destination for 
                     translate-composite-nexthop";
                 }
                 leaf translate-composite-attr-dest-plen {
                   type int32;
                   description
                     "Translation destination prefix length for 
                     translate-composite-nexthop";
                 }
                 leaf translate-composite-attr-src {
                   type jt:ipaddr;
                   description
                     "Translation source for translate-composite-nexthop";
                 }
                 leaf translate-composite-attr-src-plen {
                   type int32;
                   description
                     "Translation source prefix length for 
                     translate-composite-nexthop";
                 }
                 leaf translate-composite-attr-dest-alg-type {
                   type string;
                   description
                     "Destination algorithm type for 
                     translate-composite-nexthop";
                 }
                 leaf translate-composite-attr-src-alg-type {
                   type string;
                   description
                     "Source algorithm type for translate-composite-nexthop";
                 }
                 leaf translate-composite-attr-dest-vrf-id {
                   type int32;
                   description
                     "Destination vrf id for translate-composite-nexthop";
                 }
                 leaf translate-composite-attr-src-vrf-id {
                   type int32;
                   description
                     "Source vrf id for translate-composite-nexthop";
                 }
                 leaf translate-composite-attr-hoplimit {
                   type int32;
                   description
                     "Hoplimit for translate-composite-nexthop";
                 }
                 leaf translate-composite-attr-traffic-class {
                   type int32;
                   description
                     "Traffic class for translate-composite-nexthop";
                 }
                 leaf translate-composite-attr-ttl {
                   type int32;
                   description
                     "Ttl for translate-composite-nexthop";
                 }
                 leaf translate-composite-attr-tos {
                   type int32;
                   description
                     "Tos for translate-composite-nexthop";
                 }
               }
               container protocol-nh {
                 description
                   "Protocol next hop";
                 list nh {
                   description
                     "Next-hop gateway information";
                   container vxlan-header-rewrite {
                     description
                       "VXLAN tunnel rewrite information";
                     leaf vxlan-header-rewrite-mtu {
                       type int32;
                       description
                         "VXLAN tunnel MTU";
                     }
                     leaf vxlan-header-rewrite-flags {
                       type int32;
                       description
                         "VXLAN tunnel flags";
                     }
                     leaf vxlan-header-rewrite-encap-rtb-id {
                       type int32;
                       description
                         "VXLAN tunnel encapsulation table ID";
                     }
                     leaf vxlan-header-rewrite-decap-rtb-id {
                       type int32;
                       description
                         "VXLAN tunnel decapsulation table ID";
                     }
                     leaf vxlan-header-rewrite-encap-vnid {
                       type int32;
                       description
                         "VXLAN tunnel encapsulation VNI";
                     }
                     leaf vxlan-header-rewrite-decap-vnid {
                       type int32;
                       description
                         "VXLAN tunnel decapsulation VNI";
                     }
                     leaf vxlan-header-rewrite-svtep {
                       type jt:ipaddr;
                       description
                         "Source VTEP address";
                     }
                     leaf vxlan-header-rewrite-dvtep {
                       type jt:ipaddr;
                       description
                         "Destination VTEP address";
                     }
                     leaf vxlan-header-rewrite-smac {
                       type string;
                       description
                         "Source MAC address";
                     }
                     leaf vxlan-header-rewrite-dmac {
                       type string;
                       description
                         "Destination MAC address";
                     }
                   }
                   container srv6-info {
                     leaf srv6-info-srh-sid-mode {
                       type string;
                       description
                         "Reduced/non-reduced mode for SRH";
                     }
                     leaf srv6-info-packet-mode {
                       type string;
                       description
                         "Packet mode for SRV6-Tunnel";
                     }
                     leaf srv6-info-srh-last-sid {
                       type string;
                       description
                         "Remove last sid for ACX";
                     }
                     leaf srv6-info-dyn-tunnel {
                       type string;
                       description
                         "SRv6 tunnel created dynamically";
                     }
                     leaf srv6-cos-propagation {
                       type string;
                       description
                         "SRv6 CoS propagation";
                     }
                     leaf srv6-ttl-propagation {
                       type string;
                       description
                         "SRv6 TTL propagation";
                     }
                     leaf srv6-source {
                       type jt:ipaddr;
                       description
                         "Source IPv6 address";
                     }
                     leaf srv6-destination {
                       type jt:ipaddr;
                       description
                         "Destination IPv6 address";
                     }
                     list srv6-segment-list {
                       key "srv6-segment-list-index";
                       description
                         "SRH Segment list";
                       leaf srv6-segment-list-index {
                         type uint32;
                         description
                           "SRH segment list index";
                       }
                       leaf srv6-segment-list-addr {
                         type jt:ipaddr;
                         description
                           "SRH segment address";
                       }
                     }
                   }
                   leaf nh-string {
                     type string;
                   }
                   leaf elnh-address {
                     type string;
                     description
                       "Address of Element Next-hop";
                   }
                   leaf to {
                     type string;
                     description
                       "Neighbor address to which to send (next-hop address)";
                   }
                   leaf via {
                     type string;
                     description
                       "Reachable via a local interface";
                   }
                   leaf localized-table {
                     type string;
                     description
                       "Name of localized table";
                   }
                   leaf ae-member-interface {
                     type string;
                     description
                       "AE Member interface";
                   }
                   leaf weight {
                     type int32;
                     description
                       "Next-hop weight";
                   }
                   leaf balance {
                     type int32;
                     description
                       "Next-hop balance";
                   }
                   leaf uflags {
                     type string;
                     description
                       "Next-hop uflags";
                   }
                   leaf filter {
                     type string;
                     description
                       "Next-hop firewall filter";
                   }
                   leaf selected-next-hop {
                     type empty;
                     description
                       "Present if this next hop is selected";
                   }
                   leaf session {
                     type string;
                     description
                       "Session ID Associated with this NH";
                   }
                   leaf statistics-id-group-terse {
                     type string;
                     description
                       "Statistics ID Group Associated with this NH";
                   }
                   leaf app-specific-opaque {
                     type string;
                     description
                       "Application specific opaque data dump";
                   }
                   leaf gw-opaque {
                     type string;
                     description
                       "Nexthops gateway opaque data handle";
                   }
                   leaf statistics-pkts-count {
                     type int32;
                     description
                       "Statistics packet count Associated with this NH";
                   }
                   leaf statistics-bytes-count {
                     type int32;
                     description
                       "Statistics bytes count Associated with this NH";
                   }
                   leaf ext-int-type {
                     type string;
                     description
                       "Next-hop type of equal-external-internal multipath";
                   }
                   leaf fc {
                     type int32;
                     description
                       "Forwarding-class";
                   }
                   leaf lsp-name {
                     type string;
                     description
                       "Tunneled into an RSVP LSP";
                   }
                   leaf mpls-label {
                     type string;
                     description
                       "Label of MPLS packet";
                   }
                   leaf label-ttl-action {
                     type string;
                     description
                       "TTL action associated with labels";
                   }
                   leaf load-balance-label {
                     type string;
                     description
                       "Load balance action associated with labels";
                   }
                   leaf label-element {
                     type string;
                     description
                       "Pointer to the tag label element";
                   }
                   leaf label-element-parent {
                     type string;
                     description
                       "Pointer to the tag label element parent";
                   }
                   leaf label-element-refcount {
                     type string;
                     description
                       "Number of references to the tag label element";
                   }
                   leaf label-element-childcount {
                     type string;
                     description
                       "Number of child references to the tag label element";
                   }
                   leaf label-element-lspid {
                     type string;
                     description
                       "LSP ID of the tag label element";
                   }
                   leaf nh-table-receive {
                     type string;
                     description
                       "Destination is a local address";
                   }
                   leaf nh-table {
                     type string;
                     description
                       "Indirect pointing to another table";
                   }
                   leaf nh-localized-ifl {
                     type string;
                     description
                       "Indirect pointing to a localized ifl";
                   }
                   leaf nh-local-interface {
                     type string;
                     description
                       "Destination is a local interface";
                   }
                   leaf nh-service {
                     type string;
                     description
                       "Next-hop service";
                   }
                   leaf nh-service-pkt-dist {
                     type string;
                     description
                       "Multi services packet distribution type";
                   }
                   leaf nh-service-app-data {
                     type string;
                     description
                       "Multi services application specific data";
                   }
                   leaf nh-private-comp {
                     type string;
                     description
                       "Private Composite Next-hop";
                   }
                   leaf nh-index {
                     type uint32;
                     description
                       "Next-hop index";
                   }
                   leaf nh-address {
                     type string;
                     description
                       "Address of next hop";
                   }
                   leaf nh-reference-count {
                     type int32;
                     description
                       "Number of references to this next hop";
                   }
                   leaf tunnel-composite-attr-type {
                     type string;
                     description
                       "Tunnel-Type for tunnel-composite-nexthop";
                   }
                   leaf tunnel-composite-attr-subtype {
                     type string;
                     description
                       "Tunnel-Subtype for tunnel-composite-nexthop";
                   }
                   leaf tunnel-composite-attr-reference-count {
                     type int32;
                     description
                       "Tunnel-reference-count for tunnel-composite-nexthop";
                   }
                   leaf tunnel-composite-attr-nh-id {
                     type int32;
                     description
                       "Tunnel-NextHop-Id for tunnel-composite-nexthop";
                   }
                   leaf tunnel-composite-attr-dest {
                     type jt:ipaddr;
                     description
                       "Tunnel-Destination for tunnel-composite-nexthop";
                   }
                   leaf tunnel-composite-attr-src {
                     type jt:ipaddr;
                     description
                       "Tunnel-Source for tunnel-composite-nexthop";
                   }
                   leaf tunnel-composite-attr-tunnel-endpoint {
                     type jt:ipaddr;
                     description
                       "Tunnel-Endpoint for tunnel-composite-nexthop";
                   }
                   leaf tunnel-composite-anchor-pfe {
                     type string;
                     description
                       "Anchor PFE name, if tunnel nexthop is localized";
                   }
                   leaf tunnel-composite-encap-rtb-id {
                     type int32;
                     description
                       "Tunnel encap routing table index";
                   }
                   leaf tunnel-composite-decap-rtb-id {
                     type int32;
                     description
                       "Tunnel decap routing table index";
                   }
                   leaf tunnel-composite-attr-ttl {
                     type int32;
                     description
                       "Tunnel-TTL for tunnel-composite-nexthop";
                   }
                   leaf tunnel-composite-attr-udp-port {
                     type int32;
                     description
                       "Tunnel-UDP-Destination port for 
                       tunnel-composite-nexthop";
                   }
                   leaf tunnel-composite-attr-fc-id {
                     type int32;
                     description
                       "Tunnel-Forwarding-Class-ID for 
                       tunnel-composite-nexthop";
                   }
                   leaf tunnel-composite-attr-tid {
                     type int32;
                     description
                       "Tunnel-Id for tunnel-composite-nexthop";
                   }
                   leaf tunnel-composite-attr-label {
                     type string;
                     description
                       "Tunnel-VPN-Label for tunnel-composite-nexthop";
                   }
                   leaf tunnel-composite-attr-label-ttl {
                     type string;
                     description
                       "Tunnel-VPN-Label-TTL for tunnel-composite-nexthop";
                   }
                   leaf tunnel-composite-attr-gre-key {
                     type int32;
                     description
                       "GRE key for tunnel-composite-nexthop";
                   }
                   leaf-list tunnel-composite-attr-segment-addr {
                     type jt:ipaddr;
                     description
                       "IPv6 segment-address";
                   }
                   leaf-list tunnel-composite-attr-sid {
                     type int32;
                     description
                       "IPv6 segment-sid";
                   }
                   leaf tunnel-composite-attr-vni {
                     type int32;
                     description
                       "Tunnel-VNI for tunnel-composite-nexthop in VxLAN";
                   }
                   leaf tunnel-composite-attr-dest-mac {
                     type string;
                     description
                       "Tunnel-Dest-Mac for tunnel-composite-nexthop in 
                       VxLAN";
                   }
                   leaf translate-composite-attr-type {
                     type string;
                     description
                       "Translation type for translate-composite-nexthop";
                   }
                   leaf translate-composite-attr-flags {
                     type string;
                     description
                       "Flags for translate-composite-nexthop";
                   }
                   leaf translate-composite-attr-reference-count {
                     type int32;
                     description
                       "Reference count for translate-composite-nexthop";
                   }
                   leaf translate-composite-attr-nh-id {
                     type int32;
                     description
                       "NextHop id for translate-composite-nexthop";
                   }
                   leaf translate-composite-attr-dest {
                     type jt:ipaddr;
                     description
                       "Translation destination for 
                       translate-composite-nexthop";
                   }
                   leaf translate-composite-attr-dest-plen {
                     type int32;
                     description
                       "Translation destination prefix length for 
                       translate-composite-nexthop";
                   }
                   leaf translate-composite-attr-src {
                     type jt:ipaddr;
                     description
                       "Translation source for translate-composite-nexthop";
                   }
                   leaf translate-composite-attr-src-plen {
                     type int32;
                     description
                       "Translation source prefix length for 
                       translate-composite-nexthop";
                   }
                   leaf translate-composite-attr-dest-alg-type {
                     type string;
                     description
                       "Destination algorithm type for 
                       translate-composite-nexthop";
                   }
                   leaf translate-composite-attr-src-alg-type {
                     type string;
                     description
                       "Source algorithm type for 
                       translate-composite-nexthop";
                   }
                   leaf translate-composite-attr-dest-vrf-id {
                     type int32;
                     description
                       "Destination vrf id for translate-composite-nexthop";
                   }
                   leaf translate-composite-attr-src-vrf-id {
                     type int32;
                     description
                       "Source vrf id for translate-composite-nexthop";
                   }
                   leaf translate-composite-attr-hoplimit {
                     type int32;
                     description
                       "Hoplimit for translate-composite-nexthop";
                   }
                   leaf translate-composite-attr-traffic-class {
                     type int32;
                     description
                       "Traffic class for translate-composite-nexthop";
                   }
                   leaf translate-composite-attr-ttl {
                     type int32;
                     description
                       "Ttl for translate-composite-nexthop";
                   }
                   leaf translate-composite-attr-tos {
                     type int32;
                     description
                       "Tos for translate-composite-nexthop";
                   }
                 }
                 leaf to {
                   type string;
                   description
                     "Neighbor address to which to send (next-hop address)";
                 }
                 leaf metric {
                   type int32;
                 }
                 leaf aigp {
                   type string;
                   description
                     "AIGP";
                 }
                 leaf balance {
                   type int32;
                   description
                     "Next-hop balance";
                 }
                 leaf flags {
                   type string;
                   description
                     "Enabled trace flags";
                 }
                 leaf res-state {
                   type string;
                   description
                     "Status of route resolution";
                 }
                 leaf res-tsp-idx {
                   type int32;
                   description
                     "TSP index of the path";
                 }
                 leaf-list res-path-aux {
                   type string;
                 }
                 leaf-list res-path-aux-type {
                   type string;
                 }
                 leaf-list res-path-aux-flags {
                   type string;
                 }
                 leaf-list res-path-aux-rs-name {
                   type string;
                 }
                 leaf-list res-path-aux-rs-ribs {
                   type string;
                 }
                 leaf-list res-path-inode-flags {
                   type string;
                 }
                 leaf-list res-path-flags {
                   type string;
                 }
                 leaf-list res-path-fnh-link {
                   type string;
                 }
                 leaf-list res-path-inh-link {
                   type string;
                 }
                 leaf mpls-label {
                   type string;
                   description
                     "Label of MPLS packet";
                 }
                 leaf label-ttl-action {
                   type string;
                   description
                     "TTL action associated with labels";
                 }
                 leaf load-balance-label {
                   type string;
                   description
                     "Load balance action associated with labels";
                 }
                 leaf-list composite-nh {
                   type string;
                 }
                 leaf-list pnh-statistics-id-group {
                   type string;
                   description
                     "Statistics ID Group Associated with this protocol NH";
                 }
                 leaf-list vpnlabel-nh {
                   type string;
                 }
                 leaf-list indirect-nh {
                   type string;
                 }
                 leaf ext-int-type {
                   type string;
                   description
                     "Next-hop type of equal-external-internal multipath";
                 }
                 leaf gw-opaque {
                   type string;
                   description
                     "Nexthops gateway opaque data handle";
                 }
                 leaf-list forwarding-nh-count {
                   type int32;
                   description
                     "Number of indirect path forwarding next hops";
                 }
                 leaf-list merged-forwarding-nh-count {
                   type int32;
                   description
                     "Number of indirect path forwarding next hops (Merged)";
                 }
                 leaf nh-type {
                   type string;
                   description
                     "Special next hop: Reject, Blackhole, Receive, 
                     Multicast, Local, or Unused";
                 }
                 leaf-list node-prefix {
                   type string;
                 }
                 leaf-list node-prefix-length {
                   type int32;
                 }
                 leaf-list originating-rib {
                   type string;
                   description
                     "Routing table from which this route was learned";
                 }
                 leaf-list node-metric {
                   type int32;
                 }
                 leaf-list node-path-count {
                   type int32;
                   description
                     "Number of paths for this node";
                 }
                 leaf node-flags {
                   type int32;
                   description
                     "Flags for this node";
                 }
                 leaf-list node-address {
                   type string;
                 }
                 leaf-list node-forwarding-nh-count {
                   type int32;
                 }
                 leaf-list nh-subtype {
                   type string;
                   description
                     "Specified nexthop subtype";
                 }
                 leaf indirect-nh-count {
                   type int32;
                   description
                     "Number of indirect next hops";
                 }
                 leaf composite-nh-count {
                   type int32;
                   description
                     "Number of composite next hops";
                 }
                 container eth-header-rewrite {
                   description
                     "Ethernet header rewrite information";
                   leaf eth-header-rewrite-smac {
                     type string;
                     description
                       "Source MAC address";
                   }
                   leaf eth-header-rewrite-dmac {
                     type string;
                     description
                       "Destination MAC address";
                   }
                   leaf eth-header-rewrite-tpid {
                     type int32;
                     description
                       "Ethernet header TPID";
                   }
                   leaf eth-header-rewrite-tci {
                     type int32;
                     description
                       "Ethernet header TCI";
                   }
                   leaf eth-header-rewrite-vlan-id {
                     type int32;
                     description
                       "Ethernet header VLAN ID";
                   }
                   leaf eth-header-rewrite-ethertype {
                     type int32;
                     description
                       "Ethernet header ethertype";
                   }
                 }
                 container vxlan-header-rewrite {
                   description
                     "VXLAN tunnel rewrite information";
                   leaf vxlan-header-rewrite-mtu {
                     type int32;
                     description
                       "VXLAN tunnel MTU";
                   }
                   leaf vxlan-header-rewrite-flags {
                     type int32;
                     description
                       "VXLAN tunnel flags";
                   }
                   leaf vxlan-header-rewrite-encap-rtb-id {
                     type int32;
                     description
                       "VXLAN tunnel encapsulation table ID";
                   }
                   leaf vxlan-header-rewrite-decap-rtb-id {
                     type int32;
                     description
                       "VXLAN tunnel decapsulation table ID";
                   }
                   leaf vxlan-header-rewrite-encap-vnid {
                     type int32;
                     description
                       "VXLAN tunnel encapsulation VNI";
                   }
                   leaf vxlan-header-rewrite-decap-vnid {
                     type int32;
                     description
                       "VXLAN tunnel decapsulation VNI";
                   }
                   leaf vxlan-header-rewrite-svtep {
                     type jt:ipaddr;
                     description
                       "Source VTEP address";
                   }
                   leaf vxlan-header-rewrite-dvtep {
                     type jt:ipaddr;
                     description
                       "Destination VTEP address";
                   }
                   leaf vxlan-header-rewrite-smac {
                     type string;
                     description
                       "Source MAC address";
                   }
                   leaf vxlan-header-rewrite-dmac {
                     type string;
                     description
                       "Destination MAC address";
                   }
                 }
                 container fully-resolved-tunnel {
                   description
                     "GRE or UDP tunnel rewrite information";
                   leaf fully-resolved-tunnel-type {
                     type string;
                     description
                       "Tunnel type";
                   }
                   leaf fully-resolved-tunnel-dest {
                     type jt:ipaddr;
                     description
                       "Tunnel Destination";
                   }
                   leaf fully-resolved-tunnel-src {
                     type jt:ipaddr;
                     description
                       "Tunnel Source";
                   }
                   leaf fully-resolved-tunnel-ep-addr {
                     type jt:ipaddr;
                     description
                       "Tunnel endpoint address";
                   }
                   leaf fully-resolved-tunnel-encap-rtb-id {
                     type int32;
                     description
                       "Tunnel encap routing table id";
                   }
                   leaf fully-resolved-tunnel-decap-rtb-id {
                     type int32;
                     description
                       "Tunnel decap routing table id";
                   }
                 }
               }
               container srte-policy-state {
                 leaf sr-source {
                   type string;
                 }
                 leaf sr-origin {
                   type string;
                 }
                 leaf sr-preference {
                   type uint32;
                 }
                 leaf sr-preference-override {
                   type uint32;
                 }
                 leaf sr-route-distinguisher {
                   type uint32;
                 }
               }
               container srte-policy-information {
                 container srte-policy {
                   leaf srte-path-preference {
                     type uint32;
                   }
                   leaf srte-binding-sid {
                     type string;
                   }
                   leaf srte-adv-policy-name {
                     type string;
                   }
                   leaf srte-priority {
                     type uint32;
                   }
                   leaf srte-enlp {
                     type uint32;
                   }
                   leaf srte-tlv-recv-flags {
                     type string;
                   }
                   leaf srte-binding-sid-label-encoding {
                     type string;
                   }
                   list srte-segment-list {
                     leaf srte-segment-list-weight {
                       type uint32;
                     }
                     list srte-segment {
                       leaf srte-segment-label {
                         type uint32;
                       }
                       leaf srte-segment-label-ttl {
                         type string;
                         description
                           "SR Policy segment label ttl";
                       }
                       leaf srte-segment-type {
                         type string;
                         description
                           "SR Policy segment type";
                       }
                       leaf srte-segment-label-class {
                         type uint32;
                         description
                           "SR Policy segment label traffic-class";
                       }
                     }
                   }
                 }
               }
               container bgp-prefix-sid-attr {
                 description
                   "BGP Prefix SID Attribute";
                 container bgp-prefix-sid-attr-label-idx-tlv {
                   leaf bgp-prefix-sid-label-idx-index {
                     type int32;
                   }
                   leaf bgp-prefix-sid-attr-status {
                     type string;
                   }
                 }
                 container bgp-prefix-sid-attr-srgb-tlv {
                   list bgp-prefix-sid-srgb-block {
                     key "bgp-prefix-sid-srgb-block-start-label";
                     leaf bgp-prefix-sid-srgb-block-start-label {
                       type int32;
                     }
                     leaf bgp-prefix-sid-srgb-block-range {
                       type int32;
                     }
                   }
                 }
                 container bgp-prefix-sid-attr-service-tlv {
                   leaf bgp-prefix-sid-srv6-sid-value {
                     type jt:ipaddr;
                   }
                   leaf bgp-prefix-sid-attr-service-tlv-type {
                     type uint32;
                   }
                   leaf bgp-prefix-sid-attr-tlv-type {
                     type uint32;
                   }
                   leaf bgp-prefix-sid-srv6-sid-bh {
                     type uint32;
                   }
                   leaf bgp-prefix-sid-srv6-sid-bl {
                     type uint32;
                   }
                   leaf bgp-prefix-sid-srv6-sid-nl {
                     type uint32;
                   }
                   leaf bgp-prefix-sid-srv6-sid-fl {
                     type uint32;
                   }
                   leaf bgp-prefix-sid-srv6-sid-al {
                     type uint32;
                   }
                   leaf bgp-prefix-sid-srv6-sid-tl {
                     type uint32;
                   }
                   leaf bgp-prefix-sid-srv6-sid-to {
                     type uint32;
                   }
                 }
                 container bgp-prefix-sid-attr-unknown-tlvs {
                   list bgp-prefix-sid-attr-unknown-tlv {
                     key "bgp-prefix-sid-unknown-tlv-type";
                     leaf bgp-prefix-sid-unknown-tlv-type {
                       type uint32;
                     }
                     leaf bgp-prefix-sid-unknown-tlv-len {
                       type uint32;
                     }
                   }
                 }
               }
               container srte-policy-telemetry-statistics-state {
                 leaf srte-policy-telemetry-statistics-state.heading {
                   type string;
                 }
                 container srte-policy-telemetry-statistics-config {
                   leaf ingress {
                     type empty;
                     description
                       "Flag indicating ingress statistics is configured";
                   }
                   leaf transit {
                     type empty;
                     description
                       "Flag indicating transit statistics is configured";
                   }
                 }
                 list srte-policy-telemetry-statistics-sensor-information {
                   leaf sensor-type {
                     type string;
                   }
                   leaf sensor-status {
                     type string;
                   }
                   leaf sensor-id {
                     type int32;
                     description
                       "Unique identifier for the sensor";
                   }
                 }
               }
               list flex-tunnel-profile {
                 description
                   "Flex V4/V6 route tunnel attribute information";
                 container flex-tunnel-profile-info {
                   description
                     "The tunnel profile information";
                   leaf flex-tunnel-profile-num {
                     type int32;
                     description
                       "The tunnel profile number";
                   }
                   leaf flex-tunnel-profile-action {
                     type string;
                     description
                       "The action that this profile will be used for";
                   }
                   leaf flex-tunnel-profile-vni {
                     type int32;
                     description
                       "VXLAN Network Identifier (VNI)";
                   }
                   leaf flex-tunnel-profile-src-pfx {
                     type string;
                     description
                       "Source address and prefix length";
                   }
                   leaf flex-tunnel-profile-src-udp-port-range {
                     type string;
                     description
                       "Outer source UDP port range";
                   }
                   leaf flex-tunnel-profile-src-mac {
                     type string;
                     description
                       "Source MAC address, a 48-bit MAC value";
                   }
                   leaf flex-tunnel-profile-dest-pfx {
                     type string;
                     description
                       "Destination address";
                   }
                   leaf flex-tunnel-profile-dest-udp-port {
                     type int32;
                     description
                       "Outer destination UDP port";
                   }
                   leaf flex-tunnel-profile-dest-mac {
                     type string;
                     description
                       "Destination MAC address, a 48-bit MAC value";
                   }
                   leaf flex-tunnel-profile-flex-vxlan-flags {
                     type int32;
                     description
                       "Flex VxLAN flags";
                   }
                   leaf flex-tunnel-profile-reserved-24-bit-field {
                     type int32;
                     description
                       "VXLAN 24-bit reserved field as specified in RFC7348";
                   }
                   leaf flex-tunnel-profile-reserved-8-bit-field {
                     type int32;
                     description
                       "VXLAN 8-bit reserved field as specified in RFC7348";
                   }
                   container flex-tunnel-profile-stats {
                     description
                       "Statistics associated with tunnel";
                     leaf flex-tunnel-stats-pkts-count {
                       type int32;
                       description
                         "Packet count";
                     }
                     leaf flex-tunnel-stats-pps {
                       type int32;
                       description
                         "Packets per second";
                     }
                     leaf flex-tunnel-stats-bytes-count {
                       type int32;
                       description
                         "Byte count";
                     }
                     leaf flex-tunnel-stats-bps {
                       type int32;
                       description
                         "Bytes per second";
                     }
                   }
                 }
                 leaf flex-tunnel-profile-string {
                   type string;
                   description
                     "The tunnel profile string";
                 }
               }
               leaf preference2 {
                 type int32;
               }
               leaf age {
                 type string;
               }
               leaf med {
                 type int32;
                 description
                   "Multiple exit discriminator";
               }
               leaf local-preference {
                 type int32;
               }
               leaf rt-tag {
                 type int32;
               }
               leaf rt-tag2 {
                 type int32;
               }
               leaf learned-from {
                 type jt:ipaddr;
                 description
                   "Peer address from which this route was learned";
               }
               leaf peer-as {
                 type int32;
                 description
                   "Peer AS number";
               }
               leaf evpn-remote-mes {
                 type jt:ipaddr;
                 description
                   "Remote PE";
               }
               leaf evpn-routing-instance-name {
                 type string;
                 description
                   "Routing Instance";
               }
               leaf evpn-tag-rt-type {
                 type string;
                 description
                   "Route Type";
               }
               leaf evpn-vlan-id {
                 type int32;
                 description
                   "VLAN-ID";
               }
               leaf evpn-vpws-service-id {
                 type int32;
                 description
                   "VPWS Service-Id";
               }
               leaf rt-evpn-esi {
                 type string;
                 description
                   "ESI";
               }
               leaf evpn-isid {
                 type int32;
                 description
                   "ISID";
               }
               leaf rt-evpn-bmac {
                 type string;
                 description
                   "BMAC";
               }
               leaf bgp-rtarget-type {
                 type string;
                 description
                   "BGP RT-Constrain route type";
               }
               leaf bgp-rtarget-generation {
                 type uint32;
                 description
                   "BGP RT-Constrain generation";
               }
               leaf bgp-rtarget-for {
                 type string;
                 description
                   "BGP RT-Constrain member";
               }
               leaf nh-index {
                 type uint32;
                 description
                   "Next-hop index";
               }
               leaf transport-class {
                 type string;
                 description
                   "Transport class name";
               }
               leaf nh-address {
                 type string;
                 description
                   "Address of next hop";
               }
               leaf nh-reference-count {
                 type int32;
                 description
                   "Number of references to this next hop";
               }
               leaf ext-int-intf-index {
                 type int32;
                 description
                   "Interface index of equal-external-internal multipath";
               }
               leaf nh-session-id {
                 type uint32;
                 description
                   "Nexthop session id";
               }
               leaf nh-key-opaque {
                 type string;
                 description
                   "Nexthop key opaque handle";
               }
               leaf nh-non-key-opaque {
                 type string;
                 description
                   "Nexthop non-key opaque handle";
               }
               leaf nh-key-opaque-dump {
                 type string;
                 description
                   "Nexthop key opaque app dump";
               }
               leaf nh-non-key-opaque-dump {
                 type string;
                 description
                   "Nexthop non-key opaque app dump";
               }
               leaf nh-flood-overflow {
                 type empty;
                 description
                   "Flood nexthop exceeds maximum branches";
               }
               leaf nh-kernel-id {
                 type int32;
                 description
                   "Table Id for this next hop";
               }
               leaf client-data {
                 type string;
                 description
                   "Route server client details";
               }
               leaf route-distinguisher {
                 type string;
                 description
                   "Name of the route-distinguisher";
               }
               leaf reason-for-invalid {
                 type string;
               }
               leaf thread-name {
                 type string;
               }
               leaf pmsi {
                 type string;
                 description
                   "P-multicast service interface";
               }
               leaf connector {
                 type string;
               }
               leaf color {
                 type int32;
               }
               leaf color2 {
                 type int32;
               }
               leaf prefix-segment-index {
                 type int32;
               }
               leaf rt-isis-level {
                 type int32;
               }
               leaf rt-isis-downbit {
                 type int32;
               }
               leaf rt-entry-state {
                 type string;
                 description
                   "State of this route entry";
               }
               leaf rt-fib-install-priority {
                 type string;
                 description
                   "Route FIB installation priority";
               }
               leaf rt-ack-state {
                 type string;
                 description
                   "Route acknowledgement state";
               }
               leaf rt-ack-ll-flag {
                 type string;
                 description
                   "Status of route ACK flags";
               }
               leaf rt-ack-req-ts {
                 type string;
                 description
                   "Time when ack request is sent";
               }
               leaf rt-ack-res-time {
                 type uint32;
                 description
                   "Ack route response time";
               }
               leaf rt-ack-re-flash-time {
                 type string;
                 description
                   "Time when ack is re flashed to protocols";
               }
               leaf rt-ack-re-flash-status {
                 type string;
                 description
                   "Status of ACK re-flash to protocols";
               }
               leaf rt-ack-guid {
                 type uint64;
                 description
                   "Ack route global identifier";
               }
               leaf rt-ack-olc {
                 type uint64;
                 description
                   "Ack route global version";
               }
               leaf rt-ack-local-ver {
                 type uint32;
                 description
                   "Ack route global version";
               }
               leaf rt-ack-and-err-flag {
                 type uint32;
                 description
                   "Route ack and error flag";
               }
               leaf rt-ack-history {
                 type uint32;
                 description
                   "Route ack history";
               }
               leaf pfe-err-state {
                 type string;
                 description
                   "Route error state from PFE";
               }
               leaf pfe-err-time {
                 type uint32;
                 description
                   "Route error receive time";
               }
               leaf rt-ver-id {
                 type uint32;
                 description
                   "Route version ID";
               }
               leaf rt-entry-pim-state {
                 type string;
                 description
                   "PIM state of this route entry";
               }
               leaf inactive-reason {
                 type string;
                 description
                   "HFRR profile Inactive reason (if any)";
               }
               leaf local-as {
                 type int32;
                 description
                   "Local AS number";
               }
               leaf med-plus-igp {
                 type int32;
               }
               leaf rt-aigp {
                 type uint64;
               }
               leaf rt-effective-aigp {
                 type uint64;
                 description
                   "Effective AIGP value used by route selection";
               }
               leaf rt-effective-aigp-reason {
                 type string;
                 description
                   "Reason why the effective AIGP value was selected";
               }
               leaf rt-resolving-aigp {
                 type uint64;
               }
               leaf rt-effective-metric {
                 type uint64;
                 description
                   "Effective metric value used by route selection";
               }
               leaf rt-effective-metric-reason {
                 type string;
                 description
                   "Reason why the effective metric value was selected";
               }
               leaf rt-orr {
                 type uint32;
               }
               leaf rt-actual-igp-metric {
                 type uint32;
               }
               leaf rt-ospf-area {
                 type string;
               }
               leaf task-name {
                 type string;
                 description
                   "Name of this task";
               }
               leaf announce-bits {
                 type int32;
               }
               leaf announce-tasks {
                 type string;
               }
               leaf flow-id {
                 type int32;
               }
               leaf bgp-rt-flag {
                 type string;
                 description
                   "BGP route flag";
               }
               leaf label-base {
                 type int32;
                 description
                   "Label base for l2vpn";
               }
               leaf label-range {
                 type int32;
                 description
                   "Label range for l2vpn";
               }
               leaf l2vpn-status-vector {
                 type string;
               }
               leaf label-offset {
                 type int32;
                 description
                   "Label offset for l2vpn";
               }
               leaf remote-site {
                 type int32;
                 description
                   "Remote site id";
               }
               leaf l2vpn-mesh-group {
                 type string;
               }
               leaf vc-label {
                 type int32;
                 description
                   "VC label";
               }
               leaf context-id {
                 type jt:ipaddr;
                 description
                   "Context Identifier";
               }
               leaf route-control-word {
                 type string;
                 description
                   "Control Word";
               }
               leaf mtu {
                 type int32;
                 description
                   "MTU along an interface";
               }
               leaf cell-bundle-size {
                 type int32;
                 description
                   "Cell bundle size";
               }
               leaf vlan-id {
                 type int32;
               }
               leaf flow-label-transmit {
                 type int32;
               }
               leaf flow-label-receive {
                 type int32;
               }
               leaf tdm-payload-size {
                 type int32;
               }
               leaf tdm-bitrate {
                 type int32;
               }
               leaf pw-status-code {
                 type int32;
               }
               leaf cac-bandwidth-failure {
                 type empty;
                 description
                   "Call admission control failure due to insufficient 
                   bandwidth";
               }
               leaf vpn-label {
                 type int32;
                 description
                   "VPN label";
               }
               leaf route-label {
                 type int32;
                 description
                   "Route label";
               }
               leaf route-labels {
                 type string;
                 description
                   "Route label";
               }
               leaf mac-route-esi {
                 type string;
                 description
                   "ESI";
               }
               leaf evpn-igmp-flags {
                 type int32;
                 description
                   "IGMP flags";
               }
               leaf evpn-mld-flags {
                 type int32;
                 description
                   "MLD flags";
               }
               leaf evpn-leave-reserved {
                 type int32;
                 description
                   "IGMP Leave Reserved Field";
               }
               leaf evpn-leave-mrt {
                 type int32;
                 description
                   "IGMP Leave Max Response Time";
               }
               leaf overlay-gateway-address {
                 type jt:ipaddr;
                 description
                   "Overlay gateway address";
               }
               leaf reroute-address {
                 type jt:ipaddr;
                 description
                   "Reroute address";
               }
               leaf bgp-otc {
                 type int32;
               }
               leaf peer-id {
                 type jt:ipaddr;
               }
               leaf rt-entry-ext-pfx-attr-flags {
                 type string;
                 description
                   "Route entry extended prefix attribute flags";
               }
               leaf rt-entry-ext-pfx-source-rtrid {
                 type string;
                 description
                   "Route entry extended prefix source rtr id";
               }
               leaf path-id {
                 type string;
               }
               leaf gateway {
                 type string;
                 description
                   "Sourcing gateway";
               }
               leaf rtrib-primary {
                 type string;
                 description
                   "Primary routing table";
               }
               leaf rib-export-rtrib-primary {
                 type string;
                 description
                   "RIB export primary routing table";
               }
               leaf rtrib-secondary {
                 type string;
                 description
                   "Secondary routing table";
               }
               leaf indirect-nh-count {
                 type int32;
                 description
                   "Number of indirect next hops";
               }
               leaf composite-nh-count {
                 type int32;
                 description
                   "Number of composite next hops";
               }
               leaf helper-nhid {
                 type uint32;
                 description
                   "Helper nexthop index";
               }
               leaf helper-refcount {
                 type int32;
                 description
                   "Reference count of those needing helper route";
               }
               leaf backup-pe-group-name {
                 type string;
                 description
                   "Name of the backup PE group";
               }
               leaf designated-forwarder {
                 type string;
                 description
                   "Indicates if we are the designated forwarder for this 
                   route";
               }
               leaf rt-entry-opaque-data {
                 type string;
                 description
                   "Opaque data associated with the route entry";
               }
               leaf rt-stats-id-grp-single-line {
                 type string;
                 description
                   "Stats-id-group associated with the route entry";
               }
               leaf rt-entry-ext-pfx-sid-data {
                 type string;
                 description
                   "Route entry extended prefix sid data";
               }
               leaf hidden-reason {
                 type string;
                 description
                   "Protocol's reason for hiding the route";
               }
               leaf bgp-bmp-send-flag-start {
                 type string;
               }
               leaf bgp-bmp-send-flag-pre {
                 type string;
               }
               leaf bgp-bmp-send-flag-post {
                 type string;
               }
               leaf bgp-bmp-send-flag-ribout-prepolicy {
                 type string;
               }
               leaf bgp-bmp-send-flag-ribout-postpolicy {
                 type string;
               }
               leaf bgp-bmp-send-flag-station {
                 type string;
               }
               leaf bgp-nnh-nodes {
                 type string;
                 description
                   "Next-next-hop nodes";
               }
               leaf bgp-nh-nnh-map {
                 type string;
                 description
                   "Next-hop to next-next-hop map";
               }
               leaf bgp-profile-creation-failure-reason {
                 type string;
                 description
                   "Reason for failing to create profile for next-next-hop 
                   map";
               }
               leaf bgp-nh-nnh-entry {
                 type string;
                 description
                   "Next-hop to next-next-hop entry";
               }
               leaf glb-profile {
                 type string;
                 description
                   "GLB Profile";
               }
               leaf glb-profile-id {
                 type uint32;
                 description
                   "GLB Profile ID";
               }
               leaf rt-entry-stats {
                 type string;
                 description
                   "Route entry statistics data";
               }
               container connection-bandwidth {
                 description
                   "Bandwidth of a layer 2 connection";
                 leaf connection-bandwidth.heading {
                   type string;
                   description
                     "Bandwidth of a layer 2 connection";
                 }
                 leaf bandwidth {
                   type string;
                 }
                 leaf class-type {
                   type int32;
                 }
                 leaf class-bandwidth {
                   type int32;
                 }
               }
               container route-flap-damping {
                 leaf last-merit {
                   type int32;
                   description
                     "Last merit value";
                 }
                 leaf merit {
                   type int32;
                   description
                     "Current merit value";
                 }
                 leaf damping-parameters {
                   type string;
                 }
                 leaf default-damping-parameters {
                   type empty;
                   description
                     "Default damping parameters used";
                 }
                 leaf last-update {
                   type string;
                 }
                 leaf first-update {
                   type string;
                 }
                 leaf route-flap-count {
                   type int32;
                   description
                     "Number of times this route has flapped";
                 }
                 leaf suppressed {
                   type empty;
                   description
                     "This route is suppressed";
                 }
                 leaf reuse-time {
                   type string;
                   description
                     "Time until this route is reusable";
                 }
                 leaf reuse-preference {
                   type int32;
                   description
                     "Preference to use when this route is reused";
                 }
                 leaf expire-time {
                   type string;
                   description
                     "Time when this damping entry expires";
                 }
               }
               container nhh {
                 leaf nh-type {
                   type string;
                   description
                     "Special next hop: Reject, Blackhole, Receive, 
                     Multicast, Local, or Unused";
                 }
                 leaf nh-index {
                   type uint32;
                   description
                     "Next-hop index";
                 }
                 leaf transport-class {
                   type string;
                   description
                     "Transport class name";
                 }
                 leaf nh-address {
                   type string;
                   description
                     "Address of next hop";
                 }
                 leaf nh-reference-count {
                   type int32;
                   description
                     "Number of references to this next hop";
                 }
                 leaf ext-int-intf-index {
                   type int32;
                   description
                     "Interface index of equal-external-internal multipath";
                 }
                 leaf nh-session-id {
                   type uint32;
                   description
                     "Nexthop session id";
                 }
                 leaf nh-key-opaque {
                   type string;
                   description
                     "Nexthop key opaque handle";
                 }
                 leaf nh-non-key-opaque {
                   type string;
                   description
                     "Nexthop non-key opaque handle";
                 }
                 leaf nh-key-opaque-dump {
                   type string;
                   description
                     "Nexthop key opaque app dump";
                 }
                 leaf nh-non-key-opaque-dump {
                   type string;
                   description
                     "Nexthop non-key opaque app dump";
                 }
                 leaf nh-flood-overflow {
                   type empty;
                   description
                     "Flood nexthop exceeds maximum branches";
                 }
                 leaf nh-kernel-id {
                   type int32;
                   description
                     "Table Id for this next hop";
                 }
               }
               list nh-expand {
                 key "nhe-name nhe-handle";
                 description
                   "Next-hop gateway information";
                 leaf nhe-name {
                   type string;
                   description
                     "Name of next-hop";
                 }
                 leaf nhe-handle {
                   type string;
                   description
                     "Nexthop pointer";
                 }
                 leaf nhe-index {
                   type int32;
                   description
                     "Next-hop index";
                 }
                 leaf nhe-to {
                   type string;
                   description
                     "Nexthop address";
                 }
                 leaf nhe-mbr-count {
                   type int32;
                   description
                     "Number of child nexhops";
                 }
                 leaf nhe-mpls-label {
                   type string;
                   description
                     "Label of MPLS packet";
                 }
               }
               list rt-session-id {
                 key "rt-session-id-value";
                 description
                   "Session-IDs associated with route";
                 leaf rt-session-id-value {
                   type int32;
                   description
                     "Value of session-id";
                 }
                 leaf rt-session-id-version {
                   type int32;
                   description
                     "Version of session-id";
                 }
               }
               container flex-rt-statistics {
                 description
                   "Statistics associated with route";
                 leaf flex-rt-statistics-pkts-count {
                   type int32;
                   description
                     "Packet count";
                 }
                 leaf flex-rt-statistics-pps {
                   type int32;
                   description
                     "Pps";
                 }
                 leaf flex-rt-statistics-bytes-count {
                   type int32;
                   description
                     "Byte count";
                 }
                 leaf flex-rt-statistics-bps {
                   type int32;
                   description
                     "Bps";
                 }
               }
               leaf bgp-group-name {
                 type string;
               }
               leaf bgp-no-label-reason {
                 type string;
               }
               leaf sr-policy-distinguisher {
                 type uint32;
               }
               leaf sr-policy-color {
                 type uint32;
               }
               leaf sr-policy-endpoint {
                 type jt:ipaddr;
               }
               leaf bgp-metric-flags {
                 type string;
                 description
                   "BGP metrics flags";
               }
               leaf bgp-output-queue-class {
                 type string;
                 description
                   "BGP output queue class";
               }
               leaf cluster-id {
                 type string;
               }
               leaf originator {
                 type string;
               }
               leaf bgp-aigp {
                 type string;
                 description
                   "Accumulated IGP Metric";
               }
               leaf bgp-elc {
                 type empty;
                 description
                   "Entropy label capable";
               }
               leaf bgp-elc-v2 {
                 type empty;
                 description
                   "Entropy label capable version 2";
               }
               leaf bgp-elc-v3 {
                 type empty;
                 description
                   "Entropy label capable version 3";
               }
               leaf bgp-nhc-unknown-characteristics-len {
                 type uint32;
                 description
                   "Total length of NHC unknown characteristics";
               }
               leaf bgp-nhc-nh-valid {
                 type string;
                 description
                   "Whether next hop field matches route next hop";
               }
               leaf bgp-nhc-characteristic-code {
                 type uint32;
                 description
                   "NHC characteristic code";
               }
               leaf bgp-nhc-characteristic-len {
                 type uint32;
                 description
                   "NHC characteristic length";
               }
               leaf bgp-nhc-characteristic-val {
                 type string;
                 description
                   "NHC characteristic value";
               }
             }
             list kern-nhexpand {
               key "kern-nhe-name kern-nhe-handle";
               description
                 "Next-hop gateway information";
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
               leaf kern-nhe-platform-layer-input {
                 type empty;
                 description
                   "Platform layer input nexthop";
               }
               leaf kern-nhe-platform-layer-output {
                 type empty;
                 description
                   "Platform layer output nexthop";
               }
               leaf kern-nhe-in-kernel {
                 type empty;
                 description
                   "Nexthop install in kernel";
               }
               leaf kern-nhe-fib-channel {
                 type string;
                 description
                   "Fib channel in which route is installed";
               }
               leaf kern-nhe-name {
                 type string;
                 description
                   "Name of next-hop";
               }
               leaf kern-nhe-subtype {
                 type string;
                 description
                   "Nexthop Subtype";
               }
               leaf kern-nhe-handle {
                 type string;
                 description
                   "Nexthop pointer";
               }
               leaf kern-nhe-index {
                 type int32;
                 description
                   "Next-hop index";
               }
               leaf kern-gw-flags {
                 type string;
                 description
                   "Nexthop gateway flags";
               }
               leaf kern-gw-opaque {
                 type string;
                 description
                   "Nexthop gateway opaque data handle";
               }
               leaf kern-key-opaque {
                 type string;
                 description
                   "Nexthop key opaque data handle";
               }
               leaf kern-nhe-to {
                 type string;
                 description
                   "Nexthop address";
               }
               leaf kern-nhe-mbr-count {
                 type int32;
                 description
                   "Number of child nexhops";
               }
               leaf kern-nhe-mpls-label {
                 type string;
                 description
                   "Label of MPLS packet";
               }
               leaf kern-nhe-pnh {
                 type string;
                 description
                   "Protocol Nexthop address";
               }
               leaf kern-nhe-fib-nh-str {
                 type string;
                 description
                   "FIB inh or cnh identifier";
               }
               leaf kern-nhe-sessionid {
                 type int32;
                 description
                   "Session ID";
               }
               leaf kern-nhe-tunnel-type {
                 type string;
                 description
                   "Tunnel type";
               }
               leaf kern-nhe-tunnel-src {
                 type string;
                 description
                   "Tunnel Source address";
               }
               leaf kern-nhe-tunnel-dest {
                 type string;
                 description
                   "Tunnel Destination address";
               }
               leaf kern-nhe-tunnel-ep {
                 type string;
                 description
                   "Tunnel Endpoint address";
               }
               leaf kern-nhe-tunnel-vxlan-encap-vni {
                 type int32;
                 description
                   "VxLAN tunnel encap vni";
               }
               leaf kern-nhe-tunnel-vxlan-decap-vni {
                 type int32;
                 description
                   "VxLAN tunnel decap vni";
               }
               leaf kern-nhe-translate-type {
                 type string;
                 description
                   "Translation type";
               }
               leaf kern-nhe-translate-src {
                 type string;
                 description
                   "Translation Source address";
               }
               leaf kern-nhe-translate-src-plen {
                 type int32;
                 description
                   "Translation Source address prefix length";
               }
               leaf kern-nhe-translate-dest {
                 type string;
                 description
                   "Translation Destination address";
               }
               leaf kern-nhe-translate-dest-plen {
                 type int32;
                 description
                   "Translation Destination address prefix length";
               }
               leaf kern-nhe-tunnel-encap-rtb-id {
                 type int32;
                 description
                   "Tunnel encap routing table id";
               }
               leaf kern-nhe-tunnel-decap-rtb-id {
                 type int32;
                 description
                   "Tunnel decap routing table id";
               }
               leaf kern-nhe-interface {
                 type string;
                 description
                   "Interface";
               }
               leaf kern-nhe-slice-gencfg-id {
                 type int32;
                 description
                   "Slice-Gencfg ID";
               }
               leaf kern-nhe-sliceid {
                 type int32;
                 description
                   "Slice ID";
               }
               leaf kern-nhe-fwf {
                 type string;
                 description
                   "Filter Name";
               }
               leaf kern-nhe-flex-tunnel-info {
                 type string;
                 description
                   "Flex-tunnel information of nexthop";
               }
               leaf kern-nhe-flags {
                 type string;
                 description
                   "Nexthop flags";
               }
               leaf kern-nhe-stats-id-group {
                 type string;
                 description
                   "Statistics ID Group associated with nexthop";
               }
               leaf kern-nhe-reference-count {
                 type int32;
                 description
                   "Nexthop reference count";
               }
               leaf kern-elnh-address {
                 type string;
                 description
                   "Address of Element Next-hop";
               }
             }
             leaf rt-entry-count {
               type int32;
               description
                 "Number of route entries in this route";
             }
             leaf rt-announced-count {
               type int32;
               description
                 "Number of announced route entries";
             }
             leaf rt-state {
               type string;
               description
                 "State of this route";
             }
             leaf-list tsi {
               type string;
               description
                 "Task-specific information";
             }
             container communities {
               leaf-list community {
                 type string;
                 description
                   "Basic community";
               }
               leaf-list extended-community {
                 type string;
                 description
                   "Extended community";
               }
               leaf-list ipv6-extended-community {
                 type string;
                 description
                   "IPv6 extended community";
               }
             }
             list bgp-tunnel-attribute {
               key "tunnel-attribute-type";
               description
                 "Tunne encap attribute information";
               leaf tunnel-attribute-type {
                 type string;
               }
               leaf tunnel-attribute-rpf {
                 type empty;
               }
               leaf tunnel-attribute-color {
                 type uint32;
               }
               leaf tunnel-attribute-destination {
                 type jt:ipaddr;
               }
             }
           }
           container route-state-history {
             list route-state-history-elements {
               key "rt-history-time";
               leaf rt-history-time {
                 type string;
               }
               leaf rt-history-event {
                 type string;
               }
             }
           }
         }
       }
       container ospf-neighbor-information {
         description
           "Information about OSPF neighbors in a routing instance";
         list ospf-neighbor {
           key "interface-name neighbor-id ospf-area";
           leaf neighbor-address {
             type jt:ipaddr;
             description
               "IP address of this neighbor";
           }
           leaf interface-name {
             type string;
             description
               "Name of interface";
           }
           leaf ospf-neighbor-state {
             type string;
           }
           leaf neighbor-id {
             type jt:ipaddr;
           }
           leaf neighbor-priority {
             type int32;
           }
           leaf activity-timer {
             type int32;
           }
           leaf ospf-area {
             type string;
             description
               "Area ID";
           }
           leaf options {
             type int32;
           }
           leaf dr-address {
             type jt:ipaddr;
             description
               "IP address of DR";
           }
           leaf bdr-address {
             type jt:ipaddr;
             description
               "IP address of BDR";
           }
           leaf neighbor-secondary {
             type empty;
             description
               "OSPF neighbor is on secondary interface";
           }
           leaf neighbor-up-time {
             type string;
             description
               "Time when neighbor came up";
           }
           leaf neighbor-adjacency-time {
             type string;
             description
               "Time when neighbor became adjacent";
           }
           leaf neighbor-last-out-of-band-resync-time {
             type string;
             description
               "Time since last successful oob-resync";
           }
           leaf neighbor-suppress-hello {
             type int32;
             description
               "Time when neighbor suppressed hellos";
           }
           leaf adj-sid-list {
             type string;
           }
           leaf master-slave {
             type string;
           }
           leaf sequence-number {
             type int64;
             description
               "History event number";
           }
           leaf dbd-retransmit-time {
             type int32;
             description
               "Seconds until DBD is retransmitted";
           }
           leaf lsreq-retransmit-time {
             type int32;
             description
               "Seconds until LSREQ is retransmitted";
           }
           leaf lsreq-enqueued {
             type empty;
           }
           leaf lsreq-active {
             type empty;
           }
           leaf lsa-list {
             type string;
           }
           list ospf-neighbor-topology {
             key "ospf-topology-name";
             description
               "OSPF topology specific neighbor information";
             leaf ospf-topology-name {
               type string;
               description
                 "OSPF topology name";
             }
             leaf ospf-topology-id {
               type int32;
               description
                 "OSPF topology id";
             }
             leaf ospf-neighbor-topology-state {
               type string;
               description
                 "State of the neighbor in a topology";
             }
           }
         }
       }
       container ospf3-neighbor-information {
         list ospf3-neighbor {
           key "neighbor-id interface-name ospf-area";
           leaf neighbor-id {
             type jt:ipaddr;
           }
           leaf interface-name {
             type string;
             description
               "Name of interface";
           }
           leaf ospf-neighbor-state {
             type string;
           }
           leaf neighbor-priority {
             type int32;
           }
           leaf activity-timer {
             type int32;
           }
           leaf neighbor-address {
             type jt:ipaddr;
             description
               "IP address of this neighbor";
           }
           leaf ospf-area {
             type string;
             description
               "Area ID";
           }
           leaf options {
             type int32;
           }
           leaf neighbor-secondary {
             type empty;
             description
               "OSPF neighbor is on secondary interface";
           }
           leaf ospf3-interface-index {
             type int32;
           }
           leaf neighbor-cost {
             type int32;
             description
               "Cost associated with this neighbor";
           }
           leaf dr-id {
             type jt:ipaddr;
           }
           leaf bdr-id {
             type jt:ipaddr;
           }
           leaf neighbor-up-time {
             type string;
             description
               "Time when neighbor came up";
           }
           leaf neighbor-adjacency-time {
             type string;
             description
               "Time when neighbor became adjacent";
           }
           leaf neighbor-suppress-hello {
             type int32;
             description
               "Time when neighbor suppressed hellos";
           }
           leaf master-slave {
             type string;
           }
           leaf sequence-number {
             type int64;
             description
               "History event number";
           }
           leaf dbd-retransmit-time {
             type int32;
             description
               "Seconds until DBD is retransmitted";
           }
           leaf lsreq-retransmit-time {
             type int32;
             description
               "Seconds until LSREQ is retransmitted";
           }
           leaf lsreq-enqueued {
             type empty;
           }
           leaf lsreq-active {
             type empty;
           }
           leaf lsa-list {
             type string;
           }
         }
       }
       container isis-overview-information {
         description
           "ISIS overview information";
         container isis-overview {
           description
             "Overview information for an IS-IS instance";
           leaf instance-name {
             type string;
           }
           leaf isis-instance-id {
             type uint16;
             description
               "IS-IS Instance ID";
           }
           leaf isis-router-id {
             type jt:ipaddr;
             description
               "IS-IS router ID";
           }
           leaf isis-v6-router-id {
             type jt:ipv6addr;
             description
               "IS-IS IPv6 Router ID";
           }
           leaf isis-router-hostname {
             type string;
             description
               "IS-IS router hostname";
           }
           leaf isis-router-sysid {
             type string;
             description
               "IS-IS router sysid";
           }
           leaf isis-router-areaid {
             type string;
             description
               "IS-IS router areaid";
           }
           leaf isis-max-areas {
             type uint32;
             description
               "Maximum Number of Areas";
           }
           leaf isis-lsp-lifetime {
             type uint32;
             description
               "Maximum LSP lifetime";
           }
           leaf isis-lsp-lifetime-filter {
             type uint32;
             description
               "Low LSP life time filter";
           }
           leaf isis-reference-bandwidth {
             type uint64;
             description
               "Bandwidth for calculating metric defaults";
           }
           leaf isis-adjacency-holddown {
             type string;
             description
               "IS-IS Adjacency holddown status";
           }
           leaf isis-attached-bit-evaluation {
             type string;
             description
               "The IS-IS L1 attached bit evaluation";
           }
           leaf isis-layer2-map-enabled {
             type string;
             description
               "IS-IS controls kernel ARP/ND entries for its nexthops";
           }
           container isis-spf-information {
             description
               "SPF options";
             leaf isis-spf-delay {
               type string;
               description
                 "Delay before performing SPF calculations";
             }
             leaf isis-spf-holddown {
               type string;
               description
                 "Throttling delay between consecutive SPF calculations";
             }
             leaf isis-spf-rapid-runs {
               type uint32;
               description
                 "Number of rapid SPF calculations before SPF holddown.";
             }
             leaf isis-uloop-avoidance {
               type string;
               description
                 "Micro-loop avoidance status";
             }
             leaf isis-uloop-avoidance-method {
               type string;
               description
                 "Micro-loop avoidance mechanism employed";
             }
             leaf isis-route-convergence-delay {
               type string;
               description
                 "Delay before downloading routes to forwarding plane";
             }
             leaf isis-topo-sessid-count {
               type uint32;
               description
                 "Number of Session IDs associated with routes in this 
                 topology";
             }
             container isis-spf {
               leaf node-count {
                 type int32;
               }
               container isis-spf-results-header {
                 leaf isis-topology-id {
                   type string;
                 }
                 leaf level {
                   type int32;
                   description
                     "IS-IS Level";
                 }
               }
               list isis-spf-result {
                 leaf node-id {
                   type string;
                 }
                 leaf metric {
                   type int32;
                 }
                 leaf disconnected {
                   type empty;
                 }
                 leaf no-first-fragment {
                   type empty;
                 }
                 leaf-list node-address {
                   type string;
                 }
                 list next-hop-element {
                   leaf interface-name {
                     type string;
                     description
                       "Name of interface";
                   }
                   leaf isis-next-hop-type {
                     type string;
                   }
                   leaf isis-next-hop {
                     type string;
                   }
                   leaf-list snpa {
                     type string;
                   }
                   leaf snpa-type {
                     type string;
                     description
                       "Type of SNPA";
                   }
                   list pfe-port-snpa {
                     key "pfe-id";
                     description
                       "PFE Port SNPA";
                     leaf pfe-id {
                       type int32;
                     }
                     leaf port-id {
                       type int32;
                     }
                   }
                   container network-element-port-snpa {
                     description
                       "Network Element Port SNPA";
                     leaf port-id {
                       type int32;
                     }
                   }
                   container mstp-root-snpa {
                     description
                       "Multiple Spanning Tree Protocol Root SNPA";
                     leaf mstp-root-id {
                       type int32;
                     }
                   }
                   list gateway-snpa {
                     key "gateway-addr";
                     description
                       "Gateway SNPA";
                     leaf gateway-addr {
                       type jt:ipaddr;
                     }
                   }
                   container layer2-domain-port-snpa {
                     description
                       "Layer-2 Domain Port SNPA";
                     leaf port-id {
                       type int32;
                     }
                   }
                   container replication-block-snpa {
                     description
                       "Replication Block SNPA";
                     leaf replication-block-id {
                       type int32;
                     }
                   }
                   container replication-route-snpa {
                     description
                       "Replication Route SNPA";
                     leaf network-element-id {
                       type jt:ipaddr;
                     }
                   }
                   container layer2-multicast-port-snpa {
                     description
                       "Layer-2 Multicast Port SNPA";
                     leaf layer2-multicast-port-id {
                       type int32;
                     }
                   }
                   container inh-snpa {
                     description
                       "Indirection SNPA";
                     leaf inh-id {
                       type int32;
                     }
                   }
                 }
                 list prefix-element {
                   leaf prefix-metric {
                     type int32;
                   }
                   leaf external-prefix-metric {
                     type int32;
                   }
                   leaf address-prefix {
                     type jt:ipaddr;
                   }
                 }
                 list end-system-element {
                   leaf end-system-metric {
                     type int32;
                   }
                   leaf end-system-id {
                     type string;
                     description
                       "Six-octet ISO system ID for a end-system";
                   }
                 }
               }
               container isis-spf-log-header {
                 leaf isis-topology-id {
                   type string;
                 }
                 leaf level {
                   type int32;
                   description
                     "IS-IS Level";
                 }
               }
               container isis-spf-log {
                 leaf start-time {
                   type string;
                 }
                 leaf elapsed-time {
                   type string;
                   description
                     "Time this adjacency or session has been up or down";
                 }
                 leaf spf-trigger-count {
                   type int32;
                 }
                 leaf logging-reason {
                   type string;
                 }
                 leaf lsp-name {
                   type string;
                   description
                     "Tunneled into an RSVP LSP";
                 }
                 leaf system-name {
                   type string;
                   description
                     "Hostname for a system";
                 }
                 leaf interface-name {
                   type string;
                   description
                     "Name of interface";
                 }
                 leaf change-reason {
                   type string;
                 }
                 leaf mla-topo-change-time {
                   type string;
                 }
                 leaf mla-prefix-change-time {
                   type string;
                 }
                 leaf tilfa-topo-change-time {
                   type string;
                 }
                 leaf tilfa-prefix-change-time {
                   type string;
                 }
                 leaf-list route-build-time {
                   type string;
                 }
               }
               container isis-backup-spf-result {
                 leaf node-id {
                   type string;
                 }
                 leaf no-first-fragment {
                   type empty;
                 }
                 leaf backup-root {
                   type string;
                 }
                 leaf backup-root-metric {
                   type int32;
                 }
                 leaf metric {
                   type int32;
                 }
                 leaf backup-root-preference {
                   type int32;
                 }
                 leaf track-item {
                   type string;
                 }
                 leaf track-item-isnbr {
                   type string;
                 }
                 leaf rev-track-item {
                   type string;
                 }
                 leaf rev-track-item-isnbr {
                   type string;
                 }
                 leaf-list node-address {
                   type string;
                 }
                 list next-hop-element {
                   leaf interface-name {
                     type string;
                     description
                       "Name of interface";
                   }
                   leaf isis-next-hop-type {
                     type string;
                   }
                   leaf isis-next-hop {
                     type string;
                   }
                   leaf-list snpa {
                     type string;
                   }
                   leaf snpa-type {
                     type string;
                     description
                       "Type of SNPA";
                   }
                   list pfe-port-snpa {
                     key "pfe-id";
                     description
                       "PFE Port SNPA";
                     leaf pfe-id {
                       type int32;
                     }
                     leaf port-id {
                       type int32;
                     }
                   }
                   container network-element-port-snpa {
                     description
                       "Network Element Port SNPA";
                     leaf port-id {
                       type int32;
                     }
                   }
                   container mstp-root-snpa {
                     description
                       "Multiple Spanning Tree Protocol Root SNPA";
                     leaf mstp-root-id {
                       type int32;
                     }
                   }
                   list gateway-snpa {
                     key "gateway-addr";
                     description
                       "Gateway SNPA";
                     leaf gateway-addr {
                       type jt:ipaddr;
                     }
                   }
                   container layer2-domain-port-snpa {
                     description
                       "Layer-2 Domain Port SNPA";
                     leaf port-id {
                       type int32;
                     }
                   }
                   container replication-block-snpa {
                     description
                       "Replication Block SNPA";
                     leaf replication-block-id {
                       type int32;
                     }
                   }
                   container replication-route-snpa {
                     description
                       "Replication Route SNPA";
                     leaf network-element-id {
                       type jt:ipaddr;
                     }
                   }
                   container layer2-multicast-port-snpa {
                     description
                       "Layer-2 Multicast Port SNPA";
                     leaf layer2-multicast-port-id {
                       type int32;
                     }
                   }
                   container inh-snpa {
                     description
                       "Indirection SNPA";
                     leaf inh-id {
                       type int32;
                     }
                   }
                 }
                 list backup-next-hop-element {
                   leaf interface-name {
                     type string;
                     description
                       "Name of interface";
                   }
                   leaf isis-next-hop-type {
                     type string;
                   }
                   leaf isis-next-hop {
                     type string;
                   }
                   leaf-list snpa {
                     type string;
                   }
                   leaf snpa-type {
                     type string;
                     description
                       "Type of SNPA";
                   }
                   list pfe-port-snpa {
                     key "pfe-id";
                     description
                       "PFE Port SNPA";
                     leaf pfe-id {
                       type int32;
                     }
                     leaf port-id {
                       type int32;
                     }
                   }
                   container network-element-port-snpa {
                     description
                       "Network Element Port SNPA";
                     leaf port-id {
                       type int32;
                     }
                   }
                   container mstp-root-snpa {
                     description
                       "Multiple Spanning Tree Protocol Root SNPA";
                     leaf mstp-root-id {
                       type int32;
                     }
                   }
                   list gateway-snpa {
                     key "gateway-addr";
                     description
                       "Gateway SNPA";
                     leaf gateway-addr {
                       type jt:ipaddr;
                     }
                   }
                   container layer2-domain-port-snpa {
                     description
                       "Layer-2 Domain Port SNPA";
                     leaf port-id {
                       type int32;
                     }
                   }
                   container replication-block-snpa {
                     description
                       "Replication Block SNPA";
                     leaf replication-block-id {
                       type int32;
                     }
                   }
                   container replication-route-snpa {
                     description
                       "Replication Route SNPA";
                     leaf network-element-id {
                       type jt:ipaddr;
                     }
                   }
                   container layer2-multicast-port-snpa {
                     description
                       "Layer-2 Multicast Port SNPA";
                     leaf layer2-multicast-port-id {
                       type int32;
                     }
                   }
                   container inh-snpa {
                     description
                       "Indirection SNPA";
                     leaf inh-id {
                       type int32;
                     }
                   }
                   leaf isis-backup-prefix-refcount {
                     type uint32;
                     description
                       "Number of prefixes that uses this nexthop as backup";
                   }
                   leaf isis-backup-score {
                     type string;
                   }
                 }
                 list no-coverage-reason-element {
                   leaf isis-next-hop-type {
                     type string;
                   }
                   leaf no-coverage-reason {
                     type string;
                   }
                 }
               }
             }
           }
           container isis-overload-information {
             description
               "Overload bit behaviour at startup";
             leaf isis-overload-enabled {
               type empty;
               description
                 "Overload bit upon startup is set";
             }
             leaf isis-overload-high-metrics {
               type string;
               description
                 "High metrics are used for Overload signaling";
             }
             leaf isis-overload-allow-route-leaking {
               type string;
               description
                 "Allow route leaking when configured to be in overload";
             }
             leaf isis-overload-internal-prefixes {
               type string;
               description
                 "Allow internal prefixes to be advertised with high metric";
             }
             leaf isis-overload-external-prefixes {
               type string;
               description
                 "Allow external prefixes to be advertised with high metric";
             }
             leaf isis-overload-timeout {
               type int32;
               description
                 "Clearance of the Overload bit after startup";
             }
             leaf isis-overload-remaining-time {
               type string;
               description
                 "Time remaining on configured overload timeout";
             }
           }
           container isis-routing {
             description
               "List of routed IS-IS address families";
             leaf isis-routing-ipv4 {
               type empty;
               description
                 "Routing IPv4 prefixes is enabled";
             }
             leaf isis-routing-ipv6 {
               type empty;
               description
                 "Routing IPv6 prefixes is enabled";
             }
             leaf isis-routing-clns {
               type empty;
               description
                 "Routing CLNS prefixes is enabled";
             }
             leaf isis-routing-spring-mpls {
               type empty;
               description
                 "Routing CLNS prefixes is enabled";
             }
           }
           container isis-traffic-engineering {
             description
               "Traffic engineering";
             leaf isis-te-status {
               type string;
               description
                 "Traffic engineering status";
             }
             leaf isis-ted-ipv6 {
               type string;
               description
                 "Traffic Engineering v6 status";
             }
             leaf isis-te-shortcuts-ipv4 {
               type empty;
               description
                 "IPv4 Traffic engineering shortcuts are enabled";
             }
             leaf isis-te-shortcuts-ipv6 {
               type empty;
               description
                 "IPv6 Traffic engineering shortcuts are enabled";
             }
             leaf isis-te-shortcuts-ipv4-mpls {
               type empty;
               description
                 "IPv4-MPLS Traffic engineering shortcuts are enabled";
             }
             leaf isis-te-shortcuts-ipv6-mpls {
               type empty;
               description
                 "IPv6-MPLS Traffic engineering shortcuts are enabled";
             }
             leaf isis-te-shortcuts-clns {
               type empty;
               description
                 "CLNS Traffic engineering shortcuts are enabled";
             }
             leaf isis-ipv4-multicast-rpf-routes {
               type empty;
               description
                 "IPv4 routes for multicast RPF checks are installed into 
                 inet.2";
             }
             leaf isis-ignore-lsp-metrics {
               type empty;
               description
                 "Label-switched path metrics when doing shortcuts are 
                 ignored";
             }
             leaf isis-ted-credibility-preference {
               type empty;
               description
                 "Credibility follows protocol preference";
             }
           }
           container isis-restart {
             description
               "IS-IS restart parameters";
             leaf isis-restart-enabled {
               type string;
               description
                 "IS-IS restart mode";
             }
             leaf isis-restart-duration {
               type uint32;
               description
                 "Duration of IS-IS restart";
             }
             leaf isis-restart-helper-mode-enabled {
               type string;
               description
                 "IS-IS helper mode";
             }
           }
           container isis-tilfa {
             description
               "IS-IS Post Convergence Backup parameters";
             leaf isis-tilfa-enabled {
               type string;
               description
                 "Post Convergence Backup";
             }
             leaf isis-tilfa-max-labels {
               type int32;
               description
                 "Max labels";
             }
             leaf isis-tilfa-max-srv6-sids {
               type int32;
               description
                 "Max SRV6 SIDs";
             }
             leaf isis-tilfa-max-spf {
               type int32;
               description
                 "Max spf";
             }
             leaf isis-tilfa-ecmp-backup {
               type int32;
               description
                 "Post Convergence Max Ecmp Backup";
             }
           }
           container isis-spring {
             description
               "IS-IS SPRING parameters";
             leaf isis-spring-enabled {
               type string;
               description
                 "Source Packet Routing";
             }
             leaf isis-srgb-allocation {
               type string;
               description
                 "SRGB Block Allocation";
             }
             leaf isis-node-segment-enabled {
               type string;
               description
                 "Node Segments Enabled";
             }
             leaf isis-srv6-enabled {
               type string;
               description
                 "SRv6 Enabled";
             }
             container isis-srgb-config {
               description
                 "SRGB block configuration related information";
               leaf isis-srgb-config-block-header {
                 type string;
                 description
                   "SRGB Config Block";
               }
               leaf isis-srgb-start-label {
                 type int32;
                 description
                   "Configuration of SRGB start label";
               }
               leaf isis-srgb-index-range {
                 type int32;
                 description
                   "Configuration of SRGB index range";
               }
             }
             container isis-srgb-block {
               description
                 "SRGB block related information";
               leaf isis-srgb-start-index {
                 type int32;
                 description
                   "Starting Index for SRGB Block";
               }
               leaf isis-srgb-size {
                 type int32;
                 description
                   "Size of the specific SRGB Block";
               }
               leaf isis-srgb-first-label {
                 type int32;
                 description
                   "First label allocated for SRGB Block";
               }
               leaf isis-srgb-last-label {
                 type int32;
                 description
                   "Last label allocated for SRGB Block";
               }
             }
             container isis-node-segment {
               leaf isis-node-segment-ipv4-index {
                 type int32;
                 description
                   "IPv4 Node Segment index for this device";
               }
               leaf isis-node-segment-ipv6-index {
                 type int32;
                 description
                   "IPv6 Node Segment index for this device";
               }
               leaf isis-node-segment-index-range {
                 type int32;
                 description
                   "Range of Node Segment indices configured";
               }
               leaf isis-node-segment-block-header {
                 type empty;
                 description
                   "Node Segment Blocks";
               }
               list isis-node-segment-block {
                 key "isis-node-segment-block-start-index";
                 description
                   "Node Segment Blocks related information";
                 leaf isis-node-segment-block-start-index {
                   type int32;
                   description
                     "Starting Index for the specific Node Segment Block";
                 }
                 leaf isis-node-segment-block-size {
                   type int32;
                   description
                     "Size of the specific Node Segment Block";
                 }
                 leaf isis-node-segment-block-first-label {
                   type int32;
                   description
                     "First label allocated for the specific Node Segment 
                     Block";
                 }
                 leaf isis-node-segment-block-last-label {
                   type int32;
                   description
                     "Last label allocated for the specific Node Segment 
                     Block";
                 }
               }
             }
             list isis-srv6-locator {
               key "isis-srv6-locator-address";
               description
                 "SRv6 Locator information";
               leaf isis-srv6-locator-name {
                 type string;
                 description
                   "Locator name";
               }
               leaf isis-srv6-locator-address {
                 type string;
                 description
                   "Locator prefix";
               }
               leaf isis-srv6-locator-algorithm {
                 type uint32;
                 description
                   "Locator algorithm";
               }
               leaf isis-prefix-attribute-flags {
                 type string;
               }
               container isis-srv6-end-sid {
                 description
                   "SRv6 end sid entry";
                 leaf isis-srv6-end-sid-addr {
                   type jt:ipv6addr;
                   description
                     "SRv6 End-SID prefix";
                 }
                 leaf-list isis-srv6-sid-flavor {
                   type string;
                 }
               }
               container isis-srv6-micro-node-sid {
                 description
                   "SRv6 end sid entry";
                 leaf isis-srv6-micro-node-sid-addr {
                   type jt:ipv6addr;
                   description
                     "SRv6 micro-node-SID address";
                 }
                 leaf-list isis-srv6-micro-sid-flavor {
                   type string;
                 }
               }
             }
           }
           list isis-level-information {
             key "isis-level";
             description
               "IS-IS Level Information";
             leaf isis-level {
               type int32;
               description
                 "IS-IS Level";
             }
             leaf isis-preference {
               type uint32;
               description
                 "IS-IS internal route preference";
             }
             leaf isis-external-preference {
               type uint32;
               description
                 "IS-IS external route preference";
             }
             leaf isis-prefix-export-limit {
               type uint32;
               description
                 "IS-IS limit for external route export";
             }
             leaf isis-prefix-export-count {
               type uint32;
               description
                 "Actual number of exported prefixes";
             }
             leaf isis-wide-metrics {
               type empty;
               description
                 "Generation of wide metric TLVs is enabled";
             }
             leaf isis-narrow-metrics {
               type empty;
               description
                 "Generation of narrow metric TLVs is enabled";
             }
             leaf isis-level-spring-enabled {
               type empty;
               description
                 "Source Packet Routing is enabled";
             }
             leaf isis-adjacency-holddown-state {
               type string;
             }
             leaf isis-flood-reduction-enabled {
               type string;
               description
                 "Distributed Optimized flood reduction";
             }
             leaf isis-flood-reduction-hash-reflooder-enabled {
               type string;
               description
                 "Distributed Optimized flood reduction hash reflooder";
             }
             leaf isis-clos-miswiring-warning {
               type string;
             }
             leaf isis-purge-originator-info {
               type string;
               description
                 "Type of POI that gets added to purged LSPs";
             }
           }
         }
       }
       container task-replication-state {
         description
           "Current state of task replication";
         leaf task-gres-state {
           type string;
           description
             "Current state of graceful Routing Engine Switchover";
         }
         leaf task-re-mode {
           type string;
           description
             "Current mastership state of Routing Engine";
         }
         list task-protocol-replication {
           description
             "Current state of task protocol replication";
           leaf task-protocol-replication-name {
             type string;
           }
           leaf task-protocol-replication-state {
             type string;
           }
         }
       }
     }
   }
   grouping ospf3-neighbor-information-all-block {
     list ospf3-instance-neighbor {
       description
         "Information about OSPFv3 neighbors within this routing instance";
       leaf ospf-instance-name {
         type string;
         description
           "Name of OSPF instance";
       }
       list ospf3-realm-neighbor {
         description
           "Information about OSPFv3 neighbors within this realm";
         leaf ospf3-realm-name {
           type string;
           description
             "Name of OSPFv3 realm";
         }
         list ospf3-neighbor {
           key "neighbor-id interface-name ospf-area";
           leaf neighbor-id {
             type jt:ipaddr;
           }
           leaf interface-name {
             type string;
             description
               "Name of interface";
           }
           leaf ospf-neighbor-state {
             type string;
           }
           leaf neighbor-priority {
             type int32;
           }
           leaf activity-timer {
             type int32;
           }
           leaf neighbor-address {
             type jt:ipaddr;
             description
               "IP address of this neighbor";
           }
           leaf ospf-area {
             type string;
             description
               "Area ID";
           }
           leaf options {
             type int32;
           }
           leaf neighbor-secondary {
             type empty;
             description
               "OSPF neighbor is on secondary interface";
           }
           leaf ospf3-interface-index {
             type int32;
           }
           leaf neighbor-cost {
             type int32;
             description
               "Cost associated with this neighbor";
           }
           leaf dr-id {
             type jt:ipaddr;
           }
           leaf bdr-id {
             type jt:ipaddr;
           }
           leaf neighbor-up-time {
             type string;
             description
               "Time when neighbor came up";
           }
           leaf neighbor-adjacency-time {
             type string;
             description
               "Time when neighbor became adjacent";
           }
           leaf neighbor-suppress-hello {
             type int32;
             description
               "Time when neighbor suppressed hellos";
           }
           leaf master-slave {
             type string;
           }
           leaf sequence-number {
             type int64;
             description
               "History event number";
           }
           leaf dbd-retransmit-time {
             type int32;
             description
               "Seconds until DBD is retransmitted";
           }
           leaf lsreq-retransmit-time {
             type int32;
             description
               "Seconds until LSREQ is retransmitted";
           }
           leaf lsreq-enqueued {
             type empty;
           }
           leaf lsreq-active {
             type empty;
           }
           leaf lsa-list {
             type string;
           }
         }
       }
     }
   }
   grouping ospf3-neighbor-information-block {
     list ospf3-neighbor {
       key "neighbor-id interface-name ospf-area";
       leaf neighbor-id {
         type jt:ipaddr;
       }
       leaf interface-name {
         type string;
         description
           "Name of interface";
       }
       leaf ospf-neighbor-state {
         type string;
       }
       leaf neighbor-priority {
         type int32;
       }
       leaf activity-timer {
         type int32;
       }
       leaf neighbor-address {
         type jt:ipaddr;
         description
           "IP address of this neighbor";
       }
       leaf ospf-area {
         type string;
         description
           "Area ID";
       }
       leaf options {
         type int32;
       }
       leaf neighbor-secondary {
         type empty;
         description
           "OSPF neighbor is on secondary interface";
       }
       leaf ospf3-interface-index {
         type int32;
       }
       leaf neighbor-cost {
         type int32;
         description
           "Cost associated with this neighbor";
       }
       leaf dr-id {
         type jt:ipaddr;
       }
       leaf bdr-id {
         type jt:ipaddr;
       }
       leaf neighbor-up-time {
         type string;
         description
           "Time when neighbor came up";
       }
       leaf neighbor-adjacency-time {
         type string;
         description
           "Time when neighbor became adjacent";
       }
       leaf neighbor-suppress-hello {
         type int32;
         description
           "Time when neighbor suppressed hellos";
       }
       leaf master-slave {
         type string;
       }
       leaf sequence-number {
         type int64;
         description
           "History event number";
       }
       leaf dbd-retransmit-time {
         type int32;
         description
           "Seconds until DBD is retransmitted";
       }
       leaf lsreq-retransmit-time {
         type int32;
         description
           "Seconds until LSREQ is retransmitted";
       }
       leaf lsreq-enqueued {
         type empty;
       }
       leaf lsreq-active {
         type empty;
       }
       leaf lsa-list {
         type string;
       }
     }
   }
   grouping ospf3-route-information-block {
     list ospf3-route {
       list ospf3-route-entry {
         leaf address-prefix {
           type jt:ipaddr;
         }
         leaf route-path-type {
           type string;
         }
         leaf route-type {
           type string;
           description
             "Route type";
         }
         leaf next-hop-type {
           type string;
           description
             "Next-hop type";
         }
         leaf interface-cost {
           type int32;
           description
             "Cost associated with this interface";
         }
         leaf ospf-area {
           type string;
           description
             "Area ID";
         }
         leaf route-origin {
           type jt:ipaddr;
         }
         leaf type7 {
           type empty;
         }
         leaf pbit {
           type empty;
         }
         leaf forward-nz {
           type empty;
         }
         leaf optional-capability {
           type int32;
           description
             "VEB bits received in the router LSA";
         }
         leaf route-priority {
           type string;
         }
         leaf ospf-valid-backups {
           type empty;
         }
         leaf ospf-bgp-orr-gen-id {
           type uint32;
         }
         list ospf-next-hop {
           container next-hop-name {
             leaf interface-name {
               type string;
               description
                 "Name of interface";
             }
             leaf interface-link-name {
               type string;
             }
           }
           container next-hop-address {
             leaf interface-address {
               type jt:ipaddr;
             }
             leaf lsp-name {
               type string;
               description
                 "Tunneled into an RSVP LSP";
             }
           }
         }
         container ospf-backup-next-hop {
           leaf ospf-backup-next-hop-interface {
             type string;
           }
           leaf ospf-backup-next-hop-address {
             type string;
           }
           leaf ospf-backup-next-hop-lsp {
             type string;
           }
           leaf ospf-backup-next-hop-type {
             type string;
           }
           leaf ospf-backup-next-hop-lsp-out-if {
             type string;
           }
         }
         list ospf-rt-sessid {
           description
             "Session ID associated with the route";
           leaf-list ospf-rt-sessid-val {
             type uint32;
           }
         }
         container ospf-valid-backup-next-hop {
           leaf ospf-valid-backup-next-hop-address {
             type string;
           }
           leaf ospf-valid-backup-next-hop-interface {
             type string;
           }
           leaf ospf-valid-backup-type {
             type string;
           }
           leaf ospf-valid-backup-next-hop-lsp {
             type string;
           }
           leaf ospf-valid-backup-next-hop-lsp-out-if {
             type string;
           }
           leaf ospf-valid-backup-lsp-type {
             type string;
           }
         }
       }
     }
   }
   grouping ospf3-statistics-information-block {
     container ospf-statistics {
       leaf dbds-retransmit {
         type uint64;
       }
       leaf dbds-retransmit-5seconds {
         type int32;
       }
       leaf lsas-flooded {
         type uint64;
       }
       leaf lsas-flooded-5seconds {
         type int32;
       }
       leaf lsas-high-prio-flooded {
         type uint64;
       }
       leaf lsas-high-prio-flooded-5seconds {
         type int32;
       }
       leaf lsas-retransmit {
         type uint64;
       }
       leaf lsas-retransmit-5seconds {
         type int32;
       }
       leaf lsas-nbr-transmit {
         type uint64;
       }
       leaf lsas-nbr-transmit-5seconds {
         type int32;
       }
       leaf lsas-requested {
         type uint64;
       }
       leaf lsas-requested-5seconds {
         type int32;
       }
       leaf lsas-acknowledged {
         type uint64;
       }
       leaf lsas-acknowledged-5seconds {
         type int32;
       }
       leaf max-age-lsas-received {
         type uint64;
       }
       leaf max-age-lsas-received-5seconds {
         type int32;
       }
       leaf flood-queue-depth {
         type int32;
       }
       leaf total-retransmits {
         type int32;
       }
       leaf total-database-summaries {
         type int32;
       }
       leaf total-linkstate-request {
         type int32;
       }
       list packet-statistics {
         key "ospf-packet-type";
         leaf ospf-packet-type {
           type string;
         }
         leaf packets-sent {
           type uint64;
         }
         leaf packets-received {
           type uint64;
         }
         leaf packets-sent-5seconds {
           type int32;
         }
         leaf packets-received-5seconds {
           type int32;
         }
       }
       container ospf-errors {
         leaf runt-header-error {
           type int32;
         }
         leaf short-packets-error {
           type int32;
         }
         leaf bad-version-error {
           type int32;
         }
         leaf truncated-packets-error {
           type int32;
         }
         leaf checksum-error {
           type int32;
         }
         leaf subnet-mismatch-error {
           type int32;
         }
         leaf virtual-link-error {
           type int32;
         }
         leaf area-mismatch-error {
           type int32;
         }
         leaf authentication-mismatch-error {
           type int32;
         }
         leaf authentication-failure-error {
           type int32;
         }
         leaf bad-packettype-error {
           type int32;
         }
         leaf netmask-mismatch-error {
           type int32;
         }
         leaf hello-interval-mismatch-error {
           type int32;
         }
         leaf dead-interval-mismatch-error {
           type int32;
         }
         leaf stub-area-mismatch-error {
           type int32;
         }
         leaf nssa-mismatch-error {
           type int32;
         }
         leaf default-exclusion-mismatch-error {
           type int32;
         }
         leaf mtu-mismatch-error {
           type int32;
         }
         leaf hello-received-error {
           type int32;
         }
         leaf no-router-id-error {
           type int32;
         }
         leaf instance-id-mismatch-error {
           type int32;
         }
         leaf lanp2p-cfgmismatch-error {
           type int32;
         }
         leaf no-error {
           type empty;
         }
       }
     }
   }
   grouping ospf3-intf-statistics-information-block {
     list ospf-intf-statistics {
       leaf total-packets-received {
         type uint64;
       }
       leaf total-packets-sent {
         type uint64;
       }
       leaf intf-dbds-retransmit {
         type uint64;
       }
       leaf intf-lsas-flooded {
         type uint64;
       }
       leaf intf-lsas-high-prio-flooded {
         type uint64;
       }
       leaf intf-lsas-retransmit {
         type uint64;
       }
       leaf intf-lsas-nbr-transmit {
         type uint64;
       }
       leaf intf-lsas-requested {
         type uint64;
       }
       leaf intf-lsas-acknowledged {
         type uint64;
       }
       leaf intf-max-age-lsas-received {
         type uint64;
       }
       leaf intf-total-retransmits {
         type int32;
       }
       leaf intf-total-database-summaries {
         type int32;
       }
       leaf intf-total-linkstate-request {
         type int32;
       }
       leaf intf-name {
         type string;
       }
       list packet-statistics {
         key "ospf-packet-type";
         leaf ospf-packet-type {
           type string;
         }
         leaf packets-sent {
           type uint64;
         }
         leaf packets-received {
           type uint64;
         }
       }
       container ospf-errors {
         leaf short-packets-error {
           type int32;
         }
         leaf subnet-mismatch-error {
           type int32;
         }
         leaf virtual-link-error {
           type int32;
         }
         leaf area-mismatch-error {
           type int32;
         }
         leaf bad-packettype-error {
           type int32;
         }
         leaf netmask-mismatch-error {
           type int32;
         }
         leaf hello-interval-mismatch-error {
           type int32;
         }
         leaf dead-interval-mismatch-error {
           type int32;
         }
         leaf default-exclusion-mismatch-error {
           type int32;
         }
         leaf mtu-mismatch-error {
           type int32;
         }
         leaf lanp2p-cfgmismatch-error {
           type int32;
         }
         leaf no-error {
           type empty;
         }
       }
     }
   }
   grouping ospf3-io-statistics-information-block {
     container ospf-io-statistics {
       leaf packets-read {
         type int32;
       }
       leaf average-per-run {
         type string;
       }
       leaf max-run {
         type int32;
       }
       container ospf-errors {
         leaf no-interface-error {
           type int32;
         }
         leaf no-error {
           type empty;
         }
       }
     }
   }
   grouping ospf3-log-information-block {
     container ospf-log-instance {
       list log-element {
         leaf timestamp {
           type string;
           description
             "Time when something occurs";
         }
         leaf ospf-log-type {
           type string;
         }
         leaf elapsed-time {
           type string;
           description
             "Time this adjacency or session has been up or down";
         }
       }
     }
     container ospf-log-maximum-length {
       list log-element {
         leaf timestamp {
           type string;
           description
             "Time when something occurs";
         }
         leaf ospf-log-type {
           type string;
         }
         leaf elapsed-time {
           type string;
           description
             "Time this adjacency or session has been up or down";
         }
       }
     }
     container ospf-log-events {
       leaf number-events {
         type int32;
       }
       list log-element {
         leaf timestamp {
           type string;
           description
             "Time when something occurs";
         }
         leaf ospf-log-type {
           type string;
         }
         leaf elapsed-time {
           type string;
           description
             "Time this adjacency or session has been up or down";
         }
       }
     }
   }
   grouping ospf3-bgporr-route-information-block {
     container ospf-bgporr {
       leaf ospf-bgporr-name {
         type string;
       }
       leaf ospf-bgporr-primary {
         type jt:ipaddr;
       }
       leaf ospf-bgporr-primary-active-tag {
         type string;
       }
       leaf ospf-bgporr-backup {
         type jt:ipaddr;
       }
       leaf ospf-bgporr-backup-active-tag {
         type string;
       }
       list ospf-route {
         list ospf-route-entry {
           leaf address-prefix {
             type jt:ipaddr;
           }
           leaf route-path-type {
             type string;
           }
           leaf route-type {
             type string;
             description
               "Route type";
           }
           leaf interface-cost {
             type int32;
             description
               "Cost associated with this interface";
           }
           leaf ospf-area {
             type string;
             description
               "Area ID";
           }
           leaf route-origin {
             type jt:ipaddr;
           }
           leaf type7 {
             type empty;
           }
           leaf pbit {
             type empty;
           }
           leaf forward-nz {
             type empty;
           }
           leaf optional-capability {
             type int32;
             description
               "VEB bits received in the router LSA";
           }
           list ospf-next-hop {
           }
           container ospf-backup-next-hop {
             leaf ospf-backup-next-hop-type {
               type string;
             }
             leaf ospf-backup-next-hop-lsp-out-if {
               type string;
             }
           }
           container ospf-computed-backup-paths {
           }
         }
       }
       list ospf3-route {
         list ospf3-route-entry {
           leaf address-prefix {
             type jt:ipaddr;
           }
           leaf route-path-type {
             type string;
           }
           leaf route-type {
             type string;
             description
               "Route type";
           }
           leaf interface-cost {
             type int32;
             description
               "Cost associated with this interface";
           }
           leaf ospf-area {
             type string;
             description
               "Area ID";
           }
           leaf route-origin {
             type jt:ipaddr;
           }
           leaf type7 {
             type empty;
           }
           leaf pbit {
             type empty;
           }
           leaf forward-nz {
             type empty;
           }
           leaf optional-capability {
             type int32;
             description
               "VEB bits received in the router LSA";
           }
           list ospf-next-hop {
           }
           container ospf-backup-next-hop {
             leaf ospf-backup-next-hop-type {
               type string;
             }
             leaf ospf-backup-next-hop-lsp-out-if {
               type string;
             }
           }
         }
       }
     }
   }
 }
