/*
 * Copyright (c) 2026 Juniper Networks, Inc.
 * All rights reserved.
 */
 module junos-qfx-rpc-accounting {
   namespace "http://yang.juniper.net/junos-qfx/rpc/accounting";

   prefix accounting;

   import junos-common-types {
     prefix jt;
     revision-date 2026-01-01;
   }

   organization "Juniper Networks, Inc.";

   contact "yang-support@juniper.net";

   description "Junos RPC YANG module for accounting command(s)";

   revision 2026-01-01 {
     description "Junos: 26.2R1.7";
   }

   rpc get-accounting-profile-information {
     description "Show accounting profile information";
     input {
       leaf profile {
         description "Profile name";
         type string;
       }
     }
     output {
       choice output-tags {
         case actual-tag {
           container accounting-profile-information {
             uses accounting-profile-information-block;
           }
         }
         case multichassis-tag {
           container multi-routing-engine-results {
             list multi-routing-engine-item {
               leaf re-name {
                 type string;
               }
               choice output-tags {
                 case actual-tag {
                   container accounting-profile-information {
                     uses accounting-profile-information-block;
                   }
                 }
               }
             }
           }
         }
       }
     }
   }
   rpc get-accounting-record-information {
     description "Show accounting records";
     input {
       leaf profile {
         description "Name of profile";
         type string;
         mandatory true;
       }
       leaf since {
         description "Timestamp on earliest records to show (YYYY-MM-DD.HH:MM:SS)";
         type string;
       }
       leaf utc-timestamp {
         description "Display timestamp in UTC format";
         type empty;
       }
     }
     output {
       choice output-tags {
         case actual-tag {
           container accounting-record-information {
             uses accounting-record-information-block;
           }
         }
         case multichassis-tag {
           container multi-routing-engine-results {
             list multi-routing-engine-item {
               leaf re-name {
                 type string;
               }
               choice output-tags {
                 case actual-tag {
                   container accounting-record-information {
                     uses accounting-record-information-block;
                   }
                 }
               }
             }
           }
         }
       }
     }
   }
   rpc get-pending-accounting-stops {
     description "Show pending accounting stops related information";
     input {
       leaf access-profile {
         description "Show pending accounting stops for this access-profile";
         type string;
       }
       leaf level {
         default "terse";
         type enumeration {
           enum "terse" {
             description "Show brief output";
           }
           enum "detail" {
             description "Show detailed output";
           }
           enum "brief" {
             description "Show brief output";
           }
         }
       }
     }
     output {
       choice output-tags {
         case output-tag {
           leaf output {
             type string;
           }
         }
         case actual-tag {
           anyxml pending-accounting-stops;
         }
         case multichassis-tag {
           anyxml multi-routing-engine-results;
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping accounting-profile-information-block {
     container accounting-profile-header {
       description
         "Information from the accounting profile header";
       leaf profile-name {
         type string;
         description
           "Name of the accounting profile";
       }
       leaf profile-interval {
         type int32;
         description
           "Frequency of statistics collection for each object sampled by 
           the profile";
       }
       leaf profile-use-count {
         type int32;
         description
           "Number of objects to which this profile is applied (number of 
           objects for which the statistics defined in this profile are 
           collected)";
       }
       leaf filename {
         type string;
         description
           "Name of the file in the /var/log directory to which records are 
           written";
       }
       leaf filesize {
         type int32;
         description
           "Maximum number of bytes of data written to the active version of
           the file before the file is closed, and a new file opened. If 
           the transfer interval expires first, the file might contain less
           data.";
       }
       leaf filenumber {
         type int32;
         description
           "Maximum number of rotating versions of the file in the /var/log 
           directory (the active file plus compressed files containing 
           earlier data)";
       }
       leaf bytes-written {
         type int32;
         description
           "Number of bytes of data written to the file between the start of
           the most recent collection interval and the time of the request 
           for information about the profile";
       }
       leaf transfer-interval {
         type int32;
         description
           "Frequency, in minutes, that the active file is closed and 
           transferred to the configured archive site. The file is closed 
           even if the maximum amount of data has not yet been written. As 
           when the file is closed because the maximum size is reached, the
           contents of the active file are also compressed and copied to 
           the first rotating file in the /var/log directory.";
       }
       leaf next-transfer-time {
         type string;
         description
           "Date and time when the active file will next be closed and 
           transferred to the configured archive site, in the format 
           YYYY-MM-DD-hh:mm:ss (year, month, day, hour in 24-hour format, 
           minute, second)";
       }
       leaf profile-type {
         type string;
         description
           "Type of object to which the profile is applied";
       }
     }
     container accounting-profile-columns {
       description
         "Name of each JUNOScript output tag that is included in records 
         generated based on the profile";
       leaf-list column-label {
         type string;
         description
           "Name of an output tag that is included in records generated 
           based on the profile";
       }
     }
     container accounting-profile-interfaces {
       container accounting-profile-interface {
         description
           "Name of each interface to which the profile is applied";
         leaf interface-name {
           type string;
           description
             "Name of the interface";
         }
         leaf next-scheduled-collection {
           type string;
           description
             "Local time at which statistics collection will next begin, in 
             the format YYYY-MM-DD-hh:mm:ss (year, month, day, hour in 
             24-hour format, minute, second)";
         }
       }
     }
     container accounting-profile-mib {
       description
         "Name of each Management Information Base to which the profile is 
         applied";
       leaf mib-name {
         type string;
         description
           "Name of a MIB";
       }
       leaf next-scheduled-collection {
         type string;
         description
           "Local time at which statistics collection will next begin, in 
           the format YYYY-MM-DD-hh:mm:ss (year, month, day, hour in 
           24-hour format, minute, second)";
       }
     }
     container accounting-profile-filter {
       description
         "Name of each filter to which the profile is applied";
       leaf filter-name {
         type string;
         description
           "Name of the filter";
       }
       leaf next-scheduled-collection {
         type string;
         description
           "Local time at which statistics collection will next begin, in 
           the format YYYY-MM-DD-hh:mm:ss (year, month, day, hour in 
           24-hour format, minute, second)";
       }
     }
   }
   grouping accounting-record-information-block {
     container interface-accounting-statistics {
       description
         "Information from one or more records that were generated based on 
         an interface profile";
       container interface-accounting-record {
         description
           "Information in a record that was generated based on an interface
           profile";
         leaf epoch-timestamp {
           type string;
           description
             "Time at which the record was written, expressed as local time";
         }
         leaf interface-name {
           type string;
           description
             "Name of the interface";
         }
         leaf snmp-index {
           type string;
           description
             "Simple Network Management Protocol index of the object 
             described in the record";
         }
         leaf input-bytes {
           type string;
           description
             "Number of bytes received at the interface during the 
             collection interval";
         }
         leaf output-bytes {
           type string;
           description
             "Number of bytes sent from the interface during the collection 
             interval";
         }
         leaf input-packets {
           type string;
           description
             "Number of packets received at the interface during the 
             collection interval";
         }
         leaf output-packets {
           type string;
           description
             "Number of packets sent from the interface during the 
             collection interval";
         }
         leaf input-unicast {
           type string;
           description
             "Number of unicast packets received at the interface during the
             collection interval";
         }
         leaf output-unicast {
           type string;
           description
             "Number of unicast packets sent from the interface during the 
             collection interval";
         }
         leaf input-multicast {
           type string;
           description
             "Number of multicast packets received at the interface during 
             the collection interval";
         }
         leaf output-multicast {
           type string;
           description
             "Number of multicast packets sent from the interface during the
             collection interval";
         }
         leaf no-proto {
           type string;
           description
             "Number of packets that used an unsupported protocol";
         }
         leaf input-errors {
           type string;
           description
             "Number of packets received at the interface during the 
             collection interval that had errors (for example, frame 
             checksum sequence errors, or an invalid header length)";
         }
         leaf output-errors {
           type string;
           description
             "Number of packets scheduled to be sent from the interface 
             during the collection interval that were not sent because of 
             error conditions (for example, congestion or interface 
             outages)";
         }
         leaf rpf-check-bytes {
           type string;
           description
             "Number of bytes in reverse-path-forwarding check packets for 
             IPv4";
         }
         leaf rpf-check-packets {
           type string;
           description
             "Number of reverse-path-forwarding check packets for IPv4";
         }
         leaf rpf-check6-bytes {
           type string;
           description
             "Number of bytes in reverse-path-forwarding check packets for 
             IPv6";
         }
         leaf rpf-check6-packets {
           type string;
           description
             "Number of reverse-path-forwarding check packets for IPv6";
         }
         leaf rpf-check-total-bytes {
           type string;
           description
             "Total number of bytes in reverse-path-forwarding check packets
             for IPv4 and IPv6";
         }
         leaf rpf-check-total-packets {
           type string;
           description
             "Total number of packets in reverse-path-forwarding check for 
             both IPv4 and IPv6";
         }
         leaf profile-layout {
           type string;
         }
         leaf utc-timestamp {
           type string;
           description
             "Time at which the record was written, expressed as Coordinated
             Universal Time";
         }
       }
     }
     container routing-engine-accounting-statistics {
       description
         "Information from one or more records that were generated based on 
         a Routing Engine profile";
       container routing-engine-accounting-record {
         description
           "Information in a record that was generated based on a Routing 
           Engine profile";
         leaf epoch-timestamp {
           type string;
           description
             "Time at which the record was written, expressed as local time";
         }
         leaf utc-timestamp {
           type string;
           description
             "Time at which the record was written, expressed as Coordinated
             Universal Time";
         }
         leaf hostname {
           type string;
           description
             "Hostname of the Routing Engine";
         }
         leaf date-yyyymmdd {
           type string;
           description
             "Current date on the Routing Engine, in the format YYYYMMDD 
             (year, month, day)";
         }
         leaf timeofday-hhmmss {
           type string;
           description
             "Current time on the Routing Engine, in the format hhmmss (hour
             in 24-hour format, minute, second)";
         }
         leaf uptime {
           type int32;
           description
             "Number of seconds since the Routing Engine last rebooted";
         }
         leaf cpu1min {
           type int32;
           description
             "The load average for the minute before the record was written 
             (a damped time-dependent average based on the number of active
             jobs and jobs in the CPU run queue)";
         }
         leaf cpu5min {
           type int32;
           description
             "The load average for the five minutes before the record was 
             written (a damped time-dependent average based on the number 
             of active jobs and jobs in the CPU run queue)";
         }
         leaf cpu15min {
           type int32;
           description
             "The load average for the 15 minutes before the record was 
             written (a damped time-dependent average based on the number 
             of active jobs and jobs in the CPU run queue)";
         }
         leaf memory-usage {
           type int32;
           description
             "Megabytes of RAM in use";
         }
         leaf total-cpu-usage {
           type int32;
           description
             "Current CPU load, expressed as a percent";
         }
         leaf cpu-usage5sec {
           type int32;
           description
             "CPU usage for last 5seconds  expressed as a percent";
         }
         leaf cpu-usage1min {
           type int32;
           description
             "Average CPU usage for  last one minute expressed as a percent";
         }
         leaf cpu-usage5min {
           type int32;
           description
             "Average CPU usage for last 5 minutes expressed as a percent";
         }
         leaf free-mem {
           type int32;
           description
             "Free memory available in the system in KB";
         }
         leaf total-mem {
           type int32;
           description
             "Total memory available in system in KB";
         }
         leaf profile-layout {
           type string;
         }
       }
     }
     container filter-accounting-statistics {
       description
         "Information from one or more records that were generated based on 
         a filter profile";
       container filter-accounting-record {
         description
           "Information in a record that was generated based on a filter 
           profile";
         leaf epoch-timestamp {
           type string;
           description
             "Time at which the record was written, expressed as local time";
         }
         leaf filter-name {
           type string;
           description
             "Name of the filter";
         }
         leaf interfaces {
           type string;
           description
             "Name of one or more interfaces for which the record was 
             collected";
         }
         leaf counter-name {
           type string;
           description
             "Name of the counter";
         }
         leaf packet-count {
           type string;
           description
             "Number of packets processed by the counter";
         }
         leaf byte-count {
           type string;
           description
             "Number of bytes processed by the counter";
         }
         leaf profile-layout {
           type string;
         }
         leaf utc-timestamp {
           type string;
           description
             "Time at which the record was written, expressed as Coordinated
             Universal Time";
         }
       }
     }
     container cu-accounting-statistics {
       description
         "Information from one or more records that were generated based on 
         a destination class usage or source class usage profile";
       container cu-accounting-record {
         description
           "Information in a record that was generated based on a 
           destination class usage or source class usage profile";
         leaf epoch-timestamp {
           type string;
           description
             "Time at which the record was written, expressed as local time";
         }
         leaf interface-name {
           type string;
           description
             "Name of the interface";
         }
         leaf address-family {
           type string;
           description
             "Interface family configured on the interface";
         }
         leaf destination-class-name {
           type string;
           description
             "Name of the destination class";
         }
         leaf source-class-name {
           type string;
           description
             "Name of the source class";
         }
         leaf packet-count {
           type string;
           description
             "Number of packets processed by the counter";
         }
         leaf byte-count {
           type string;
           description
             "Number of bytes processed by the counter";
         }
         leaf profile-layout {
           type string;
         }
         leaf counter-name {
           type string;
           description
             "Name of the counter";
         }
         leaf utc-timestamp {
           type string;
           description
             "Time at which the record was written, expressed as Coordinated
             Universal Time";
         }
       }
     }
     container mib-accounting-statistics {
       description
         "Information from one or more records that were generated based on 
         a Management Information Base profile";
       list mib-accounting-record {
         description
           "Information in a record that was generated based on a Management
           Information Base profile";
         leaf epoch-timestamp {
           type string;
           description
             "Time at which the record was written, expressed as local time";
         }
         leaf name {
           type string;
           description
             "SNMP object name";
         }
         leaf object-value {
           type string;
           description
             "SNMP object value";
         }
         leaf profile {
           type string;
           description
             "Name of the MIB profile";
         }
         leaf utc-timestamp {
           type string;
           description
             "Time at which the record was written, expressed as Coordinated
             Universal Time";
         }
       }
     }
     container file-accounting-records {
       description
         "Records from an accounting file";
       container file-accounting-record {
         description
           "Record from an accounting file";
         leaf profile-layout {
           type string;
         }
         leaf epoch-timestamp {
           type string;
           description
             "Time at which the record was written, expressed as local time";
         }
       }
     }
   }
 }
